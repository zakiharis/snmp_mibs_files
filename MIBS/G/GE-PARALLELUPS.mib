GE-PARALLELUPS DEFINITIONS ::= BEGIN

IMPORTS
        
       MODULE-IDENTITY, OBJECT-TYPE, NOTIFICATION-TYPE,
       OBJECT-IDENTITY, Counter32, Gauge32, Integer32,enterprises, IpAddress
       FROM SNMPv2-SMI
       DisplayString, TimeStamp, TimeInterval, TestAndIncr,
         AutonomousType, TEXTUAL-CONVENTION
           FROM SNMPv2-TC;		
              
PositiveInteger32 ::= TEXTUAL-CONVENTION
       DISPLAY-HINT "d"
       STATUS       current
       DESCRIPTION
               "This data type is a non-zero and non-negative value."
       SYNTAX       Integer32 (1..2147483647)

              
NonNegativeInteger32 ::= TEXTUAL-CONVENTION
       DISPLAY-HINT "d"
       STATUS       current
       DESCRIPTION
               "This data type is a non-negative value."
       SYNTAX       Integer32 (0..2147483647)

imv                     OBJECT IDENTIFIER ::=  { enterprises 818 }

geHardware             OBJECT IDENTIFIER ::=  { imv 1 }
geSoftware             OBJECT IDENTIFIER ::=  { imv 2 }
geAgent                OBJECT IDENTIFIER ::=  { imv 3 }

geUPS                  OBJECT IDENTIFIER ::=  { geHardware 1 }

-- The following list is not really a table, but can be implemented as one in the software.
-- The complete UPS section is simply too large to fit in a pre-defined table.
-- The solution: 
-- * All objects are defined for geGenericUPS
-- * All individual UPSs of parallel systems can be reached by their respective sequence
--   number as reflected in below list in stead of the geGenericUPS objects.

geGenericUPS           OBJECT IDENTIFIER ::=  { geUPS 10 }
geFirstUPS             OBJECT IDENTIFIER ::=  { geUPS 11 }
geSecondUPS            OBJECT IDENTIFIER ::=  { geUPS 12 }
geThirdUPS             OBJECT IDENTIFIER ::=  { geUPS 13 }
geFourthUPS            OBJECT IDENTIFIER ::=  { geUPS 14 }
geFifthUPS             OBJECT IDENTIFIER ::=  { geUPS 15 }
geSixthUPS             OBJECT IDENTIFIER ::=  { geUPS 16 }
geSeventhUPS           OBJECT IDENTIFIER ::=  { geUPS 17 }
geEighthUPS            OBJECT IDENTIFIER ::=  { geUPS 18 }
                                              
-- Generic UPS 
                                              
upsIdent-gen                OBJECT IDENTIFIER ::=  { geGenericUPS 1 }
upsBattery-gen              OBJECT IDENTIFIER ::=  { geGenericUPS 2 }
upsInput-gen                OBJECT IDENTIFIER ::=  { geGenericUPS 3 }
upsOutput-gen               OBJECT IDENTIFIER ::=  { geGenericUPS 4 }
upsBypass-gen               OBJECT IDENTIFIER ::=  { geGenericUPS 5 }
upsAlarm-gen                OBJECT IDENTIFIER ::=  { geGenericUPS 6 }
upsWellKnownAlarms-gen      OBJECT IDENTIFIER ::=  { upsAlarm-gen 3 }
upsTest-gen                 OBJECT IDENTIFIER ::=  { geGenericUPS 7 }
upsWellKnownTests-gen       OBJECT IDENTIFIER ::=  { upsTest-gen 7 }
upsControl-gen              OBJECT IDENTIFIER ::=  { geGenericUPS 8 }
upsConfig-gen               OBJECT IDENTIFIER ::=  { geGenericUPS 9 }
upsGetSet-gen               OBJECT IDENTIFIER ::=  { geGenericUPS 10 }
geUPSTraps-gen             OBJECT IDENTIFIER ::=  { geGenericUPS 11 }

-- First UPS 
                                              
upsIdent-first                OBJECT IDENTIFIER ::=  { geFirstUPS 1 }
upsBattery-first              OBJECT IDENTIFIER ::=  { geFirstUPS 2 }
upsInput-first                OBJECT IDENTIFIER ::=  { geFirstUPS 3 }
upsOutput-first               OBJECT IDENTIFIER ::=  { geFirstUPS 4 }
upsBypass-first               OBJECT IDENTIFIER ::=  { geFirstUPS 5 }
upsAlarm-first                OBJECT IDENTIFIER ::=  { geFirstUPS 6 }
upsWellKnownAlarms-first      OBJECT IDENTIFIER ::=  { upsAlarm-first 3 }
upsTest-first                 OBJECT IDENTIFIER ::=  { geFirstUPS 7 }
upsWellKnownTests-first       OBJECT IDENTIFIER ::=  { upsTest-first 7 }
upsControl-first              OBJECT IDENTIFIER ::=  { geFirstUPS 8 }
upsConfig-first               OBJECT IDENTIFIER ::=  { geFirstUPS 9 }
upsGetSet-first               OBJECT IDENTIFIER ::=  { geFirstUPS 10 }
geUPSTraps-first             OBJECT IDENTIFIER ::=  { geFirstUPS 11 }

-- Second UPS 
                                              
upsIdent-second                OBJECT IDENTIFIER ::=  { geSecondUPS 1 }
upsBattery-second              OBJECT IDENTIFIER ::=  { geSecondUPS 2 }
upsInput-second                OBJECT IDENTIFIER ::=  { geSecondUPS 3 }
upsOutput-second               OBJECT IDENTIFIER ::=  { geSecondUPS 4 }
upsBypass-second               OBJECT IDENTIFIER ::=  { geSecondUPS 5 }
upsAlarm-second                OBJECT IDENTIFIER ::=  { geSecondUPS 6 }
upsWellKnownAlarms-second      OBJECT IDENTIFIER ::=  { upsAlarm-second 3 }
upsTest-second                 OBJECT IDENTIFIER ::=  { geSecondUPS 7 }
upsWellKnownTests-second       OBJECT IDENTIFIER ::=  { upsTest-second 7 }
upsControl-second              OBJECT IDENTIFIER ::=  { geSecondUPS 8 }
upsConfig-second               OBJECT IDENTIFIER ::=  { geSecondUPS 9 }
upsGetSet-second               OBJECT IDENTIFIER ::=  { geSecondUPS 10 }
geUPSTraps-second             OBJECT IDENTIFIER ::=  { geSecondUPS 11 }

-- Third UPS 
                                              
upsIdent-third                OBJECT IDENTIFIER ::=  { geThirdUPS 1 }
upsBattery-third              OBJECT IDENTIFIER ::=  { geThirdUPS 2 }
upsInput-third                OBJECT IDENTIFIER ::=  { geThirdUPS 3 }
upsOutput-third               OBJECT IDENTIFIER ::=  { geThirdUPS 4 }
upsBypass-third               OBJECT IDENTIFIER ::=  { geThirdUPS 5 }
upsAlarm-third                OBJECT IDENTIFIER ::=  { geThirdUPS 6 }
upsWellKnownAlarms-third      OBJECT IDENTIFIER ::=  { upsAlarm-third 3 }
upsTest-third                 OBJECT IDENTIFIER ::=  { geThirdUPS 7 }
upsWellKnownTests-third       OBJECT IDENTIFIER ::=  { upsTest-third 7 }
upsControl-third              OBJECT IDENTIFIER ::=  { geThirdUPS 8 }
upsConfig-third               OBJECT IDENTIFIER ::=  { geThirdUPS 9 }
upsGetSet-third               OBJECT IDENTIFIER ::=  { geThirdUPS 10 }
geUPSTraps-third             OBJECT IDENTIFIER ::=  { geThirdUPS 11 }

-- Fourth UPS 
                                              
upsIdent-fourth                OBJECT IDENTIFIER ::=  { geFourthUPS 1 }
upsBattery-fourth              OBJECT IDENTIFIER ::=  { geFourthUPS 2 }
upsInput-fourth                OBJECT IDENTIFIER ::=  { geFourthUPS 3 }
upsOutput-fourth               OBJECT IDENTIFIER ::=  { geFourthUPS 4 }
upsBypass-fourth               OBJECT IDENTIFIER ::=  { geFourthUPS 5 }
upsAlarm-fourth                OBJECT IDENTIFIER ::=  { geFourthUPS 6 }
upsWellKnownAlarms-fourth      OBJECT IDENTIFIER ::=  { upsAlarm-fourth 3 }
upsTest-fourth                 OBJECT IDENTIFIER ::=  { geFourthUPS 7 }
upsWellKnownTests-fourth       OBJECT IDENTIFIER ::=  { upsTest-fourth 7 }
upsControl-fourth              OBJECT IDENTIFIER ::=  { geFourthUPS 8 }
upsConfig-fourth               OBJECT IDENTIFIER ::=  { geFourthUPS 9 }
upsGetSet-fourth               OBJECT IDENTIFIER ::=  { geFourthUPS 10 }
geUPSTraps-fourth             OBJECT IDENTIFIER ::=  { geFourthUPS 11 }

-- Fifth UPS 
                                              
upsIdent-fifth                OBJECT IDENTIFIER ::=  { geFifthUPS 1 }
upsBattery-fifth              OBJECT IDENTIFIER ::=  { geFifthUPS 2 }
upsInput-fifth                OBJECT IDENTIFIER ::=  { geFifthUPS 3 }
upsOutput-fifth               OBJECT IDENTIFIER ::=  { geFifthUPS 4 }
upsBypass-fifth               OBJECT IDENTIFIER ::=  { geFifthUPS 5 }
upsAlarm-fifth                OBJECT IDENTIFIER ::=  { geFifthUPS 6 }
upsWellKnownAlarms-fifth      OBJECT IDENTIFIER ::=  { upsAlarm-fifth 3 }
upsTest-fifth                 OBJECT IDENTIFIER ::=  { geFifthUPS 7 }
upsWellKnownTests-fifth       OBJECT IDENTIFIER ::=  { upsTest-fifth 7 }
upsControl-fifth              OBJECT IDENTIFIER ::=  { geFifthUPS 8 }
upsConfig-fifth               OBJECT IDENTIFIER ::=  { geFifthUPS 9 }
upsGetSet-fifth               OBJECT IDENTIFIER ::=  { geFifthUPS 10 }
geUPSTraps-fifth             OBJECT IDENTIFIER ::=  { geFifthUPS 11 }

-- Sixth UPS 
                                              
upsIdent-sixth                OBJECT IDENTIFIER ::=  { geSixthUPS 1 }
upsBattery-sixth              OBJECT IDENTIFIER ::=  { geSixthUPS 2 }
upsInput-sixth                OBJECT IDENTIFIER ::=  { geSixthUPS 3 }
upsOutput-sixth               OBJECT IDENTIFIER ::=  { geSixthUPS 4 }
upsBypass-sixth               OBJECT IDENTIFIER ::=  { geSixthUPS 5 }
upsAlarm-sixth                OBJECT IDENTIFIER ::=  { geSixthUPS 6 }
upsWellKnownAlarms-sixth      OBJECT IDENTIFIER ::=  { upsAlarm-sixth 3 }
upsTest-sixth                 OBJECT IDENTIFIER ::=  { geSixthUPS 7 }
upsWellKnownTests-sixth       OBJECT IDENTIFIER ::=  { upsTest-sixth 7 }
upsControl-sixth              OBJECT IDENTIFIER ::=  { geSixthUPS 8 }
upsConfig-sixth               OBJECT IDENTIFIER ::=  { geSixthUPS 9 }
upsGetSet-sixth               OBJECT IDENTIFIER ::=  { geSixthUPS 10 }
geUPSTraps-sixth             OBJECT IDENTIFIER ::=  { geSixthUPS 11 }

-- Seventh UPS 
                                              
upsIdent-seventh                OBJECT IDENTIFIER ::=  { geSeventhUPS 1 }
upsBattery-seventh              OBJECT IDENTIFIER ::=  { geSeventhUPS 2 }
upsInput-seventh                OBJECT IDENTIFIER ::=  { geSeventhUPS 3 }
upsOutput-seventh               OBJECT IDENTIFIER ::=  { geSeventhUPS 4 }
upsBypass-seventh               OBJECT IDENTIFIER ::=  { geSeventhUPS 5 }
upsAlarm-seventh                OBJECT IDENTIFIER ::=  { geSeventhUPS 6 }
upsWellKnownAlarms-seventh      OBJECT IDENTIFIER ::=  { upsAlarm-seventh 3 }
upsTest-seventh                 OBJECT IDENTIFIER ::=  { geSeventhUPS 7 }
upsWellKnownTests-seventh       OBJECT IDENTIFIER ::=  { upsTest-seventh 7 }
upsControl-seventh              OBJECT IDENTIFIER ::=  { geSeventhUPS 8 }
upsConfig-seventh               OBJECT IDENTIFIER ::=  { geSeventhUPS 9 }
upsGetSet-seventh               OBJECT IDENTIFIER ::=  { geSeventhUPS 10 }
geUPSTraps-seventh             OBJECT IDENTIFIER ::=  { geSeventhUPS 11 }

-- Eighth UPS 
                                              
upsIdent-eighth                OBJECT IDENTIFIER ::=  { geEighthUPS 1 }
upsBattery-eighth              OBJECT IDENTIFIER ::=  { geEighthUPS 2 }
upsInput-eighth                OBJECT IDENTIFIER ::=  { geEighthUPS 3 }
upsOutput-eighth               OBJECT IDENTIFIER ::=  { geEighthUPS 4 }
upsBypass-eighth               OBJECT IDENTIFIER ::=  { geEighthUPS 5 }
upsAlarm-eighth                OBJECT IDENTIFIER ::=  { geEighthUPS 6 }
upsWellKnownAlarms-eighth      OBJECT IDENTIFIER ::=  { upsAlarm-eighth 3 }
upsTest-eighth                 OBJECT IDENTIFIER ::=  { geEighthUPS 7 }
upsWellKnownTests-eighth       OBJECT IDENTIFIER ::=  { upsTest-eighth 7 }
upsControl-eighth              OBJECT IDENTIFIER ::=  { geEighthUPS 8 }
upsConfig-eighth               OBJECT IDENTIFIER ::=  { geEighthUPS 9 }
upsGetSet-eighth               OBJECT IDENTIFIER ::=  { geEighthUPS 10 }
geUPSTraps-eighth             OBJECT IDENTIFIER ::=  { geEighthUPS 11 }

--
-- Environtmental card 
--

geEnvironmental        OBJECT IDENTIFIER ::=  { geHardware 2 }

ioInterface-First       OBJECT IDENTIFIER ::=  { geEnvironmental 1 }
ioInterface-Second      OBJECT IDENTIFIER ::=  { geEnvironmental 2 }
ioInterface-Third       OBJECT IDENTIFIER ::=  { geEnvironmental 3 }
ioInterface-Fourth      OBJECT IDENTIFIER ::=  { geEnvironmental 4 }
ioInterface-Fifth       OBJECT IDENTIFIER ::=  { geEnvironmental 5 }
ioInterface-Sixth       OBJECT IDENTIFIER ::=  { geEnvironmental 6 }
ioInterface-Seventh     OBJECT IDENTIFIER ::=  { geEnvironmental 7 }
ioInterface-Eighth      OBJECT IDENTIFIER ::=  { geEnvironmental 8 }

-- First Environmental card 

ioInterfaceInputLine-First     OBJECT IDENTIFIER ::=  { ioInterface-First 1 }
ioInterfaceOutputLine-First    OBJECT IDENTIFIER ::=  { ioInterface-First 2 }
ioInterfaceAnalogueLine-First  OBJECT IDENTIFIER ::=  { ioInterface-First 3 }
ioInterfaceTraps-First         OBJECT IDENTIFIER ::=  { ioInterface-First 4 }

-- Second Environmental card 

ioInterfaceInputLine-Second     OBJECT IDENTIFIER ::=  { ioInterface-Second 1 }
ioInterfaceOutputLine-Second    OBJECT IDENTIFIER ::=  { ioInterface-Second 2 }
ioInterfaceAnalogueLine-Second  OBJECT IDENTIFIER ::=  { ioInterface-Second 3 }
ioInterfaceTraps-Second         OBJECT IDENTIFIER ::=  { ioInterface-Second 4 }

-- Third Environmental card

ioInterfaceInputLine-Third     OBJECT IDENTIFIER ::=  { ioInterface-Third 1 }
ioInterfaceOutputLine-Third    OBJECT IDENTIFIER ::=  { ioInterface-Third 2 }
ioInterfaceAnalogueLine-Third  OBJECT IDENTIFIER ::=  { ioInterface-Third 3 }
ioInterfaceTraps-Third         OBJECT IDENTIFIER ::=  { ioInterface-Third 4 }

-- Fourth Environmental card 

ioInterfaceInputLine-Fourth     OBJECT IDENTIFIER ::=  { ioInterface-Fourth 1 }
ioInterfaceOutputLine-Fourth    OBJECT IDENTIFIER ::=  { ioInterface-Fourth 2 }
ioInterfaceAnalogueLine-Fourth  OBJECT IDENTIFIER ::=  { ioInterface-Fourth 3 }
ioInterfaceTraps-Fourth         OBJECT IDENTIFIER ::=  { ioInterface-Fourth 4 }

-- Fifth Environmental card 

ioInterfaceInputLine-Fifth     OBJECT IDENTIFIER ::=  { ioInterface-Fifth 1 }
ioInterfaceOutputLine-Fifth    OBJECT IDENTIFIER ::=  { ioInterface-Fifth 2 }
ioInterfaceAnalogueLine-Fifth  OBJECT IDENTIFIER ::=  { ioInterface-Fifth 3 }
ioInterfaceTraps-Fifth         OBJECT IDENTIFIER ::=  { ioInterface-Fifth 4 }

-- Sixth Environmental card 

ioInterfaceInputLine-Sixth     OBJECT IDENTIFIER ::=  { ioInterface-Sixth 1 }
ioInterfaceOutputLine-Sixth    OBJECT IDENTIFIER ::=  { ioInterface-Sixth 2 }
ioInterfaceAnalogueLine-Sixth  OBJECT IDENTIFIER ::=  { ioInterface-Sixth 3 }
ioInterfaceTraps-Sixth         OBJECT IDENTIFIER ::=  { ioInterface-Sixth 4 }

-- Seventh Environmental card

ioInterfaceInputLine-Seventh     OBJECT IDENTIFIER ::=  { ioInterface-Seventh 1 }
ioInterfaceOutputLine-Seventh    OBJECT IDENTIFIER ::=  { ioInterface-Seventh 2 }
ioInterfaceAnalogueLine-Seventh  OBJECT IDENTIFIER ::=  { ioInterface-Seventh 3 }
ioInterfaceTraps-Seventh         OBJECT IDENTIFIER ::=  { ioInterface-Seventh 4 }

-- Eighth Environmental card -

ioInterfaceInputLine-Eighth     OBJECT IDENTIFIER ::=  { ioInterface-Eighth 1 }
ioInterfaceOutputLine-Eighth    OBJECT IDENTIFIER ::=  { ioInterface-Eighth 2 }
ioInterfaceAnalogueLine-Eighth  OBJECT IDENTIFIER ::=  { ioInterface-Eighth 3 }
ioInterfaceTraps-Eighth         OBJECT IDENTIFIER ::=  { ioInterface-Eighth 4 }

--
-- Modem 
--

geModem                OBJECT IDENTIFIER ::=  { geHardware 3 }

--
-- Device 
--

geDevices              OBJECT IDENTIFIER ::=  { geHardware 100 }
geDevicesDescriptions  OBJECT IDENTIFIER ::=  { geDevices 1 }

advSNMPWebIntCard       OBJECT IDENTIFIER ::=  { geDevicesDescriptions 1 }
snmpPWebIntCard          OBJECT IDENTIFIER ::=  { geDevicesDescriptions 2 }
snmpWebIntBox           OBJECT IDENTIFIER ::=  { geDevicesDescriptions 3 }
snmpSWPFAgent           OBJECT IDENTIFIER ::=  { geDevicesDescriptions 4 }
snmpSWJUMPAgent         OBJECT IDENTIFIER ::=  { geDevicesDescriptions 5 }

--
-- Client 
--

geClient               OBJECT IDENTIFIER ::=  { geSoftware 1 }
          
--
-- Agent 
--
          
geAgentConfig          OBJECT IDENTIFIER ::=  { geAgent 1 }
geAgentTraps           OBJECT IDENTIFIER ::=  { geAgent 2 }

--
-- The GE UPS group
--

geDiscoveredUPSsMask OBJECT-TYPE
    SYNTAX     Integer32
    MAX-ACCESS read-only
    STATUS     current
    DESCRIPTION
            "Reading this variable returns bit mask indicating which 
            UPSs in a parallel system are alive. Management 
            software should poll only these UPSs on their snmp
            branches 11-18 as follows:

              1  FirstUPS alive
              2  SecondUPS alive
              4  ThirdUPS alive
              8  FourthUPS alive
             16  FifthUPS alive
             32  SixthUPS alive
             64  SeventhUPS alive
            128  EigthUPS alive

            Since the management software should always monitor
            the GenericUPS branch (10), this value has no meaning 
            for single upses (which provide values on that snmp 
            branch), and should be set to zero in that case."
    ::= { geUPS 1 }

geRequestPacket OBJECT-TYPE
    SYNTAX     DisplayString (SIZE (0..63))
    MAX-ACCESS read-write 
    STATUS     current
    DESCRIPTION
            "Put the string, formatted as a IMV/CP4 packet, directly to internally RS485 bus. 
	This OID could be used for accede directly to the internally RS485 bus from a remote place."
    ::= { geUPS 2 }

geReplyPacket OBJECT-TYPE
    SYNTAX     DisplayString (SIZE (0..63))
    MAX-ACCESS read-only
    STATUS     current
    DESCRIPTION
            "Contain the reply of the IMV/CP4 request packet sent using the OID geRequestPacket. 
	Every time that a write command has be made at the OID ge RequestPacket, the value of this OID is erased."
    ::= { geUPS 3 }



--
-- The Device Identification group. Generic
--      All objects in this group except for upsIdentName and
--      upsIdentAttachedDevices are set at device initialization
--      and remain static.
--

upsIdentManufacturer-gen OBJECT-TYPE
    SYNTAX     DisplayString (SIZE (0..31))
    MAX-ACCESS read-only
    STATUS     current
    DESCRIPTION
            "The name of the UPS manufacturer.(*)"
    ::= { upsIdent-gen 1 }

upsIdentModel-gen OBJECT-TYPE
    SYNTAX     DisplayString (SIZE (0..63))
    MAX-ACCESS read-only
    STATUS     current
    DESCRIPTION
            "The UPS Model designation.(*)"
    ::= { upsIdent-gen 2 }

upsIdentUPSSoftwareVersion-gen OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-gen 3 }

upsIdentAgentSoftwareVersion-gen OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-gen 4 }

upsIdentName-gen OBJECT-TYPE
    SYNTAX     DisplayString (SIZE(0..63))
    MAX-ACCESS read-write
    STATUS     current
    DESCRIPTION
            "A string identifying the UPS.  This object should be
            set by the administrator.(*)"
    ::= { upsIdent-gen 5 }

upsIdentAttachedDevices-gen OBJECT-TYPE
    SYNTAX     DisplayString (SIZE(0..63))
    MAX-ACCESS read-write
    STATUS     current
    DESCRIPTION
            "A string identifying the devices attached to the
            output(s) of the UPS.  This object should be set by
            the administrator.(*)"
    ::= { upsIdent-gen 6 }

upsIdentUPSSerialNumber-gen OBJECT-TYPE
    SYNTAX     DisplayString (SIZE(0..31))
    MAX-ACCESS read-only
    STATUS     current
    DESCRIPTION
            "The UPS serial number"
    ::= { upsIdent-gen 7 }
				
upsIdentComProtVersion-gen OBJECT-TYPE
    SYNTAX     DisplayString (SIZE(0..15))
    MAX-ACCESS read-only
    STATUS     current
    DESCRIPTION
            "The IMV communication protocol version"
    ::= { upsIdent-gen 8 }	
		
upsIdentOperatingTime-gen OBJECT-TYPE
    SYNTAX     NonNegativeInteger32
    UNITS      "seconds"
    MAX-ACCESS read-only
    STATUS     current
    DESCRIPTION
            "The present value of the operating time.
             total 'on' time since UPS manufactured"
    ::= { upsIdent-gen 9 }	
				
--
-- Battery Group Generic
--

upsBatteryStatus-gen OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-gen 1 }

upsSecondsOnBattery-gen OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-gen 2 }

upsEstimatedMinutesRemaining-gen OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-gen 3 }

upsEstimatedChargeRemaining-gen OBJECT-TYPE
    SYNTAX     Integer32 (0..100)
    UNITS      "percent"
    MAX-ACCESS read-only
    STATUS     current
    DESCRIPTION
            "An estimate of the battery charge remaining expressed
            as a percent of full charge.(*)"
    ::= { upsBattery-gen 4 }

upsBatteryVoltage-gen OBJECT-TYPE
    SYNTAX     NonNegativeInteger32
    UNITS      "0.1 Volt DC"
    MAX-ACCESS read-only
    STATUS     current
    DESCRIPTION
            "The magnitude of the present battery voltage.(*)"
    ::= { upsBattery-gen 5 }

upsBatteryCurrent-gen OBJECT-TYPE
    SYNTAX     Integer32
    UNITS      "0.1 Amp DC"
    MAX-ACCESS read-only
    STATUS     current
    DESCRIPTION
            "The present battery current.(*)"
    ::= { upsBattery-gen 6 }

upsBatteryTemperature-gen OBJECT-TYPE
    SYNTAX     Integer32
    UNITS      "degrees Centigrade"
    MAX-ACCESS read-only
    STATUS     current
    DESCRIPTION
            "The ambient temperature at or near the UPS Battery
            casing.(*)"
    ::= { upsBattery-gen 7 }

--
-- Input Group
--

upsInputLineBads-gen OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-gen 1 }

upsInputNumLines-gen OBJECT-TYPE
    SYNTAX     NonNegativeInteger32
    MAX-ACCESS read-only
    STATUS     current
    DESCRIPTION
            "The number of input lines utilized in this device.
            This variable indicates the number of rows in the
            input table.(*)"
    ::= { upsInput-gen 2 }

upsInputTable-gen OBJECT-TYPE
    SYNTAX     SEQUENCE OF UpsInputEntry-gen
    MAX-ACCESS not-accessible
    STATUS     current
    DESCRIPTION
            "A list of input table entries.  The number of entries
            is given by the value of upsInputNumLines.(*)"
    ::= { upsInput-gen 3 }

upsInputEntry-gen OBJECT-TYPE
    SYNTAX     UpsInputEntry-gen
    MAX-ACCESS not-accessible
    STATUS     current
    DESCRIPTION
            "An entry containing information applicable to a
            particular input line.(*)"
    INDEX { upsInputLineIndex-gen }
    ::= { upsInputTable-gen 1 }

UpsInputEntry-gen ::= SEQUENCE {
    upsInputLineIndex-gen   PositiveInteger32,
    upsInputFrequency-gen   NonNegativeInteger32,
    upsInputVoltage-gen     NonNegativeInteger32,
    upsInputCurrent-gen     NonNegativeInteger32,
    upsInputTruePower-gen   NonNegativeInteger32,
    upsInputVoltageMin-gen  NonNegativeInteger32,
    upsInputVoltageMax-gen  NonNegativeInteger32
}

upsInputLineIndex-gen OBJECT-TYPE
    SYNTAX     PositiveInteger32
    MAX-ACCESS not-accessible
    STATUS     current
    DESCRIPTION
            "The input line identifier.(*)"
    ::= { upsInputEntry-gen 1 }

upsInputFrequency-gen OBJECT-TYPE
    SYNTAX     NonNegativeInteger32
    UNITS      "0.1 Hertz"
    MAX-ACCESS read-only
    STATUS     current
    DESCRIPTION
            "The present input frequency.(*)"
    ::= { upsInputEntry-gen 2 }

upsInputVoltage-gen OBJECT-TYPE
    SYNTAX     NonNegativeInteger32
    UNITS      "RMS Volts"
    MAX-ACCESS read-only
    STATUS     current
    DESCRIPTION
            "The magnitude of the present input voltage.(*)"
    ::= { upsInputEntry-gen 3 }

upsInputCurrent-gen OBJECT-TYPE
    SYNTAX     NonNegativeInteger32
    UNITS      "0.1 RMS Amp"
    MAX-ACCESS read-only
    STATUS     current
    DESCRIPTION
            "The magnitude of the present input current.(*)"
    ::= { upsInputEntry-gen 4 }

upsInputTruePower-gen OBJECT-TYPE
    SYNTAX     NonNegativeInteger32
    UNITS      "Watts"
    MAX-ACCESS read-only
    STATUS     current
    DESCRIPTION
            "The magnitude of the present input true power.(*)"
    ::= { upsInputEntry-gen 5 }

upsInputVoltageMin-gen OBJECT-TYPE
    SYNTAX     NonNegativeInteger32
    UNITS      "RMS Volts"
    MAX-ACCESS read-only
    STATUS     current
    DESCRIPTION
            "The lowest magnitude of the input voltage since last read out."
    ::= { upsInputEntry-gen 6 }

upsInputVoltageMax-gen OBJECT-TYPE
    SYNTAX     NonNegativeInteger32
    UNITS      "RMS Volts"
    MAX-ACCESS read-only
    STATUS     current
    DESCRIPTION
            "The highest magnitude of the input voltage since last read out."
    ::= { upsInputEntry-gen 7 }

--
-- The Output group.
--

upsOutputSource-gen OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-gen 1 }

upsOutputFrequency-gen OBJECT-TYPE
    SYNTAX     NonNegativeInteger32
    UNITS      "0.1 Hertz"
    MAX-ACCESS read-only
    STATUS     current
    DESCRIPTION
            "The present output frequency.(*)"
    ::= { upsOutput-gen 2 }

upsOutputNumLines-gen OBJECT-TYPE
    SYNTAX     NonNegativeInteger32
    MAX-ACCESS read-only
    STATUS     current
    DESCRIPTION
            "The number of output lines utilized in this device.
            This variable indicates the number of rows in the
            output table.(*)"
    ::= { upsOutput-gen 3 }

upsOutputTable-gen OBJECT-TYPE
    SYNTAX     SEQUENCE OF UpsOutputEntry-gen
    MAX-ACCESS not-accessible
    STATUS     current
    DESCRIPTION
            "A list of output table entries.  The number of
            entries is given by the value of upsOutputNumLines.(*)"
    ::= { upsOutput-gen 4 }

upsOutputEntry-gen OBJECT-TYPE
    SYNTAX     UpsOutputEntry-gen
    MAX-ACCESS not-accessible
    STATUS     current
    DESCRIPTION
            "An entry containing information applicable to a
            particular output line.(*)"
    INDEX { upsOutputLineIndex-gen }
    ::= { upsOutputTable-gen 1 }

UpsOutputEntry-gen ::= SEQUENCE {
    upsOutputLineIndex-gen   PositiveInteger32,
    upsOutputVoltage-gen     NonNegativeInteger32,
    upsOutputCurrent-gen     NonNegativeInteger32,
    upsOutputPower-gen       NonNegativeInteger32,
    upsOutputPercentLoad-gen Integer32
}

upsOutputLineIndex-gen OBJECT-TYPE
    SYNTAX     PositiveInteger32
    MAX-ACCESS not-accessible
    STATUS     current
    DESCRIPTION
            "The output line identifier.(*)"
    ::= { upsOutputEntry-gen 1 }

upsOutputVoltage-gen OBJECT-TYPE
    SYNTAX     NonNegativeInteger32
    UNITS      "RMS Volts"
    MAX-ACCESS read-only
    STATUS     current
    DESCRIPTION
            "The present output voltage.(*)"
    ::= { upsOutputEntry-gen 2 }

upsOutputCurrent-gen OBJECT-TYPE
    SYNTAX     NonNegativeInteger32
    UNITS      "0.1 RMS Amp"
    MAX-ACCESS read-only
    STATUS     current
    DESCRIPTION
            "The present output current.(*)"
    ::= { upsOutputEntry-gen 3 }

upsOutputPower-gen OBJECT-TYPE
    SYNTAX     NonNegativeInteger32
    UNITS      "Watts"
    MAX-ACCESS read-only
    STATUS     current
    DESCRIPTION
            "The present output true power.(*)"
    ::= { upsOutputEntry-gen 4 }

upsOutputPercentLoad-gen OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-gen 5 }

--
-- The Bypass group generic.
--

upsBypassFrequency-gen OBJECT-TYPE
    SYNTAX     NonNegativeInteger32
    UNITS      "0.1 Hertz"
    MAX-ACCESS read-only
    STATUS     current
    DESCRIPTION
            "The present bypass frequency.(*)"
    ::= { upsBypass-gen 1 }

upsBypassNumLines-gen OBJECT-TYPE
    SYNTAX     NonNegativeInteger32
    MAX-ACCESS read-only
    STATUS     current
    DESCRIPTION
            "The number of bypass lines utilized in this device.
            This entry indicates the number of rows in the bypass
            table.(*)"
    ::= { upsBypass-gen 2 }

upsBypassTable-gen OBJECT-TYPE
    SYNTAX     SEQUENCE OF UpsBypassEntry-gen
    MAX-ACCESS not-accessible
    STATUS     current
    DESCRIPTION
            "A list of bypass table entries.  The number of
            entries is given by the value of upsBypassNumLines.(*)"
    ::= { upsBypass-gen 3 }

upsBypassEntry-gen OBJECT-TYPE
    SYNTAX     UpsBypassEntry-gen
    MAX-ACCESS not-accessible
    STATUS     current
    DESCRIPTION
            "An entry containing information applicable to a
            particular bypass input.(*)"
    INDEX { upsBypassLineIndex-gen }
    ::= { upsBypassTable-gen 1 }

UpsBypassEntry-gen ::= SEQUENCE {
    upsBypassLineIndex-gen  PositiveInteger32,
    upsBypassVoltage-gen    NonNegativeInteger32,
    upsBypassCurrent-gen    NonNegativeInteger32,
    upsBypassPower-gen      NonNegativeInteger32
}

upsBypassLineIndex-gen OBJECT-TYPE
    SYNTAX     PositiveInteger32
    MAX-ACCESS not-accessible
    STATUS     current
    DESCRIPTION
            "The bypass line identifier.(*)"
    ::= { upsBypassEntry-gen 1 }

upsBypassVoltage-gen OBJECT-TYPE
    SYNTAX     NonNegativeInteger32
    UNITS      "RMS Volts"
    MAX-ACCESS read-only
    STATUS     current
    DESCRIPTION
            "The present bypass voltage.(*)"
    ::= { upsBypassEntry-gen 2 }

upsBypassCurrent-gen OBJECT-TYPE
    SYNTAX     NonNegativeInteger32
    UNITS      "0.1 RMS Amp"
    MAX-ACCESS read-only
    STATUS     current
    DESCRIPTION
            "The present bypass current.(*)"
    ::= { upsBypassEntry-gen 3 }

upsBypassPower-gen OBJECT-TYPE
    SYNTAX     NonNegativeInteger32
    UNITS      "Watts"
    MAX-ACCESS read-only
    STATUS     current
    DESCRIPTION
            "The present true power conveyed by the bypass.(*)"
    ::= { upsBypassEntry-gen 4 }

--
-- The Alarm group generic.
--

upsAlarmsPresent-gen OBJECT-TYPE
    SYNTAX     Gauge32
    MAX-ACCESS read-only
    STATUS     current
    DESCRIPTION
            "The present number of active alarm conditions.(*)"
    ::= { upsAlarm-gen 1 }

upsAlarmTable-gen OBJECT-TYPE
    SYNTAX     SEQUENCE OF UpsAlarmEntry-gen
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-gen 2 }

upsAlarmEntry-gen OBJECT-TYPE
    SYNTAX     UpsAlarmEntry-gen
    MAX-ACCESS not-accessible
    STATUS     current
    DESCRIPTION
            "An entry containing information applicable to a
            particular alarm.(*)"
    INDEX { upsAlarmId-gen }
    ::= { upsAlarmTable-gen 1 }

UpsAlarmEntry-gen ::= SEQUENCE {
    upsAlarmId-gen          PositiveInteger32,
    upsAlarmDescr-gen       AutonomousType,
    upsAlarmTime-gen       TimeStamp
}

upsAlarmId-gen OBJECT-TYPE
    SYNTAX     PositiveInteger32
    MAX-ACCESS not-accessible
    STATUS     current
    DESCRIPTION
            "A unique identifier for an alarm condition.  This
            value must remain constant.(*)"
    ::= { upsAlarmEntry-gen 1 }

upsAlarmDescr-gen OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-gen 2 }

upsAlarmTime-gen OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-gen 3 }

--
-- Well known alarm conditions generic.
--

upsAlarmBatteryBad-gen OBJECT-IDENTITY
    STATUS     current
    DESCRIPTION
            "One or more batteries have been determined to require
            replacement.(*)"
    ::= { upsWellKnownAlarms-gen  1 }

upsAlarmOnBattery-gen OBJECT-IDENTITY
    STATUS     current
    DESCRIPTION
            "The UPS is drawing power from the batteries.(*)"
    ::= { upsWellKnownAlarms-gen  2 }

upsAlarmLowBattery-gen OBJECT-IDENTITY
    STATUS     current
    DESCRIPTION
            "The remaining battery run-time is less than or equal
            to upsConfigLowBattTime.(*)"
    ::= { upsWellKnownAlarms-gen  3 }

upsAlarmDepletedBattery-gen OBJECT-IDENTITY
    STATUS     current
    DESCRIPTION
            "The UPS will be unable to sustain the present load
            when and if the utility power is lost.(*)"
    ::= { upsWellKnownAlarms-gen  4 }

upsAlarmTempBad-gen OBJECT-IDENTITY
    STATUS     current
    DESCRIPTION
            "A temperature is out of tolerance.(*)"
    ::= { upsWellKnownAlarms-gen  5 }

upsAlarmInputBad-gen OBJECT-IDENTITY
    STATUS     current
    DESCRIPTION
            "An input condition is out of tolerance.(*)"
    ::= { upsWellKnownAlarms-gen  6 }

upsAlarmOutputBad-gen OBJECT-IDENTITY
    STATUS     current
    DESCRIPTION
            "An output condition (other than OutputOverload) is
            out of tolerance.(*)"
    ::= { upsWellKnownAlarms-gen  7 }

upsAlarmOutputOverload-gen OBJECT-IDENTITY
    STATUS     current
    DESCRIPTION
            "The output load exceeds the UPS output capacity.(*)"
    ::= { upsWellKnownAlarms-gen  8 }

upsAlarmOnBypass-gen OBJECT-IDENTITY
    STATUS     current
    DESCRIPTION
            "The Bypass is presently engaged on the UPS.(*)"
    ::= { upsWellKnownAlarms-gen  9 }

upsAlarmBypassBad-gen OBJECT-IDENTITY
    STATUS     current
    DESCRIPTION
            "The Bypass is out of tolerance.(*)"
    ::= { upsWellKnownAlarms-gen 10 }

upsAlarmOutputOffAsRequested-gen OBJECT-IDENTITY
    STATUS     current
    DESCRIPTION
            "The UPS has shutdown as requested, i.e., the output
            is off.(*)"
    ::= { upsWellKnownAlarms-gen 11 }

upsAlarmUpsOffAsRequested-gen OBJECT-IDENTITY
    STATUS     current
    DESCRIPTION
            "The entire UPS has shutdown as commanded.(*)"
    ::= { upsWellKnownAlarms-gen 12 }

upsAlarmChargerFailed-gen OBJECT-IDENTITY
    STATUS     current
    DESCRIPTION
            "An uncorrected problem has been detected within the
            UPS charger subsystem.(*)"
    ::= { upsWellKnownAlarms-gen 13 }

upsAlarmUpsOutputOff-gen OBJECT-IDENTITY
    STATUS     current
    DESCRIPTION
            "The output of the UPS is in the off state.(*)"
    ::= { upsWellKnownAlarms-gen 14 }

upsAlarmUpsSystemOff-gen OBJECT-IDENTITY
    STATUS     current
    DESCRIPTION
            "The UPS system is in the off state.(*)"
    ::= { upsWellKnownAlarms-gen 15 }

upsAlarmFanFailure-gen OBJECT-IDENTITY
    STATUS     current
    DESCRIPTION
            "The failure of one or more fans in the UPS has been
            detected.(*)"
    ::= { upsWellKnownAlarms-gen 16 }

upsAlarmFuseFailure-gen OBJECT-IDENTITY
    STATUS     current
    DESCRIPTION
            "The failure of one or more fuses has been detected.(*)"
    ::= { upsWellKnownAlarms-gen 17 }

upsAlarmGeneralFault-gen OBJECT-IDENTITY
    STATUS     current
    DESCRIPTION
            "A general fault in the UPS has been detected.(*)"
    ::= { upsWellKnownAlarms-gen 18 }

upsAlarmDiagnosticTestFailed-gen OBJECT-IDENTITY
    STATUS     current
    DESCRIPTION
            "The result of the last diagnostic test indicates a
            failure.(*)"
    ::= { upsWellKnownAlarms-gen 19 }

upsAlarmCommunicationsLost-gen OBJECT-IDENTITY
    STATUS     current
    DESCRIPTION
            "A problem has been encountered in the communications
            between the agent and the UPS.(*)"
    ::= { upsWellKnownAlarms-gen 20 }

upsAlarmAwaitingPower-gen OBJECT-IDENTITY
    STATUS     current
    DESCRIPTION
            "The UPS output is off and the UPS is awaiting the
            return of input power.(*)"
    ::= { upsWellKnownAlarms-gen 21 }

upsAlarmShutdownPending-gen OBJECT-IDENTITY
    STATUS     current
    DESCRIPTION
            "A upsShutdownAfterDelay countdown is underway.(*)"
    ::= { upsWellKnownAlarms-gen 22 }

upsAlarmShutdownImminent-gen OBJECT-IDENTITY
    STATUS     current
    DESCRIPTION
            "The UPS will turn off power to the load in less than
            5 seconds; this may be either a timed shutdown or a
            low battery shutdown.(*)"
    ::= { upsWellKnownAlarms-gen 23 }

upsAlarmTestInProgress-gen OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-gen 24 }

upsAlarmReceptacleOff-gen OBJECT-IDENTITY
    STATUS     current
    DESCRIPTION
            "The receptacle are switch off    "
    ::= { upsWellKnownAlarms-gen 25 }

upsAlarmMaskA-gen OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-gen 4 }

--
-- The Test Group generic
--

upsTestId-gen OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-gen 1 }

-- see [6] for more information on the semantics of objects with
-- syntax of TestAndIncr

upsTestSpinLock-gen OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-gen 2 }

upsTestResultsSummary-gen OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-gen 3 }

upsTestResultsDetail-gen OBJECT-TYPE
    SYNTAX     DisplayString (SIZE (0..255))
    MAX-ACCESS read-only
    STATUS     current
    DESCRIPTION
            "Additional information about upsTestResultsSummary.
            If no additional information available, a zero length
            string is returned.(*)"
    ::= { upsTest-gen 4 }

upsTestStartTime-gen OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-gen 5 }

upsTestElapsedTime-gen OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-gen 6 }

--
-- Well known tests generic.
--

upsTestNoTestsInitiated-gen OBJECT-IDENTITY
    STATUS     current
    DESCRIPTION
            "No tests have been initiated and no test is in
            progress.(*)"
    ::= { upsWellKnownTests-gen  1 }

upsTestAbortTestInProgress-gen OBJECT-IDENTITY
    STATUS     current
    DESCRIPTION
            "The test in progress is to be aborted / the test in
            progress was aborted.(*)"
    ::= { upsWellKnownTests-gen  2 }

upsTestGeneralSystemsTest-gen OBJECT-IDENTITY
    STATUS     current
    DESCRIPTION
            "The manufacturer's standard test of UPS device
            systems.(*)"
    ::= { upsWellKnownTests-gen  3 }

upsTestQuickBatteryTest-gen OBJECT-IDENTITY
    STATUS     current
    DESCRIPTION
            "A test that is sufficient to determine if the battery
            needs replacement.(*)"
    ::= { upsWellKnownTests-gen  4 }

upsTestDeepBatteryCalibration-gen OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-gen  5 }

--
-- The Control group generic.
--

upsShutdownType-gen OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-gen 1 }

upsShutdownAfterDelay-gen OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-gen 2 }

upsStartupAfterDelay-gen OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-gen 3 }

upsRebootWithDuration-gen OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-gen 4 }

upsAutoRestart-gen OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-gen 5 }

upsReceptaclesNum-gen OBJECT-TYPE
    SYNTAX     NonNegativeInteger32
    MAX-ACCESS read-only
    STATUS     current
    DESCRIPTION
            "The number of receptacles utilized in this device.
            This entry indicates the number of rows in the receptacle
            table."
    ::= { upsControl-gen 6 }

upsReceptacleTable-gen OBJECT-TYPE
    SYNTAX     SEQUENCE OF UpsReceptacleEntry-gen
    MAX-ACCESS not-accessible
    STATUS     current
    DESCRIPTION
            "A list of receptacle table entries.  The number of
            entries is given by the value of upsReceptacleNum."
    ::= { upsControl-gen 7 }

upsReceptacleEntry-gen OBJECT-TYPE
    SYNTAX     UpsReceptacleEntry-gen
    MAX-ACCESS not-accessible
    STATUS     current
    DESCRIPTION
            "An entry containing information applicable to a
            particular receptacle."
    INDEX { upsReceptacleLineIndex-gen }
    ::= { upsReceptacleTable-gen 1 }

UpsReceptacleEntry-gen ::= SEQUENCE {
    upsReceptacleLineIndex-gen  PositiveInteger32,
    upsReceptacleOnOff-gen      Integer32    
}

upsReceptacleLineIndex-gen OBJECT-TYPE
    SYNTAX     PositiveInteger32
    MAX-ACCESS not-accessible
    STATUS     current
    DESCRIPTION
            "The receptacle line identifier."
    ::= { upsReceptacleEntry-gen 1 }

upsReceptacleOnOff-gen OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-gen 2 }

upsUPSMode-gen OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-gen 8 }

upsRectifierOnOff-gen OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-gen 9 }

upsBatteryChargeMethod-gen OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-gen 10 }

upsInverterOnOff-gen OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-gen 11 }

upsBypassOnOff-gen OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-gen 12 }

upsLoadSource-gen OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-gen 13 }
	
--
-- The Configuration group generic.
--

upsConfigInputVoltage-gen OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-gen 1 }

upsConfigInputFreq-gen OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-gen 2 }

upsConfigOutputVoltage-gen OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-gen 3 }

upsConfigOutputFreq-gen OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-gen 4 }

upsConfigOutputVA-gen OBJECT-TYPE
    SYNTAX     NonNegativeInteger32
    UNITS      "Volt-Amps"
    MAX-ACCESS read-only
    STATUS     current
    DESCRIPTION
            "The magnitude of the nominal Volt-Amp rating.(*)"
    ::= { upsConfig-gen 5 }

upsConfigOutputPower-gen OBJECT-TYPE
    SYNTAX     NonNegativeInteger32
    UNITS      "Watts"
    MAX-ACCESS read-only
    STATUS     current
    DESCRIPTION
            "The magnitude of the nominal true power rating.(*)"
    ::= { upsConfig-gen 6 }

upsConfigLowBattTime-gen OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-gen 7 }

upsConfigAudibleStatus-gen OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-gen 8 }

upsConfigLowVoltageTransferPoint-gen OBJECT-TYPE
    SYNTAX     NonNegativeInteger32
    UNITS      "RMS Volts"
    MAX-ACCESS read-write
    STATUS     current
    DESCRIPTION
            "The minimum input line voltage allowed before the UPS
            system transfers to battery backup.(*)"
    ::= { upsConfig-gen 9 }

upsConfigHighVoltageTransferPoint-gen OBJECT-TYPE
    SYNTAX     NonNegativeInteger32
    UNITS      "RMS Volts"
    MAX-ACCESS read-write
    STATUS     current
    DESCRIPTION
            "The maximum line voltage allowed before the UPS
            system transfers to battery backup.(*)"
    ::= { upsConfig-gen 10 }

upsConfigBatteryCapacity-gen OBJECT-TYPE
    SYNTAX     NonNegativeInteger32
    UNITS      "Amps Hours"
    MAX-ACCESS read-write
    STATUS     current
    DESCRIPTION
            "The installed battery capacity. This value is the 'factory'-value,
             not the value after calibration."
    ::= { upsConfig-gen 11 }

upsConfigBatteryChargeCurrent-gen OBJECT-TYPE
    SYNTAX     NonNegativeInteger32
    UNITS      "0.1 Amp DC"
    MAX-ACCESS read-write
    STATUS     current
    DESCRIPTION
            "The maximum battery charge current, including external chargers."
    ::= { upsConfig-gen 12 }						

upsConfigNoLoadShutdown-gen OBJECT-TYPE
    SYNTAX     Integer32 {
        disabled(1),
        enabled(2)
    }
    MAX-ACCESS read-write
    STATUS     current
    DESCRIPTION
            "Dis- or enable 'no load' shutdown from the contact interface."
    ::= { upsConfig-gen 13 }
	
upsConfigStartDelay-gen OBJECT-TYPE
    SYNTAX     PositiveInteger32
    UNITS      "minutes"				
    MAX-ACCESS read-write
    STATUS     current
    DESCRIPTION
            "Minimum required autonomy time before the UPS may perform an
             autorestart."
    ::= { upsConfig-gen 14 }

--
-- The GetSet group generic.
--

upsEventGetNext-gen OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-gen 1 }

upsEventGetPrevious-gen OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-gen 2 }
				
upsEventSetStartingTimeStamp-gen OBJECT-TYPE
    SYNTAX     NonNegativeInteger32
    MAX-ACCESS read-write
    STATUS     current
    DESCRIPTION
            "The timestamp which is used as starting point for downloading
             events from the UPS event buffer"
    ::= { upsGetSet-gen 3 }				

upsEventRetreiveCurrentTimeStamp-gen OBJECT-TYPE
    SYNTAX     NonNegativeInteger32
    MAX-ACCESS read-only
    STATUS     current
    DESCRIPTION
            "The current timestamp is retreived from the UPS"
    ::= { upsGetSet-gen 4 }				

upsEventTableSize-gen OBJECT-TYPE
    SYNTAX     NonNegativeInteger32
    MAX-ACCESS read-only
    STATUS     current
    DESCRIPTION
            "The number of entries in the event table.
            This object indicates the number of rows in the event table."
    ::= { upsGetSet-gen 5 }

upsEventTable-gen OBJECT-TYPE
    SYNTAX     SEQUENCE OF UpsEventEntry-gen
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-gen 6 }

upsEventEntry-gen OBJECT-TYPE
    SYNTAX     UpsEventEntry-gen
    MAX-ACCESS not-accessible
    STATUS     current
    DESCRIPTION
            "An entry containing information applicable to a
            particular event."
    INDEX { upsEventLineIndex-gen }
    ::= { upsEventTable-gen 1 }

UpsEventEntry-gen ::= SEQUENCE {
    upsEventLineIndex-gen PositiveInteger32,
    upsEventCode-gen      Integer32,
    upsEventStatus-gen    NonNegativeInteger32,
    upsEventTime-gen      NonNegativeInteger32
}

upsEventLineIndex-gen OBJECT-TYPE
    SYNTAX     PositiveInteger32
    MAX-ACCESS not-accessible
    STATUS     current
    DESCRIPTION
            "The event line identifier."
    ::= { upsEventEntry-gen 1 }

upsEventCode-gen OBJECT-TYPE
    SYNTAX     NonNegativeInteger32
    MAX-ACCESS read-only
    STATUS     current
    DESCRIPTION
            "The event code in numerical format."
    ::= { upsEventEntry-gen 2 }

upsEventStatus-gen OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-gen 3 }

upsEventTime-gen OBJECT-TYPE
    SYNTAX     NonNegativeInteger32
    MAX-ACCESS read-only
    STATUS     current
    DESCRIPTION
            "The timestamp of the moment the event was generated."
    ::= { upsEventEntry-gen 4 }

upsParametersRead-gen OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-gen 7 }

upsParametersWrite-gen OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-gen 8 }

upsParametersStartAddress-gen OBJECT-TYPE
    SYNTAX     NonNegativeInteger32
    MAX-ACCESS read-write
    STATUS     current
    DESCRIPTION
            "The address which is used as starting point for downloading
             parameters from the UPS"
    ::= { upsGetSet-gen 9 }				

upsParameterTableSize-gen OBJECT-TYPE
    SYNTAX     NonNegativeInteger32
    MAX-ACCESS read-only
    STATUS     current
    DESCRIPTION
            "The number of entries in the parameter table.
            This object indicates the number of rows in the parameter table."
    ::= { upsGetSet-gen 10 }

upsParameterTable-gen OBJECT-TYPE
    SYNTAX     SEQUENCE OF UpsParameterEntry-gen
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-gen 11 }

upsParameterEntry-gen OBJECT-TYPE
    SYNTAX     UpsParameterEntry-gen
    MAX-ACCESS not-accessible
    STATUS     current
    DESCRIPTION
            "An entry containing information applicable to a
            particular parameter."
    INDEX { upsParameterLineIndex-gen }
    ::= { upsParameterTable-gen 1 }

UpsParameterEntry-gen ::= SEQUENCE {
    upsParameterLineIndex-gen PositiveInteger32,
    upsParameterValue-gen     Integer32   
}

upsParameterLineIndex-gen OBJECT-TYPE
    SYNTAX     PositiveInteger32
    MAX-ACCESS not-accessible
    STATUS     current
    DESCRIPTION
            "The parameter line identifier."
    ::= { upsParameterEntry-gen 1 }

upsParameterValue-gen OBJECT-TYPE
    SYNTAX     Integer32
    MAX-ACCESS read-write
    STATUS     current
    DESCRIPTION
            "The parameter value in numerical format."
    ::= { upsParameterEntry-gen 2 }

upsStatus-gen OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-gen 12 }

upsMainsStatisticsMBfail-gen OBJECT-TYPE
    SYNTAX     NonNegativeInteger32
    MAX-ACCESS read-only
    STATUS     current
    DESCRIPTION
            "Count of main bypass failures (>200 ms), since UPS installation."
    ::= { upsGetSet-gen 13 }

upsMainsStatisticsMRfail-gen OBJECT-TYPE
    SYNTAX     NonNegativeInteger32
    MAX-ACCESS read-only
    STATUS     current
    DESCRIPTION
            "Count of mains rectifier failures (>200 ms), since UPS installation."
    ::= { upsGetSet-gen 14 }
		
upsMainsStatisticsB2-gen OBJECT-TYPE
    SYNTAX     NonNegativeInteger32
    MAX-ACCESS read-only
    STATUS     current
    DESCRIPTION
            "Count of transients on the mains bypass (0..2 ms), during the last 7 days."
    ::= { upsGetSet-gen 15 }

upsMainsStatisticsB5-gen OBJECT-TYPE
    SYNTAX     NonNegativeInteger32
    MAX-ACCESS read-only
    STATUS     current
    DESCRIPTION
            "Count of transients on the mains bypass (2..5 ms), during the last 7 days."
    ::= { upsGetSet-gen 16 }

upsMainsStatisticsB10-gen OBJECT-TYPE
    SYNTAX     NonNegativeInteger32
    MAX-ACCESS read-only
    STATUS     current
    DESCRIPTION
            "Count of transients on the mains bypass (5..10 ms), during the last 7 days."
    ::= { upsGetSet-gen 17 }

upsMainsStatisticsB200-gen OBJECT-TYPE
    SYNTAX     NonNegativeInteger32
    MAX-ACCESS read-only
    STATUS     current
    DESCRIPTION
            "Count of transients on the mains bypass (10..200 ms), during the last 7 days."
    ::= { upsGetSet-gen 18 }

upsMainsStatisticsBypRel-gen OBJECT-TYPE
    SYNTAX     NonNegativeInteger32
    MAX-ACCESS read-only
    STATUS     current
    DESCRIPTION
            "Bypass reliability degree [0..100%;255]. The value NOSUCHNAME means 'not available'."
    ::= { upsGetSet-gen 19 }

upsTime-gen OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-genERROR, 
             meaning 'command not supported'. It is possible to know which is the timestamp 
             format supported by the UPS, by issuing a read-command or by reading events, 
             which includes timestamps."
    ::= { upsGetSet-gen 20 }

upsRequestPermission-gen OBJECT-TYPE
    SYNTAX     DisplayString (SIZE(0..63))
    MAX-ACCESS write-only
    STATUS     current
    DESCRIPTION
            "An encrypted code is send to enable use of restricted write objects during
             a limited period of time."
    ::= { upsGetSet-gen 21 }
    
upsEventGetCode-gen OBJECT-TYPE
    SYNTAX     Integer32
    MAX-ACCESS write-only
    STATUS     current
    DESCRIPTION
            "The code which is used as starting point to downloading the events from the 
            UPS event buffer."
    ::= { upsGetSet-gen 22 }    
    
upsEventSpinLock-gen OBJECT-TYPE
    SYNTAX     TestAndIncr
    MAX-ACCESS read-write
    STATUS     current
    DESCRIPTION
            "A spin lock on the event subsystem. "

    ::= { upsGetSet-gen 23 }
    
upsParameterSpinLock-gen OBJECT-TYPE
    SYNTAX     TestAndIncr
    MAX-ACCESS read-write
    STATUS     current
    DESCRIPTION
            "A spin lock on the parameters subsystem. "

    ::= { upsGetSet-gen 24 }


--
-- GE Trap group generic
--

upsAlarmBatteryBad-gen TRAP-TYPE
    ENTERPRISE geUPSTraps-gen
    VARIABLES  { trapArg  }
    DESCRIPTION
            "One or more batteries have been determined to require
            replacement."
    ::= 1

upsAlarmOnBattery-gen TRAP-TYPE
    ENTERPRISE geUPSTraps-gen
    VARIABLES  { trapArg , upsSecondsOnBattery-gen  }
    DESCRIPTION
            "An On Battery condition is restored."
    ::= 2

upsAlarmLowBattery-gen TRAP-TYPE
    ENTERPRISE geUPSTraps-gen
    VARIABLES  { trapArg  }
    DESCRIPTION
            "The remaining battery run-time is less than or equal
            to upsConfigLowBattTime."
    ::= 3

upsAlarmDepletedBattery-gen TRAP-TYPE
    ENTERPRISE geUPSTraps-gen
    VARIABLES  { trapArg  }
    DESCRIPTION
            "The UPS will be unable to sustain the present load
            when and if the utility power is lost)"
    ::= 4

upsAlarmTempBad-gen TRAP-TYPE
    ENTERPRISE geUPSTraps-gen
    VARIABLES  { trapArg , upsBatteryTemperature }
    DESCRIPTION
            "A temperature is out of tolerance."
    ::= 5

upsAlarmInputBad-gen TRAP-TYPE
    ENTERPRISE geUPSTraps-gen
    VARIABLES  { trapArg  }
    DESCRIPTION
            "An input condition is out of tolerance."
    ::= 6

upsAlarmOutputBad-gen TRAP-TYPE
    ENTERPRISE geUPSTraps-gen
    VARIABLES  { trapArg  }
    DESCRIPTION
            "An output condition (other than OutputOverload) is
            out of tolerance."
    ::= 7

upsAlarmOutputOverload-gen TRAP-TYPE
    ENTERPRISE geUPSTraps-gen
    VARIABLES  { trapArg , upsOutputPercentLoad-gen }
    DESCRIPTION
            "The output load exceeds the UPS output capacity."
    ::= 8

upsAlarmOnBypass-gen TRAP-TYPE
    ENTERPRISE geUPSTraps-gen
    VARIABLES  { trapArg  }
    DESCRIPTION
            "The Bypass is presently engaged on the UPS."
    ::= 9

upsAlarmBypassBad-gen TRAP-TYPE
    ENTERPRISE geUPSTraps-gen
    VARIABLES  { trapArg  }
    DESCRIPTION
            "The Bypass is out of tolerance."
    ::= 10

upsAlarmOutputOffAsRequested-gen TRAP-TYPE
    ENTERPRISE geUPSTraps-gen
    VARIABLES  { trapArg  }
    DESCRIPTION
            "The UPS has shutdown as requested, i.e., the output
            is off."
    ::= 11

upsAlarmUpsOffAsRequested-gen TRAP-TYPE
    ENTERPRISE geUPSTraps-gen-gen
    VARIABLES  { trapArg  }
    DESCRIPTION
            "The entire UPS has shutdown as commanded."
    ::= 12

upsAlarmChargerFailed-gen TRAP-TYPE
    ENTERPRISE geUPSTraps-gen
    VARIABLES  { trapArg  }
    DESCRIPTION
            "An uncorrected problem has been detected within the
            UPS charger subsystem."
    ::= 13

upsAlarmUpsOutputOff-gen TRAP-TYPE
    ENTERPRISE geUPSTraps-gen
    VARIABLES  { trapArg  }
    DESCRIPTION
            "The output of the UPS is in the off state."
    ::= 14

upsAlarmUpsSystemOff-gen TRAP-TYPE
    ENTERPRISE geUPSTraps-gen
    VARIABLES  { trapArg  }
    DESCRIPTION
            "The UPS system is in the off state."
    ::= 15

upsAlarmFanFailure-gen TRAP-TYPE
    ENTERPRISE geUPSTraps-gen
    VARIABLES  { trapArg  }
    DESCRIPTION
            "The failure of one or more fans in the UPS has been
            detected."
    ::= 16

upsAlarmFuseFailure-gen TRAP-TYPE
    ENTERPRISE geUPSTraps-gen
    VARIABLES  { trapArg  }
    DESCRIPTION
            "The failure of one or more fuses has been detected."
    ::= 17

upsAlarmGeneralFault-gen TRAP-TYPE
    ENTERPRISE geUPSTraps-gen
    VARIABLES  { trapArg  }
    DESCRIPTION
            "A general fault in the UPS has been detected."
    ::= 18

upsAlarmDiagnosticTestFailed-gen TRAP-TYPE
    ENTERPRISE geUPSTraps-gen
    VARIABLES  { trapArg  }
    DESCRIPTION
            "The result of the last diagnostic test indicates a
            failure."
    ::= 19

upsAlarmCommunicationsLost-gen TRAP-TYPE
    ENTERPRISE geUPSTraps-gen
    VARIABLES  { trapArg  }
    DESCRIPTION
            "A problem has been encountered in the communication
            between the agent and the UPS."
    ::= 20
    
upsAlarmAwaitingPower-gen TRAP-TYPE
    ENTERPRISE geUPSTraps-gen
    VARIABLES  { trapArg  }
    DESCRIPTION
            "The UPS output is off and the UPS is awaiting the
            return of the input power (*)."
    ::= 21    

upsAlarmShutdownPending-gen TRAP-TYPE
    ENTERPRISE geUPSTraps-gen
    VARIABLES  { trapArg , upsShutdownAfterDelay-gen }
    DESCRIPTION
            "A upsShutdownAfterDelay countdown is underway."
    ::= 22

upsAlarmShutdownImminent-gen TRAP-TYPE
    ENTERPRISE geUPSTraps-gen
    VARIABLES  { trapArg  }
    DESCRIPTION
            "The UPS will turn off power to the load in less than
            5 seconds; this may be either a timed shutdown or a
            low battery shutdown."
    ::= 23

upsAlarmTestInProgress-gen TRAP-TYPE
    ENTERPRISE geUPSTraps-gen
    VARIABLES  { trapArg , upsTestId-gen }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-gen TRAP-TYPE
    ENTERPRISE geUPSTraps-gen
    VARIABLES  { trapArg  }
    DESCRIPTION
            "A receptacle has been switched off."
    ::= 25

upsAlarmBatteryBadRestored-gen TRAP-TYPE
    ENTERPRISE geUPSTraps-gen
    VARIABLES  { trapArg  }
    DESCRIPTION
            "A Battery bad condition is restored."
    ::= 33

upsAlarmOnBatteryRestored-gen TRAP-TYPE
    ENTERPRISE geUPSTraps-gen
    VARIABLES  { trapArg  }
    DESCRIPTION
            "The UPS is drawing power from mains again."
    ::= 34

upsAlarmLowBatteryRestored-gen TRAP-TYPE
    ENTERPRISE geUPSTraps-gen
    VARIABLES  { trapArg  }
    DESCRIPTION
            "A Low Battery condition is restored."
    ::= 35

upsAlarmDepletedBatteryRestored-gen TRAP-TYPE
    ENTERPRISE geUPSTraps-gen
    VARIABLES  { trapArg  }
    DESCRIPTION
            "A Depleted Battery condition is restored."
    ::= 36

upsAlarmTempBadRestored-gen TRAP-TYPE
    ENTERPRISE geUPSTraps-gen
    VARIABLES  { trapArg  }
    DESCRIPTION
            "A bad temperature condition is restored."
    ::= 37

upsAlarmInputBadRestored-gen TRAP-TYPE
    ENTERPRISE geUPSTraps-gen
    VARIABLES  { trapArg  }
    DESCRIPTION
            "An input bad condition is restored."
    ::= 38

upsAlarmOutputBadRestored-gen TRAP-TYPE
    ENTERPRISE geUPSTraps-gen
    VARIABLES  { trapArg  }
    DESCRIPTION
            "An output bad condition is restored."
    ::= 39

upsAlarmOutputOverloadRestored-gen TRAP-TYPE
    ENTERPRISE geUPSTraps-gen
    VARIABLES  { trapArg  }
    DESCRIPTION
            "An output overload condition is restored."
    ::= 40

upsAlarmOnBypassRestored-gen TRAP-TYPE
    ENTERPRISE geUPSTraps-gen
    VARIABLES  { trapArg  }
    DESCRIPTION
            "An On Bypass condition is restored."
    ::= 41

upsAlarmBypassBadRestored-gen TRAP-TYPE
    ENTERPRISE geUPSTraps-gen
    VARIABLES  { trapArg  }
    DESCRIPTION
            "A Bypass bad condition is restored."
    ::= 42

upsAlarmOutputOffAsRequestedRestored-gen TRAP-TYPE
    ENTERPRISE geUPSTraps-gen
    VARIABLES  { trapArg  }
    DESCRIPTION
            "A request shutdown has been restored."
    ::= 43

upsAlarmUpsOffAsRequestedRestored-gen TRAP-TYPE
    ENTERPRISE geUPSTraps-gen-gen
    VARIABLES  { trapArg  }
    DESCRIPTION
            "A entire UPS command has been restored."
    ::= 44

upsAlarmChargerFailedRestored-gen TRAP-TYPE
    ENTERPRISE geUPSTraps-gen
    VARIABLES  { trapArg  }
    DESCRIPTION
            "A Charger Failer condition is restored."
    ::= 45

upsAlarmUpsOutputOn-gen TRAP-TYPE
    ENTERPRISE geUPSTraps-gen
    VARIABLES  { trapArg  }
    DESCRIPTION
            "The output of the UPS switched in the on state."
    ::= 46

upsAlarmUpsSystemOn-gen TRAP-TYPE
    ENTERPRISE geUPSTraps-gen
    VARIABLES  { trapArg  }
    DESCRIPTION
            "The UPS system is switched in the on state."
    ::= 47

upsAlarmFanFailureRestored-gen TRAP-TYPE
    ENTERPRISE geUPSTraps-gen
    VARIABLES  { trapArg  }
    DESCRIPTION
            "A Fan failure condition is restored."
    ::= 48

upsAlarmFuseFailureRestored-gen TRAP-TYPE
    ENTERPRISE geUPSTraps-gen
    VARIABLES  { trapArg  }
    DESCRIPTION
            "A Fuse failure condition is restored."
    ::= 49

upsAlarmGeneralFaultRestored-gen TRAP-TYPE
    ENTERPRISE geUPSTraps-gen
    VARIABLES  { trapArg  }
    DESCRIPTION
            "A general fault is restored."
    ::= 50

upsAlarmDiagnosticTestFailedRestored-gen TRAP-TYPE
    ENTERPRISE geUPSTraps-gen
    VARIABLES  { trapArg  }
    DESCRIPTION
            "A last diagnostic test indicates a failure is 
            restored."
    ::= 51

upsAlarmCommunicationsLostRestored-gen TRAP-TYPE
    ENTERPRISE geUPSTraps-gen
    VARIABLES  { trapArg  }
    DESCRIPTION
            "A problem in the communication between the agent 
            and the UPS is restored."
    ::= 52
    
upsAlarmAwaitingPowerRestored-gen TRAP-TYPE
    ENTERPRISE geUPSTraps-gen
    VARIABLES  { trapArg  }
    DESCRIPTION
            "A awaiting power condition is restored (*)."
    ::= 53    

upsAlarmShutdownPendingRestored-gen TRAP-TYPE
    ENTERPRISE geUPSTraps-gen
    VARIABLES  { trapArg , upsShutdownAfterDelay-gen }
    DESCRIPTION
            "A upsShutdownAfterDelay countdown is restored."
    ::= 54

upsAlarmShutdownImminentRestored-gen TRAP-TYPE
    ENTERPRISE geUPSTraps-gen
    VARIABLES  { trapArg  }
    DESCRIPTION
            "A shutdown imminent condition is restored."
    ::= 55

upsAlarmTestInProgressRestored-gen TRAP-TYPE
    ENTERPRISE geUPSTraps-gen
    VARIABLES  { trapArg , upsTestId-gen }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-gen TRAP-TYPE
    ENTERPRISE geUPSTraps-gen
    VARIABLES  { trapArg  }
    DESCRIPTION
            "A measurement value reached a value below its low-level threshold."
    ::= 129

upsAlarmValueHigh-gen TRAP-TYPE
    ENTERPRISE geUPSTraps-gen
    VARIABLES  { trapArg  }
    DESCRIPTION
            "A measurement value reached a value higher than its high-level threshold."
    ::= 130

upsAlarmValueLowRestored-gen TRAP-TYPE
    ENTERPRISE geUPSTraps-gen
    VARIABLES  { trapArg  }
    DESCRIPTION
            "A ValueLow alarm condition is restored."
    ::= 133

upsAlarmValueHighRestored-gen TRAP-TYPE
    ENTERPRISE geUPSTraps-gen
    VARIABLES  { trapArg }
    DESCRIPTION
            "A ValueHigh alarm condition is restored."
    ::= 134






--
-- First Environmental cards/boxes handing dry contact and/or analogue signals
--


--
-- Input lines group
--

ioInterfaceNumInputs-First OBJECT-TYPE
    SYNTAX     NonNegativeInteger32
    MAX-ACCESS read-only
    STATUS     current
    DESCRIPTION
            "The number of input lines utilized in this device.
            This entry indicates the number of rows in the input
            table."
    ::= { ioInterfaceInputLine-First 1 }

ioInterfaceInputTable-First OBJECT-TYPE
    SYNTAX     SEQUENCE OF IoInterfaceInputEntry-First
    MAX-ACCESS not-accessible
    STATUS     current
    DESCRIPTION
            "A list of input line table entries.  The number of
            entries is given by the value of ioInterfaceNumInputs."
    ::= { ioInterfaceInputLine-First 2 }

ioInterfaceInputEntry-First OBJECT-TYPE
    SYNTAX     IoInterfaceInputEntry-First
    MAX-ACCESS not-accessible
    STATUS     current
    DESCRIPTION
            "An entry containing information applicable to a
            particular input line."
    INDEX { ioInterfaceInputLineIndex-First }
    ::= { ioInterfaceInputTable-First 1 }

IoInterfaceInputEntry-First ::= SEQUENCE {
    ioInterfaceInputLineIndex-First    PositiveInteger32,
    ioInterfaceInputDescription-First  DisplayString,
    ioInterfaceInputStatus-First       Integer32,
    ioInterfaceEdgeMode-First	       Integer32,
    ioInterfaceAlarmMask-First         Integer32
}

ioInterfaceInputLineIndex-First OBJECT-TYPE
    SYNTAX     PositiveInteger32
    MAX-ACCESS not-accessible
    STATUS     current
    DESCRIPTION
            "The input line identifier."
    ::= { ioInterfaceInputEntry-First 1 }

ioInterfaceInputDescription-First OBJECT-TYPE
    SYNTAX     DisplayString (SIZE(0..63))
    MAX-ACCESS read-write
    STATUS     current
    DESCRIPTION
            "A description of the alarm monitored by this input line."
    ::= { ioInterfaceInputEntry-First 2 }

ioInterfaceInputStatus-First OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-First 3 }

ioInterfaceEdgeMode-First OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-First 4 }

 ioInterfaceAlarmMask-First OBJECT-TYPE
    SYNTAX     Integer32 {
        inactive(0),
        active(1) 
    }
    MAX-ACCESS read-write
    STATUS     current
    DESCRIPTION
            "Alarm functionality for the input line can be set active or
             inactive."
    ::= { ioInterfaceInputEntry-First 5 }

 ioInterfaceAlarmDelay-First OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputLine-First 3 }

--
-- Output lines group
--

ioInterfaceNumOutput-First OBJECT-TYPE
    SYNTAX     NonNegativeInteger32
    MAX-ACCESS read-only
    STATUS     current
    DESCRIPTION
            "The number of output lines utilized by this device.
            This entry indicates the number of rows in the output
            line table."
    ::= { ioInterfaceOutputLine-First 1 }

ioInterfaceOutputTable-First OBJECT-TYPE
    SYNTAX     SEQUENCE OF IoInterfaceOutputEntry-First
    MAX-ACCESS not-accessible
    STATUS     current
    DESCRIPTION
            "A list of output line table entries.  The number of
            entries is given by the value of ioInterfaceNumOutputs."
    ::= { ioInterfaceOutputLine-First 2 }

ioInterfaceOutputEntry-First OBJECT-TYPE
    SYNTAX     IoInterfaceOutputEntry-First
    MAX-ACCESS not-accessible
    STATUS     current
    DESCRIPTION
            "An entry containing information applicable to a
            particular output line."
    INDEX { ioInterfaceOutputLineIndex-First }
    ::= { ioInterfaceOutputTable-First 1 }

IoInterfaceOutputEntry-First ::= SEQUENCE {
    ioInterfaceOutputLineIndex-First    PositiveInteger32,
    ioInterfaceOutputDescription-First  DisplayString,
    ioInterfaceOutputStatus-First       Integer32
}

ioInterfaceOutputLineIndex-First OBJECT-TYPE
    SYNTAX     PositiveInteger32
    MAX-ACCESS not-accessible
    STATUS     current
    DESCRIPTION
            "The output line identifier."
    ::= { ioInterfaceOutputEntry-First 1 }

ioInterfaceOutputDescription-First OBJECT-TYPE
    SYNTAX     DisplayString (SIZE(0..63))
    MAX-ACCESS read-write
    STATUS     current
    DESCRIPTION
            "A description of the alarm monitored by this output line."
    ::= { ioInterfaceOutputEntry-First 2 }

ioInterfaceOutputStatus-First OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-First 3 }

--
-- Analogue lines group
--

ioInterfaceNumAnalogue-First OBJECT-TYPE
    SYNTAX     NonNegativeInteger32
    MAX-ACCESS read-only
    STATUS     current
    DESCRIPTION
            "The number of analogue lines utilized by this device.
            This entry indicates the number of rows in the analogue
            line table."
    ::= { ioInterfaceAnalogueLine-First 1 }

ioInterfaceAnalogueTable-First OBJECT-TYPE
    SYNTAX     SEQUENCE OF IoInterfaceAnalogueEntry-First
    MAX-ACCESS not-accessible
    STATUS     current
    DESCRIPTION
            "A list of analogue line table entries.  The number of
            entries is given by the value of ioInterfaceNumAnalogue."
    ::= { ioInterfaceAnalogueLine-First 2 }

ioInterfaceAnalogueEntry-First OBJECT-TYPE
    SYNTAX     IoInterfaceAnalogueEntry-First
    MAX-ACCESS not-accessible
    STATUS     current
    DESCRIPTION
            "An entry containing information applicable to a
            particular analogue line."
    INDEX { ioInterfaceAnalogueLineInde-First }
    ::= { ioInterfaceAnalogueTable-First 1 }

IoInterfaceAnalogueEntry-First::= SEQUENCE {
    ioInterfaceAnalogueLineIndex-First     PositiveInteger32,
    ioInterfaceAnalogueDescription-First   DisplayString,
    ioInterfaceAnalogueStatus-First        Integer32,
    ioInterfaceAnalogueLowThreshold-First  Integer32,
    ioInterfaceAnalogueHighThreshold-First Integer32,
    ioInterfaceAnalogueResetLowThreshold-First Integer32,
    ioInterfaceAnalogueResetHighThreshold-First Integer32
}

ioInterfaceAnalogueLineIndex-First OBJECT-TYPE
    SYNTAX     PositiveInteger32
    MAX-ACCESS not-accessible
    STATUS     current
    DESCRIPTION
            "The analogue line identifier."
    ::= { ioInterfaceAnalogueEntry-First 1 }

ioInterfaceAnalogueDescription-First OBJECT-TYPE
    SYNTAX     DisplayString (SIZE(0..63))
    MAX-ACCESS read-write
    STATUS     current
    DESCRIPTION
            "A description of the alarm monitored by this analogue line."
    ::= { ioInterfaceAnalogueEntry-First 2 }

ioInterfaceAnalogueStatus-First OBJECT-TYPE
    SYNTAX     Integer32
    MAX-ACCESS read-only
    STATUS     current
    DESCRIPTION
            "Read analogue value 1, when the board support such functionality"
    ::= { ioInterfaceAnalogueEntry-First 3 }

 ioInterfaceAnalogueLowThreshold-First OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-First 4 }

 ioInterfaceAnalogueHighThreshold-First OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-First 5 }
    
    
 ioInterfaceAnalogueResetLowThreshold-First OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-First 6 }

 ioInterfaceAnalogueResetHighThreshold-First OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-First 7 }

--
-- ioInterface trap group
--

ioAlarmGenericChange-First TRAP-TYPE
    ENTERPRISE ioInterfaceTraps-First
    VARIABLES  { trapArg  }
    DESCRIPTION
            "An generic change of a digital input/digital output/analog input has become active."
    ::= 1

--
-- Second Environmental cards/boxes handing dry contact and/or analogue signals
--


--
-- Input lines group
--

ioInterfaceNumInputs-Second OBJECT-TYPE
    SYNTAX     NonNegativeInteger32
    MAX-ACCESS read-only
    STATUS     current
    DESCRIPTION
            "The number of input lines utilized in this device.
            This entry indicates the number of rows in the input
            table."
    ::= { ioInterfaceInputLine-Second 1 }

ioInterfaceInputTable-Second OBJECT-TYPE
    SYNTAX     SEQUENCE OF IoInterfaceInputEntry-Second
    MAX-ACCESS not-accessible
    STATUS     current
    DESCRIPTION
            "A list of input line table entries.  The number of
            entries is given by the value of ioInterfaceNumInputs."
    ::= { ioInterfaceInputLine-Second 2 }

ioInterfaceInputEntry-Second OBJECT-TYPE
    SYNTAX     IoInterfaceInputEntry-Second
    MAX-ACCESS not-accessible
    STATUS     current
    DESCRIPTION
            "An entry containing information applicable to a
            particular input line."
    INDEX { ioInterfaceInputLineIndex-Second }
    ::= { ioInterfaceInputTable-Second 1 }

IoInterfaceInputEntry-Second ::= SEQUENCE {
    ioInterfaceInputLineIndex-Second    PositiveInteger32,
    ioInterfaceInputDescription-Second  DisplayString,
    ioInterfaceInputStatus-Second       Integer32,
    ioInterfaceEdgeMode-Second          Integer32,
    ioInterfaceAlarmMask-Second         Integer32,
    ioInterfaceAlarmDelay-Second        NonNegativeInteger32
}

ioInterfaceInputLineIndex-Second OBJECT-TYPE
    SYNTAX     PositiveInteger32
    MAX-ACCESS not-accessible
    STATUS     current
    DESCRIPTION
            "The input line identifier."
    ::= { ioInterfaceInputEntry-Second 1 }

ioInterfaceInputDescription-Second OBJECT-TYPE
    SYNTAX     DisplayString (SIZE(0..63))
    MAX-ACCESS read-write
    STATUS     current
    DESCRIPTION
            "A description of the alarm monitored by this input line."
    ::= { ioInterfaceInputEntry-Second 2 }

ioInterfaceInputStatus-Second OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Second 3 }

ioInterfaceEdgeMode-Second OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Second 4 }

 ioInterfaceAlarmMask-Second OBJECT-TYPE
    SYNTAX     Integer32 {
        inactive(0),
        active(1) 
    }
    MAX-ACCESS read-write
    STATUS     current
    DESCRIPTION
            "Alarm functionality for the input line can be set active or
             inactive."
    ::= { ioInterfaceInputEntry-Second 5 }

 ioInterfaceAlarmDelay-Second OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Second 6 }

--
-- Output lines group
--

ioInterfaceNumOutput-Second OBJECT-TYPE
    SYNTAX     NonNegativeInteger32
    MAX-ACCESS read-only
    STATUS     current
    DESCRIPTION
            "The number of output lines utilized by this device.
            This entry indicates the number of rows in the output
            line table."
    ::= { ioInterfaceOutputLine-Second 1 }

ioInterfaceOutputTable-Second OBJECT-TYPE
    SYNTAX     SEQUENCE OF IoInterfaceOutputEntry-Second
    MAX-ACCESS not-accessible
    STATUS     current
    DESCRIPTION
            "A list of output line table entries.  The number of
            entries is given by the value of ioInterfaceNumOutputs."
    ::= { ioInterfaceOutputLine-Second 2 }

ioInterfaceOutputEntry-Second OBJECT-TYPE
    SYNTAX     IoInterfaceOutputEntry-Second
    MAX-ACCESS not-accessible
    STATUS     current
    DESCRIPTION
            "An entry containing information applicable to a
            particular output line."
    INDEX { ioInterfaceOutputLineIndex-Second }
    ::= { ioInterfaceOutputTable-Second 1 }

IoInterfaceOutputEntry-Second ::= SEQUENCE {
    ioInterfaceOutputLineIndex-Second    PositiveInteger32,
    ioInterfaceOutputDescription-Second  DisplayString,
    ioInterfaceOutputStatus-Second       Integer32
}

ioInterfaceOutputLineIndex-Second OBJECT-TYPE
    SYNTAX     PositiveInteger32
    MAX-ACCESS not-accessible
    STATUS     current
    DESCRIPTION
            "The output line identifier."
    ::= { ioInterfaceOutputEntry-Second 1 }

ioInterfaceOutputDescription-Second OBJECT-TYPE
    SYNTAX     DisplayString (SIZE(0..63))
    MAX-ACCESS read-write
    STATUS     current
    DESCRIPTION
            "A description of the alarm monitored by this output line."
    ::= { ioInterfaceOutputEntry-Second 2 }

ioInterfaceOutputStatus-Second OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Second 3 }

--
-- Analogue lines group
--

ioInterfaceNumAnalogue-Second OBJECT-TYPE
    SYNTAX     NonNegativeInteger32
    MAX-ACCESS read-only
    STATUS     current
    DESCRIPTION
            "The number of analogue lines utilized by this device.
            This entry indicates the number of rows in the analogue
            line table."
    ::= { ioInterfaceAnalogueLine-Second 1 }

ioInterfaceAnalogueTable-Second OBJECT-TYPE
    SYNTAX     SEQUENCE OF IoInterfaceAnalogueEntry-Second
    MAX-ACCESS not-accessible
    STATUS     current
    DESCRIPTION
            "A list of analogue line table entries.  The number of
            entries is given by the value of ioInterfaceNumAnalogue."
    ::= { ioInterfaceAnalogueLine-Second 2 }

ioInterfaceAnalogueEntry-Second OBJECT-TYPE
    SYNTAX     IoInterfaceAnalogueEntry-Second
    MAX-ACCESS not-accessible
    STATUS     current
    DESCRIPTION
            "An entry containing information applicable to a
            particular analogue line."
    INDEX { ioInterfaceAnalogueLineInde-Second }
    ::= { ioInterfaceAnalogueTable-Second 1 }

IoInterfaceAnalogueEntry-Second::= SEQUENCE {
    ioInterfaceAnalogueLineIndex-Second     PositiveInteger32,
    ioInterfaceAnalogueDescription-Second   DisplayString,
    ioInterfaceAnalogueStatus-Second        Integer32,
    ioInterfaceAnalogueLowThreshold-Second  Integer32,
    ioInterfaceAnalogueHighThreshold-Second Integer32,
    ioInterfaceAnalogueResetLowThreshold-Second Integer32,
    ioInterfaceAnalogueResetHighThreshold-Second Integer32
}

ioInterfaceAnalogueLineIndex-Second OBJECT-TYPE
    SYNTAX     PositiveInteger32
    MAX-ACCESS not-accessible
    STATUS     current
    DESCRIPTION
            "The analogue line identifier."
    ::= { ioInterfaceAnalogueEntry-Second 1 }

ioInterfaceAnalogueDescription-Second OBJECT-TYPE
    SYNTAX     DisplayString (SIZE(0..63))
    MAX-ACCESS read-write
    STATUS     current
    DESCRIPTION
            "A description of the alarm monitored by this analogue line."
    ::= { ioInterfaceAnalogueEntry-Second 2 }

ioInterfaceAnalogueStatus-Second OBJECT-TYPE
    SYNTAX     Integer32
    MAX-ACCESS read-only
    STATUS     current
    DESCRIPTION
            "Read analogue value 1, when the board support such functionality"
    ::= { ioInterfaceAnalogueEntry-Second 3 }

 ioInterfaceAnalogueLowThreshold-Second OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Second 4 }

 ioInterfaceAnalogueHighThreshold-Second OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Second 5 }
    
 ioInterfaceAnalogueResetLowThreshold-Second OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Second 6 }

 ioInterfaceAnalogueResetHighThreshold-Second OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Second 7 }

--
-- ioInterface trap group
--

ioAlarmGenericChange-Second TRAP-TYPE
    ENTERPRISE ioInterfaceTraps-Second
    VARIABLES  { trapArg  }
    DESCRIPTION
            "An generic change of a digital input/digital output/analog input has become active."
    ::= 1

--
-- Third Environmental cards/boxes handing dry contact and/or analogue signals
--


--
-- Input lines group
--

ioInterfaceNumInputs-Third OBJECT-TYPE
    SYNTAX     NonNegativeInteger32
    MAX-ACCESS read-only
    STATUS     current
    DESCRIPTION
            "The number of input lines utilized in this device.
            This entry indicates the number of rows in the input
            table."
    ::= { ioInterfaceInputLine-Third 1 }

ioInterfaceInputTable-Third OBJECT-TYPE
    SYNTAX     SEQUENCE OF IoInterfaceInputEntry-Third
    MAX-ACCESS not-accessible
    STATUS     current
    DESCRIPTION
            "A list of input line table entries.  The number of
            entries is given by the value of ioInterfaceNumInputs."
    ::= { ioInterfaceInputLine-Third 2 }

ioInterfaceInputEntry-Third OBJECT-TYPE
    SYNTAX     IoInterfaceInputEntry-Third
    MAX-ACCESS not-accessible
    STATUS     current
    DESCRIPTION
            "An entry containing information applicable to a
            particular input line."
    INDEX { ioInterfaceInputLineIndex-Third }
    ::= { ioInterfaceInputTable-Third 1 }

IoInterfaceInputEntry-Third ::= SEQUENCE {
    ioInterfaceInputLineIndex-Third    PositiveInteger32,
    ioInterfaceInputDescription-Third  DisplayString,
    ioInterfaceInputStatus-Third       Integer32,
    ioInterfaceEdgeMode-Third          Integer32,
    ioInterfaceAlarmMask-Third         Integer32,
    ioInterfaceAlarmDelay-Third        NonNegativeInteger32
}

ioInterfaceInputLineIndex-Third OBJECT-TYPE
    SYNTAX     PositiveInteger32
    MAX-ACCESS not-accessible
    STATUS     current
    DESCRIPTION
            "The input line identifier."
    ::= { ioInterfaceInputEntry-Third 1 }

ioInterfaceInputDescription-Third OBJECT-TYPE
    SYNTAX     DisplayString (SIZE(0..63))
    MAX-ACCESS read-write
    STATUS     current
    DESCRIPTION
            "A description of the alarm monitored by this input line."
    ::= { ioInterfaceInputEntry-Third 2 }

ioInterfaceInputStatus-Third OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Third 3 }

ioInterfaceEdgeMode-Third OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Third 4 }

 ioInterfaceAlarmMask-Third OBJECT-TYPE
    SYNTAX     Integer32 {
        inactive(0),
        active(1) 
    }
    MAX-ACCESS read-write
    STATUS     current
    DESCRIPTION
            "Alarm functionality for the input line can be set active or
             inactive."
    ::= { ioInterfaceInputEntry-Third 5 }

 ioInterfaceAlarmDelay-Third OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Third 6 }

--
-- Output lines group
--

ioInterfaceNumOutput-Third OBJECT-TYPE
    SYNTAX     NonNegativeInteger32
    MAX-ACCESS read-only
    STATUS     current
    DESCRIPTION
            "The number of output lines utilized by this device.
            This entry indicates the number of rows in the output
            line table."
    ::= { ioInterfaceOutputLine-Third 1 }

ioInterfaceOutputTable-Third OBJECT-TYPE
    SYNTAX     SEQUENCE OF IoInterfaceOutputEntry-Third
    MAX-ACCESS not-accessible
    STATUS     current
    DESCRIPTION
            "A list of output line table entries.  The number of
            entries is given by the value of ioInterfaceNumOutputs."
    ::= { ioInterfaceOutputLine-Third 2 }

ioInterfaceOutputEntry-Third OBJECT-TYPE
    SYNTAX     IoInterfaceOutputEntry-Third
    MAX-ACCESS not-accessible
    STATUS     current
    DESCRIPTION
            "An entry containing information applicable to a
            particular output line."
    INDEX { ioInterfaceOutputLineIndex-Third }
    ::= { ioInterfaceOutputTable-Third 1 }

IoInterfaceOutputEntry-Third ::= SEQUENCE {
    ioInterfaceOutputLineIndex-Third    PositiveInteger32,
    ioInterfaceOutputDescription-Third  DisplayString,
    ioInterfaceOutputStatus-Third       Integer32
}

ioInterfaceOutputLineIndex-Third OBJECT-TYPE
    SYNTAX     PositiveInteger32
    MAX-ACCESS not-accessible
    STATUS     current
    DESCRIPTION
            "The output line identifier."
    ::= { ioInterfaceOutputEntry-Third 1 }

ioInterfaceOutputDescription-Third OBJECT-TYPE
    SYNTAX     DisplayString (SIZE(0..63))
    MAX-ACCESS read-write
    STATUS     current
    DESCRIPTION
            "A description of the alarm monitored by this output line."
    ::= { ioInterfaceOutputEntry-Third 2 }

ioInterfaceOutputStatus-Third OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Third 3 }

--
-- Analogue lines group
--

ioInterfaceNumAnalogue-Third OBJECT-TYPE
    SYNTAX     NonNegativeInteger32
    MAX-ACCESS read-only
    STATUS     current
    DESCRIPTION
            "The number of analogue lines utilized by this device.
            This entry indicates the number of rows in the analogue
            line table."
    ::= { ioInterfaceAnalogueLine-Third 1 }

ioInterfaceAnalogueTable-Third OBJECT-TYPE
    SYNTAX     SEQUENCE OF IoInterfaceAnalogueEntry-Third
    MAX-ACCESS not-accessible
    STATUS     current
    DESCRIPTION
            "A list of analogue line table entries.  The number of
            entries is given by the value of ioInterfaceNumAnalogue."
    ::= { ioInterfaceAnalogueLine-Third 2 }

ioInterfaceAnalogueEntry-Third OBJECT-TYPE
    SYNTAX     IoInterfaceAnalogueEntry-Third
    MAX-ACCESS not-accessible
    STATUS     current
    DESCRIPTION
            "An entry containing information applicable to a
            particular analogue line."
    INDEX { ioInterfaceAnalogueLineInde-Third }
    ::= { ioInterfaceAnalogueTable-Third 1 }

IoInterfaceAnalogueEntry-Third::= SEQUENCE {
    ioInterfaceAnalogueLineIndex-Third     PositiveInteger32,
    ioInterfaceAnalogueDescription-Third   DisplayString,
    ioInterfaceAnalogueStatus-Third        Integer32,
    ioInterfaceAnalogueLowThreshold-Third  Integer32,
    ioInterfaceAnalogueHighThreshold-Third Integer32,
    ioInterfaceAnalogueResetLowThreshold-Third Integer32,
    ioInterfaceAnalogueResetHighThreshold-Third Integer32
}

ioInterfaceAnalogueLineIndex-Third OBJECT-TYPE
    SYNTAX     PositiveInteger32
    MAX-ACCESS not-accessible
    STATUS     current
    DESCRIPTION
            "The analogue line identifier."
    ::= { ioInterfaceAnalogueEntry-Third 1 }

ioInterfaceAnalogueDescription-Third OBJECT-TYPE
    SYNTAX     DisplayString (SIZE(0..63))
    MAX-ACCESS read-write
    STATUS     current
    DESCRIPTION
            "A description of the alarm monitored by this analogue line."
    ::= { ioInterfaceAnalogueEntry-Third 2 }

ioInterfaceAnalogueStatus-Third OBJECT-TYPE
    SYNTAX     Integer32
    MAX-ACCESS read-only
    STATUS     current
    DESCRIPTION
            "Read analogue value 1, when the board support such functionality"
    ::= { ioInterfaceAnalogueEntry-Third 3 }

 ioInterfaceAnalogueLowThreshold-Third OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Third 4 }

 ioInterfaceAnalogueHighThreshold-Third OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Third 5 }
 
 ioInterfaceAnalogueResetLowThreshold-Third OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Third 6 }

 ioInterfaceAnalogueResetHighThreshold-Third OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Third 7 }
--
-- ioInterface trap group
--

ioAlarmGenericChange-Third TRAP-TYPE
    ENTERPRISE ioInterfaceTraps-Third
    VARIABLES  { trapArg  }
    DESCRIPTION
            "An generic change of a digital input/digital output/analog input has become active."
    ::= 1
    
--
-- Fourth Environmental cards/boxes handing dry contact and/or analogue signals
--


--
-- Input lines group
--

ioInterfaceNumInputs-Fourth OBJECT-TYPE
    SYNTAX     NonNegativeInteger32
    MAX-ACCESS read-only
    STATUS     current
    DESCRIPTION
            "The number of input lines utilized in this device.
            This entry indicates the number of rows in the input
            table."
    ::= { ioInterfaceInputLine-Fourth 1 }

ioInterfaceInputTable-Fourth OBJECT-TYPE
    SYNTAX     SEQUENCE OF IoInterfaceInputEntry-Fourth
    MAX-ACCESS not-accessible
    STATUS     current
    DESCRIPTION
            "A list of input line table entries.  The number of
            entries is given by the value of ioInterfaceNumInputs."
    ::= { ioInterfaceInputLine-Fourth 2 }

ioInterfaceInputEntry-Fourth OBJECT-TYPE
    SYNTAX     IoInterfaceInputEntry-Fourth
    MAX-ACCESS not-accessible
    STATUS     current
    DESCRIPTION
            "An entry containing information applicable to a
            particular input line."
    INDEX { ioInterfaceInputLineIndex-Fourth }
    ::= { ioInterfaceInputTable-Fourth 1 }

IoInterfaceInputEntry-Fourth ::= SEQUENCE {
    ioInterfaceInputLineIndex-Fourth    PositiveInteger32,
    ioInterfaceInputDescription-Fourth  DisplayString,
    ioInterfaceInputStatus-Fourth       Integer32,
    ioInterfaceEdgeMode-Fourth          Integer32,
    ioInterfaceAlarmMask-Fourth         Integer32,
    ioInterfaceAlarmDelay-Fourth        NonNegativeInteger32
}

ioInterfaceInputLineIndex-Fourth OBJECT-TYPE
    SYNTAX     PositiveInteger32
    MAX-ACCESS not-accessible
    STATUS     current
    DESCRIPTION
            "The input line identifier."
    ::= { ioInterfaceInputEntry-Fourth 1 }

ioInterfaceInputDescription-Fourth OBJECT-TYPE
    SYNTAX     DisplayString (SIZE(0..63))
    MAX-ACCESS read-write
    STATUS     current
    DESCRIPTION
            "A description of the alarm monitored by this input line."
    ::= { ioInterfaceInputEntry-Fourth 2 }

ioInterfaceInputStatus-Fourth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Fourth 3 }

ioInterfaceEdgeMode-Fourth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Fourth 4 }

 ioInterfaceAlarmMask-Fourth OBJECT-TYPE
    SYNTAX     Integer32 {
        inactive(0),
        active(1) 
    }
    MAX-ACCESS read-write
    STATUS     current
    DESCRIPTION
            "Alarm functionality for the input line can be set active or
             inactive."
    ::= { ioInterfaceInputEntry-Fourth 5 }

 ioInterfaceAlarmDelay-Fourth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Fourth 6 }

--
-- Output lines group
--

ioInterfaceNumOutput-Fourth OBJECT-TYPE
    SYNTAX     NonNegativeInteger32
    MAX-ACCESS read-only
    STATUS     current
    DESCRIPTION
            "The number of output lines utilized by this device.
            This entry indicates the number of rows in the output
            line table."
    ::= { ioInterfaceOutputLine-Fourth 1 }

ioInterfaceOutputTable-Fourth OBJECT-TYPE
    SYNTAX     SEQUENCE OF IoInterfaceOutputEntry-Fourth
    MAX-ACCESS not-accessible
    STATUS     current
    DESCRIPTION
            "A list of output line table entries.  The number of
            entries is given by the value of ioInterfaceNumOutputs."
    ::= { ioInterfaceOutputLine-Fourth 2 }

ioInterfaceOutputEntry-Fourth OBJECT-TYPE
    SYNTAX     IoInterfaceOutputEntry-Fourth
    MAX-ACCESS not-accessible
    STATUS     current
    DESCRIPTION
            "An entry containing information applicable to a
            particular output line."
    INDEX { ioInterfaceOutputLineIndex-Fourth }
    ::= { ioInterfaceOutputTable-Fourth 1 }

IoInterfaceOutputEntry-Fourth ::= SEQUENCE {
    ioInterfaceOutputLineIndex-Fourth    PositiveInteger32,
    ioInterfaceOutputDescription-Fourth  DisplayString,
    ioInterfaceOutputStatus-Fourth       Integer32
}

ioInterfaceOutputLineIndex-Fourth OBJECT-TYPE
    SYNTAX     PositiveInteger32
    MAX-ACCESS not-accessible
    STATUS     current
    DESCRIPTION
            "The output line identifier."
    ::= { ioInterfaceOutputEntry-Fourth 1 }

ioInterfaceOutputDescription-Fourth OBJECT-TYPE
    SYNTAX     DisplayString (SIZE(0..63))
    MAX-ACCESS read-write
    STATUS     current
    DESCRIPTION
            "A description of the alarm monitored by this output line."
    ::= { ioInterfaceOutputEntry-Fourth 2 }

ioInterfaceOutputStatus-Fourth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Fourth 3 }

--
-- Analogue lines group
--

ioInterfaceNumAnalogue-Fourth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Fourth 1 }

ioInterfaceAnalogueTable-Fourth OBJECT-TYPE
    SYNTAX     SEQUENCE OF IoInterfaceAnalogueEntry-Fourth
    MAX-ACCESS not-accessible
    STATUS     current
    DESCRIPTION
            "A list of analogue line table entries.  The number of
            entries is given by the value of ioInterfaceNumAnalogue."
    ::= { ioInterfaceAnalogueLine-Fourth 2 }

ioInterfaceAnalogueEntry-Fourth OBJECT-TYPE
    SYNTAX     IoInterfaceAnalogueEntry-Fourth
    MAX-ACCESS not-accessible
    STATUS     current
    DESCRIPTION
            "An entry containing information applicable to a
            particular analogue line."
    INDEX { ioInterfaceAnalogueLineInde-Fourth }
    ::= { ioInterfaceAnalogueTable-Fourth 1 }

IoInterfaceAnalogueEntry-Fourth::= SEQUENCE {
    ioInterfaceAnalogueLineIndex-Fourth     PositiveInteger32,
    ioInterfaceAnalogueDescription-Fourth   DisplayString,
    ioInterfaceAnalogueStatus-Fourth        Integer32,
    ioInterfaceAnalogueLowThreshold-Fourth  Integer32,
    ioInterfaceAnalogueHighThreshold-Fourth Integer32,
    ioInterfaceAnalogueResetLowThreshold-Fourth Integer32,
    ioInterfaceAnalogueResetHighThreshold-Fourth Integer32
}

ioInterfaceAnalogueLineIndex-Fourth OBJECT-TYPE
    SYNTAX     PositiveInteger32
    MAX-ACCESS not-accessible
    STATUS     current
    DESCRIPTION
            "The analogue line identifier."
    ::= { ioInterfaceAnalogueEntry-Fourth 1 }

ioInterfaceAnalogueDescription-Fourth OBJECT-TYPE
    SYNTAX     DisplayString (SIZE(0..63))
    MAX-ACCESS read-write
    STATUS     current
    DESCRIPTION
            "A description of the alarm monitored by this analogue line."
    ::= { ioInterfaceAnalogueEntry-Fourth 2 }

ioInterfaceAnalogueStatus-Fourth OBJECT-TYPE
    SYNTAX     Integer32
    MAX-ACCESS read-only
    STATUS     current
    DESCRIPTION
            "Read analogue value 1, when the board support such functionality"
    ::= { ioInterfaceAnalogueEntry-Fourth 3 }

 ioInterfaceAnalogueLowThreshold-Fourth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Fourth 4 }

 ioInterfaceAnalogueHighThreshold-Fourth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Fourth 5 }
    
 ioInterfaceAnalogueResetLowThreshold-Fourth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Fourth 6 }

 ioInterfaceAnalogueResetHighThreshold-Fourth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Fourth 7 }

--
-- ioInterface trap group
--

ioAlarmGenericChange-Fourth TRAP-TYPE
    ENTERPRISE ioInterfaceTraps-Fourth
    VARIABLES  { trapArg  }
    DESCRIPTION
            "An generic change of a digital input/digital output/analog input has become active."
    ::= 1

--
-- Fifth Environmental cards/boxes handing dry contact and/or analogue signals
--


--
-- Input lines group
--

ioInterfaceNumInputs-Fifth OBJECT-TYPE
    SYNTAX     NonNegativeInteger32
    MAX-ACCESS read-only
    STATUS     current
    DESCRIPTION
            "The number of input lines utilized in this device.
            This entry indicates the number of rows in the input
            table."
    ::= { ioInterfaceInputLine-Fifth 1 }

ioInterfaceInputTable-Fifth OBJECT-TYPE
    SYNTAX     SEQUENCE OF IoInterfaceInputEntry-Fifth
    MAX-ACCESS not-accessible
    STATUS     current
    DESCRIPTION
            "A list of input line table entries.  The number of
            entries is given by the value of ioInterfaceNumInputs."
    ::= { ioInterfaceInputLine-Fifth 2 }

ioInterfaceInputEntry-Fifth OBJECT-TYPE
    SYNTAX     IoInterfaceInputEntry-Fifth
    MAX-ACCESS not-accessible
    STATUS     current
    DESCRIPTION
            "An entry containing information applicable to a
            particular input line."
    INDEX { ioInterfaceInputLineIndex-Fifth }
    ::= { ioInterfaceInputTable-Fifth 1 }

IoInterfaceInputEntry-Fifth ::= SEQUENCE {
    ioInterfaceInputLineIndex-Fifth    PositiveInteger32,
    ioInterfaceInputDescription-Fifth  DisplayString,
    ioInterfaceInputStatus-Fifth       Integer32,
    ioInterfaceEdgeMode-Fifth          Integer32,
    ioInterfaceAlarmMask-Fifth         Integer32,
    ioInterfaceAlarmDelay-Fifth        NonNegativeInteger32
}

ioInterfaceInputLineIndex-Fifth OBJECT-TYPE
    SYNTAX     PositiveInteger32
    MAX-ACCESS not-accessible
    STATUS     current
    DESCRIPTION
            "The input line identifier."
    ::= { ioInterfaceInputEntry-Fifth 1 }

ioInterfaceInputDescription-Fifth OBJECT-TYPE
    SYNTAX     DisplayString (SIZE(0..63))
    MAX-ACCESS read-write
    STATUS     current
    DESCRIPTION
            "A description of the alarm monitored by this input line."
    ::= { ioInterfaceInputEntry-Fifth 2 }

ioInterfaceInputStatus-Fifth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Fifth 3 }

ioInterfaceEdgeMode-Fifth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Fifth 4 }

 ioInterfaceAlarmMask-Fifth OBJECT-TYPE
    SYNTAX     Integer32 {
        inactive(0),
        active(1) 
    }
    MAX-ACCESS read-write
    STATUS     current
    DESCRIPTION
            "Alarm functionality for the input line can be set active or
             inactive."
    ::= { ioInterfaceInputEntry-Fifth 5 }

 ioInterfaceAlarmDelay-Fifth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Fifth 6 }

--
-- Output lines group
--

ioInterfaceNumOutput-Fifth OBJECT-TYPE
    SYNTAX     NonNegativeInteger32
    MAX-ACCESS read-only
    STATUS     current
    DESCRIPTION
            "The number of output lines utilized by this device.
            This entry indicates the number of rows in the output
            line table."
    ::= { ioInterfaceOutputLine-Fifth 1 }

ioInterfaceOutputTable-Fifth OBJECT-TYPE
    SYNTAX     SEQUENCE OF IoInterfaceOutputEntry-Fifth
    MAX-ACCESS not-accessible
    STATUS     current
    DESCRIPTION
            "A list of output line table entries.  The number of
            entries is given by the value of ioInterfaceNumOutputs."
    ::= { ioInterfaceOutputLine-Fifth 2 }

ioInterfaceOutputEntry-Fifth OBJECT-TYPE
    SYNTAX     IoInterfaceOutputEntry-Fifth
    MAX-ACCESS not-accessible
    STATUS     current
    DESCRIPTION
            "An entry containing information applicable to a
            particular output line."
    INDEX { ioInterfaceOutputLineIndex-Fifth }
    ::= { ioInterfaceOutputTable-Fifth 1 }

IoInterfaceOutputEntry-Fifth ::= SEQUENCE {
    ioInterfaceOutputLineIndex-Fifth    PositiveInteger32,
    ioInterfaceOutputDescription-Fifth  DisplayString,
    ioInterfaceOutputStatus-Fifth       Integer32
}

ioInterfaceOutputLineIndex-Fifth OBJECT-TYPE
    SYNTAX     PositiveInteger32
    MAX-ACCESS not-accessible
    STATUS     current
    DESCRIPTION
            "The output line identifier."
    ::= { ioInterfaceOutputEntry-Fifth 1 }

ioInterfaceOutputDescription-Fifth OBJECT-TYPE
    SYNTAX     DisplayString (SIZE(0..63))
    MAX-ACCESS read-write
    STATUS     current
    DESCRIPTION
            "A description of the alarm monitored by this output line."
    ::= { ioInterfaceOutputEntry-Fifth 2 }

ioInterfaceOutputStatus-Fifth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Fifth 3 }

--
-- Analogue lines group
--

ioInterfaceNumAnalogue-Fifth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Fifth 1 }

ioInterfaceAnalogueTable-Fifth OBJECT-TYPE
    SYNTAX     SEQUENCE OF IoInterfaceAnalogueEntry-Fifth
    MAX-ACCESS not-accessible
    STATUS     current
    DESCRIPTION
            "A list of analogue line table entries.  The number of
            entries is given by the value of ioInterfaceNumAnalogue."
    ::= { ioInterfaceAnalogueLine-Fifth 2 }

ioInterfaceAnalogueEntry-Fifth OBJECT-TYPE
    SYNTAX     IoInterfaceAnalogueEntry-Fifth
    MAX-ACCESS not-accessible
    STATUS     current
    DESCRIPTION
            "An entry containing information applicable to a
            particular analogue line."
    INDEX { ioInterfaceAnalogueLineInde-Fifth }
    ::= { ioInterfaceAnalogueTable-Fifth 1 }

IoInterfaceAnalogueEntry-Fifth::= SEQUENCE {
    ioInterfaceAnalogueLineIndex-Fifth     PositiveInteger32,
    ioInterfaceAnalogueDescription-Fifth   DisplayString,
    ioInterfaceAnalogueStatus-Fifth        Integer32,
    ioInterfaceAnalogueLowThreshold-Fifth  Integer32,
    ioInterfaceAnalogueHighThreshold-Fifth Integer32,
    ioInterfaceAnalogueResetLowThreshold-Fifth Integer32,
    ioInterfaceAnalogueResetHighThreshold-Fifth Integer32
}

ioInterfaceAnalogueLineIndex-Fifth OBJECT-TYPE
    SYNTAX     PositiveInteger32
    MAX-ACCESS not-accessible
    STATUS     current
    DESCRIPTION
            "The analogue line identifier."
    ::= { ioInterfaceAnalogueEntry-Fifth 1 }

ioInterfaceAnalogueDescription-Fifth OBJECT-TYPE
    SYNTAX     DisplayString (SIZE(0..63))
    MAX-ACCESS read-write
    STATUS     current
    DESCRIPTION
            "A description of the alarm monitored by this analogue line."
    ::= { ioInterfaceAnalogueEntry-Fifth 2 }

ioInterfaceAnalogueStatus-Fifth OBJECT-TYPE
    SYNTAX     Integer32
    MAX-ACCESS read-only
    STATUS     current
    DESCRIPTION
            "Read analogue value 1, when the board support such functionality"
    ::= { ioInterfaceAnalogueEntry-Fifth 3 }

 ioInterfaceAnalogueLowThreshold-Fifth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Fifth 4 }

 ioInterfaceAnalogueHighThreshold-Fifth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Fifth 5 }
    
 ioInterfaceAnalogueResetLowThreshold-Fifth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Fifth 6 }

 ioInterfaceAnalogueResetHighThreshold-Fifth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Fifth 7 }

--
-- ioInterface trap group
--

ioAlarmGenericChange-Fifth TRAP-TYPE
    ENTERPRISE ioInterfaceTraps-Fifth
    VARIABLES  { trapArg  }
    DESCRIPTION
            "An generic change of a digital input/digital output/analog input has become active."
    ::= 1
--
-- Sixth Environmental cards/boxes handing dry contact and/or analogue signals
--


--
-- Input lines group
--

ioInterfaceNumInputs-Sixth OBJECT-TYPE
    SYNTAX     NonNegativeInteger32
    MAX-ACCESS read-only
    STATUS     current
    DESCRIPTION
            "The number of input lines utilized in this device.
            This entry indicates the number of rows in the input
            table."
    ::= { ioInterfaceInputLine-Sixth 1 }

ioInterfaceInputTable-Sixth OBJECT-TYPE
    SYNTAX     SEQUENCE OF IoInterfaceInputEntry-Sixth
    MAX-ACCESS not-accessible
    STATUS     current
    DESCRIPTION
            "A list of input line table entries.  The number of
            entries is given by the value of ioInterfaceNumInputs."
    ::= { ioInterfaceInputLine-Sixth 2 }

ioInterfaceInputEntry-Sixth OBJECT-TYPE
    SYNTAX     IoInterfaceInputEntry-Sixth
    MAX-ACCESS not-accessible
    STATUS     current
    DESCRIPTION
            "An entry containing information applicable to a
            particular input line."
    INDEX { ioInterfaceInputLineIndex-Sixth }
    ::= { ioInterfaceInputTable-Sixth 1 }

IoInterfaceInputEntry-Sixth ::= SEQUENCE {
    ioInterfaceInputLineIndex-Sixth    PositiveInteger32,
    ioInterfaceInputDescription-Sixth  DisplayString,
    ioInterfaceInputStatus-Sixth       Integer32,
    ioInterfaceEdgeMode-Sixth          Integer32,
    ioInterfaceAlarmMask-Sixth         Integer32,
    ioInterfaceAlarmDelay-Sixth        NonNegativeInteger32
}

ioInterfaceInputLineIndex-Sixth OBJECT-TYPE
    SYNTAX     PositiveInteger32
    MAX-ACCESS not-accessible
    STATUS     current
    DESCRIPTION
            "The input line identifier."
    ::= { ioInterfaceInputEntry-Sixth 1 }

ioInterfaceInputDescription-Sixth OBJECT-TYPE
    SYNTAX     DisplayString (SIZE(0..63))
    MAX-ACCESS read-write
    STATUS     current
    DESCRIPTION
            "A description of the alarm monitored by this input line."
    ::= { ioInterfaceInputEntry-Sixth 2 }

ioInterfaceInputStatus-Sixth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Sixth 3 }

ioInterfaceEdgeMode-Sixth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Sixth 4 }

 ioInterfaceAlarmMask-Sixth OBJECT-TYPE
    SYNTAX     Integer32 {
        inactive(0),
        active(1) 
    }
    MAX-ACCESS read-write
    STATUS     current
    DESCRIPTION
            "Alarm functionality for the input line can be set active or
             inactive."
    ::= { ioInterfaceInputEntry-Sixth 5 }

 ioInterfaceAlarmDelay-Sixth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Sixth 6 }

--
-- Output lines group
--

ioInterfaceNumOutput-Sixth OBJECT-TYPE
    SYNTAX     NonNegativeInteger32
    MAX-ACCESS read-only
    STATUS     current
    DESCRIPTION
            "The number of output lines utilized by this device.
            This entry indicates the number of rows in the output
            line table."
    ::= { ioInterfaceOutputLine-Sixth 1 }

ioInterfaceOutputTable-Sixth OBJECT-TYPE
    SYNTAX     SEQUENCE OF IoInterfaceOutputEntry-Sixth
    MAX-ACCESS not-accessible
    STATUS     current
    DESCRIPTION
            "A list of output line table entries.  The number of
            entries is given by the value of ioInterfaceNumOutputs."
    ::= { ioInterfaceOutputLine-Sixth 2 }

ioInterfaceOutputEntry-Sixth OBJECT-TYPE
    SYNTAX     IoInterfaceOutputEntry-Sixth
    MAX-ACCESS not-accessible
    STATUS     current
    DESCRIPTION
            "An entry containing information applicable to a
            particular output line."
    INDEX { ioInterfaceOutputLineIndex-Sixth }
    ::= { ioInterfaceOutputTable-Sixth 1 }

IoInterfaceOutputEntry-Sixth ::= SEQUENCE {
    ioInterfaceOutputLineIndex-Sixth    PositiveInteger32,
    ioInterfaceOutputDescription-Sixth  DisplayString,
    ioInterfaceOutputStatus-Sixth       Integer32
}

ioInterfaceOutputLineIndex-Sixth OBJECT-TYPE
    SYNTAX     PositiveInteger32
    MAX-ACCESS not-accessible
    STATUS     current
    DESCRIPTION
            "The output line identifier."
    ::= { ioInterfaceOutputEntry-Sixth 1 }

ioInterfaceOutputDescription-Sixth OBJECT-TYPE
    SYNTAX     DisplayString (SIZE(0..63))
    MAX-ACCESS read-write
    STATUS     current
    DESCRIPTION
            "A description of the alarm monitored by this output line."
    ::= { ioInterfaceOutputEntry-Sixth 2 }

ioInterfaceOutputStatus-Sixth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Sixth 3 }

--
-- Analogue lines group
--

ioInterfaceNumAnalogue-Sixth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Sixth 1 }

ioInterfaceAnalogueTable-Sixth OBJECT-TYPE
    SYNTAX     SEQUENCE OF IoInterfaceAnalogueEntry-Sixth
    MAX-ACCESS not-accessible
    STATUS     current
    DESCRIPTION
            "A list of analogue line table entries.  The number of
            entries is given by the value of ioInterfaceNumAnalogue."
    ::= { ioInterfaceAnalogueLine-Sixth 2 }

ioInterfaceAnalogueEntry-Sixth OBJECT-TYPE
    SYNTAX     IoInterfaceAnalogueEntry-Sixth
    MAX-ACCESS not-accessible
    STATUS     current
    DESCRIPTION
            "An entry containing information applicable to a
            particular analogue line."
    INDEX { ioInterfaceAnalogueLineInde-Sixth }
    ::= { ioInterfaceAnalogueTable-Sixth 1 }

IoInterfaceAnalogueEntry-Sixth::= SEQUENCE {
    ioInterfaceAnalogueLineIndex-Sixth     PositiveInteger32,
    ioInterfaceAnalogueDescription-Sixth   DisplayString,
    ioInterfaceAnalogueStatus-Sixth        Integer32,
    ioInterfaceAnalogueLowThreshold-Sixth  Integer32,
    ioInterfaceAnalogueHighThreshold-Sixth Integer32,
    ioInterfaceAnalogueResetLowThreshold-Sixth Integer32,
    ioInterfaceAnalogueResetHighThreshold-Sixth Integer32
}

ioInterfaceAnalogueLineIndex-Sixth OBJECT-TYPE
    SYNTAX     PositiveInteger32
    MAX-ACCESS not-accessible
    STATUS     current
    DESCRIPTION
            "The analogue line identifier."
    ::= { ioInterfaceAnalogueEntry-Sixth 1 }

ioInterfaceAnalogueDescription-Sixth OBJECT-TYPE
    SYNTAX     DisplayString (SIZE(0..63))
    MAX-ACCESS read-write
    STATUS     current
    DESCRIPTION
            "A description of the alarm monitored by this analogue line."
    ::= { ioInterfaceAnalogueEntry-Sixth 2 }

ioInterfaceAnalogueStatus-Sixth OBJECT-TYPE
    SYNTAX     Integer32
    MAX-ACCESS read-only
    STATUS     current
    DESCRIPTION
            "Read analogue value 1, when the board support such functionality"
    ::= { ioInterfaceAnalogueEntry-Sixth 3 }

 ioInterfaceAnalogueLowThreshold-Sixth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Sixth 4 }

 ioInterfaceAnalogueHighThreshold-Sixth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Sixth 5 }
    
 ioInterfaceAnalogueResetLowThreshold-Sixth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Sixth 6 }

 ioInterfaceAnalogueResetHighThreshold-Sixth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Sixth 7 }

--
-- ioInterface trap group
--

ioAlarmGenericChange-Sixth TRAP-TYPE
    ENTERPRISE ioInterfaceTraps-Sixth
    VARIABLES  { trapArg  }
    DESCRIPTION
            "An generic change of a digital input/digital output/analog input has become active."
    ::= 1
--
-- Seventh Environmental cards/boxes handing dry contact and/or analogue signals
--


--
-- Input lines group
--

ioInterfaceNumInputs-Seventh OBJECT-TYPE
    SYNTAX     NonNegativeInteger32
    MAX-ACCESS read-only
    STATUS     current
    DESCRIPTION
            "The number of input lines utilized in this device.
            This entry indicates the number of rows in the input
            table."
    ::= { ioInterfaceInputLine-Seventh 1 }

ioInterfaceInputTable-Seventh OBJECT-TYPE
    SYNTAX     SEQUENCE OF IoInterfaceInputEntry-Seventh
    MAX-ACCESS not-accessible
    STATUS     current
    DESCRIPTION
            "A list of input line table entries.  The number of
            entries is given by the value of ioInterfaceNumInputs."
    ::= { ioInterfaceInputLine-Seventh 2 }

ioInterfaceInputEntry-Seventh OBJECT-TYPE
    SYNTAX     IoInterfaceInputEntry-Seventh
    MAX-ACCESS not-accessible
    STATUS     current
    DESCRIPTION
            "An entry containing information applicable to a
            particular input line."
    INDEX { ioInterfaceInputLineIndex-Seventh }
    ::= { ioInterfaceInputTable-Seventh 1 }

IoInterfaceInputEntry-Seventh ::= SEQUENCE {
    ioInterfaceInputLineIndex-Seventh    PositiveInteger32,
    ioInterfaceInputDescription-Seventh  DisplayString,
    ioInterfaceInputStatus-Seventh       Integer32,
    ioInterfaceEdgeMode-Seventh          Integer32,
    ioInterfaceAlarmMask-Seventh         Integer32,
    ioInterfaceAlarmDelay-Seventh        NonNegativeInteger32
}

ioInterfaceInputLineIndex-Seventh OBJECT-TYPE
    SYNTAX     PositiveInteger32
    MAX-ACCESS not-accessible
    STATUS     current
    DESCRIPTION
            "The input line identifier."
    ::= { ioInterfaceInputEntry-Seventh 1 }

ioInterfaceInputDescription-Seventh OBJECT-TYPE
    SYNTAX     DisplayString (SIZE(0..63))
    MAX-ACCESS read-write
    STATUS     current
    DESCRIPTION
            "A description of the alarm monitored by this input line."
    ::= { ioInterfaceInputEntry-Seventh 2 }

ioInterfaceInputStatus-Seventh OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Seventh 3 }

ioInterfaceEdgeMode-Seventh OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Seventh 4 }

 ioInterfaceAlarmMask-Seventh OBJECT-TYPE
    SYNTAX     Integer32 {
        inactive(0),
        active(1) 
    }
    MAX-ACCESS read-write
    STATUS     current
    DESCRIPTION
            "Alarm functionality for the input line can be set active or
             inactive."
    ::= { ioInterfaceInputEntry-Seventh 5 }

 ioInterfaceAlarmDelay-Seventh OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Seventh 6 }

--
-- Output lines group
--

ioInterfaceNumOutput-Seventh OBJECT-TYPE
    SYNTAX     NonNegativeInteger32
    MAX-ACCESS read-only
    STATUS     current
    DESCRIPTION
            "The number of output lines utilized by this device.
            This entry indicates the number of rows in the output
            line table."
    ::= { ioInterfaceOutputLine-Seventh 1 }

ioInterfaceOutputTable-Seventh OBJECT-TYPE
    SYNTAX     SEQUENCE OF IoInterfaceOutputEntry-Seventh
    MAX-ACCESS not-accessible
    STATUS     current
    DESCRIPTION
            "A list of output line table entries.  The number of
            entries is given by the value of ioInterfaceNumOutputs."
    ::= { ioInterfaceOutputLine-Seventh 2 }

ioInterfaceOutputEntry-Seventh OBJECT-TYPE
    SYNTAX     IoInterfaceOutputEntry-Seventh
    MAX-ACCESS not-accessible
    STATUS     current
    DESCRIPTION
            "An entry containing information applicable to a
            particular output line."
    INDEX { ioInterfaceOutputLineIndex-Seventh }
    ::= { ioInterfaceOutputTable-Seventh 1 }

IoInterfaceOutputEntry-Seventh ::= SEQUENCE {
    ioInterfaceOutputLineIndex-Seventh    PositiveInteger32,
    ioInterfaceOutputDescription-Seventh  DisplayString,
    ioInterfaceOutputStatus-Seventh       Integer32
}

ioInterfaceOutputLineIndex-Seventh OBJECT-TYPE
    SYNTAX     PositiveInteger32
    MAX-ACCESS not-accessible
    STATUS     current
    DESCRIPTION
            "The output line identifier."
    ::= { ioInterfaceOutputEntry-Seventh 1 }

ioInterfaceOutputDescription-Seventh OBJECT-TYPE
    SYNTAX     DisplayString (SIZE(0..63))
    MAX-ACCESS read-write
    STATUS     current
    DESCRIPTION
            "A description of the alarm monitored by this output line."
    ::= { ioInterfaceOutputEntry-Seventh 2 }

ioInterfaceOutputStatus-Seventh OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Seventh 3 }

--
-- Analogue lines group
--

ioInterfaceNumAnalogue-Seventh OBJECT-TYPE
    SYNTAX     NonNegativeInteger32
    MAX-ACCESS read-only
    STATUS     current
    DESCRIPTION
            "The number of analogue lines utilized by this device.
            This entry indicates the number of rows in the analogue
            line table."
    ::= { ioInterfaceAnalogueLine-Seventh 1 }

ioInterfaceAnalogueTable-Seventh OBJECT-TYPE
    SYNTAX     SEQUENCE OF IoInterfaceAnalogueEntry-Seventh
    MAX-ACCESS not-accessible
    STATUS     current
    DESCRIPTION
            "A list of analogue line table entries.  The number of
            entries is given by the value of ioInterfaceNumAnalogue."
    ::= { ioInterfaceAnalogueLine-Seventh 2 }

ioInterfaceAnalogueEntry-Seventh OBJECT-TYPE
    SYNTAX     IoInterfaceAnalogueEntry-Seventh
    MAX-ACCESS not-accessible
    STATUS     current
    DESCRIPTION
            "An entry containing information applicable to a
            particular analogue line."
    INDEX { ioInterfaceAnalogueLineInde-Seventh }
    ::= { ioInterfaceAnalogueTable-Seventh 1 }

IoInterfaceAnalogueEntry-Seventh::= SEQUENCE {
    ioInterfaceAnalogueLineIndex-Seventh     PositiveInteger32,
    ioInterfaceAnalogueDescription-Seventh   DisplayString,
    ioInterfaceAnalogueStatus-Seventh        Integer32,
    ioInterfaceAnalogueLowThreshold-Seventh  Integer32,
    ioInterfaceAnalogueHighThreshold-Seventh Integer32,
    ioInterfaceAnalogueResetLowThreshold-Seventh Integer32,
    ioInterfaceAnalogueResetHighThreshold-Seventh Integer32
}

ioInterfaceAnalogueLineIndex-Seventh OBJECT-TYPE
    SYNTAX     PositiveInteger32
    MAX-ACCESS not-accessible
    STATUS     current
    DESCRIPTION
            "The analogue line identifier."
    ::= { ioInterfaceAnalogueEntry-Seventh 1 }

ioInterfaceAnalogueDescription-Seventh OBJECT-TYPE
    SYNTAX     DisplayString (SIZE(0..63))
    MAX-ACCESS read-write
    STATUS     current
    DESCRIPTION
            "A description of the alarm monitored by this analogue line."
    ::= { ioInterfaceAnalogueEntry-Seventh 2 }

ioInterfaceAnalogueStatus-Seventh OBJECT-TYPE
    SYNTAX     Integer32
    MAX-ACCESS read-only
    STATUS     current
    DESCRIPTION
            "Read analogue value 1, when the board support such functionality"
    ::= { ioInterfaceAnalogueEntry-Seventh 3 }

 ioInterfaceAnalogueLowThreshold-Seventh OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Seventh 4 }

 ioInterfaceAnalogueHighThreshold-Seventh OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Seventh 5 }
    
 ioInterfaceAnalogueResetLowThreshold-Seventh OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Seventh 6 }

 ioInterfaceAnalogueResetHighThreshold-Seventh OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Seventh 7 }

--
-- ioInterface trap group
--

ioAlarmGenericChange-Seventh TRAP-TYPE
    ENTERPRISE ioInterfaceTraps-Seventh
    VARIABLES  { trapArg  }
    DESCRIPTION
            "An generic change of a digital input/digital output/analog input has become active."
    ::= 1
--
-- Eighth Environmental cards/boxes handing dry contact and/or analogue signals
--


--
-- Input lines group
--

ioInterfaceNumInputs-Eighth OBJECT-TYPE
    SYNTAX     NonNegativeInteger32
    MAX-ACCESS read-only
    STATUS     current
    DESCRIPTION
            "The number of input lines utilized in this device.
            This entry indicates the number of rows in the input
            table."
    ::= { ioInterfaceInputLine-Eighth 1 }

ioInterfaceInputTable-Eighth OBJECT-TYPE
    SYNTAX     SEQUENCE OF IoInterfaceInputEntry-Eighth
    MAX-ACCESS not-accessible
    STATUS     current
    DESCRIPTION
            "A list of input line table entries.  The number of
            entries is given by the value of ioInterfaceNumInputs."
    ::= { ioInterfaceInputLine-Eighth 2 }

ioInterfaceInputEntry-Eighth OBJECT-TYPE
    SYNTAX     IoInterfaceInputEntry-Eighth
    MAX-ACCESS not-accessible
    STATUS     current
    DESCRIPTION
            "An entry containing information applicable to a
            particular input line."
    INDEX { ioInterfaceInputLineIndex-Eighth }
    ::= { ioInterfaceInputTable-Eighth 1 }

IoInterfaceInputEntry-Eighth ::= SEQUENCE {
    ioInterfaceInputLineIndex-Eighth    PositiveInteger32,
    ioInterfaceInputDescription-Eighth  DisplayString,
    ioInterfaceInputStatus-Eighth       Integer32,
    ioInterfaceEdgeMode-Eighth          Integer32,
    ioInterfaceAlarmMask-Eighth         Integer32,
    ioInterfaceAlarmDelay-Eighth        NonNegativeInteger32
}

ioInterfaceInputLineIndex-Eighth OBJECT-TYPE
    SYNTAX     PositiveInteger32
    MAX-ACCESS not-accessible
    STATUS     current
    DESCRIPTION
            "The input line identifier."
    ::= { ioInterfaceInputEntry-Eighth 1 }

ioInterfaceInputDescription-Eighth OBJECT-TYPE
    SYNTAX     DisplayString (SIZE(0..63))
    MAX-ACCESS read-write
    STATUS     current
    DESCRIPTION
            "A description of the alarm monitored by this input line."
    ::= { ioInterfaceInputEntry-Eighth 2 }

ioInterfaceInputStatus-Eighth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Eighth 3 }

ioInterfaceEdgeMode-Eighth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Eighth 4 }

 ioInterfaceAlarmMask-Eighth OBJECT-TYPE
    SYNTAX     Integer32 {
        inactive(0),
        active(1) 
    }
    MAX-ACCESS read-write
    STATUS     current
    DESCRIPTION
            "Alarm functionality for the input line can be set active or
             inactive."
    ::= { ioInterfaceInputEntry-Eighth 5 }

 ioInterfaceAlarmDelay-Eighth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Eighth 6 }

--
-- Output lines group
--

ioInterfaceNumOutput-Eighth OBJECT-TYPE
    SYNTAX     NonNegativeInteger32
    MAX-ACCESS read-only
    STATUS     current
    DESCRIPTION
            "The number of output lines utilized by this device.
            This entry indicates the number of rows in the output
            line table."
    ::= { ioInterfaceOutputLine-Eighth 1 }

ioInterfaceOutputTable-Eighth OBJECT-TYPE
    SYNTAX     SEQUENCE OF IoInterfaceOutputEntry-Eighth
    MAX-ACCESS not-accessible
    STATUS     current
    DESCRIPTION
            "A list of output line table entries.  The number of
            entries is given by the value of ioInterfaceNumOutputs."
    ::= { ioInterfaceOutputLine-Eighth 2 }

ioInterfaceOutputEntry-Eighth OBJECT-TYPE
    SYNTAX     IoInterfaceOutputEntry-Eighth
    MAX-ACCESS not-accessible
    STATUS     current
    DESCRIPTION
            "An entry containing information applicable to a
            particular output line."
    INDEX { ioInterfaceOutputLineIndex-Eighth }
    ::= { ioInterfaceOutputTable-Eighth 1 }

IoInterfaceOutputEntry-Eighth ::= SEQUENCE {
    ioInterfaceOutputLineIndex-Eighth    PositiveInteger32,
    ioInterfaceOutputDescription-Eighth  DisplayString,
    ioInterfaceOutputStatus-Eighth       Integer32
}

ioInterfaceOutputLineIndex-Eighth OBJECT-TYPE
    SYNTAX     PositiveInteger32
    MAX-ACCESS not-accessible
    STATUS     current
    DESCRIPTION
            "The output line identifier."
    ::= { ioInterfaceOutputEntry-Eighth 1 }

ioInterfaceOutputDescription-Eighth OBJECT-TYPE
    SYNTAX     DisplayString (SIZE(0..63))
    MAX-ACCESS read-write
    STATUS     current
    DESCRIPTION
            "A description of the alarm monitored by this output line."
    ::= { ioInterfaceOutputEntry-Eighth 2 }

ioInterfaceOutputStatus-Eighth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Eighth 3 }

--
-- Analogue lines group
--

ioInterfaceNumAnalogue-Eighth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Eighth 1 }

ioInterfaceAnalogueTable-Eighth OBJECT-TYPE
    SYNTAX     SEQUENCE OF IoInterfaceAnalogueEntry-Eighth
    MAX-ACCESS not-accessible
    STATUS     current
    DESCRIPTION
            "A list of analogue line table entries.  The number of
            entries is given by the value of ioInterfaceNumAnalogue."
    ::= { ioInterfaceAnalogueLine-Eighth 2 }

ioInterfaceAnalogueEntry-Eighth OBJECT-TYPE
    SYNTAX     IoInterfaceAnalogueEntry-Eighth
    MAX-ACCESS not-accessible
    STATUS     current
    DESCRIPTION
            "An entry containing information applicable to a
            particular analogue line."
    INDEX { ioInterfaceAnalogueLineInde-Eighth }
    ::= { ioInterfaceAnalogueTable-Eighth 1 }

IoInterfaceAnalogueEntry-Eighth::= SEQUENCE {
    ioInterfaceAnalogueLineIndex-Eighth     PositiveInteger32,
    ioInterfaceAnalogueDescription-Eighth   DisplayString,
    ioInterfaceAnalogueStatus-Eighth        Integer32,
    ioInterfaceAnalogueLowThreshold-Eighth  Integer32,
    ioInterfaceAnalogueHighThreshold-Eighth Integer32,
    ioInterfaceAnalogueResetLowThreshold-Eighth Integer32,
    ioInterfaceAnalogueResetHighThreshold-Eighth Integer32
}

ioInterfaceAnalogueLineIndex-Eighth OBJECT-TYPE
    SYNTAX     PositiveInteger32
    MAX-ACCESS not-accessible
    STATUS     current
    DESCRIPTION
            "The analogue line identifier."
    ::= { ioInterfaceAnalogueEntry-Eighth 1 }

ioInterfaceAnalogueDescription-Eighth OBJECT-TYPE
    SYNTAX     DisplayString (SIZE(0..63))
    MAX-ACCESS read-write
    STATUS     current
    DESCRIPTION
            "A description of the alarm monitored by this analogue line."
    ::= { ioInterfaceAnalogueEntry-Eighth 2 }

ioInterfaceAnalogueStatus-Eighth OBJECT-TYPE
    SYNTAX     Integer32
    MAX-ACCESS read-only
    STATUS     current
    DESCRIPTION
            "Read analogue value 1, when the board support such functionality"
    ::= { ioInterfaceAnalogueEntry-Eighth 3 }

 ioInterfaceAnalogueLowThreshold-Eighth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Eighth 4 }

 ioInterfaceAnalogueHighThreshold-Eighth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Eighth 5 }
    
 ioInterfaceAnalogueResetLowThreshold-Eighth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Eighth 6 }

 ioInterfaceAnalogueResetHighThreshold-Eighth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Eighth 7 }

--
-- ioInterface trap group
--

ioAlarmGenericChange-Eighth TRAP-TYPE
    ENTERPRISE ioInterfaceTraps-Eighth
    VARIABLES  { trapArg  }
    DESCRIPTION
            "An generic change of a digital input/digital output/analog input has become active."
    ::= 1
 
--
-- The Modem group
--

geModemStatus OBJECT-TYPE
    SYNTAX     NonNegativeInteger32
    MAX-ACCESS read-only
    STATUS     current
    DESCRIPTION
            " The status of the modem, controlled by the addressed device.
              The status word is a collection of bits, as specified below.               The SNMP value NOSUCHNAME means 'status not (yet) available'. 
		1	modemStatOnline. There is a valid online connection. 
		2	modemStatError. The last operation has failed. The device 
			will clear this bit when a new modem command is received. 
		4	unused (should be defined = 0).
		8	unused (should be defined = 0).
		16	modemStatDialling. The dialling procedure is pending.
		32	modemStatBusy. The device is performing some operation, 
			and can not be accessed, temporarily.
		64	unused (should be defined = 0).
		128	modemStatNoModem. The modem is not connected or not responding.
		256	modemStatDCD. The DCD line status signal is on.
		512	modemStatRing. The RING line status signal is on.
		1024	modemStatCTS. The CTS line status signal is on.
		2048	modemStatDSR. The DSR line status signal is on.
		4096	unused (should be defined = 0).
		8192	unused (should be defined = 0).
		16384	unused (should be defined = 0).
		32768	unused (should be defined = 0)."
    ::= { geModem 1 }

geModemNumInitString OBJECT-TYPE
    SYNTAX     NonNegativeInteger32
    MAX-ACCESS read-only
    STATUS     current
    DESCRIPTION
            "The number of modem init strings utilized by this ups.
            This entry indicates the number of rows in the init 
            string table."
    ::= { geModem 2 }

geModemInitStringTable OBJECT-TYPE
    SYNTAX     SEQUENCE OF GeModemInitStringEntry
    MAX-ACCESS not-accessible
    STATUS     current
    DESCRIPTION
            "A list of init string table entries.  The number of
            entries is given by the value of geModemNumInitString."
    ::= { geModem 3 }

geModemInitStringEntry OBJECT-TYPE
    SYNTAX     GeModemInitStringEntry
    MAX-ACCESS not-accessible
    STATUS     current
    DESCRIPTION
            "An entry containing information applicable to a
            particular Init string."
    INDEX { geModemInitStringLineIndex }
    ::= { geModemInitStringTable 1 }

GeModemInitStringEntry ::= SEQUENCE {
    geModemInitStringLineIndex     PositiveInteger32,
    geModemInitstring              DisplayString
}

geModemInitStringLineIndex OBJECT-TYPE
    SYNTAX     PositiveInteger32
    MAX-ACCESS not-accessible
    STATUS     current
    DESCRIPTION
            "The Init string line identifier."
    ::= { geModemInitStringEntry 1 }

geModemInitstring OBJECT-TYPE
    SYNTAX     DisplayString (SIZE(0..63))
    MAX-ACCESS read-write
    STATUS     current
    DESCRIPTION
            "A modem Init string."
    ::= { geModemInitStringEntry 2 }

geModemNumPhoneNumber OBJECT-TYPE
    SYNTAX     NonNegativeInteger32
    MAX-ACCESS read-only
    STATUS     current
    DESCRIPTION
            "The number of modem phone numbers utilized by this ups.
            This entry indicates the number of rows in the table."
    ::= { geModem 4 }

geModemPhoneNumberTable OBJECT-TYPE
    SYNTAX     SEQUENCE OF GeModemPhoneNumberEntry
    MAX-ACCESS not-accessible
    STATUS     current
    DESCRIPTION
            "A list of phone number table entries.  The number of
            entries is given by the value of geModemNumPhoneNumber."
    ::= { geModem 5 }

geModemPhoneNumberEntry OBJECT-TYPE
    SYNTAX     GeModemPhoneNumberEntry
    MAX-ACCESS not-accessible
    STATUS     current
    DESCRIPTION
            "An entry containing information applicable to a
            particular phone number."
    INDEX { geModemPhoneNumberLineIndex }
    ::= { geModemPhoneNumberTable 1 }

GeModemPhoneNumberEntry ::= SEQUENCE {
    geModemPhoneNumberLineIndex     PositiveInteger32,
    geModemPhoneNumber              DisplayString
}

geModemPhoneNumberLineIndex OBJECT-TYPE
    SYNTAX     PositiveInteger32
    MAX-ACCESS not-accessible
    STATUS     current
    DESCRIPTION
            "The phone number line identifier."
    ::= { geModemPhoneNumberEntry 1 }

geModemPhoneNumber OBJECT-TYPE
    SYNTAX     DisplayString (SIZE(0..63))
    MAX-ACCESS read-write
    STATUS     current
    DESCRIPTION
            "A phone number."
    ::= { geModemPhoneNumberEntry 2 }

--
-- The [partner] group
--
--
-- ge[partner]       OBJECT IDENTIFIER ::=  { geHardware [Partner-ID] }


--
-- The ProtectionClient group
--

--
-- Environment
--

geClientProcessor OBJECT-TYPE
    SYNTAX     DisplayString (SIZE(0..63))
    MAX-ACCESS read-only
    STATUS     current
    DESCRIPTION
            "The processor used by the clients machine."
    ::= { geClient 1 }

geClientOperatingSystem OBJECT-TYPE
    SYNTAX     DisplayString (SIZE(0..63))
    MAX-ACCESS read-only
    STATUS     current
    DESCRIPTION
            "Operating system on which the client runs."
    ::= { geClient 2 }

geClientJavaRuntimeVersion OBJECT-TYPE
    SYNTAX     DisplayString (SIZE(0..63))
    MAX-ACCESS read-only
    STATUS     current
    DESCRIPTION
            "JavaRuntimeVersion of the client machine."
    ::= { geClient 3 }

--
-- Config 
--

geClientMaxSizeOfLogfiles OBJECT-TYPE
    SYNTAX     NonNegativeInteger32
    MAX-ACCESS read-write
    STATUS     current
    DESCRIPTION
            "The max. size of the logfiles in Kb."
    ::= { geClient 4 }

geClientLanguageSelection OBJECT-TYPE
    SYNTAX     DisplayString (SIZE(0..32))
    MAX-ACCESS read-only
    STATUS     current
    DESCRIPTION
            "Shows the currently activated language of the client."
    ::= { geClient 5 }

geClientInternalCommunicationPort OBJECT-TYPE
    SYNTAX     NonNegativeInteger32
    MAX-ACCESS read-write
    STATUS     current
    DESCRIPTION
            "UDP port used between server and client part."
    ::= { geClient 6 }

geClientReboot OBJECT-TYPE
    SYNTAX     Integer32 {
        reboot(1)
    }
    MAX-ACCESS write-only
    STATUS     current
    DESCRIPTION
            "setting this object causes the protection client to reboot 
             and activate new settings."
    ::= { geClient 7 }

geClientNumUPS OBJECT-TYPE
    SYNTAX     NonNegativeInteger32
    MAX-ACCESS read-only
    STATUS     current
    DESCRIPTION
            "The number of UPSs utilized by this client.
            This entry indicates the number of rows in the table."
    ::= { geClient 8 }

geClientUPSTable OBJECT-TYPE
    SYNTAX     SEQUENCE OF GeClientUPSEntry
    MAX-ACCESS not-accessible
    STATUS     current
    DESCRIPTION
            "A list of UPS table entries.  The number of
            entries is given by the value of geClientNumUPS."
    ::= { geClient 9 }

geClientUPSEntry OBJECT-TYPE
    SYNTAX     GeClientUPSEntry
    MAX-ACCESS not-accessible
    STATUS     current
    DESCRIPTION
            "An entry containing information applicable to a
            particular UPS."
    INDEX { geClientUPSLineIndex }
    ::= { geClientUPSTable 1 }

GeClientUPSEntry ::= SEQUENCE {
    geClientUPSLineIndex           PositiveInteger32,
    geClientUPSName                DisplayString,
    geClientUPSCommunicationType   Integer32,
    geClientUPSCommunicationPort   DisplayString,
    geClientUPSReadCommName        DisplayString,
    geClientUPSWriteCommName       DisplayString,
    geClientUPSCommRetries         NonNegativeInteger32,
    geClientAlarmManagement        Integer32,
    geClientPreDelay               NonNegativeInteger32,
    geClientSystemShutdown         Integer32,
    geClientRuntime                NonNegativeInteger32,
    geClientUPSShutdown            Integer32,
    geClientMaxScriptExecutionTime NonNegativeInteger32,
    geClientGraceperiod            NonNegativeInteger32
}

geClientUPSLineIndex OBJECT-TYPE
    SYNTAX     PositiveInteger32
    MAX-ACCESS not-accessible
    STATUS     current
    DESCRIPTION
            "The UPS line identifier."
    ::= { geClientUPSEntry 1 }

geClientUPSName OBJECT-TYPE
    SYNTAX     DisplayString (SIZE(0..32))
    MAX-ACCESS read-write
    STATUS     current
    DESCRIPTION
            "The administrative name of the UPS."
    ::= { geClientUPSEntry 2 }

geClientUPSCommunicationType OBJECT-TYPE
    SYNTAX     Integer32 {
        serial(0),
        snmp(1)
    }
    MAX-ACCESS read-write
    STATUS     current
    DESCRIPTION
            "The method of communication."
    ::= { geClientUPSEntry 3 }

geClientUPSCommunicationPort OBJECT-TYPE
    SYNTAX     DisplayString (SIZE(0..32))
    MAX-ACCESS read-write
    STATUS     current
    DESCRIPTION
            "The communication port."
    ::= { geClientUPSEntry 4 }

geClientUPSReadCommName OBJECT-TYPE
    SYNTAX     DisplayString (SIZE(0..32))
    MAX-ACCESS read-write
    STATUS     current
    DESCRIPTION
            "The Read community string. Used when communication
             method is SNMP."
    ::= { geClientUPSEntry 5 }

geClientUPSWriteCommName OBJECT-TYPE
    SYNTAX     DisplayString (SIZE(0..32))
    MAX-ACCESS read-write
    STATUS     current
    DESCRIPTION
            "The Write community string. Used when communication
             method is SNMP."
    ::= { geClientUPSEntry 6 }

geClientUPSCommRetries OBJECT-TYPE
    SYNTAX     NonNegativeInteger32
    MAX-ACCESS read-write
    STATUS     current
    DESCRIPTION
            "Number of retries in case an answer times out.
             When the max. number of retries is reached a
             lost communication alarm will be raised."
    ::= { geClientUPSEntry 7 }

geClientAlarmManagement OBJECT-TYPE
    SYNTAX     Integer32 {
        off(0),
        on(1)
    }
    MAX-ACCESS read-write
    STATUS     current
    DESCRIPTION
            "Alarm Management enabled or disabled."
    ::= { geClientUPSEntry 8 }

geClientPreDelay OBJECT-TYPE
    SYNTAX     NonNegativeInteger32
    MAX-ACCESS read-only
    STATUS     current
    DESCRIPTION
            "The number of second an alarm needs to be active
             before action is taken."
    ::= { geClientUPSEntry 9 }

geClientSystemShutdown OBJECT-TYPE
    SYNTAX     Integer32 {
        off(0),
        on(1)
    }
    MAX-ACCESS read-only
    STATUS     current
    DESCRIPTION
            "Specifies whether the client should shutdown the machine 
             when an alarm situation occurs."
    ::= { geClientUPSEntry 10 }

geClientRuntime OBJECT-TYPE
    SYNTAX     NonNegativeInteger32
    MAX-ACCESS read-only
    STATUS     current
    DESCRIPTION
            "The user defined preferable runtime."
    ::= { geClientUPSEntry 11 }

geClientUPSShutdown OBJECT-TYPE
    SYNTAX     Integer32 {
        off(0),
        on(1)
    }
    MAX-ACCESS read-only
    STATUS     current
    DESCRIPTION
            "Defines whether the UPS will be shut down after an 
             Operating System shutdown."
    ::= { geClientUPSEntry 12 }

geClientMaxScriptExecutionTime OBJECT-TYPE
    SYNTAX     NonNegativeInteger32
    MAX-ACCESS read-only
    STATUS     current
    DESCRIPTION
            "The max. number of seconds the script file is allowed to run."
    ::= { geClientUPSEntry 13 }
						
geClientGraceperiod OBJECT-TYPE
    SYNTAX     NonNegativeInteger32
    MAX-ACCESS read-only
    STATUS     current
    DESCRIPTION
            "The time between start of the Operating System shutdown 
             and the UPS shutdown."
    ::= { geClientUPSEntry 14 }

-- Scheduled Tests

geClientNumTests OBJECT-TYPE
    SYNTAX     NonNegativeInteger32
    MAX-ACCESS read-only
    STATUS     current
    DESCRIPTION
            "The number of scheduled tests.
            This entry indicates the number of rows in the table."
    ::= { geClient 20 }

geClientTestTable OBJECT-TYPE
    SYNTAX     SEQUENCE OF GeClientTestEntry
    MAX-ACCESS not-accessible
    STATUS     current
    DESCRIPTION
            "A list of test table entries.  The number of
            entries is given by the value of geClientNumTests."
    ::= { geClient 21 }

geClientTestEntry OBJECT-TYPE
    SYNTAX     GeClientTestEntry
    MAX-ACCESS not-accessible
    STATUS     current
    DESCRIPTION
            "An entry containing information applicable to a
            particular Test."
    INDEX { geClientTestLineIndex }
    ::= { geClientTestTable 1 }

GeClientTestEntry ::= SEQUENCE {
    geClientTestLineIndex    PositiveInteger32,
    geClientTestId           Integer32,
    geClientTestDayTime      Integer32,
    geClientTestWeekDay	Integer32,
    geClientTestMonthDay	Integer32
}

geClientTestLineIndex OBJECT-TYPE
    SYNTAX     PositiveInteger32
    MAX-ACCESS not-accessible
    STATUS     current
    DESCRIPTION
            "The test line identifier."
    ::= { geClientTestEntry 1 }

geClientTestId OBJECT-TYPE
    SYNTAX     Integer32
    MAX-ACCESS read-write
    STATUS     current
    DESCRIPTION
            "The test Id."
    ::= { geClientTestEntry 2 }
		
geClientTestDayTime OBJECT-TYPE
    SYNTAX     Integer32
    MAX-ACCESS read-write
    STATUS     current
    DESCRIPTION
            "The time on which the test is due to be performed."
    ::= { geClientTestEntry 3 }

geClientTestWeekDay OBJECT-TYPE
    SYNTAX     Integer32
    MAX-ACCESS read-write
    STATUS     current
    DESCRIPTION
            "The day in the week on which the test will be performed."
    ::= { geClientTestEntry 4 }

geClientTestMonthDay OBJECT-TYPE
    SYNTAX     Integer32
    MAX-ACCESS read-write
    STATUS     current
    DESCRIPTION
            "The month day on which the test will be performed."
    ::= { geClientTestEntry 5 }

-- ScheduledShutdown

geClientNumShutdowns OBJECT-TYPE
    SYNTAX     NonNegativeInteger32
    MAX-ACCESS read-only
    STATUS     current
    DESCRIPTION
            "The number of scheduled Shutdowns.
            This entry indicates the number of rows in the table."
    ::= { geClient 30 }

geClientShutdownTable OBJECT-TYPE
    SYNTAX     SEQUENCE OF GeClientShutdownEntry
    MAX-ACCESS not-accessible
    STATUS     current
    DESCRIPTION
            "A list of Shutdown table entries.  The number of
            entries is given by the value of geClientNumShutdowns."
    ::= { geClient 31 }

geClientShutdownEntry OBJECT-TYPE
    SYNTAX     GeClientShutdownEntry
    MAX-ACCESS not-accessible
    STATUS     current
    DESCRIPTION
            "An entry containing information applicable to a
            particular Shutdown."
    INDEX { geClientShutdownLineIndex }
    ::= { geClientShutdownTable 1 }

GeClientShutdownEntry ::= SEQUENCE {
    geClientShutdownLineIndex    PositiveInteger32,
    geClientShutdownDelay        Integer32,
    geClientShutdownDuration     Integer32,
    geClientShutdownDayTime      Integer32,
    geClientShutdownWeekDay      Integer32,
    geClientShutdownMonthDay	    Integer32,
    geClientShutdownPreWarnTime  Integer32
}

geClientShutdownLineIndex OBJECT-TYPE
    SYNTAX     PositiveInteger32
    MAX-ACCESS not-accessible
    STATUS     current
    DESCRIPTION
            "The Shutdown line identifier."
    ::= { geClientShutdownEntry 1 }

geClientShutdownDelay OBJECT-TYPE
    SYNTAX     Integer32
    MAX-ACCESS read-write
    STATUS     current
    DESCRIPTION
            "The delay before start of the Shutdown."
    ::= { geClientShutdownEntry 2 }

geClientShutdownDuration OBJECT-TYPE
    SYNTAX     Integer32
    MAX-ACCESS read-write
    STATUS     current
    DESCRIPTION
            "The duration of the Shutdown."
    ::= { geClientShutdownEntry 3 }
	
geClientShutdownDayTime OBJECT-TYPE
    SYNTAX     Integer32
    MAX-ACCESS read-write
    STATUS     current
    DESCRIPTION
            "The time on which the Shutdown is due to be performed."
    ::= { geClientShutdownEntry 4 }

geClientShutdownWeekDay OBJECT-TYPE
    SYNTAX     Integer32
    MAX-ACCESS read-write
    STATUS     current
    DESCRIPTION
            "The day in the week on which the Shutdown will be performed."
    ::= { geClientShutdownEntry 5 }

geClientShutdownMonthDay OBJECT-TYPE
    SYNTAX     Integer32
    MAX-ACCESS read-write
    STATUS     current
    DESCRIPTION
            "The month day on which the Shutdown will be performed."
    ::= { geClientShutdownEntry 6 }

geClientShutdownPreWarnTime OBJECT-TYPE
    SYNTAX     Integer32
    MAX-ACCESS read-write
    STATUS     current
    DESCRIPTION
            "The number of seconds before start of the shutdown a pre 
             warning will be raised."
    ::= { geClientShutdownEntry 7 }

--
-- The AgentConfig group
--

geAgentUDPPort OBJECT-TYPE
    SYNTAX     NonNegativeInteger32
    MAX-ACCESS read-write
    STATUS     current
    DESCRIPTION
            "The UDP port number used by agent."
    ::= { geAgentConfig 1 }

geAgentWebServerPort OBJECT-TYPE
    SYNTAX     NonNegativeInteger32
    MAX-ACCESS read-write
    STATUS     current
    DESCRIPTION
            "The UDP port number used by the HTTP server."
    ::= { geAgentConfig 2 }

geAgentComPort OBJECT-TYPE
    SYNTAX     DisplayString(SIZE(0..32))
    MAX-ACCESS read-write
    STATUS     current
    DESCRIPTION
            "The COM port used by the agent."
    ::= { geAgentConfig 3 }

geAgentComTimeout OBJECT-TYPE
    SYNTAX     NonNegativeInteger32
    MAX-ACCESS read-write
    STATUS     current
    DESCRIPTION
            "The Timeout delay in seconds of the serial communication."
    ::= { geAgentConfig 4 }

geAgentComRetries OBJECT-TYPE
    SYNTAX     NonNegativeInteger32
    MAX-ACCESS read-write
    STATUS     current
    DESCRIPTION
            "The number of retries when serial communication fails."
    ::= { geAgentConfig 5 }

geAgentReadCommunity OBJECT-TYPE
    SYNTAX     DisplayString(SIZE(0..63))
    MAX-ACCESS read-write
    STATUS     current
    DESCRIPTION
            "The read community string of the agent."
    ::= { geAgentConfig 6 }

geAgentWriteCommunity OBJECT-TYPE
    SYNTAX     DisplayString(SIZE(0..63))
    MAX-ACCESS read-write
    STATUS     current
    DESCRIPTION
            "The write community string of the agent."
    ::= { geAgentConfig 7 }

geAgentResponsibleEmailAddress OBJECT-TYPE
    SYNTAX     DisplayString(SIZE(0..63))
    MAX-ACCESS read-write
    STATUS     current
    DESCRIPTION
            "The email address of the responsible person for this agent."
    ::= { geAgentConfig 8 }

geRFCTrapsToSend OBJECT-TYPE
    SYNTAX     Integer32 {
        off(0),
        on(1)
    }
    MAX-ACCESS read-write
    STATUS     current
    DESCRIPTION
            "This object defines whether RFC traps need to be send.
             The bit value 1 indicates that the traps needs to be send, while 
             value 0 does not result in a trap to send."
    ::= { geAgentConfig 9 }

geIMVTrapsToSend OBJECT-TYPE
    SYNTAX     NonNegativeInteger32
    MAX-ACCESS read-write
    STATUS     current
    DESCRIPTION
            "This object defines for which device(s) IMV traps need to be send.
             The bit value 1 indicates that the trap needs to be send, while 
             value 0 does not result in a trap to send.
             The value presents the devices as a mask:
		   1  GenericUPS
               2  FirstUPS
               4  SecondUPS
	         8  ThirdUPS
	        16  FourthUPS
	        32  FifthUPS
              64  SixthUPS
             128  SeventhUPS
             256  EigthUPS
             512  IOInterface
            "
    ::= { geAgentConfig 10 }

--
-- The AgentTrap group
--

geAgentNumTraps OBJECT-TYPE
    SYNTAX     NonNegativeInteger32
    MAX-ACCESS read-only
    STATUS     current
    DESCRIPTION
            "The number of configured traps.
            This entry indicates the number of rows in the table."
    ::= { geAgentTraps 1 }

geAgentTrapTable OBJECT-TYPE
    SYNTAX     SEQUENCE OF GeAgentTrapEntry
    MAX-ACCESS not-accessible
    STATUS     current
    DESCRIPTION
            "A list of trap table entries.  The number of
            entries is given by the value of geAgentNumTraps."
    ::= { geAgentTraps 2 }

geAgentTrapEntry OBJECT-TYPE
    SYNTAX     GeAgentTrapEntry
    MAX-ACCESS not-accessible
    STATUS     current
    DESCRIPTION
            "An entry containing information applicable to a
            particular trap target."
    INDEX { geAgentTrapLineIndex }
    ::= { geAgentTrapTable 1 }

GeAgentTrapEntry ::= SEQUENCE {
    geAgentTrapLineIndex    PositiveInteger32,
    geAgentTrapAddress      DisplayString,
    geAgentTrapCommunity    DisplayString,
    geAgentTrapPort         Integer32
}

geAgentTrapLineIndex OBJECT-TYPE
    SYNTAX     PositiveInteger32
    MAX-ACCESS not-accessible
    STATUS     current
    DESCRIPTION
            "The Trap line identifier."
    ::= { geAgentTrapEntry 1 }

geAgentTrapAddress OBJECT-TYPE
    SYNTAX     DisplayString(SIZE(0..63))
    MAX-ACCESS read-write
    STATUS     current
    DESCRIPTION
            "The destination IP-address of the trap."
    ::= { geAgentTrapEntry 2 }

geAgentTrapCommunity OBJECT-TYPE
    SYNTAX     DisplayString(SIZE(0..63))
    MAX-ACCESS read-write
    STATUS     current
    DESCRIPTION
            "The communication string used by the trap."
    ::= { geAgentTrapEntry 3 }
	
geAgentTrapPort OBJECT-TYPE
    SYNTAX     Integer32
    MAX-ACCESS read-write
    STATUS     current
    DESCRIPTION
            "The UDP port on the receiving side."
    ::= { geAgentTrapEntry 4 }

--
-- The Device Identification group. First
--      All objects in this group except for upsIdentName and
--      upsIdentAttachedDevices are set at device initialization
--      and remain static.
--

upsIdentManufacturer-first OBJECT-TYPE
    SYNTAX     DisplayString (SIZE (0..31))
    MAX-ACCESS read-only
    STATUS     current
    DESCRIPTION
            "The name of the UPS manufacturer.(*)"
    ::= { upsIdent-first 1 }

upsIdentModel-first OBJECT-TYPE
    SYNTAX     DisplayString (SIZE (0..63))
    MAX-ACCESS read-only
    STATUS     current
    DESCRIPTION
            "The UPS Model designation.(*)"
    ::= { upsIdent-first 2 }

upsIdentUPSSoftwareVersion-first OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-first 3 }

upsIdentAgentSoftwareVersion-first OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-first 4 }

upsIdentName-first OBJECT-TYPE
    SYNTAX     DisplayString (SIZE(0..63))
    MAX-ACCESS read-write
    STATUS     current
    DESCRIPTION
            "A string identifying the UPS.  This object should be
            set by the administrator.(*)"
    ::= { upsIdent-first 5 }

upsIdentAttachedDevices-first OBJECT-TYPE
    SYNTAX     DisplayString (SIZE(0..63))
    MAX-ACCESS read-write
    STATUS     current
    DESCRIPTION
            "A string identifying the devices attached to the
            output(s) of the UPS.  This object should be set by
            the administrator.(*)"
    ::= { upsIdent-first 6 }

upsIdentUPSSerialNumber-first OBJECT-TYPE
    SYNTAX     DisplayString (SIZE(0..31))
    MAX-ACCESS read-only
    STATUS     current
    DESCRIPTION
            "The UPS serial number"
    ::= { upsIdent-first 7 }
				
upsIdentComProtVersion-first OBJECT-TYPE
    SYNTAX     DisplayString (SIZE(0..15))
    MAX-ACCESS read-only
    STATUS     current
    DESCRIPTION
            "The IMV communication protocol version"
    ::= { upsIdent-first 8 }	
		
upsIdentOperatingTime-first OBJECT-TYPE
    SYNTAX     NonNegativeInteger32
    UNITS      "seconds"
    MAX-ACCESS read-only
    STATUS     current
    DESCRIPTION
            "The present value of the operating time.
             total 'on' time since UPS manufactured"
    ::= { upsIdent-first 9 }	
				
--
-- Battery Group Generic
--

upsBatteryStatus-first OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-first 1 }

upsSecondsOnBattery-first OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-first 2 }

upsEstimatedMinutesRemaining-first OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-first 3 }

upsEstimatedChargeRemaining-first OBJECT-TYPE
    SYNTAX     Integer32 (0..100)
    UNITS      "percent"
    MAX-ACCESS read-only
    STATUS     current
    DESCRIPTION
            "An estimate of the battery charge remaining expressed
            as a percent of full charge.(*)"
    ::= { upsBattery-first 4 }

upsBatteryVoltage-first OBJECT-TYPE
    SYNTAX     NonNegativeInteger32
    UNITS      "0.1 Volt DC"
    MAX-ACCESS read-only
    STATUS     current
    DESCRIPTION
            "The magnitude of the present battery voltage.(*)"
    ::= { upsBattery-first 5 }

upsBatteryCurrent-first OBJECT-TYPE
    SYNTAX     Integer32
    UNITS      "0.1 Amp DC"
    MAX-ACCESS read-only
    STATUS     current
    DESCRIPTION
            "The present battery current.(*)"
    ::= { upsBattery-first 6 }

upsBatteryTemperature-first OBJECT-TYPE
    SYNTAX     Integer32
    UNITS      "degrees Centigrade"
    MAX-ACCESS read-only
    STATUS     current
    DESCRIPTION
            "The ambient temperature at or near the UPS Battery
            casing.(*)"
    ::= { upsBattery-first 7 }

--
-- Input Group
--

upsInputLineBads-first OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-first 1 }

upsInputNumLines-first OBJECT-TYPE
    SYNTAX     NonNegativeInteger32
    MAX-ACCESS read-only
    STATUS     current
    DESCRIPTION
            "The number of input lines utilized in this device.
            This variable indicates the number of rows in the
            input table.(*)"
    ::= { upsInput-first 2 }

upsInputTable-first OBJECT-TYPE
    SYNTAX     SEQUENCE OF UpsInputEntry-first
    MAX-ACCESS not-accessible
    STATUS     current
    DESCRIPTION
            "A list of input table entries.  The number of entries
            is given by the value of upsInputNumLines.(*)"
    ::= { upsInput-first 3 }

upsInputEntry-first OBJECT-TYPE
    SYNTAX     UpsInputEntry-first
    MAX-ACCESS not-accessible
    STATUS     current
    DESCRIPTION
            "An entry containing information applicable to a
            particular input line.(*)"
    INDEX { upsInputLineIndex-first }
    ::= { upsInputTable-first 1 }

UpsInputEntry-first ::= SEQUENCE {
    upsInputLineIndex-first   PositiveInteger32,
    upsInputFrequency-first   NonNegativeInteger32,
    upsInputVoltage-first     NonNegativeInteger32,
    upsInputCurrent-first     NonNegativeInteger32,
    upsInputTruePower-first   NonNegativeInteger32,
    upsInputVoltageMin-first  NonNegativeInteger32,
    upsInputVoltageMax-first  NonNegativeInteger32
}

upsInputLineIndex-first OBJECT-TYPE
    SYNTAX     PositiveInteger32
    MAX-ACCESS not-accessible
    STATUS     current
    DESCRIPTION
            "The input line identifier.(*)"
    ::= { upsInputEntry-first 1 }

upsInputFrequency-first OBJECT-TYPE
    SYNTAX     NonNegativeInteger32
    UNITS      "0.1 Hertz"
    MAX-ACCESS read-only
    STATUS     current
    DESCRIPTION
            "The present input frequency.(*)"
    ::= { upsInputEntry-first 2 }

upsInputVoltage-first OBJECT-TYPE
    SYNTAX     NonNegativeInteger32
    UNITS      "RMS Volts"
    MAX-ACCESS read-only
    STATUS     current
    DESCRIPTION
            "The magnitude of the present input voltage.(*)"
    ::= { upsInputEntry-first 3 }

upsInputCurrent-first OBJECT-TYPE
    SYNTAX     NonNegativeInteger32
    UNITS      "0.1 RMS Amp"
    MAX-ACCESS read-only
    STATUS     current
    DESCRIPTION
            "The magnitude of the present input current.(*)"
    ::= { upsInputEntry-first 4 }

upsInputTruePower-first OBJECT-TYPE
    SYNTAX     NonNegativeInteger32
    UNITS      "Watts"
    MAX-ACCESS read-only
    STATUS     current
    DESCRIPTION
            "The magnitude of the present input true power.(*)"
    ::= { upsInputEntry-first 5 }

upsInputVoltageMin-first OBJECT-TYPE
    SYNTAX     NonNegativeInteger32
    UNITS      "RMS Volts"
    MAX-ACCESS read-only
    STATUS     current
    DESCRIPTION
            "The lowest magnitude of the input voltage since last read out."
    ::= { upsInputEntry-first 6 }

upsInputVoltageMax-first OBJECT-TYPE
    SYNTAX     NonNegativeInteger32
    UNITS      "RMS Volts"
    MAX-ACCESS read-only
    STATUS     current
    DESCRIPTION
            "The highest magnitude of the input voltage since last read out."
    ::= { upsInputEntry-first 7 }

--
-- The Output group.
--

upsOutputSource-first OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-first 1 }

upsOutputFrequency-first OBJECT-TYPE
    SYNTAX     NonNegativeInteger32
    UNITS      "0.1 Hertz"
    MAX-ACCESS read-only
    STATUS     current
    DESCRIPTION
            "The present output frequency.(*)"
    ::= { upsOutput-first 2 }

upsOutputNumLines-first OBJECT-TYPE
    SYNTAX     NonNegativeInteger32
    MAX-ACCESS read-only
    STATUS     current
    DESCRIPTION
            "The number of output lines utilized in this device.
            This variable indicates the number of rows in the
            output table.(*)"
    ::= { upsOutput-first 3 }

upsOutputTable-first OBJECT-TYPE
    SYNTAX     SEQUENCE OF UpsOutputEntry-first
    MAX-ACCESS not-accessible
    STATUS     current
    DESCRIPTION
            "A list of output table entries.  The number of
            entries is given by the value of upsOutputNumLines.(*)"
    ::= { upsOutput-first 4 }

upsOutputEntry-first OBJECT-TYPE
    SYNTAX     UpsOutputEntry-first
    MAX-ACCESS not-accessible
    STATUS     current
    DESCRIPTION
            "An entry containing information applicable to a
            particular output line.(*)"
    INDEX { upsOutputLineIndex-first }
    ::= { upsOutputTable-first 1 }

UpsOutputEntry-first ::= SEQUENCE {
    upsOutputLineIndex-first   PositiveInteger32,
    upsOutputVoltage-first     NonNegativeInteger32,
    upsOutputCurrent-first     NonNegativeInteger32,
    upsOutputPower-first       NonNegativeInteger32,
    upsOutputPercentLoad-first Integer32
}

upsOutputLineIndex-first OBJECT-TYPE
    SYNTAX     PositiveInteger32
    MAX-ACCESS not-accessible
    STATUS     current
    DESCRIPTION
            "The output line identifier.(*)"
    ::= { upsOutputEntry-first 1 }

upsOutputVoltage-first OBJECT-TYPE
    SYNTAX     NonNegativeInteger32
    UNITS      "RMS Volts"
    MAX-ACCESS read-only
    STATUS     current
    DESCRIPTION
            "The present output voltage.(*)"
    ::= { upsOutputEntry-first 2 }

upsOutputCurrent-first OBJECT-TYPE
    SYNTAX     NonNegativeInteger32
    UNITS      "0.1 RMS Amp"
    MAX-ACCESS read-only
    STATUS     current
    DESCRIPTION
            "The present output current.(*)"
    ::= { upsOutputEntry-first 3 }

upsOutputPower-first OBJECT-TYPE
    SYNTAX     NonNegativeInteger32
    UNITS      "Watts"
    MAX-ACCESS read-only
    STATUS     current
    DESCRIPTION
            "The present output true power.(*)"
    ::= { upsOutputEntry-first 4 }

upsOutputPercentLoad-first OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-first 5 }

--
-- The Bypass group generic.
--

upsBypassFrequency-first OBJECT-TYPE
    SYNTAX     NonNegativeInteger32
    UNITS      "0.1 Hertz"
    MAX-ACCESS read-only
    STATUS     current
    DESCRIPTION
            "The present bypass frequency.(*)"
    ::= { upsBypass-first 1 }

upsBypassNumLines-first OBJECT-TYPE
    SYNTAX     NonNegativeInteger32
    MAX-ACCESS read-only
    STATUS     current
    DESCRIPTION
            "The number of bypass lines utilized in this device.
            This entry indicates the number of rows in the bypass
            table.(*)"
    ::= { upsBypass-first 2 }

upsBypassTable-first OBJECT-TYPE
    SYNTAX     SEQUENCE OF UpsBypassEntry-first
    MAX-ACCESS not-accessible
    STATUS     current
    DESCRIPTION
            "A list of bypass table entries.  The number of
            entries is given by the value of upsBypassNumLines.(*)"
    ::= { upsBypass-first 3 }

upsBypassEntry-first OBJECT-TYPE
    SYNTAX     UpsBypassEntry-first
    MAX-ACCESS not-accessible
    STATUS     current
    DESCRIPTION
            "An entry containing information applicable to a
            particular bypass input.(*)"
    INDEX { upsBypassLineIndex-first }
    ::= { upsBypassTable-first 1 }

UpsBypassEntry-first ::= SEQUENCE {
    upsBypassLineIndex-first  PositiveInteger32,
    upsBypassVoltage-first    NonNegativeInteger32,
    upsBypassCurrent-first    NonNegativeInteger32,
    upsBypassPower-first      NonNegativeInteger32
}

upsBypassLineIndex-first OBJECT-TYPE
    SYNTAX     PositiveInteger32
    MAX-ACCESS not-accessible
    STATUS     current
    DESCRIPTION
            "The bypass line identifier.(*)"
    ::= { upsBypassEntry-first 1 }

upsBypassVoltage-first OBJECT-TYPE
    SYNTAX     NonNegativeInteger32
    UNITS      "RMS Volts"
    MAX-ACCESS read-only
    STATUS     current
    DESCRIPTION
            "The present bypass voltage.(*)"
    ::= { upsBypassEntry-first 2 }

upsBypassCurrent-first OBJECT-TYPE
    SYNTAX     NonNegativeInteger32
    UNITS      "0.1 RMS Amp"
    MAX-ACCESS read-only
    STATUS     current
    DESCRIPTION
            "The present bypass current.(*)"
    ::= { upsBypassEntry-first 3 }

upsBypassPower-first OBJECT-TYPE
    SYNTAX     NonNegativeInteger32
    UNITS      "Watts"
    MAX-ACCESS read-only
    STATUS     current
    DESCRIPTION
            "The present true power conveyed by the bypass.(*)"
    ::= { upsBypassEntry-first 4 }

--
-- The Alarm group generic.
--

upsAlarmsPresent-first OBJECT-TYPE
    SYNTAX     Gauge32
    MAX-ACCESS read-only
    STATUS     current
    DESCRIPTION
            "The present number of active alarm conditions.(*)"
    ::= { upsAlarm-first 1 }

upsAlarmTable-first OBJECT-TYPE
    SYNTAX     SEQUENCE OF UpsAlarmEntry-first
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-first 2 }

upsAlarmEntry-first OBJECT-TYPE
    SYNTAX     UpsAlarmEntry-first
    MAX-ACCESS not-accessible
    STATUS     current
    DESCRIPTION
            "An entry containing information applicable to a
            particular alarm.(*)"
    INDEX { upsAlarmId-first }
    ::= { upsAlarmTable-first 1 }

UpsAlarmEntry-first ::= SEQUENCE {
    upsAlarmId-first          PositiveInteger32,
    upsAlarmDescr-first       AutonomousType,
    upsAlarmTime-first       TimeStamp
}

upsAlarmId-first OBJECT-TYPE
    SYNTAX     PositiveInteger32
    MAX-ACCESS not-accessible
    STATUS     current
    DESCRIPTION
            "A unique identifier for an alarm condition.  This
            value must remain constant.(*)"
    ::= { upsAlarmEntry-first 1 }

upsAlarmDescr-first OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-first 2 }

upsAlarmTime-first OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-first 3 }

--
-- Well known alarm conditions generic.
--

upsAlarmBatteryBad-first OBJECT-IDENTITY
    STATUS     current
    DESCRIPTION
            "One or more batteries have been determined to require
            replacement.(*)"
    ::= { upsWellKnownAlarms-first  1 }

upsAlarmOnBattery-first OBJECT-IDENTITY
    STATUS     current
    DESCRIPTION
            "The UPS is drawing power from the batteries.(*)"
    ::= { upsWellKnownAlarms-first  2 }

upsAlarmLowBattery-first OBJECT-IDENTITY
    STATUS     current
    DESCRIPTION
            "The remaining battery run-time is less than or equal
            to upsConfigLowBattTime.(*)"
    ::= { upsWellKnownAlarms-first  3 }

upsAlarmDepletedBattery-first OBJECT-IDENTITY
    STATUS     current
    DESCRIPTION
            "The UPS will be unable to sustain the present load
            when and if the utility power is lost.(*)"
    ::= { upsWellKnownAlarms-first  4 }

upsAlarmTempBad-first OBJECT-IDENTITY
    STATUS     current
    DESCRIPTION
            "A temperature is out of tolerance.(*)"
    ::= { upsWellKnownAlarms-first  5 }

upsAlarmInputBad-first OBJECT-IDENTITY
    STATUS     current
    DESCRIPTION
            "An input condition is out of tolerance.(*)"
    ::= { upsWellKnownAlarms-first  6 }

upsAlarmOutputBad-first OBJECT-IDENTITY
    STATUS     current
    DESCRIPTION
            "An output condition (other than OutputOverload) is
            out of tolerance.(*)"
    ::= { upsWellKnownAlarms-first  7 }

upsAlarmOutputOverload-first OBJECT-IDENTITY
    STATUS     current
    DESCRIPTION
            "The output load exceeds the UPS output capacity.(*)"
    ::= { upsWellKnownAlarms-first  8 }

upsAlarmOnBypass-first OBJECT-IDENTITY
    STATUS     current
    DESCRIPTION
            "The Bypass is presently engaged on the UPS.(*)"
    ::= { upsWellKnownAlarms-first  9 }

upsAlarmBypassBad-first OBJECT-IDENTITY
    STATUS     current
    DESCRIPTION
            "The Bypass is out of tolerance.(*)"
    ::= { upsWellKnownAlarms-first 10 }

upsAlarmOutputOffAsRequested-first OBJECT-IDENTITY
    STATUS     current
    DESCRIPTION
            "The UPS has shutdown as requested, i.e., the output
            is off.(*)"
    ::= { upsWellKnownAlarms-first 11 }

upsAlarmUpsOffAsRequested-first OBJECT-IDENTITY
    STATUS     current
    DESCRIPTION
            "The entire UPS has shutdown as commanded.(*)"
    ::= { upsWellKnownAlarms-first 12 }

upsAlarmChargerFailed-first OBJECT-IDENTITY
    STATUS     current
    DESCRIPTION
            "An uncorrected problem has been detected within the
            UPS charger subsystem.(*)"
    ::= { upsWellKnownAlarms-first 13 }

upsAlarmUpsOutputOff-first OBJECT-IDENTITY
    STATUS     current
    DESCRIPTION
            "The output of the UPS is in the off state.(*)"
    ::= { upsWellKnownAlarms-first 14 }

upsAlarmUpsSystemOff-first OBJECT-IDENTITY
    STATUS     current
    DESCRIPTION
            "The UPS system is in the off state.(*)"
    ::= { upsWellKnownAlarms-first 15 }

upsAlarmFanFailure-first OBJECT-IDENTITY
    STATUS     current
    DESCRIPTION
            "The failure of one or more fans in the UPS has been
            detected.(*)"
    ::= { upsWellKnownAlarms-first 16 }

upsAlarmFuseFailure-first OBJECT-IDENTITY
    STATUS     current
    DESCRIPTION
            "The failure of one or more fuses has been detected.(*)"
    ::= { upsWellKnownAlarms-first 17 }

upsAlarmGeneralFault-first OBJECT-IDENTITY
    STATUS     current
    DESCRIPTION
            "A general fault in the UPS has been detected.(*)"
    ::= { upsWellKnownAlarms-first 18 }

upsAlarmDiagnosticTestFailed-first OBJECT-IDENTITY
    STATUS     current
    DESCRIPTION
            "The result of the last diagnostic test indicates a
            failure.(*)"
    ::= { upsWellKnownAlarms-first 19 }

upsAlarmCommunicationsLost-first OBJECT-IDENTITY
    STATUS     current
    DESCRIPTION
            "A problem has been encountered in the communications
            between the agent and the UPS.(*)"
    ::= { upsWellKnownAlarms-first 20 }

upsAlarmAwaitingPower-first OBJECT-IDENTITY
    STATUS     current
    DESCRIPTION
            "The UPS output is off and the UPS is awaiting the
            return of input power.(*)"
    ::= { upsWellKnownAlarms-first 21 }

upsAlarmShutdownPending-first OBJECT-IDENTITY
    STATUS     current
    DESCRIPTION
            "A upsShutdownAfterDelay countdown is underway.(*)"
    ::= { upsWellKnownAlarms-first 22 }

upsAlarmShutdownImminent-first OBJECT-IDENTITY
    STATUS     current
    DESCRIPTION
            "The UPS will turn off power to the load in less than
            5 seconds; this may be either a timed shutdown or a
            low battery shutdown.(*)"
    ::= { upsWellKnownAlarms-first 23 }

upsAlarmTestInProgress-first OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-first 24 }

upsAlarmReceptacleOff-first OBJECT-IDENTITY
    STATUS     current
    DESCRIPTION
            "The receptacle are switch off    "
    ::= { upsWellKnownAlarms-first 25 }

upsAlarmMaskA-first OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-first 4 }

--
-- The Test Group generic
--

upsTestId-first OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-first 1 }

-- see [6] for more information on the semantics of objects with
-- syntax of TestAndIncr

upsTestSpinLock-first OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-first 2 }

upsTestResultsSummary-first OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-first 3 }

upsTestResultsDetail-first OBJECT-TYPE
    SYNTAX     DisplayString (SIZE (0..255))
    MAX-ACCESS read-only
    STATUS     current
    DESCRIPTION
            "Additional information about upsTestResultsSummary.
            If no additional information available, a zero length
            string is returned.(*)"
    ::= { upsTest-first 4 }

upsTestStartTime-first OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-first 5 }

upsTestElapsedTime-first OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-first 6 }

--
-- Well known tests generic.
--

upsTestNoTestsInitiated-first OBJECT-IDENTITY
    STATUS     current
    DESCRIPTION
            "No tests have been initiated and no test is in
            progress.(*)"
    ::= { upsWellKnownTests-first  1 }

upsTestAbortTestInProgress-first OBJECT-IDENTITY
    STATUS     current
    DESCRIPTION
            "The test in progress is to be aborted / the test in
            progress was aborted.(*)"
    ::= { upsWellKnownTests-first  2 }

upsTestGeneralSystemsTest-first OBJECT-IDENTITY
    STATUS     current
    DESCRIPTION
            "The manufacturer's standard test of UPS device
            systems.(*)"
    ::= { upsWellKnownTests-first  3 }

upsTestQuickBatteryTest-first OBJECT-IDENTITY
    STATUS     current
    DESCRIPTION
            "A test that is sufficient to determine if the battery
            needs replacement.(*)"
    ::= { upsWellKnownTests-first  4 }

upsTestDeepBatteryCalibration-first OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-first  5 }

--
-- The Control group generic.
--

upsShutdownType-first OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-first 1 }

upsShutdownAfterDelay-first OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-first 2 }

upsStartupAfterDelay-first OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-first 3 }

upsRebootWithDuration-first OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-first 4 }

upsAutoRestart-first OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-first 5 }

upsReceptaclesNum-first OBJECT-TYPE
    SYNTAX     NonNegativeInteger32
    MAX-ACCESS read-only
    STATUS     current
    DESCRIPTION
            "The number of receptacles utilized in this device.
            This entry indicates the number of rows in the receptacle
            table."
    ::= { upsControl-first 6 }

upsReceptacleTable-first OBJECT-TYPE
    SYNTAX     SEQUENCE OF UpsReceptacleEntry-first
    MAX-ACCESS not-accessible
    STATUS     current
    DESCRIPTION
            "A list of receptacle table entries.  The number of
            entries is given by the value of upsReceptacleNum."
    ::= { upsControl-first 7 }

upsReceptacleEntry-first OBJECT-TYPE
    SYNTAX     UpsReceptacleEntry-first
    MAX-ACCESS not-accessible
    STATUS     current
    DESCRIPTION
            "An entry containing information applicable to a
            particular receptacle."
    INDEX { upsReceptacleLineIndex-first }
    ::= { upsReceptacleTable-first 1 }

UpsReceptacleEntry-first ::= SEQUENCE {
    upsReceptacleLineIndex-first  PositiveInteger32,
    upsReceptacleOnOff-first      Integer32    
}

upsReceptacleLineIndex-first OBJECT-TYPE
    SYNTAX     PositiveInteger32
    MAX-ACCESS not-accessible
    STATUS     current
    DESCRIPTION
            "The receptacle line identifier."
    ::= { upsReceptacleEntry-first 1 }

upsReceptacleOnOff-first OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-first 2 }

upsUPSMode-first OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-first 8 }

upsRectifierOnOff-first OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-first 9 }

upsBatteryChargeMethod-first OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-first 10 }

upsInverterOnOff-first OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-first 11 }

upsBypassOnOff-first OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-first 12 }

upsLoadSource-first OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-first 13 }
	
--
-- The Configuration group generic.
--

upsConfigInputVoltage-first OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-first 1 }

upsConfigInputFreq-first OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-first 2 }

upsConfigOutputVoltage-first OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-first 3 }

upsConfigOutputFreq-first OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-first 4 }

upsConfigOutputVA-first OBJECT-TYPE
    SYNTAX     NonNegativeInteger32
    UNITS      "Volt-Amps"
    MAX-ACCESS read-only
    STATUS     current
    DESCRIPTION
            "The magnitude of the nominal Volt-Amp rating.(*)"
    ::= { upsConfig-first 5 }

upsConfigOutputPower-first OBJECT-TYPE
    SYNTAX     NonNegativeInteger32
    UNITS      "Watts"
    MAX-ACCESS read-only
    STATUS     current
    DESCRIPTION
            "The magnitude of the nominal true power rating.(*)"
    ::= { upsConfig-first 6 }

upsConfigLowBattTime-first OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-first 7 }

upsConfigAudibleStatus-first OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-first 8 }

upsConfigLowVoltageTransferPoint-first OBJECT-TYPE
    SYNTAX     NonNegativeInteger32
    UNITS      "RMS Volts"
    MAX-ACCESS read-write
    STATUS     current
    DESCRIPTION
            "The minimum input line voltage allowed before the UPS
            system transfers to battery backup.(*)"
    ::= { upsConfig-first 9 }

upsConfigHighVoltageTransferPoint-first OBJECT-TYPE
    SYNTAX     NonNegativeInteger32
    UNITS      "RMS Volts"
    MAX-ACCESS read-write
    STATUS     current
    DESCRIPTION
            "The maximum line voltage allowed before the UPS
            system transfers to battery backup.(*)"
    ::= { upsConfig-first 10 }

upsConfigBatteryCapacity-first OBJECT-TYPE
    SYNTAX     NonNegativeInteger32
    UNITS      "Amps Hours"
    MAX-ACCESS read-write
    STATUS     current
    DESCRIPTION
            "The installed battery capacity. This value is the 'factory'-value,
             not the value after calibration."
    ::= { upsConfig-first 11 }

upsConfigBatteryChargeCurrent-first OBJECT-TYPE
    SYNTAX     NonNegativeInteger32
    UNITS      "0.1 Amp DC"
    MAX-ACCESS read-write
    STATUS     current
    DESCRIPTION
            "The maximum battery charge current, including external chargers."
    ::= { upsConfig-first 12 }						

upsConfigNoLoadShutdown-first OBJECT-TYPE
    SYNTAX     Integer32 {
        disabled(1),
        enabled(2)
    }
    MAX-ACCESS read-write
    STATUS     current
    DESCRIPTION
            "Dis- or enable 'no load' shutdown from the contact interface."
    ::= { upsConfig-first 13 }
	
upsConfigStartDelay-first OBJECT-TYPE
    SYNTAX     PositiveInteger32
    UNITS      "minutes"				
    MAX-ACCESS read-write
    STATUS     current
    DESCRIPTION
            "Minimum required autonomy time before the UPS may perform an
             autorestart."
    ::= { upsConfig-first 14 }

--
-- The GetSet group generic.
--

upsEventGetNext-first OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-first 1 }

upsEventGetPrevious-first OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-first 2 }
				
upsEventSetStartingTimeStamp-first OBJECT-TYPE
    SYNTAX     NonNegativeInteger32
    MAX-ACCESS read-write
    STATUS     current
    DESCRIPTION
            "The timestamp which is used as starting point for downloading
             events from the UPS event buffer"
    ::= { upsGetSet-first 3 }				

upsEventRetreiveCurrentTimeStamp-first OBJECT-TYPE
    SYNTAX     NonNegativeInteger32
    MAX-ACCESS read-only
    STATUS     current
    DESCRIPTION
            "The current timestamp is retreived from the UPS"
    ::= { upsGetSet-first 4 }				

upsEventTableSize-first OBJECT-TYPE
    SYNTAX     NonNegativeInteger32
    MAX-ACCESS read-only
    STATUS     current
    DESCRIPTION
            "The number of entries in the event table.
            This object indicates the number of rows in the event table."
    ::= { upsGetSet-first 5 }

upsEventTable-first OBJECT-TYPE
    SYNTAX     SEQUENCE OF UpsEventEntry-first
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-first 6 }

upsEventEntry-first OBJECT-TYPE
    SYNTAX     UpsEventEntry-first
    MAX-ACCESS not-accessible
    STATUS     current
    DESCRIPTION
            "An entry containing information applicable to a
            particular event."
    INDEX { upsEventLineIndex-first }
    ::= { upsEventTable-first 1 }

UpsEventEntry-first ::= SEQUENCE {
    upsEventLineIndex-first PositiveInteger32,
    upsEventCode-first      Integer32,
    upsEventStatus-first    NonNegativeInteger32,
    upsEventTime-first      NonNegativeInteger32
}

upsEventLineIndex-first OBJECT-TYPE
    SYNTAX     PositiveInteger32
    MAX-ACCESS not-accessible
    STATUS     current
    DESCRIPTION
            "The event line identifier."
    ::= { upsEventEntry-first 1 }

upsEventCode-first OBJECT-TYPE
    SYNTAX     NonNegativeInteger32
    MAX-ACCESS read-only
    STATUS     current
    DESCRIPTION
            "The event code in numerical format."
    ::= { upsEventEntry-first 2 }

upsEventStatus-first OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-first 3 }

upsEventTime-first OBJECT-TYPE
    SYNTAX     NonNegativeInteger32
    MAX-ACCESS read-only
    STATUS     current
    DESCRIPTION
            "The timestamp of the moment the event was generated."
    ::= { upsEventEntry-first 4 }

upsParametersRead-first OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-first 7 }

upsParametersWrite-first OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-first 8 }

upsParametersStartAddress-first OBJECT-TYPE
    SYNTAX     NonNegativeInteger32
    MAX-ACCESS read-write
    STATUS     current
    DESCRIPTION
            "The address which is used as starting point for downloading
             parameters from the UPS"
    ::= { upsGetSet-first 9 }				

upsParameterTableSize-first OBJECT-TYPE
    SYNTAX     NonNegativeInteger32
    MAX-ACCESS read-only
    STATUS     current
    DESCRIPTION
            "The number of entries in the parameter table.
            This object indicates the number of rows in the parameter table."
    ::= { upsGetSet-first 10 }

upsParameterTable-first OBJECT-TYPE
    SYNTAX     SEQUENCE OF UpsParameterEntry-first
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-first 11 }

upsParameterEntry-first OBJECT-TYPE
    SYNTAX     UpsParameterEntry-first
    MAX-ACCESS not-accessible
    STATUS     current
    DESCRIPTION
            "An entry containing information applicable to a
            particular parameter."
    INDEX { upsParameterLineIndex-first }
    ::= { upsParameterTable-first 1 }

UpsParameterEntry-first ::= SEQUENCE {
    upsParameterLineIndex-first PositiveInteger32,
    upsParameterValue-first     Integer32   
}

upsParameterLineIndex-first OBJECT-TYPE
    SYNTAX     PositiveInteger32
    MAX-ACCESS not-accessible
    STATUS     current
    DESCRIPTION
            "The parameter line identifier."
    ::= { upsParameterEntry-first 1 }

upsParameterValue-first OBJECT-TYPE
    SYNTAX     Integer32
    MAX-ACCESS read-write
    STATUS     current
    DESCRIPTION
            "The parameter value in numerical format."
    ::= { upsParameterEntry-first 2 }

upsStatus-first OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-first 12 }

upsMainsStatisticsMBfail-first OBJECT-TYPE
    SYNTAX     NonNegativeInteger32
    MAX-ACCESS read-only
    STATUS     current
    DESCRIPTION
            "Count of main bypass failures (>200 ms), since UPS installation."
    ::= { upsGetSet-first 13 }

upsMainsStatisticsMRfail-first OBJECT-TYPE
    SYNTAX     NonNegativeInteger32
    MAX-ACCESS read-only
    STATUS     current
    DESCRIPTION
            "Count of mains rectifier failures (>200 ms), since UPS installation."
    ::= { upsGetSet-first 14 }
		
upsMainsStatisticsB2-first OBJECT-TYPE
    SYNTAX     NonNegativeInteger32
    MAX-ACCESS read-only
    STATUS     current
    DESCRIPTION
            "Count of transients on the mains bypass (0..2 ms), during the last 7 days."
    ::= { upsGetSet-first 15 }

upsMainsStatisticsB5-first OBJECT-TYPE
    SYNTAX     NonNegativeInteger32
    MAX-ACCESS read-only
    STATUS     current
    DESCRIPTION
            "Count of transients on the mains bypass (2..5 ms), during the last 7 days."
    ::= { upsGetSet-first 16 }

upsMainsStatisticsB10-first OBJECT-TYPE
    SYNTAX     NonNegativeInteger32
    MAX-ACCESS read-only
    STATUS     current
    DESCRIPTION
            "Count of transients on the mains bypass (5..10 ms), during the last 7 days."
    ::= { upsGetSet-first 17 }

upsMainsStatisticsB200-first OBJECT-TYPE
    SYNTAX     NonNegativeInteger32
    MAX-ACCESS read-only
    STATUS     current
    DESCRIPTION
            "Count of transients on the mains bypass (10..200 ms), during the last 7 days."
    ::= { upsGetSet-first 18 }

upsMainsStatisticsBypRel-first OBJECT-TYPE
    SYNTAX     NonNegativeInteger32
    MAX-ACCESS read-only
    STATUS     current
    DESCRIPTION
            "Bypass reliability degree [0..100%;255]. The value NOSUCHNAME means 'not available'."
    ::= { upsGetSet-first 19 }

upsTime-first OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-firstERROR,              meaning 'command not supported'. It is possible to know which is the timestamp 
             format supported by the UPS, by issuing a read-command or by reading events, 
             which includes timestamps."
    ::= { upsGetSet-first 20 }

upsRequestPermission-first OBJECT-TYPE
    SYNTAX     DisplayString (SIZE(0..63))
    MAX-ACCESS write-only
    STATUS     current
    DESCRIPTION
            "An encrypted code is send to enable use of restricted write objects during
             a limited period of time."
    ::= { upsGetSet-first 21 }
    
upsEventGetCode-first OBJECT-TYPE
    SYNTAX     Integer32
    MAX-ACCESS write-only
    STATUS     current
    DESCRIPTION
            "The code which is used as starting point to downloading the events from the 
            UPS event buffer."
    ::= { upsGetSet-first 22 }    
    
upsEventSpinLock-first OBJECT-TYPE
    SYNTAX     TestAndIncr
    MAX-ACCESS read-write
    STATUS     current
    DESCRIPTION
            "A spin lock on the event subsystem. "

    ::= { upsGetSet-first 23 }
    
upsParameterSpinLock-first OBJECT-TYPE
    SYNTAX     TestAndIncr
    MAX-ACCESS read-write
    STATUS     current
    DESCRIPTION
            "A spin lock on the parameters subsystem. "

    ::= { upsGetSet-first 24 }


--
-- GE Trap group generic
--

upsAlarmBatteryBad-first TRAP-TYPE
    ENTERPRISE geUPSTraps-first
    VARIABLES  { trapArg  }
    DESCRIPTION
            "One or more batteries have been determined to require
            replacement."
    ::= 1

upsAlarmOnBattery-first TRAP-TYPE
    ENTERPRISE geUPSTraps-first
    VARIABLES  { trapArg , upsSecondsOnBattery-first  }
    DESCRIPTION
            "An On Battery condition is restored."
    ::= 2

upsAlarmLowBattery-first TRAP-TYPE
    ENTERPRISE geUPSTraps-first
    VARIABLES  { trapArg  }
    DESCRIPTION
            "The remaining battery run-time is less than or equal
            to upsConfigLowBattTime."
    ::= 3

upsAlarmDepletedBattery-first TRAP-TYPE
    ENTERPRISE geUPSTraps-first
    VARIABLES  { trapArg  }
    DESCRIPTION
            "The UPS will be unable to sustain the present load
            when and if the utility power is lost)"
    ::= 4

upsAlarmTempBad-first TRAP-TYPE
    ENTERPRISE geUPSTraps-first
    VARIABLES  { trapArg , upsBatteryTemperature }
    DESCRIPTION
            "A temperature is out of tolerance."
    ::= 5

upsAlarmInputBad-first TRAP-TYPE
    ENTERPRISE geUPSTraps-first
    VARIABLES  { trapArg  }
    DESCRIPTION
            "An input condition is out of tolerance."
    ::= 6

upsAlarmOutputBad-first TRAP-TYPE
    ENTERPRISE geUPSTraps-first
    VARIABLES  { trapArg  }
    DESCRIPTION
            "An output condition (other than OutputOverload) is
            out of tolerance."
    ::= 7

upsAlarmOutputOverload-first TRAP-TYPE
    ENTERPRISE geUPSTraps-first
    VARIABLES  { trapArg , upsOutputPercentLoad-first }
    DESCRIPTION
            "The output load exceeds the UPS output capacity."
    ::= 8

upsAlarmOnBypass-first TRAP-TYPE
    ENTERPRISE geUPSTraps-first
    VARIABLES  { trapArg  }
    DESCRIPTION
            "The Bypass is presently engaged on the UPS."
    ::= 9

upsAlarmBypassBad-first TRAP-TYPE
    ENTERPRISE geUPSTraps-first
    VARIABLES  { trapArg  }
    DESCRIPTION
            "The Bypass is out of tolerance."
    ::= 10

upsAlarmOutputOffAsRequested-first TRAP-TYPE
    ENTERPRISE geUPSTraps-first
    VARIABLES  { trapArg  }
    DESCRIPTION
            "The UPS has shutdown as requested, i.e., the output
            is off."
    ::= 11

upsAlarmUpsOffAsRequested-first TRAP-TYPE
    ENTERPRISE geUPSTraps-first-first
    VARIABLES  { trapArg  }
    DESCRIPTION
            "The entire UPS has shutdown as commanded."
    ::= 12

upsAlarmChargerFailed-first TRAP-TYPE
    ENTERPRISE geUPSTraps-first
    VARIABLES  { trapArg  }
    DESCRIPTION
            "An uncorrected problem has been detected within the
            UPS charger subsystem."
    ::= 13

upsAlarmUpsOutputOff-first TRAP-TYPE
    ENTERPRISE geUPSTraps-first
    VARIABLES  { trapArg  }
    DESCRIPTION
            "The output of the UPS is in the off state."
    ::= 14

upsAlarmUpsSystemOff-first TRAP-TYPE
    ENTERPRISE geUPSTraps-first
    VARIABLES  { trapArg  }
    DESCRIPTION
            "The UPS system is in the off state."
    ::= 15

upsAlarmFanFailure-first TRAP-TYPE
    ENTERPRISE geUPSTraps-first
    VARIABLES  { trapArg  }
    DESCRIPTION
            "The failure of one or more fans in the UPS has been
            detected."
    ::= 16

upsAlarmFuseFailure-first TRAP-TYPE
    ENTERPRISE geUPSTraps-first
    VARIABLES  { trapArg  }
    DESCRIPTION
            "The failure of one or more fuses has been detected."
    ::= 17

upsAlarmGeneralFault-first TRAP-TYPE
    ENTERPRISE geUPSTraps-first
    VARIABLES  { trapArg  }
    DESCRIPTION
            "A general fault in the UPS has been detected."
    ::= 18

upsAlarmDiagnosticTestFailed-first TRAP-TYPE
    ENTERPRISE geUPSTraps-first
    VARIABLES  { trapArg  }
    DESCRIPTION
            "The result of the last diagnostic test indicates a
            failure."
    ::= 19

upsAlarmCommunicationsLost-first TRAP-TYPE
    ENTERPRISE geUPSTraps-first
    VARIABLES  { trapArg  }
    DESCRIPTION
            "A problem has been encountered in the communication
            between the agent and the UPS."
    ::= 20
    
upsAlarmAwaitingPower-first TRAP-TYPE
    ENTERPRISE geUPSTraps-first
    VARIABLES  { trapArg  }
    DESCRIPTION
            "The UPS output is off and the UPS is awaiting the
            return of the input power (*)."
    ::= 21    

upsAlarmShutdownPending-first TRAP-TYPE
    ENTERPRISE geUPSTraps-first
    VARIABLES  { trapArg , upsShutdownAfterDelay-first }
    DESCRIPTION
            "A upsShutdownAfterDelay countdown is underway."
    ::= 22

upsAlarmShutdownImminent-first TRAP-TYPE
    ENTERPRISE geUPSTraps-first
    VARIABLES  { trapArg  }
    DESCRIPTION
            "The UPS will turn off power to the load in less than
            5 seconds; this may be either a timed shutdown or a
            low battery shutdown."
    ::= 23

upsAlarmTestInProgress-first TRAP-TYPE
    ENTERPRISE geUPSTraps-first
    VARIABLES  { trapArg , upsTestId-first }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-first TRAP-TYPE
    ENTERPRISE geUPSTraps-first
    VARIABLES  { trapArg  }
    DESCRIPTION
            "A receptacle has been switched off."
    ::= 25

upsAlarmBatteryBadRestored-first TRAP-TYPE
    ENTERPRISE geUPSTraps-first
    VARIABLES  { trapArg  }
    DESCRIPTION
            "A Battery bad condition is restored."
    ::= 33

upsAlarmOnBatteryRestored-first TRAP-TYPE
    ENTERPRISE geUPSTraps-first
    VARIABLES  { trapArg  }
    DESCRIPTION
            "The UPS is drawing power from mains again."
    ::= 34

upsAlarmLowBatteryRestored-first TRAP-TYPE
    ENTERPRISE geUPSTraps-first
    VARIABLES  { trapArg  }
    DESCRIPTION
            "A Low Battery condition is restored."
    ::= 35

upsAlarmDepletedBatteryRestored-first TRAP-TYPE
    ENTERPRISE geUPSTraps-first
    VARIABLES  { trapArg  }
    DESCRIPTION
            "A Depleted Battery condition is restored."
    ::= 36

upsAlarmTempBadRestored-first TRAP-TYPE
    ENTERPRISE geUPSTraps-first
    VARIABLES  { trapArg  }
    DESCRIPTION
            "A bad temperature condition is restored."
    ::= 37

upsAlarmInputBadRestored-first TRAP-TYPE
    ENTERPRISE geUPSTraps-first
    VARIABLES  { trapArg  }
    DESCRIPTION
            "An input bad condition is restored."
    ::= 38

upsAlarmOutputBadRestored-first TRAP-TYPE
    ENTERPRISE geUPSTraps-first
    VARIABLES  { trapArg  }
    DESCRIPTION
            "An output bad condition is restored."
    ::= 39

upsAlarmOutputOverloadRestored-first TRAP-TYPE
    ENTERPRISE geUPSTraps-first
    VARIABLES  { trapArg  }
    DESCRIPTION
            "An output overload condition is restored."
    ::= 40

upsAlarmOnBypassRestored-first TRAP-TYPE
    ENTERPRISE geUPSTraps-first
    VARIABLES  { trapArg  }
    DESCRIPTION
            "An On Bypass condition is restored."
    ::= 41

upsAlarmBypassBadRestored-first TRAP-TYPE
    ENTERPRISE geUPSTraps-first
    VARIABLES  { trapArg  }
    DESCRIPTION
            "A Bypass bad condition is restored."
    ::= 42

upsAlarmOutputOffAsRequestedRestored-first TRAP-TYPE
    ENTERPRISE geUPSTraps-first
    VARIABLES  { trapArg  }
    DESCRIPTION
            "A request shutdown has been restored."
    ::= 43

upsAlarmUpsOffAsRequestedRestored-first TRAP-TYPE
    ENTERPRISE geUPSTraps-first-first
    VARIABLES  { trapArg  }
    DESCRIPTION
            "A entire UPS command has been restored."
    ::= 44

upsAlarmChargerFailedRestored-first TRAP-TYPE
    ENTERPRISE geUPSTraps-first
    VARIABLES  { trapArg  }
    DESCRIPTION
            "A Charger Failer condition is restored."
    ::= 45

upsAlarmUpsOutputOn-first TRAP-TYPE
    ENTERPRISE geUPSTraps-first
    VARIABLES  { trapArg  }
    DESCRIPTION
            "The output of the UPS switched in the on state."
    ::= 46

upsAlarmUpsSystemOn-first TRAP-TYPE
    ENTERPRISE geUPSTraps-first
    VARIABLES  { trapArg  }
    DESCRIPTION
            "The UPS system is switched in the on state."
    ::= 47

upsAlarmFanFailureRestored-first TRAP-TYPE
    ENTERPRISE geUPSTraps-first
    VARIABLES  { trapArg  }
    DESCRIPTION
            "A Fan failure condition is restored."
    ::= 48

upsAlarmFuseFailureRestored-first TRAP-TYPE
    ENTERPRISE geUPSTraps-first
    VARIABLES  { trapArg  }
    DESCRIPTION
            "A Fuse failure condition is restored."
    ::= 49

upsAlarmGeneralFaultRestored-first TRAP-TYPE
    ENTERPRISE geUPSTraps-first
    VARIABLES  { trapArg  }
    DESCRIPTION
            "A general fault is restored."
    ::= 50

upsAlarmDiagnosticTestFailedRestored-first TRAP-TYPE
    ENTERPRISE geUPSTraps-first
    VARIABLES  { trapArg  }
    DESCRIPTION
            "A last diagnostic test indicates a failure is 
            restored."
    ::= 51

upsAlarmCommunicationsLostRestored-first TRAP-TYPE
    ENTERPRISE geUPSTraps-first
    VARIABLES  { trapArg  }
    DESCRIPTION
            "A problem in the communication between the agent 
            and the UPS is restored."
    ::= 52
    
upsAlarmAwaitingPowerRestored-first TRAP-TYPE
    ENTERPRISE geUPSTraps-first
    VARIABLES  { trapArg  }
    DESCRIPTION
            "A awaiting power condition is restored (*)."
    ::= 53    

upsAlarmShutdownPendingRestored-first TRAP-TYPE
    ENTERPRISE geUPSTraps-first
    VARIABLES  { trapArg , upsShutdownAfterDelay-first }
    DESCRIPTION
            "A upsShutdownAfterDelay countdown is restored."
    ::= 54

upsAlarmShutdownImminentRestored-first TRAP-TYPE
    ENTERPRISE geUPSTraps-first
    VARIABLES  { trapArg  }
    DESCRIPTION
            "A shutdown imminent condition is restored."
    ::= 55

upsAlarmTestInProgressRestored-first TRAP-TYPE
    ENTERPRISE geUPSTraps-first
    VARIABLES  { trapArg , upsTestId-first }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-first TRAP-TYPE
    ENTERPRISE geUPSTraps-first
    VARIABLES  { trapArg  }
    DESCRIPTION
            "A measurement value reached a value below its low-level threshold."
    ::= 129

upsAlarmValueHigh-first TRAP-TYPE
    ENTERPRISE geUPSTraps-first
    VARIABLES  { trapArg  }
    DESCRIPTION
            "A measurement value reached a value higher than its high-level threshold."
    ::= 130

upsAlarmValueLowRestored-first TRAP-TYPE
    ENTERPRISE geUPSTraps-first
    VARIABLES  { trapArg  }
    DESCRIPTION
            "A ValueLow alarm condition is restored."
    ::= 133

upsAlarmValueHighRestored-first TRAP-TYPE
    ENTERPRISE geUPSTraps-first
    VARIABLES  { trapArg }
    DESCRIPTION
            "A ValueHigh alarm condition is restored."
    ::= 134


--
-- The Device Identification group. Second
--      All objects in this group except for upsIdentName and
--      upsIdentAttachedDevices are set at device initialization
--      and remain static.
--

upsIdentManufacturer-second OBJECT-TYPE
    SYNTAX     DisplayString (SIZE (0..31))
    MAX-ACCESS read-only
    STATUS     current
    DESCRIPTION
            "The name of the UPS manufacturer.(*)"
    ::= { upsIdent-second 1 }

upsIdentModel-second OBJECT-TYPE
    SYNTAX     DisplayString (SIZE (0..63))
    MAX-ACCESS read-only
    STATUS     current
    DESCRIPTION
            "The UPS Model designation.(*)"
    ::= { upsIdent-second 2 }

upsIdentUPSSoftwareVersion-second OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-second 3 }

upsIdentAgentSoftwareVersion-second OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-second 4 }

upsIdentName-second OBJECT-TYPE
    SYNTAX     DisplayString (SIZE(0..63))
    MAX-ACCESS read-write
    STATUS     current
    DESCRIPTION
            "A string identifying the UPS.  This object should be
            set by the administrator.(*)"
    ::= { upsIdent-second 5 }

upsIdentAttachedDevices-second OBJECT-TYPE
    SYNTAX     DisplayString (SIZE(0..63))
    MAX-ACCESS read-write
    STATUS     current
    DESCRIPTION
            "A string identifying the devices attached to the
            output(s) of the UPS.  This object should be set by
            the administrator.(*)"
    ::= { upsIdent-second 6 }

upsIdentUPSSerialNumber-second OBJECT-TYPE
    SYNTAX     DisplayString (SIZE(0..31))
    MAX-ACCESS read-only
    STATUS     current
    DESCRIPTION
            "The UPS serial number"
    ::= { upsIdent-second 7 }
				
upsIdentComProtVersion-second OBJECT-TYPE
    SYNTAX     DisplayString (SIZE(0..15))
    MAX-ACCESS read-only
    STATUS     current
    DESCRIPTION
            "The IMV communication protocol version"
    ::= { upsIdent-second 8 }	
		
upsIdentOperatingTime-second OBJECT-TYPE
    SYNTAX     NonNegativeInteger32
    UNITS      "seconds"
    MAX-ACCESS read-only
    STATUS     current
    DESCRIPTION
            "The present value of the operating time.
             total 'on' time since UPS manufactured"
    ::= { upsIdent-second 9 }	
				
--
-- Battery Group Generic
--

upsBatteryStatus-second OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-second 1 }

upsSecondsOnBattery-second OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-second 2 }

upsEstimatedMinutesRemaining-second OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-second 3 }

upsEstimatedChargeRemaining-second OBJECT-TYPE
    SYNTAX     Integer32 (0..100)
    UNITS      "percent"
    MAX-ACCESS read-only
    STATUS     current
    DESCRIPTION
            "An estimate of the battery charge remaining expressed
            as a percent of full charge.(*)"
    ::= { upsBattery-second 4 }

upsBatteryVoltage-second OBJECT-TYPE
    SYNTAX     NonNegativeInteger32
    UNITS      "0.1 Volt DC"
    MAX-ACCESS read-only
    STATUS     current
    DESCRIPTION
            "The magnitude of the present battery voltage.(*)"
    ::= { upsBattery-second 5 }

upsBatteryCurrent-second OBJECT-TYPE
    SYNTAX     Integer32
    UNITS      "0.1 Amp DC"
    MAX-ACCESS read-only
    STATUS     current
    DESCRIPTION
            "The present battery current.(*)"
    ::= { upsBattery-second 6 }

upsBatteryTemperature-second OBJECT-TYPE
    SYNTAX     Integer32
    UNITS      "degrees Centigrade"
    MAX-ACCESS read-only
    STATUS     current
    DESCRIPTION
            "The ambient temperature at or near the UPS Battery
            casing.(*)"
    ::= { upsBattery-second 7 }

--
-- Input Group
--

upsInputLineBads-second OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-second 1 }

upsInputNumLines-second OBJECT-TYPE
    SYNTAX     NonNegativeInteger32
    MAX-ACCESS read-only
    STATUS     current
    DESCRIPTION
            "The number of input lines utilized in this device.
            This variable indicates the number of rows in the
            input table.(*)"
    ::= { upsInput-second 2 }

upsInputTable-second OBJECT-TYPE
    SYNTAX     SEQUENCE OF UpsInputEntry-second
    MAX-ACCESS not-accessible
    STATUS     current
    DESCRIPTION
            "A list of input table entries.  The number of entries
            is given by the value of upsInputNumLines.(*)"
    ::= { upsInput-second 3 }

upsInputEntry-second OBJECT-TYPE
    SYNTAX     UpsInputEntry-second
    MAX-ACCESS not-accessible
    STATUS     current
    DESCRIPTION
            "An entry containing information applicable to a
            particular input line.(*)"
    INDEX { upsInputLineIndex-second }
    ::= { upsInputTable-second 1 }

UpsInputEntry-second ::= SEQUENCE {
    upsInputLineIndex-second   PositiveInteger32,
    upsInputFrequency-second   NonNegativeInteger32,
    upsInputVoltage-second     NonNegativeInteger32,
    upsInputCurrent-second     NonNegativeInteger32,
    upsInputTruePower-second   NonNegativeInteger32,
    upsInputVoltageMin-second  NonNegativeInteger32,
    upsInputVoltageMax-second  NonNegativeInteger32
}

upsInputLineIndex-second OBJECT-TYPE
    SYNTAX     PositiveInteger32
    MAX-ACCESS not-accessible
    STATUS     current
    DESCRIPTION
            "The input line identifier.(*)"
    ::= { upsInputEntry-second 1 }

upsInputFrequency-second OBJECT-TYPE
    SYNTAX     NonNegativeInteger32
    UNITS      "0.1 Hertz"
    MAX-ACCESS read-only
    STATUS     current
    DESCRIPTION
            "The present input frequency.(*)"
    ::= { upsInputEntry-second 2 }

upsInputVoltage-second OBJECT-TYPE
    SYNTAX     NonNegativeInteger32
    UNITS      "RMS Volts"
    MAX-ACCESS read-only
    STATUS     current
    DESCRIPTION
            "The magnitude of the present input voltage.(*)"
    ::= { upsInputEntry-second 3 }

upsInputCurrent-second OBJECT-TYPE
    SYNTAX     NonNegativeInteger32
    UNITS      "0.1 RMS Amp"
    MAX-ACCESS read-only
    STATUS     current
    DESCRIPTION
            "The magnitude of the present input current.(*)"
    ::= { upsInputEntry-second 4 }

upsInputTruePower-second OBJECT-TYPE
    SYNTAX     NonNegativeInteger32
    UNITS      "Watts"
    MAX-ACCESS read-only
    STATUS     current
    DESCRIPTION
            "The magnitude of the present input true power.(*)"
    ::= { upsInputEntry-second 5 }

upsInputVoltageMin-second OBJECT-TYPE
    SYNTAX     NonNegativeInteger32
    UNITS      "RMS Volts"
    MAX-ACCESS read-only
    STATUS     current
    DESCRIPTION
            "The lowest magnitude of the input voltage since last read out."
    ::= { upsInputEntry-second 6 }

upsInputVoltageMax-second OBJECT-TYPE
    SYNTAX     NonNegativeInteger32
    UNITS      "RMS Volts"
    MAX-ACCESS read-only
    STATUS     current
    DESCRIPTION
            "The highest magnitude of the input voltage since last read out."
    ::= { upsInputEntry-second 7 }

--
-- The Output group.
--

upsOutputSource-second OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-second 1 }

upsOutputFrequency-second OBJECT-TYPE
    SYNTAX     NonNegativeInteger32
    UNITS      "0.1 Hertz"
    MAX-ACCESS read-only
    STATUS     current
    DESCRIPTION
            "The present output frequency.(*)"
    ::= { upsOutput-second 2 }

upsOutputNumLines-second OBJECT-TYPE
    SYNTAX     NonNegativeInteger32
    MAX-ACCESS read-only
    STATUS     current
    DESCRIPTION
            "The number of output lines utilized in this device.
            This variable indicates the number of rows in the
            output table.(*)"
    ::= { upsOutput-second 3 }

upsOutputTable-second OBJECT-TYPE
    SYNTAX     SEQUENCE OF UpsOutputEntry-second
    MAX-ACCESS not-accessible
    STATUS     current
    DESCRIPTION
            "A list of output table entries.  The number of
            entries is given by the value of upsOutputNumLines.(*)"
    ::= { upsOutput-second 4 }

upsOutputEntry-second OBJECT-TYPE
    SYNTAX     UpsOutputEntry-second
    MAX-ACCESS not-accessible
    STATUS     current
    DESCRIPTION
            "An entry containing information applicable to a
            particular output line.(*)"
    INDEX { upsOutputLineIndex-second }
    ::= { upsOutputTable-second 1 }

UpsOutputEntry-second ::= SEQUENCE {
    upsOutputLineIndex-second   PositiveInteger32,
    upsOutputVoltage-second     NonNegativeInteger32,
    upsOutputCurrent-second     NonNegativeInteger32,
    upsOutputPower-second       NonNegativeInteger32,
    upsOutputPercentLoad-second Integer32
}

upsOutputLineIndex-second OBJECT-TYPE
    SYNTAX     PositiveInteger32
    MAX-ACCESS not-accessible
    STATUS     current
    DESCRIPTION
            "The output line identifier.(*)"
    ::= { upsOutputEntry-second 1 }

upsOutputVoltage-second OBJECT-TYPE
    SYNTAX     NonNegativeInteger32
    UNITS      "RMS Volts"
    MAX-ACCESS read-only
    STATUS     current
    DESCRIPTION
            "The present output voltage.(*)"
    ::= { upsOutputEntry-second 2 }

upsOutputCurrent-second OBJECT-TYPE
    SYNTAX     NonNegativeInteger32
    UNITS      "0.1 RMS Amp"
    MAX-ACCESS read-only
    STATUS     current
    DESCRIPTION
            "The present output current.(*)"
    ::= { upsOutputEntry-second 3 }

upsOutputPower-second OBJECT-TYPE
    SYNTAX     NonNegativeInteger32
    UNITS      "Watts"
    MAX-ACCESS read-only
    STATUS     current
    DESCRIPTION
            "The present output true power.(*)"
    ::= { upsOutputEntry-second 4 }

upsOutputPercentLoad-second OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-second 5 }

--
-- The Bypass group generic.
--

upsBypassFrequency-second OBJECT-TYPE
    SYNTAX     NonNegativeInteger32
    UNITS      "0.1 Hertz"
    MAX-ACCESS read-only
    STATUS     current
    DESCRIPTION
            "The present bypass frequency.(*)"
    ::= { upsBypass-second 1 }

upsBypassNumLines-second OBJECT-TYPE
    SYNTAX     NonNegativeInteger32
    MAX-ACCESS read-only
    STATUS     current
    DESCRIPTION
            "The number of bypass lines utilized in this device.
            This entry indicates the number of rows in the bypass
            table.(*)"
    ::= { upsBypass-second 2 }

upsBypassTable-second OBJECT-TYPE
    SYNTAX     SEQUENCE OF UpsBypassEntry-second
    MAX-ACCESS not-accessible
    STATUS     current
    DESCRIPTION
            "A list of bypass table entries.  The number of
            entries is given by the value of upsBypassNumLines.(*)"
    ::= { upsBypass-second 3 }

upsBypassEntry-second OBJECT-TYPE
    SYNTAX     UpsBypassEntry-second
    MAX-ACCESS not-accessible
    STATUS     current
    DESCRIPTION
            "An entry containing information applicable to a
            particular bypass input.(*)"
    INDEX { upsBypassLineIndex-second }
    ::= { upsBypassTable-second 1 }

UpsBypassEntry-second ::= SEQUENCE {
    upsBypassLineIndex-second  PositiveInteger32,
    upsBypassVoltage-second    NonNegativeInteger32,
    upsBypassCurrent-second    NonNegativeInteger32,
    upsBypassPower-second      NonNegativeInteger32
}

upsBypassLineIndex-second OBJECT-TYPE
    SYNTAX     PositiveInteger32
    MAX-ACCESS not-accessible
    STATUS     current
    DESCRIPTION
            "The bypass line identifier.(*)"
    ::= { upsBypassEntry-second 1 }

upsBypassVoltage-second OBJECT-TYPE
    SYNTAX     NonNegativeInteger32
    UNITS      "RMS Volts"
    MAX-ACCESS read-only
    STATUS     current
    DESCRIPTION
            "The present bypass voltage.(*)"
    ::= { upsBypassEntry-second 2 }

upsBypassCurrent-second OBJECT-TYPE
    SYNTAX     NonNegativeInteger32
    UNITS      "0.1 RMS Amp"
    MAX-ACCESS read-only
    STATUS     current
    DESCRIPTION
            "The present bypass current.(*)"
    ::= { upsBypassEntry-second 3 }

upsBypassPower-second OBJECT-TYPE
    SYNTAX     NonNegativeInteger32
    UNITS      "Watts"
    MAX-ACCESS read-only
    STATUS     current
    DESCRIPTION
            "The present true power conveyed by the bypass.(*)"
    ::= { upsBypassEntry-second 4 }

--
-- The Alarm group generic.
--

upsAlarmsPresent-second OBJECT-TYPE
    SYNTAX     Gauge32
    MAX-ACCESS read-only
    STATUS     current
    DESCRIPTION
            "The present number of active alarm conditions.(*)"
    ::= { upsAlarm-second 1 }

upsAlarmTable-second OBJECT-TYPE
    SYNTAX     SEQUENCE OF UpsAlarmEntry-second
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-second 2 }

upsAlarmEntry-second OBJECT-TYPE
    SYNTAX     UpsAlarmEntry-second
    MAX-ACCESS not-accessible
    STATUS     current
    DESCRIPTION
            "An entry containing information applicable to a
            particular alarm.(*)"
    INDEX { upsAlarmId-second }
    ::= { upsAlarmTable-second 1 }

UpsAlarmEntry-second ::= SEQUENCE {
    upsAlarmId-second          PositiveInteger32,
    upsAlarmDescr-second       AutonomousType,
    upsAlarmTime-second       TimeStamp
}

upsAlarmId-second OBJECT-TYPE
    SYNTAX     PositiveInteger32
    MAX-ACCESS not-accessible
    STATUS     current
    DESCRIPTION
            "A unique identifier for an alarm condition.  This
            value must remain constant.(*)"
    ::= { upsAlarmEntry-second 1 }

upsAlarmDescr-second OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-second 2 }

upsAlarmTime-second OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-second 3 }

--
-- Well known alarm conditions generic.
--

upsAlarmBatteryBad-second OBJECT-IDENTITY
    STATUS     current
    DESCRIPTION
            "One or more batteries have been determined to require
            replacement.(*)"
    ::= { upsWellKnownAlarms-second  1 }

upsAlarmOnBattery-second OBJECT-IDENTITY
    STATUS     current
    DESCRIPTION
            "The UPS is drawing power from the batteries.(*)"
    ::= { upsWellKnownAlarms-second  2 }

upsAlarmLowBattery-second OBJECT-IDENTITY
    STATUS     current
    DESCRIPTION
            "The remaining battery run-time is less than or equal
            to upsConfigLowBattTime.(*)"
    ::= { upsWellKnownAlarms-second  3 }

upsAlarmDepletedBattery-second OBJECT-IDENTITY
    STATUS     current
    DESCRIPTION
            "The UPS will be unable to sustain the present load
            when and if the utility power is lost.(*)"
    ::= { upsWellKnownAlarms-second  4 }

upsAlarmTempBad-second OBJECT-IDENTITY
    STATUS     current
    DESCRIPTION
            "A temperature is out of tolerance.(*)"
    ::= { upsWellKnownAlarms-second  5 }

upsAlarmInputBad-second OBJECT-IDENTITY
    STATUS     current
    DESCRIPTION
            "An input condition is out of tolerance.(*)"
    ::= { upsWellKnownAlarms-second  6 }

upsAlarmOutputBad-second OBJECT-IDENTITY
    STATUS     current
    DESCRIPTION
            "An output condition (other than OutputOverload) is
            out of tolerance.(*)"
    ::= { upsWellKnownAlarms-second  7 }

upsAlarmOutputOverload-second OBJECT-IDENTITY
    STATUS     current
    DESCRIPTION
            "The output load exceeds the UPS output capacity.(*)"
    ::= { upsWellKnownAlarms-second  8 }

upsAlarmOnBypass-second OBJECT-IDENTITY
    STATUS     current
    DESCRIPTION
            "The Bypass is presently engaged on the UPS.(*)"
    ::= { upsWellKnownAlarms-second  9 }

upsAlarmBypassBad-second OBJECT-IDENTITY
    STATUS     current
    DESCRIPTION
            "The Bypass is out of tolerance.(*)"
    ::= { upsWellKnownAlarms-second 10 }

upsAlarmOutputOffAsRequested-second OBJECT-IDENTITY
    STATUS     current
    DESCRIPTION
            "The UPS has shutdown as requested, i.e., the output
            is off.(*)"
    ::= { upsWellKnownAlarms-second 11 }

upsAlarmUpsOffAsRequested-second OBJECT-IDENTITY
    STATUS     current
    DESCRIPTION
            "The entire UPS has shutdown as commanded.(*)"
    ::= { upsWellKnownAlarms-second 12 }

upsAlarmChargerFailed-second OBJECT-IDENTITY
    STATUS     current
    DESCRIPTION
            "An uncorrected problem has been detected within the
            UPS charger subsystem.(*)"
    ::= { upsWellKnownAlarms-second 13 }

upsAlarmUpsOutputOff-second OBJECT-IDENTITY
    STATUS     current
    DESCRIPTION
            "The output of the UPS is in the off state.(*)"
    ::= { upsWellKnownAlarms-second 14 }

upsAlarmUpsSystemOff-second OBJECT-IDENTITY
    STATUS     current
    DESCRIPTION
            "The UPS system is in the off state.(*)"
    ::= { upsWellKnownAlarms-second 15 }

upsAlarmFanFailure-second OBJECT-IDENTITY
    STATUS     current
    DESCRIPTION
            "The failure of one or more fans in the UPS has been
            detected.(*)"
    ::= { upsWellKnownAlarms-second 16 }

upsAlarmFuseFailure-second OBJECT-IDENTITY
    STATUS     current
    DESCRIPTION
            "The failure of one or more fuses has been detected.(*)"
    ::= { upsWellKnownAlarms-second 17 }

upsAlarmGeneralFault-second OBJECT-IDENTITY
    STATUS     current
    DESCRIPTION
            "A general fault in the UPS has been detected.(*)"
    ::= { upsWellKnownAlarms-second 18 }

upsAlarmDiagnosticTestFailed-second OBJECT-IDENTITY
    STATUS     current
    DESCRIPTION
            "The result of the last diagnostic test indicates a
            failure.(*)"
    ::= { upsWellKnownAlarms-second 19 }

upsAlarmCommunicationsLost-second OBJECT-IDENTITY
    STATUS     current
    DESCRIPTION
            "A problem has been encountered in the communications
            between the agent and the UPS.(*)"
    ::= { upsWellKnownAlarms-second 20 }

upsAlarmAwaitingPower-second OBJECT-IDENTITY
    STATUS     current
    DESCRIPTION
            "The UPS output is off and the UPS is awaiting the
            return of input power.(*)"
    ::= { upsWellKnownAlarms-second 21 }

upsAlarmShutdownPending-second OBJECT-IDENTITY
    STATUS     current
    DESCRIPTION
            "A upsShutdownAfterDelay countdown is underway.(*)"
    ::= { upsWellKnownAlarms-second 22 }

upsAlarmShutdownImminent-second OBJECT-IDENTITY
    STATUS     current
    DESCRIPTION
            "The UPS will turn off power to the load in less than
            5 seconds; this may be either a timed shutdown or a
            low battery shutdown.(*)"
    ::= { upsWellKnownAlarms-second 23 }

upsAlarmTestInProgress-second OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-second 24 }

upsAlarmReceptacleOff-second OBJECT-IDENTITY
    STATUS     current
    DESCRIPTION
            "The receptacle are switch off    "
    ::= { upsWellKnownAlarms-second 25 }

upsAlarmMaskA-second OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-second 4 }

--
-- The Test Group generic
--

upsTestId-second OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-second 1 }

-- see [6] for more information on the semantics of objects with
-- syntax of TestAndIncr

upsTestSpinLock-second OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-second 2 }

upsTestResultsSummary-second OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-second 3 }

upsTestResultsDetail-second OBJECT-TYPE
    SYNTAX     DisplayString (SIZE (0..255))
    MAX-ACCESS read-only
    STATUS     current
    DESCRIPTION
            "Additional information about upsTestResultsSummary.
            If no additional information available, a zero length
            string is returned.(*)"
    ::= { upsTest-second 4 }

upsTestStartTime-second OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-second 5 }

upsTestElapsedTime-second OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-second 6 }

--
-- Well known tests generic.
--

upsTestNoTestsInitiated-second OBJECT-IDENTITY
    STATUS     current
    DESCRIPTION
            "No tests have been initiated and no test is in
            progress.(*)"
    ::= { upsWellKnownTests-second  1 }

upsTestAbortTestInProgress-second OBJECT-IDENTITY
    STATUS     current
    DESCRIPTION
            "The test in progress is to be aborted / the test in
            progress was aborted.(*)"
    ::= { upsWellKnownTests-second  2 }

upsTestGeneralSystemsTest-second OBJECT-IDENTITY
    STATUS     current
    DESCRIPTION
            "The manufacturer's standard test of UPS device
            systems.(*)"
    ::= { upsWellKnownTests-second  3 }

upsTestQuickBatteryTest-second OBJECT-IDENTITY
    STATUS     current
    DESCRIPTION
            "A test that is sufficient to determine if the battery
            needs replacement.(*)"
    ::= { upsWellKnownTests-second  4 }

upsTestDeepBatteryCalibration-second OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-second  5 }

--
-- The Control group generic.
--

upsShutdownType-second OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-second 1 }

upsShutdownAfterDelay-second OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-second 2 }

upsStartupAfterDelay-second OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-second 3 }

upsRebootWithDuration-second OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-second 4 }

upsAutoRestart-second OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-second 5 }

upsReceptaclesNum-second OBJECT-TYPE
    SYNTAX     NonNegativeInteger32
    MAX-ACCESS read-only
    STATUS     current
    DESCRIPTION
            "The number of receptacles utilized in this device.
            This entry indicates the number of rows in the receptacle
            table."
    ::= { upsControl-second 6 }

upsReceptacleTable-second OBJECT-TYPE
    SYNTAX     SEQUENCE OF UpsReceptacleEntry-second
    MAX-ACCESS not-accessible
    STATUS     current
    DESCRIPTION
            "A list of receptacle table entries.  The number of
            entries is given by the value of upsReceptacleNum."
    ::= { upsControl-second 7 }

upsReceptacleEntry-second OBJECT-TYPE
    SYNTAX     UpsReceptacleEntry-second
    MAX-ACCESS not-accessible
    STATUS     current
    DESCRIPTION
            "An entry containing information applicable to a
            particular receptacle."
    INDEX { upsReceptacleLineIndex-second }
    ::= { upsReceptacleTable-second 1 }

UpsReceptacleEntry-second ::= SEQUENCE {
    upsReceptacleLineIndex-second  PositiveInteger32,
    upsReceptacleOnOff-second      Integer32    
}

upsReceptacleLineIndex-second OBJECT-TYPE
    SYNTAX     PositiveInteger32
    MAX-ACCESS not-accessible
    STATUS     current
    DESCRIPTION
            "The receptacle line identifier."
    ::= { upsReceptacleEntry-second 1 }

upsReceptacleOnOff-second OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-second 2 }

upsUPSMode-second OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-second 8 }

upsRectifierOnOff-second OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-second 9 }

upsBatteryChargeMethod-second OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-second 10 }

upsInverterOnOff-second OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-second 11 }

upsBypassOnOff-second OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-second 12 }

upsLoadSource-second OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-second 13 }
	
--
-- The Configuration group generic.
--

upsConfigInputVoltage-second OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-second 1 }

upsConfigInputFreq-second OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-second 2 }

upsConfigOutputVoltage-second OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-second 3 }

upsConfigOutputFreq-second OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-second 4 }

upsConfigOutputVA-second OBJECT-TYPE
    SYNTAX     NonNegativeInteger32
    UNITS      "Volt-Amps"
    MAX-ACCESS read-only
    STATUS     current
    DESCRIPTION
            "The magnitude of the nominal Volt-Amp rating.(*)"
    ::= { upsConfig-second 5 }

upsConfigOutputPower-second OBJECT-TYPE
    SYNTAX     NonNegativeInteger32
    UNITS      "Watts"
    MAX-ACCESS read-only
    STATUS     current
    DESCRIPTION
            "The magnitude of the nominal true power rating.(*)"
    ::= { upsConfig-second 6 }

upsConfigLowBattTime-second OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-second 7 }

upsConfigAudibleStatus-second OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-second 8 }

upsConfigLowVoltageTransferPoint-second OBJECT-TYPE
    SYNTAX     NonNegativeInteger32
    UNITS      "RMS Volts"
    MAX-ACCESS read-write
    STATUS     current
    DESCRIPTION
            "The minimum input line voltage allowed before the UPS
            system transfers to battery backup.(*)"
    ::= { upsConfig-second 9 }

upsConfigHighVoltageTransferPoint-second OBJECT-TYPE
    SYNTAX     NonNegativeInteger32
    UNITS      "RMS Volts"
    MAX-ACCESS read-write
    STATUS     current
    DESCRIPTION
            "The maximum line voltage allowed before the UPS
            system transfers to battery backup.(*)"
    ::= { upsConfig-second 10 }

upsConfigBatteryCapacity-second OBJECT-TYPE
    SYNTAX     NonNegativeInteger32
    UNITS      "Amps Hours"
    MAX-ACCESS read-write
    STATUS     current
    DESCRIPTION
            "The installed battery capacity. This value is the 'factory'-value,
             not the value after calibration."
    ::= { upsConfig-second 11 }

upsConfigBatteryChargeCurrent-second OBJECT-TYPE
    SYNTAX     NonNegativeInteger32
    UNITS      "0.1 Amp DC"
    MAX-ACCESS read-write
    STATUS     current
    DESCRIPTION
            "The maximum battery charge current, including external chargers."
    ::= { upsConfig-second 12 }						

upsConfigNoLoadShutdown-second OBJECT-TYPE
    SYNTAX     Integer32 {
        disabled(1),
        enabled(2)
    }
    MAX-ACCESS read-write
    STATUS     current
    DESCRIPTION
            "Dis- or enable 'no load' shutdown from the contact interface."
    ::= { upsConfig-second 13 }
	
upsConfigStartDelay-second OBJECT-TYPE
    SYNTAX     PositiveInteger32
    UNITS      "minutes"				
    MAX-ACCESS read-write
    STATUS     current
    DESCRIPTION
            "Minimum required autonomy time before the UPS may perform an
             autorestart."
    ::= { upsConfig-second 14 }

--
-- The GetSet group generic.
--

upsEventGetNext-second OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-second 1 }

upsEventGetPrevious-second OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-second 2 }
				
upsEventSetStartingTimeStamp-second OBJECT-TYPE
    SYNTAX     NonNegativeInteger32
    MAX-ACCESS read-write
    STATUS     current
    DESCRIPTION
            "The timestamp which is used as starting point for downloading
             events from the UPS event buffer"
    ::= { upsGetSet-second 3 }				

upsEventRetreiveCurrentTimeStamp-second OBJECT-TYPE
    SYNTAX     NonNegativeInteger32
    MAX-ACCESS read-only
    STATUS     current
    DESCRIPTION
            "The current timestamp is retreived from the UPS"
    ::= { upsGetSet-second 4 }				

upsEventTableSize-second OBJECT-TYPE
    SYNTAX     NonNegativeInteger32
    MAX-ACCESS read-only
    STATUS     current
    DESCRIPTION
            "The number of entries in the event table.
            This object indicates the number of rows in the event table."
    ::= { upsGetSet-second 5 }

upsEventTable-second OBJECT-TYPE
    SYNTAX     SEQUENCE OF UpsEventEntry-second
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-second 6 }

upsEventEntry-second OBJECT-TYPE
    SYNTAX     UpsEventEntry-second
    MAX-ACCESS not-accessible
    STATUS     current
    DESCRIPTION
            "An entry containing information applicable to a
            particular event."
    INDEX { upsEventLineIndex-second }
    ::= { upsEventTable-second 1 }

UpsEventEntry-second ::= SEQUENCE {
    upsEventLineIndex-second PositiveInteger32,
    upsEventCode-second      Integer32,
    upsEventStatus-second    NonNegativeInteger32,
    upsEventTime-second      NonNegativeInteger32
}

upsEventLineIndex-second OBJECT-TYPE
    SYNTAX     PositiveInteger32
    MAX-ACCESS not-accessible
    STATUS     current
    DESCRIPTION
            "The event line identifier."
    ::= { upsEventEntry-second 1 }

upsEventCode-second OBJECT-TYPE
    SYNTAX     NonNegativeInteger32
    MAX-ACCESS read-only
    STATUS     current
    DESCRIPTION
            "The event code in numerical format."
    ::= { upsEventEntry-second 2 }

upsEventStatus-second OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-second 3 }

upsEventTime-second OBJECT-TYPE
    SYNTAX     NonNegativeInteger32
    MAX-ACCESS read-only
    STATUS     current
    DESCRIPTION
            "The timestamp of the moment the event was generated."
    ::= { upsEventEntry-second 4 }

upsParametersRead-second OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-second 7 }

upsParametersWrite-second OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-second 8 }

upsParametersStartAddress-second OBJECT-TYPE
    SYNTAX     NonNegativeInteger32
    MAX-ACCESS read-write
    STATUS     current
    DESCRIPTION
            "The address which is used as starting point for downloading
             parameters from the UPS"
    ::= { upsGetSet-second 9 }				

upsParameterTableSize-second OBJECT-TYPE
    SYNTAX     NonNegativeInteger32
    MAX-ACCESS read-only
    STATUS     current
    DESCRIPTION
            "The number of entries in the parameter table.
            This object indicates the number of rows in the parameter table."
    ::= { upsGetSet-second 10 }

upsParameterTable-second OBJECT-TYPE
    SYNTAX     SEQUENCE OF UpsParameterEntry-second
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-second 11 }

upsParameterEntry-second OBJECT-TYPE
    SYNTAX     UpsParameterEntry-second
    MAX-ACCESS not-accessible
    STATUS     current
    DESCRIPTION
            "An entry containing information applicable to a
            particular parameter."
    INDEX { upsParameterLineIndex-second }
    ::= { upsParameterTable-second 1 }

UpsParameterEntry-second ::= SEQUENCE {
    upsParameterLineIndex-second PositiveInteger32,
    upsParameterValue-second     Integer32   
}

upsParameterLineIndex-second OBJECT-TYPE
    SYNTAX     PositiveInteger32
    MAX-ACCESS not-accessible
    STATUS     current
    DESCRIPTION
            "The parameter line identifier."
    ::= { upsParameterEntry-second 1 }

upsParameterValue-second OBJECT-TYPE
    SYNTAX     Integer32
    MAX-ACCESS read-write
    STATUS     current
    DESCRIPTION
            "The parameter value in numerical format."
    ::= { upsParameterEntry-second 2 }

upsStatus-second OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-second 12 }

upsMainsStatisticsMBfail-second OBJECT-TYPE
    SYNTAX     NonNegativeInteger32
    MAX-ACCESS read-only
    STATUS     current
    DESCRIPTION
            "Count of main bypass failures (>200 ms), since UPS installation."
    ::= { upsGetSet-second 13 }

upsMainsStatisticsMRfail-second OBJECT-TYPE
    SYNTAX     NonNegativeInteger32
    MAX-ACCESS read-only
    STATUS     current
    DESCRIPTION
            "Count of mains rectifier failures (>200 ms), since UPS installation."
    ::= { upsGetSet-second 14 }
		
upsMainsStatisticsB2-second OBJECT-TYPE
    SYNTAX     NonNegativeInteger32
    MAX-ACCESS read-only
    STATUS     current
    DESCRIPTION
            "Count of transients on the mains bypass (0..2 ms), during the last 7 days."
    ::= { upsGetSet-second 15 }

upsMainsStatisticsB5-second OBJECT-TYPE
    SYNTAX     NonNegativeInteger32
    MAX-ACCESS read-only
    STATUS     current
    DESCRIPTION
            "Count of transients on the mains bypass (2..5 ms), during the last 7 days."
    ::= { upsGetSet-second 16 }

upsMainsStatisticsB10-second OBJECT-TYPE
    SYNTAX     NonNegativeInteger32
    MAX-ACCESS read-only
    STATUS     current
    DESCRIPTION
            "Count of transients on the mains bypass (5..10 ms), during the last 7 days."
    ::= { upsGetSet-second 17 }

upsMainsStatisticsB200-second OBJECT-TYPE
    SYNTAX     NonNegativeInteger32
    MAX-ACCESS read-only
    STATUS     current
    DESCRIPTION
            "Count of transients on the mains bypass (10..200 ms), during the last 7 days."
    ::= { upsGetSet-second 18 }

upsMainsStatisticsBypRel-second OBJECT-TYPE
    SYNTAX     NonNegativeInteger32
    MAX-ACCESS read-only
    STATUS     current
    DESCRIPTION
            "Bypass reliability degree [0..100%;255]. The value NOSUCHNAME means 'not available'."
    ::= { upsGetSet-second 19 }

upsTime-second OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-secondERROR,              meaning 'command not supported'. It is possible to know which is the timestamp 
             format supported by the UPS, by issuing a read-command or by reading events, 
             which includes timestamps."
    ::= { upsGetSet-second 20 }

upsRequestPermission-second OBJECT-TYPE
    SYNTAX     DisplayString (SIZE(0..63))
    MAX-ACCESS write-only
    STATUS     current
    DESCRIPTION
            "An encrypted code is send to enable use of restricted write objects during
             a limited period of time."
    ::= { upsGetSet-second 21 }

upsEventGetCode-second OBJECT-TYPE
    SYNTAX     Integer32
    MAX-ACCESS write-only
    STATUS     current
    DESCRIPTION
            "The code which is used as starting point to downloading the events from the 
            UPS event buffer."
    ::= { upsGetSet-second 22 }    
    
upsEventSpinLock-second OBJECT-TYPE
    SYNTAX     TestAndIncr
    MAX-ACCESS read-write
    STATUS     current
    DESCRIPTION
            "A spin lock on the event subsystem. "

    ::= { upsGetSet-second 23 }
    
upsParameterSpinLock-second OBJECT-TYPE
    SYNTAX     TestAndIncr
    MAX-ACCESS read-write
    STATUS     current
    DESCRIPTION
            "A spin lock on the parameters subsystem. "

    ::= { upsGetSet-second 24 }

--
-- GE Trap group generic
--

upsAlarmBatteryBad-second TRAP-TYPE
    ENTERPRISE geUPSTraps-second
    VARIABLES  { trapArg  }
    DESCRIPTION
            "One or more batteries have been determined to require
            replacement."
    ::= 1

upsAlarmOnBattery-second TRAP-TYPE
    ENTERPRISE geUPSTraps-second
    VARIABLES  { trapArg , upsSecondsOnBattery-second  }
    DESCRIPTION
            "An On Battery condition is restored."
    ::= 2

upsAlarmLowBattery-second TRAP-TYPE
    ENTERPRISE geUPSTraps-second
    VARIABLES  { trapArg  }
    DESCRIPTION
            "The remaining battery run-time is less than or equal
            to upsConfigLowBattTime."
    ::= 3

upsAlarmDepletedBattery-second TRAP-TYPE
    ENTERPRISE geUPSTraps-second
    VARIABLES  { trapArg  }
    DESCRIPTION
            "The UPS will be unable to sustain the present load
            when and if the utility power is lost)"
    ::= 4

upsAlarmTempBad-second TRAP-TYPE
    ENTERPRISE geUPSTraps-second
    VARIABLES  { trapArg , upsBatteryTemperature }
    DESCRIPTION
            "A temperature is out of tolerance."
    ::= 5

upsAlarmInputBad-second TRAP-TYPE
    ENTERPRISE geUPSTraps-second
    VARIABLES  { trapArg  }
    DESCRIPTION
            "An input condition is out of tolerance."
    ::= 6

upsAlarmOutputBad-second TRAP-TYPE
    ENTERPRISE geUPSTraps-second
    VARIABLES  { trapArg  }
    DESCRIPTION
            "An output condition (other than OutputOverload) is
            out of tolerance."
    ::= 7

upsAlarmOutputOverload-second TRAP-TYPE
    ENTERPRISE geUPSTraps-second
    VARIABLES  { trapArg , upsOutputPercentLoad-second }
    DESCRIPTION
            "The output load exceeds the UPS output capacity."
    ::= 8

upsAlarmOnBypass-second TRAP-TYPE
    ENTERPRISE geUPSTraps-second
    VARIABLES  { trapArg  }
    DESCRIPTION
            "The Bypass is presently engaged on the UPS."
    ::= 9

upsAlarmBypassBad-second TRAP-TYPE
    ENTERPRISE geUPSTraps-second
    VARIABLES  { trapArg  }
    DESCRIPTION
            "The Bypass is out of tolerance."
    ::= 10

upsAlarmOutputOffAsRequested-second TRAP-TYPE
    ENTERPRISE geUPSTraps-second
    VARIABLES  { trapArg  }
    DESCRIPTION
            "The UPS has shutdown as requested, i.e., the output
            is off."
    ::= 11

upsAlarmUpsOffAsRequested-second TRAP-TYPE
    ENTERPRISE geUPSTraps-second-second
    VARIABLES  { trapArg  }
    DESCRIPTION
            "The entire UPS has shutdown as commanded."
    ::= 12

upsAlarmChargerFailed-second TRAP-TYPE
    ENTERPRISE geUPSTraps-second
    VARIABLES  { trapArg  }
    DESCRIPTION
            "An uncorrected problem has been detected within the
            UPS charger subsystem."
    ::= 13

upsAlarmUpsOutputOff-second TRAP-TYPE
    ENTERPRISE geUPSTraps-second
    VARIABLES  { trapArg  }
    DESCRIPTION
            "The output of the UPS is in the off state."
    ::= 14

upsAlarmUpsSystemOff-second TRAP-TYPE
    ENTERPRISE geUPSTraps-second
    VARIABLES  { trapArg  }
    DESCRIPTION
            "The UPS system is in the off state."
    ::= 15

upsAlarmFanFailure-second TRAP-TYPE
    ENTERPRISE geUPSTraps-second
    VARIABLES  { trapArg  }
    DESCRIPTION
            "The failure of one or more fans in the UPS has been
            detected."
    ::= 16

upsAlarmFuseFailure-second TRAP-TYPE
    ENTERPRISE geUPSTraps-second
    VARIABLES  { trapArg  }
    DESCRIPTION
            "The failure of one or more fuses has been detected."
    ::= 17

upsAlarmGeneralFault-second TRAP-TYPE
    ENTERPRISE geUPSTraps-second
    VARIABLES  { trapArg  }
    DESCRIPTION
            "A general fault in the UPS has been detected."
    ::= 18

upsAlarmDiagnosticTestFailed-second TRAP-TYPE
    ENTERPRISE geUPSTraps-second
    VARIABLES  { trapArg  }
    DESCRIPTION
            "The result of the last diagnostic test indicates a
            failure."
    ::= 19

upsAlarmCommunicationsLost-second TRAP-TYPE
    ENTERPRISE geUPSTraps-second
    VARIABLES  { trapArg  }
    DESCRIPTION
            "A problem has been encountered in the communication
            between the agent and the UPS."
    ::= 20
    
upsAlarmAwaitingPower-second TRAP-TYPE
    ENTERPRISE geUPSTraps-second
    VARIABLES  { trapArg  }
    DESCRIPTION
            "The UPS output is off and the UPS is awaiting the
            return of the input power (*)."
    ::= 21    

upsAlarmShutdownPending-second TRAP-TYPE
    ENTERPRISE geUPSTraps-second
    VARIABLES  { trapArg , upsShutdownAfterDelay-second }
    DESCRIPTION
            "A upsShutdownAfterDelay countdown is underway."
    ::= 22

upsAlarmShutdownImminent-second TRAP-TYPE
    ENTERPRISE geUPSTraps-second
    VARIABLES  { trapArg  }
    DESCRIPTION
            "The UPS will turn off power to the load in less than
            5 seconds; this may be either a timed shutdown or a
            low battery shutdown."
    ::= 23

upsAlarmTestInProgress-second TRAP-TYPE
    ENTERPRISE geUPSTraps-second
    VARIABLES  { trapArg , upsTestId-second }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-second TRAP-TYPE
    ENTERPRISE geUPSTraps-second
    VARIABLES  { trapArg  }
    DESCRIPTION
            "A receptacle has been switched off."
    ::= 25

upsAlarmBatteryBadRestored-second TRAP-TYPE
    ENTERPRISE geUPSTraps-second
    VARIABLES  { trapArg  }
    DESCRIPTION
            "A Battery bad condition is restored."
    ::= 33

upsAlarmOnBatteryRestored-second TRAP-TYPE
    ENTERPRISE geUPSTraps-second
    VARIABLES  { trapArg  }
    DESCRIPTION
            "The UPS is drawing power from mains again."
    ::= 34

upsAlarmLowBatteryRestored-second TRAP-TYPE
    ENTERPRISE geUPSTraps-second
    VARIABLES  { trapArg  }
    DESCRIPTION
            "A Low Battery condition is restored."
    ::= 35

upsAlarmDepletedBatteryRestored-second TRAP-TYPE
    ENTERPRISE geUPSTraps-second
    VARIABLES  { trapArg  }
    DESCRIPTION
            "A Depleted Battery condition is restored."
    ::= 36

upsAlarmTempBadRestored-second TRAP-TYPE
    ENTERPRISE geUPSTraps-second
    VARIABLES  { trapArg  }
    DESCRIPTION
            "A bad temperature condition is restored."
    ::= 37

upsAlarmInputBadRestored-second TRAP-TYPE
    ENTERPRISE geUPSTraps-second
    VARIABLES  { trapArg  }
    DESCRIPTION
            "An input bad condition is restored."
    ::= 38

upsAlarmOutputBadRestored-second TRAP-TYPE
    ENTERPRISE geUPSTraps-second
    VARIABLES  { trapArg  }
    DESCRIPTION
            "An output bad condition is restored."
    ::= 39

upsAlarmOutputOverloadRestored-second TRAP-TYPE
    ENTERPRISE geUPSTraps-second
    VARIABLES  { trapArg  }
    DESCRIPTION
            "An output overload condition is restored."
    ::= 40

upsAlarmOnBypassRestored-second TRAP-TYPE
    ENTERPRISE geUPSTraps-second
    VARIABLES  { trapArg  }
    DESCRIPTION
            "An On Bypass condition is restored."
    ::= 41

upsAlarmBypassBadRestored-second TRAP-TYPE
    ENTERPRISE geUPSTraps-second
    VARIABLES  { trapArg  }
    DESCRIPTION
            "A Bypass bad condition is restored."
    ::= 42

upsAlarmOutputOffAsRequestedRestored-second TRAP-TYPE
    ENTERPRISE geUPSTraps-second
    VARIABLES  { trapArg  }
    DESCRIPTION
            "A request shutdown has been restored."
    ::= 43

upsAlarmUpsOffAsRequestedRestored-second TRAP-TYPE
    ENTERPRISE geUPSTraps-second-second
    VARIABLES  { trapArg  }
    DESCRIPTION
            "A entire UPS command has been restored."
    ::= 44

upsAlarmChargerFailedRestored-second TRAP-TYPE
    ENTERPRISE geUPSTraps-second
    VARIABLES  { trapArg  }
    DESCRIPTION
            "A Charger Failer condition is restored."
    ::= 45

upsAlarmUpsOutputOn-second TRAP-TYPE
    ENTERPRISE geUPSTraps-second
    VARIABLES  { trapArg  }
    DESCRIPTION
            "The output of the UPS switched in the on state."
    ::= 46

upsAlarmUpsSystemOn-second TRAP-TYPE
    ENTERPRISE geUPSTraps-second
    VARIABLES  { trapArg  }
    DESCRIPTION
            "The UPS system is switched in the on state."
    ::= 47

upsAlarmFanFailureRestored-second TRAP-TYPE
    ENTERPRISE geUPSTraps-second
    VARIABLES  { trapArg  }
    DESCRIPTION
            "A Fan failure condition is restored."
    ::= 48

upsAlarmFuseFailureRestored-second TRAP-TYPE
    ENTERPRISE geUPSTraps-second
    VARIABLES  { trapArg  }
    DESCRIPTION
            "A Fuse failure condition is restored."
    ::= 49

upsAlarmGeneralFaultRestored-second TRAP-TYPE
    ENTERPRISE geUPSTraps-second
    VARIABLES  { trapArg  }
    DESCRIPTION
            "A general fault is restored."
    ::= 50

upsAlarmDiagnosticTestFailedRestored-second TRAP-TYPE
    ENTERPRISE geUPSTraps-second
    VARIABLES  { trapArg  }
    DESCRIPTION
            "A last diagnostic test indicates a failure is 
            restored."
    ::= 51

upsAlarmCommunicationsLostRestored-second TRAP-TYPE
    ENTERPRISE geUPSTraps-second
    VARIABLES  { trapArg  }
    DESCRIPTION
            "A problem in the communication between the agent 
            and the UPS is restored."
    ::= 52
    
upsAlarmAwaitingPowerRestored-second TRAP-TYPE
    ENTERPRISE geUPSTraps-second
    VARIABLES  { trapArg  }
    DESCRIPTION
            "A awaiting power condition is restored (*)."
    ::= 53    

upsAlarmShutdownPendingRestored-second TRAP-TYPE
    ENTERPRISE geUPSTraps-second
    VARIABLES  { trapArg , upsShutdownAfterDelay-second }
    DESCRIPTION
            "A upsShutdownAfterDelay countdown is restored."
    ::= 54

upsAlarmShutdownImminentRestored-second TRAP-TYPE
    ENTERPRISE geUPSTraps-second
    VARIABLES  { trapArg  }
    DESCRIPTION
            "A shutdown imminent condition is restored."
    ::= 55

upsAlarmTestInProgressRestored-second TRAP-TYPE
    ENTERPRISE geUPSTraps-second
    VARIABLES  { trapArg , upsTestId-second }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-second TRAP-TYPE
    ENTERPRISE geUPSTraps-second
    VARIABLES  { trapArg  }
    DESCRIPTION
            "A measurement value reached a value below its low-level threshold."
    ::= 129

upsAlarmValueHigh-second TRAP-TYPE
    ENTERPRISE geUPSTraps-second
    VARIABLES  { trapArg  }
    DESCRIPTION
            "A measurement value reached a value higher than its high-level threshold."
    ::= 130

upsAlarmValueLowRestored-second TRAP-TYPE
    ENTERPRISE geUPSTraps-second
    VARIABLES  { trapArg  }
    DESCRIPTION
            "A ValueLow alarm condition is restored."
    ::= 133

upsAlarmValueHighRestored-second TRAP-TYPE
    ENTERPRISE geUPSTraps-second
    VARIABLES  { trapArg }
    DESCRIPTION
            "A ValueHigh alarm condition is restored."
    ::= 134


--
-- The Device Identification group. Third
--      All objects in this group except for upsIdentName and
--      upsIdentAttachedDevices are set at device initialization
--      and remain static.
--

upsIdentManufacturer-third OBJECT-TYPE
    SYNTAX     DisplayString (SIZE (0..31))
    MAX-ACCESS read-only
    STATUS     current
    DESCRIPTION
            "The name of the UPS manufacturer.(*)"
    ::= { upsIdent-third 1 }

upsIdentModel-third OBJECT-TYPE
    SYNTAX     DisplayString (SIZE (0..63))
    MAX-ACCESS read-only
    STATUS     current
    DESCRIPTION
            "The UPS Model designation.(*)"
    ::= { upsIdent-third 2 }

upsIdentUPSSoftwareVersion-third OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-third 3 }

upsIdentAgentSoftwareVersion-third OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-third 4 }

upsIdentName-third OBJECT-TYPE
    SYNTAX     DisplayString (SIZE(0..63))
    MAX-ACCESS read-write
    STATUS     current
    DESCRIPTION
            "A string identifying the UPS.  This object should be
            set by the administrator.(*)"
    ::= { upsIdent-third 5 }

upsIdentAttachedDevices-third OBJECT-TYPE
    SYNTAX     DisplayString (SIZE(0..63))
    MAX-ACCESS read-write
    STATUS     current
    DESCRIPTION
            "A string identifying the devices attached to the
            output(s) of the UPS.  This object should be set by
            the administrator.(*)"
    ::= { upsIdent-third 6 }

upsIdentUPSSerialNumber-third OBJECT-TYPE
    SYNTAX     DisplayString (SIZE(0..31))
    MAX-ACCESS read-only
    STATUS     current
    DESCRIPTION
            "The UPS serial number"
    ::= { upsIdent-third 7 }
				
upsIdentComProtVersion-third OBJECT-TYPE
    SYNTAX     DisplayString (SIZE(0..15))
    MAX-ACCESS read-only
    STATUS     current
    DESCRIPTION
            "The IMV communication protocol version"
    ::= { upsIdent-third 8 }	
		
upsIdentOperatingTime-third OBJECT-TYPE
    SYNTAX     NonNegativeInteger32
    UNITS      "seconds"
    MAX-ACCESS read-only
    STATUS     current
    DESCRIPTION
            "The present value of the operating time.
             total 'on' time since UPS manufactured"
    ::= { upsIdent-third 9 }	
				
--
-- Battery Group Generic
--

upsBatteryStatus-third OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-third 1 }

upsSecondsOnBattery-third OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-third 2 }

upsEstimatedMinutesRemaining-third OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-third 3 }

upsEstimatedChargeRemaining-third OBJECT-TYPE
    SYNTAX     Integer32 (0..100)
    UNITS      "percent"
    MAX-ACCESS read-only
    STATUS     current
    DESCRIPTION
            "An estimate of the battery charge remaining expressed
            as a percent of full charge.(*)"
    ::= { upsBattery-third 4 }

upsBatteryVoltage-third OBJECT-TYPE
    SYNTAX     NonNegativeInteger32
    UNITS      "0.1 Volt DC"
    MAX-ACCESS read-only
    STATUS     current
    DESCRIPTION
            "The magnitude of the present battery voltage.(*)"
    ::= { upsBattery-third 5 }

upsBatteryCurrent-third OBJECT-TYPE
    SYNTAX     Integer32
    UNITS      "0.1 Amp DC"
    MAX-ACCESS read-only
    STATUS     current
    DESCRIPTION
            "The present battery current.(*)"
    ::= { upsBattery-third 6 }

upsBatteryTemperature-third OBJECT-TYPE
    SYNTAX     Integer32
    UNITS      "degrees Centigrade"
    MAX-ACCESS read-only
    STATUS     current
    DESCRIPTION
            "The ambient temperature at or near the UPS Battery
            casing.(*)"
    ::= { upsBattery-third 7 }

--
-- Input Group
--

upsInputLineBads-third OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-third 1 }

upsInputNumLines-third OBJECT-TYPE
    SYNTAX     NonNegativeInteger32
    MAX-ACCESS read-only
    STATUS     current
    DESCRIPTION
            "The number of input lines utilized in this device.
            This variable indicates the number of rows in the
            input table.(*)"
    ::= { upsInput-third 2 }

upsInputTable-third OBJECT-TYPE
    SYNTAX     SEQUENCE OF UpsInputEntry-third
    MAX-ACCESS not-accessible
    STATUS     current
    DESCRIPTION
            "A list of input table entries.  The number of entries
            is given by the value of upsInputNumLines.(*)"
    ::= { upsInput-third 3 }

upsInputEntry-third OBJECT-TYPE
    SYNTAX     UpsInputEntry-third
    MAX-ACCESS not-accessible
    STATUS     current
    DESCRIPTION
            "An entry containing information applicable to a
            particular input line.(*)"
    INDEX { upsInputLineIndex-third }
    ::= { upsInputTable-third 1 }

UpsInputEntry-third ::= SEQUENCE {
    upsInputLineIndex-third   PositiveInteger32,
    upsInputFrequency-third   NonNegativeInteger32,
    upsInputVoltage-third     NonNegativeInteger32,
    upsInputCurrent-third     NonNegativeInteger32,
    upsInputTruePower-third   NonNegativeInteger32,
    upsInputVoltageMin-third  NonNegativeInteger32,
    upsInputVoltageMax-third  NonNegativeInteger32
}

upsInputLineIndex-third OBJECT-TYPE
    SYNTAX     PositiveInteger32
    MAX-ACCESS not-accessible
    STATUS     current
    DESCRIPTION
            "The input line identifier.(*)"
    ::= { upsInputEntry-third 1 }

upsInputFrequency-third OBJECT-TYPE
    SYNTAX     NonNegativeInteger32
    UNITS      "0.1 Hertz"
    MAX-ACCESS read-only
    STATUS     current
    DESCRIPTION
            "The present input frequency.(*)"
    ::= { upsInputEntry-third 2 }

upsInputVoltage-third OBJECT-TYPE
    SYNTAX     NonNegativeInteger32
    UNITS      "RMS Volts"
    MAX-ACCESS read-only
    STATUS     current
    DESCRIPTION
            "The magnitude of the present input voltage.(*)"
    ::= { upsInputEntry-third 3 }

upsInputCurrent-third OBJECT-TYPE
    SYNTAX     NonNegativeInteger32
    UNITS      "0.1 RMS Amp"
    MAX-ACCESS read-only
    STATUS     current
    DESCRIPTION
            "The magnitude of the present input current.(*)"
    ::= { upsInputEntry-third 4 }

upsInputTruePower-third OBJECT-TYPE
    SYNTAX     NonNegativeInteger32
    UNITS      "Watts"
    MAX-ACCESS read-only
    STATUS     current
    DESCRIPTION
            "The magnitude of the present input true power.(*)"
    ::= { upsInputEntry-third 5 }

upsInputVoltageMin-third OBJECT-TYPE
    SYNTAX     NonNegativeInteger32
    UNITS      "RMS Volts"
    MAX-ACCESS read-only
    STATUS     current
    DESCRIPTION
            "The lowest magnitude of the input voltage since last read out."
    ::= { upsInputEntry-third 6 }

upsInputVoltageMax-third OBJECT-TYPE
    SYNTAX     NonNegativeInteger32
    UNITS      "RMS Volts"
    MAX-ACCESS read-only
    STATUS     current
    DESCRIPTION
            "The highest magnitude of the input voltage since last read out."
    ::= { upsInputEntry-third 7 }

--
-- The Output group.
--

upsOutputSource-third OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-third 1 }

upsOutputFrequency-third OBJECT-TYPE
    SYNTAX     NonNegativeInteger32
    UNITS      "0.1 Hertz"
    MAX-ACCESS read-only
    STATUS     current
    DESCRIPTION
            "The present output frequency.(*)"
    ::= { upsOutput-third 2 }

upsOutputNumLines-third OBJECT-TYPE
    SYNTAX     NonNegativeInteger32
    MAX-ACCESS read-only
    STATUS     current
    DESCRIPTION
            "The number of output lines utilized in this device.
            This variable indicates the number of rows in the
            output table.(*)"
    ::= { upsOutput-third 3 }

upsOutputTable-third OBJECT-TYPE
    SYNTAX     SEQUENCE OF UpsOutputEntry-third
    MAX-ACCESS not-accessible
    STATUS     current
    DESCRIPTION
            "A list of output table entries.  The number of
            entries is given by the value of upsOutputNumLines.(*)"
    ::= { upsOutput-third 4 }

upsOutputEntry-third OBJECT-TYPE
    SYNTAX     UpsOutputEntry-third
    MAX-ACCESS not-accessible
    STATUS     current
    DESCRIPTION
            "An entry containing information applicable to a
            particular output line.(*)"
    INDEX { upsOutputLineIndex-third }
    ::= { upsOutputTable-third 1 }

UpsOutputEntry-third ::= SEQUENCE {
    upsOutputLineIndex-third   PositiveInteger32,
    upsOutputVoltage-third     NonNegativeInteger32,
    upsOutputCurrent-third     NonNegativeInteger32,
    upsOutputPower-third       NonNegativeInteger32,
    upsOutputPercentLoad-third Integer32
}

upsOutputLineIndex-third OBJECT-TYPE
    SYNTAX     PositiveInteger32
    MAX-ACCESS not-accessible
    STATUS     current
    DESCRIPTION
            "The output line identifier.(*)"
    ::= { upsOutputEntry-third 1 }

upsOutputVoltage-third OBJECT-TYPE
    SYNTAX     NonNegativeInteger32
    UNITS      "RMS Volts"
    MAX-ACCESS read-only
    STATUS     current
    DESCRIPTION
            "The present output voltage.(*)"
    ::= { upsOutputEntry-third 2 }

upsOutputCurrent-third OBJECT-TYPE
    SYNTAX     NonNegativeInteger32
    UNITS      "0.1 RMS Amp"
    MAX-ACCESS read-only
    STATUS     current
    DESCRIPTION
            "The present output current.(*)"
    ::= { upsOutputEntry-third 3 }

upsOutputPower-third OBJECT-TYPE
    SYNTAX     NonNegativeInteger32
    UNITS      "Watts"
    MAX-ACCESS read-only
    STATUS     current
    DESCRIPTION
            "The present output true power.(*)"
    ::= { upsOutputEntry-third 4 }

upsOutputPercentLoad-third OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-third 5 }

--
-- The Bypass group generic.
--

upsBypassFrequency-third OBJECT-TYPE
    SYNTAX     NonNegativeInteger32
    UNITS      "0.1 Hertz"
    MAX-ACCESS read-only
    STATUS     current
    DESCRIPTION
            "The present bypass frequency.(*)"
    ::= { upsBypass-third 1 }

upsBypassNumLines-third OBJECT-TYPE
    SYNTAX     NonNegativeInteger32
    MAX-ACCESS read-only
    STATUS     current
    DESCRIPTION
            "The number of bypass lines utilized in this device.
            This entry indicates the number of rows in the bypass
            table.(*)"
    ::= { upsBypass-third 2 }

upsBypassTable-third OBJECT-TYPE
    SYNTAX     SEQUENCE OF UpsBypassEntry-third
    MAX-ACCESS not-accessible
    STATUS     current
    DESCRIPTION
            "A list of bypass table entries.  The number of
            entries is given by the value of upsBypassNumLines.(*)"
    ::= { upsBypass-third 3 }

upsBypassEntry-third OBJECT-TYPE
    SYNTAX     UpsBypassEntry-third
    MAX-ACCESS not-accessible
    STATUS     current
    DESCRIPTION
            "An entry containing information applicable to a
            particular bypass input.(*)"
    INDEX { upsBypassLineIndex-third }
    ::= { upsBypassTable-third 1 }

UpsBypassEntry-third ::= SEQUENCE {
    upsBypassLineIndex-third  PositiveInteger32,
    upsBypassVoltage-third    NonNegativeInteger32,
    upsBypassCurrent-third    NonNegativeInteger32,
    upsBypassPower-third      NonNegativeInteger32
}

upsBypassLineIndex-third OBJECT-TYPE
    SYNTAX     PositiveInteger32
    MAX-ACCESS not-accessible
    STATUS     current
    DESCRIPTION
            "The bypass line identifier.(*)"
    ::= { upsBypassEntry-third 1 }

upsBypassVoltage-third OBJECT-TYPE
    SYNTAX     NonNegativeInteger32
    UNITS      "RMS Volts"
    MAX-ACCESS read-only
    STATUS     current
    DESCRIPTION
            "The present bypass voltage.(*)"
    ::= { upsBypassEntry-third 2 }

upsBypassCurrent-third OBJECT-TYPE
    SYNTAX     NonNegativeInteger32
    UNITS      "0.1 RMS Amp"
    MAX-ACCESS read-only
    STATUS     current
    DESCRIPTION
            "The present bypass current.(*)"
    ::= { upsBypassEntry-third 3 }

upsBypassPower-third OBJECT-TYPE
    SYNTAX     NonNegativeInteger32
    UNITS      "Watts"
    MAX-ACCESS read-only
    STATUS     current
    DESCRIPTION
            "The present true power conveyed by the bypass.(*)"
    ::= { upsBypassEntry-third 4 }

--
-- The Alarm group generic.
--

upsAlarmsPresent-third OBJECT-TYPE
    SYNTAX     Gauge32
    MAX-ACCESS read-only
    STATUS     current
    DESCRIPTION
            "The present number of active alarm conditions.(*)"
    ::= { upsAlarm-third 1 }

upsAlarmTable-third OBJECT-TYPE
    SYNTAX     SEQUENCE OF UpsAlarmEntry-third
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-third 2 }

upsAlarmEntry-third OBJECT-TYPE
    SYNTAX     UpsAlarmEntry-third
    MAX-ACCESS not-accessible
    STATUS     current
    DESCRIPTION
            "An entry containing information applicable to a
            particular alarm.(*)"
    INDEX { upsAlarmId-third }
    ::= { upsAlarmTable-third 1 }

UpsAlarmEntry-third ::= SEQUENCE {
    upsAlarmId-third          PositiveInteger32,
    upsAlarmDescr-third       AutonomousType,
    upsAlarmTime-third       TimeStamp
}

upsAlarmId-third OBJECT-TYPE
    SYNTAX     PositiveInteger32
    MAX-ACCESS not-accessible
    STATUS     current
    DESCRIPTION
            "A unique identifier for an alarm condition.  This
            value must remain constant.(*)"
    ::= { upsAlarmEntry-third 1 }

upsAlarmDescr-third OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-third 2 }

upsAlarmTime-third OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-third 3 }

--
-- Well known alarm conditions generic.
--

upsAlarmBatteryBad-third OBJECT-IDENTITY
    STATUS     current
    DESCRIPTION
            "One or more batteries have been determined to require
            replacement.(*)"
    ::= { upsWellKnownAlarms-third  1 }

upsAlarmOnBattery-third OBJECT-IDENTITY
    STATUS     current
    DESCRIPTION
            "The UPS is drawing power from the batteries.(*)"
    ::= { upsWellKnownAlarms-third  2 }

upsAlarmLowBattery-third OBJECT-IDENTITY
    STATUS     current
    DESCRIPTION
            "The remaining battery run-time is less than or equal
            to upsConfigLowBattTime.(*)"
    ::= { upsWellKnownAlarms-third  3 }

upsAlarmDepletedBattery-third OBJECT-IDENTITY
    STATUS     current
    DESCRIPTION
            "The UPS will be unable to sustain the present load
            when and if the utility power is lost.(*)"
    ::= { upsWellKnownAlarms-third  4 }

upsAlarmTempBad-third OBJECT-IDENTITY
    STATUS     current
    DESCRIPTION
            "A temperature is out of tolerance.(*)"
    ::= { upsWellKnownAlarms-third  5 }

upsAlarmInputBad-third OBJECT-IDENTITY
    STATUS     current
    DESCRIPTION
            "An input condition is out of tolerance.(*)"
    ::= { upsWellKnownAlarms-third  6 }

upsAlarmOutputBad-third OBJECT-IDENTITY
    STATUS     current
    DESCRIPTION
            "An output condition (other than OutputOverload) is
            out of tolerance.(*)"
    ::= { upsWellKnownAlarms-third  7 }

upsAlarmOutputOverload-third OBJECT-IDENTITY
    STATUS     current
    DESCRIPTION
            "The output load exceeds the UPS output capacity.(*)"
    ::= { upsWellKnownAlarms-third  8 }

upsAlarmOnBypass-third OBJECT-IDENTITY
    STATUS     current
    DESCRIPTION
            "The Bypass is presently engaged on the UPS.(*)"
    ::= { upsWellKnownAlarms-third  9 }

upsAlarmBypassBad-third OBJECT-IDENTITY
    STATUS     current
    DESCRIPTION
            "The Bypass is out of tolerance.(*)"
    ::= { upsWellKnownAlarms-third 10 }

upsAlarmOutputOffAsRequested-third OBJECT-IDENTITY
    STATUS     current
    DESCRIPTION
            "The UPS has shutdown as requested, i.e., the output
            is off.(*)"
    ::= { upsWellKnownAlarms-third 11 }

upsAlarmUpsOffAsRequested-third OBJECT-IDENTITY
    STATUS     current
    DESCRIPTION
            "The entire UPS has shutdown as commanded.(*)"
    ::= { upsWellKnownAlarms-third 12 }

upsAlarmChargerFailed-third OBJECT-IDENTITY
    STATUS     current
    DESCRIPTION
            "An uncorrected problem has been detected within the
            UPS charger subsystem.(*)"
    ::= { upsWellKnownAlarms-third 13 }

upsAlarmUpsOutputOff-third OBJECT-IDENTITY
    STATUS     current
    DESCRIPTION
            "The output of the UPS is in the off state.(*)"
    ::= { upsWellKnownAlarms-third 14 }

upsAlarmUpsSystemOff-third OBJECT-IDENTITY
    STATUS     current
    DESCRIPTION
            "The UPS system is in the off state.(*)"
    ::= { upsWellKnownAlarms-third 15 }

upsAlarmFanFailure-third OBJECT-IDENTITY
    STATUS     current
    DESCRIPTION
            "The failure of one or more fans in the UPS has been
            detected.(*)"
    ::= { upsWellKnownAlarms-third 16 }

upsAlarmFuseFailure-third OBJECT-IDENTITY
    STATUS     current
    DESCRIPTION
            "The failure of one or more fuses has been detected.(*)"
    ::= { upsWellKnownAlarms-third 17 }

upsAlarmGeneralFault-third OBJECT-IDENTITY
    STATUS     current
    DESCRIPTION
            "A general fault in the UPS has been detected.(*)"
    ::= { upsWellKnownAlarms-third 18 }

upsAlarmDiagnosticTestFailed-third OBJECT-IDENTITY
    STATUS     current
    DESCRIPTION
            "The result of the last diagnostic test indicates a
            failure.(*)"
    ::= { upsWellKnownAlarms-third 19 }

upsAlarmCommunicationsLost-third OBJECT-IDENTITY
    STATUS     current
    DESCRIPTION
            "A problem has been encountered in the communications
            between the agent and the UPS.(*)"
    ::= { upsWellKnownAlarms-third 20 }

upsAlarmAwaitingPower-third OBJECT-IDENTITY
    STATUS     current
    DESCRIPTION
            "The UPS output is off and the UPS is awaiting the
            return of input power.(*)"
    ::= { upsWellKnownAlarms-third 21 }

upsAlarmShutdownPending-third OBJECT-IDENTITY
    STATUS     current
    DESCRIPTION
            "A upsShutdownAfterDelay countdown is underway.(*)"
    ::= { upsWellKnownAlarms-third 22 }

upsAlarmShutdownImminent-third OBJECT-IDENTITY
    STATUS     current
    DESCRIPTION
            "The UPS will turn off power to the load in less than
            5 seconds; this may be either a timed shutdown or a
            low battery shutdown.(*)"
    ::= { upsWellKnownAlarms-third 23 }

upsAlarmTestInProgress-third OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-third 24 }

upsAlarmReceptacleOff-third OBJECT-IDENTITY
    STATUS     current
    DESCRIPTION
            "The receptacle are switch off    "
    ::= { upsWellKnownAlarms-third 25 }

upsAlarmMaskA-third OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-third 4 }

--
-- The Test Group generic
--

upsTestId-third OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-third 1 }

-- see [6] for more information on the semantics of objects with
-- syntax of TestAndIncr

upsTestSpinLock-third OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-third 2 }

upsTestResultsSummary-third OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-third 3 }

upsTestResultsDetail-third OBJECT-TYPE
    SYNTAX     DisplayString (SIZE (0..255))
    MAX-ACCESS read-only
    STATUS     current
    DESCRIPTION
            "Additional information about upsTestResultsSummary.
            If no additional information available, a zero length
            string is returned.(*)"
    ::= { upsTest-third 4 }

upsTestStartTime-third OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-third 5 }

upsTestElapsedTime-third OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-third 6 }

--
-- Well known tests generic.
--

upsTestNoTestsInitiated-third OBJECT-IDENTITY
    STATUS     current
    DESCRIPTION
            "No tests have been initiated and no test is in
            progress.(*)"
    ::= { upsWellKnownTests-third  1 }

upsTestAbortTestInProgress-third OBJECT-IDENTITY
    STATUS     current
    DESCRIPTION
            "The test in progress is to be aborted / the test in
            progress was aborted.(*)"
    ::= { upsWellKnownTests-third  2 }

upsTestGeneralSystemsTest-third OBJECT-IDENTITY
    STATUS     current
    DESCRIPTION
            "The manufacturer's standard test of UPS device
            systems.(*)"
    ::= { upsWellKnownTests-third  3 }

upsTestQuickBatteryTest-third OBJECT-IDENTITY
    STATUS     current
    DESCRIPTION
            "A test that is sufficient to determine if the battery
            needs replacement.(*)"
    ::= { upsWellKnownTests-third  4 }

upsTestDeepBatteryCalibration-third OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-third  5 }

--
-- The Control group generic.
--

upsShutdownType-third OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-third 1 }

upsShutdownAfterDelay-third OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-third 2 }

upsStartupAfterDelay-third OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-third 3 }

upsRebootWithDuration-third OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-third 4 }

upsAutoRestart-third OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-third 5 }

upsReceptaclesNum-third OBJECT-TYPE
    SYNTAX     NonNegativeInteger32
    MAX-ACCESS read-only
    STATUS     current
    DESCRIPTION
            "The number of receptacles utilized in this device.
            This entry indicates the number of rows in the receptacle
            table."
    ::= { upsControl-third 6 }

upsReceptacleTable-third OBJECT-TYPE
    SYNTAX     SEQUENCE OF UpsReceptacleEntry-third
    MAX-ACCESS not-accessible
    STATUS     current
    DESCRIPTION
            "A list of receptacle table entries.  The number of
            entries is given by the value of upsReceptacleNum."
    ::= { upsControl-third 7 }

upsReceptacleEntry-third OBJECT-TYPE
    SYNTAX     UpsReceptacleEntry-third
    MAX-ACCESS not-accessible
    STATUS     current
    DESCRIPTION
            "An entry containing information applicable to a
            particular receptacle."
    INDEX { upsReceptacleLineIndex-third }
    ::= { upsReceptacleTable-third 1 }

UpsReceptacleEntry-third ::= SEQUENCE {
    upsReceptacleLineIndex-third  PositiveInteger32,
    upsReceptacleOnOff-third      Integer32    
}

upsReceptacleLineIndex-third OBJECT-TYPE
    SYNTAX     PositiveInteger32
    MAX-ACCESS not-accessible
    STATUS     current
    DESCRIPTION
            "The receptacle line identifier."
    ::= { upsReceptacleEntry-third 1 }

upsReceptacleOnOff-third OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-third 2 }

upsUPSMode-third OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-third 8 }

upsRectifierOnOff-third OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-third 9 }

upsBatteryChargeMethod-third OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-third 10 }

upsInverterOnOff-third OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-third 11 }

upsBypassOnOff-third OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-third 12 }

upsLoadSource-third OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-third 13 }
	
--
-- The Configuration group generic.
--

upsConfigInputVoltage-third OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-third 1 }

upsConfigInputFreq-third OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-third 2 }

upsConfigOutputVoltage-third OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-third 3 }

upsConfigOutputFreq-third OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-third 4 }

upsConfigOutputVA-third OBJECT-TYPE
    SYNTAX     NonNegativeInteger32
    UNITS      "Volt-Amps"
    MAX-ACCESS read-only
    STATUS     current
    DESCRIPTION
            "The magnitude of the nominal Volt-Amp rating.(*)"
    ::= { upsConfig-third 5 }

upsConfigOutputPower-third OBJECT-TYPE
    SYNTAX     NonNegativeInteger32
    UNITS      "Watts"
    MAX-ACCESS read-only
    STATUS     current
    DESCRIPTION
            "The magnitude of the nominal true power rating.(*)"
    ::= { upsConfig-third 6 }

upsConfigLowBattTime-third OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-third 7 }

upsConfigAudibleStatus-third OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-third 8 }

upsConfigLowVoltageTransferPoint-third OBJECT-TYPE
    SYNTAX     NonNegativeInteger32
    UNITS      "RMS Volts"
    MAX-ACCESS read-write
    STATUS     current
    DESCRIPTION
            "The minimum input line voltage allowed before the UPS
            system transfers to battery backup.(*)"
    ::= { upsConfig-third 9 }

upsConfigHighVoltageTransferPoint-third OBJECT-TYPE
    SYNTAX     NonNegativeInteger32
    UNITS      "RMS Volts"
    MAX-ACCESS read-write
    STATUS     current
    DESCRIPTION
            "The maximum line voltage allowed before the UPS
            system transfers to battery backup.(*)"
    ::= { upsConfig-third 10 }

upsConfigBatteryCapacity-third OBJECT-TYPE
    SYNTAX     NonNegativeInteger32
    UNITS      "Amps Hours"
    MAX-ACCESS read-write
    STATUS     current
    DESCRIPTION
            "The installed battery capacity. This value is the 'factory'-value,
             not the value after calibration."
    ::= { upsConfig-third 11 }

upsConfigBatteryChargeCurrent-third OBJECT-TYPE
    SYNTAX     NonNegativeInteger32
    UNITS      "0.1 Amp DC"
    MAX-ACCESS read-write
    STATUS     current
    DESCRIPTION
            "The maximum battery charge current, including external chargers."
    ::= { upsConfig-third 12 }						

upsConfigNoLoadShutdown-third OBJECT-TYPE
    SYNTAX     Integer32 {
        disabled(1),
        enabled(2)
    }
    MAX-ACCESS read-write
    STATUS     current
    DESCRIPTION
            "Dis- or enable 'no load' shutdown from the contact interface."
    ::= { upsConfig-third 13 }
	
upsConfigStartDelay-third OBJECT-TYPE
    SYNTAX     PositiveInteger32
    UNITS      "minutes"				
    MAX-ACCESS read-write
    STATUS     current
    DESCRIPTION
            "Minimum required autonomy time before the UPS may perform an
             autorestart."
    ::= { upsConfig-third 14 }

--
-- The GetSet group generic.
--

upsEventGetNext-third OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-third 1 }

upsEventGetPrevious-third OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-third 2 }
				
upsEventSetStartingTimeStamp-third OBJECT-TYPE
    SYNTAX     NonNegativeInteger32
    MAX-ACCESS read-write
    STATUS     current
    DESCRIPTION
            "The timestamp which is used as starting point for downloading
             events from the UPS event buffer"
    ::= { upsGetSet-third 3 }				

upsEventRetreiveCurrentTimeStamp-third OBJECT-TYPE
    SYNTAX     NonNegativeInteger32
    MAX-ACCESS read-only
    STATUS     current
    DESCRIPTION
            "The current timestamp is retreived from the UPS"
    ::= { upsGetSet-third 4 }				

upsEventTableSize-third OBJECT-TYPE
    SYNTAX     NonNegativeInteger32
    MAX-ACCESS read-only
    STATUS     current
    DESCRIPTION
            "The number of entries in the event table.
            This object indicates the number of rows in the event table."
    ::= { upsGetSet-third 5 }

upsEventTable-third OBJECT-TYPE
    SYNTAX     SEQUENCE OF UpsEventEntry-third
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-third 6 }

upsEventEntry-third OBJECT-TYPE
    SYNTAX     UpsEventEntry-third
    MAX-ACCESS not-accessible
    STATUS     current
    DESCRIPTION
            "An entry containing information applicable to a
            particular event."
    INDEX { upsEventLineIndex-third }
    ::= { upsEventTable-third 1 }

UpsEventEntry-third ::= SEQUENCE {
    upsEventLineIndex-third PositiveInteger32,
    upsEventCode-third      Integer32,
    upsEventStatus-third    NonNegativeInteger32,
    upsEventTime-third      NonNegativeInteger32
}

upsEventLineIndex-third OBJECT-TYPE
    SYNTAX     PositiveInteger32
    MAX-ACCESS not-accessible
    STATUS     current
    DESCRIPTION
            "The event line identifier."
    ::= { upsEventEntry-third 1 }

upsEventCode-third OBJECT-TYPE
    SYNTAX     NonNegativeInteger32
    MAX-ACCESS read-only
    STATUS     current
    DESCRIPTION
            "The event code in numerical format."
    ::= { upsEventEntry-third 2 }

upsEventStatus-third OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-third 3 }

upsEventTime-third OBJECT-TYPE
    SYNTAX     NonNegativeInteger32
    MAX-ACCESS read-only
    STATUS     current
    DESCRIPTION
            "The timestamp of the moment the event was generated."
    ::= { upsEventEntry-third 4 }

upsParametersRead-third OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-third 7 }

upsParametersWrite-third OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-third 8 }

upsParametersStartAddress-third OBJECT-TYPE
    SYNTAX     NonNegativeInteger32
    MAX-ACCESS read-write
    STATUS     current
    DESCRIPTION
            "The address which is used as starting point for downloading
             parameters from the UPS"
    ::= { upsGetSet-third 9 }				

upsParameterTableSize-third OBJECT-TYPE
    SYNTAX     NonNegativeInteger32
    MAX-ACCESS read-only
    STATUS     current
    DESCRIPTION
            "The number of entries in the parameter table.
            This object indicates the number of rows in the parameter table."
    ::= { upsGetSet-third 10 }

upsParameterTable-third OBJECT-TYPE
    SYNTAX     SEQUENCE OF UpsParameterEntry-third
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-third 11 }

upsParameterEntry-third OBJECT-TYPE
    SYNTAX     UpsParameterEntry-third
    MAX-ACCESS not-accessible
    STATUS     current
    DESCRIPTION
            "An entry containing information applicable to a
            particular parameter."
    INDEX { upsParameterLineIndex-third }
    ::= { upsParameterTable-third 1 }

UpsParameterEntry-third ::= SEQUENCE {
    upsParameterLineIndex-third PositiveInteger32,
    upsParameterValue-third     Integer32   
}

upsParameterLineIndex-third OBJECT-TYPE
    SYNTAX     PositiveInteger32
    MAX-ACCESS not-accessible
    STATUS     current
    DESCRIPTION
            "The parameter line identifier."
    ::= { upsParameterEntry-third 1 }

upsParameterValue-third OBJECT-TYPE
    SYNTAX     Integer32
    MAX-ACCESS read-write
    STATUS     current
    DESCRIPTION
            "The parameter value in numerical format."
    ::= { upsParameterEntry-third 2 }

upsStatus-third OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-third 12 }

upsMainsStatisticsMBfail-third OBJECT-TYPE
    SYNTAX     NonNegativeInteger32
    MAX-ACCESS read-only
    STATUS     current
    DESCRIPTION
            "Count of main bypass failures (>200 ms), since UPS installation."
    ::= { upsGetSet-third 13 }

upsMainsStatisticsMRfail-third OBJECT-TYPE
    SYNTAX     NonNegativeInteger32
    MAX-ACCESS read-only
    STATUS     current
    DESCRIPTION
            "Count of mains rectifier failures (>200 ms), since UPS installation."
    ::= { upsGetSet-third 14 }
		
upsMainsStatisticsB2-third OBJECT-TYPE
    SYNTAX     NonNegativeInteger32
    MAX-ACCESS read-only
    STATUS     current
    DESCRIPTION
            "Count of transients on the mains bypass (0..2 ms), during the last 7 days."
    ::= { upsGetSet-third 15 }

upsMainsStatisticsB5-third OBJECT-TYPE
    SYNTAX     NonNegativeInteger32
    MAX-ACCESS read-only
    STATUS     current
    DESCRIPTION
            "Count of transients on the mains bypass (2..5 ms), during the last 7 days."
    ::= { upsGetSet-third 16 }

upsMainsStatisticsB10-third OBJECT-TYPE
    SYNTAX     NonNegativeInteger32
    MAX-ACCESS read-only
    STATUS     current
    DESCRIPTION
            "Count of transients on the mains bypass (5..10 ms), during the last 7 days."
    ::= { upsGetSet-third 17 }

upsMainsStatisticsB200-third OBJECT-TYPE
    SYNTAX     NonNegativeInteger32
    MAX-ACCESS read-only
    STATUS     current
    DESCRIPTION
            "Count of transients on the mains bypass (10..200 ms), during the last 7 days."
    ::= { upsGetSet-third 18 }

upsMainsStatisticsBypRel-third OBJECT-TYPE
    SYNTAX     NonNegativeInteger32
    MAX-ACCESS read-only
    STATUS     current
    DESCRIPTION
            "Bypass reliability degree [0..100%;255]. The value NOSUCHNAME means 'not available'."
    ::= { upsGetSet-third 19 }

upsTime-third OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-thirdERROR,              meaning 'command not supported'. It is possible to know which is the timestamp 
             format supported by the UPS, by issuing a read-command or by reading events, 
             which includes timestamps."
    ::= { upsGetSet-third 20 }

upsRequestPermission-third OBJECT-TYPE
    SYNTAX     DisplayString (SIZE(0..63))
    MAX-ACCESS write-only
    STATUS     current
    DESCRIPTION
            "An encrypted code is send to enable use of restricted write objects during
             a limited period of time."
    ::= { upsGetSet-third 21 }

upsEventGetCode-third OBJECT-TYPE
    SYNTAX     Integer32
    MAX-ACCESS write-only
    STATUS     current
    DESCRIPTION
            "The code which is used as starting point to downloading the events from the 
            UPS event buffer."
    ::= { upsGetSet-third 22 }    
    
upsEventSpinLock-third OBJECT-TYPE
    SYNTAX     TestAndIncr
    MAX-ACCESS read-write
    STATUS     current
    DESCRIPTION
            "A spin lock on the event subsystem. "

    ::= { upsGetSet-third 23 }
    
upsParameterSpinLock-third OBJECT-TYPE
    SYNTAX     TestAndIncr
    MAX-ACCESS read-write
    STATUS     current
    DESCRIPTION
            "A spin lock on the parameters subsystem. "

    ::= { upsGetSet-third 24 }

--
-- GE Trap group generic
--

upsAlarmBatteryBad-third TRAP-TYPE
    ENTERPRISE geUPSTraps-third
    VARIABLES  { trapArg  }
    DESCRIPTION
            "One or more batteries have been determined to require
            replacement."
    ::= 1

upsAlarmOnBattery-third TRAP-TYPE
    ENTERPRISE geUPSTraps-third
    VARIABLES  { trapArg , upsSecondsOnBattery-third  }
    DESCRIPTION
            "An On Battery condition is restored."
    ::= 2

upsAlarmLowBattery-third TRAP-TYPE
    ENTERPRISE geUPSTraps-third
    VARIABLES  { trapArg  }
    DESCRIPTION
            "The remaining battery run-time is less than or equal
            to upsConfigLowBattTime."
    ::= 3

upsAlarmDepletedBattery-third TRAP-TYPE
    ENTERPRISE geUPSTraps-third
    VARIABLES  { trapArg  }
    DESCRIPTION
            "The UPS will be unable to sustain the present load
            when and if the utility power is lost)"
    ::= 4

upsAlarmTempBad-third TRAP-TYPE
    ENTERPRISE geUPSTraps-third
    VARIABLES  { trapArg , upsBatteryTemperature }
    DESCRIPTION
            "A temperature is out of tolerance."
    ::= 5

upsAlarmInputBad-third TRAP-TYPE
    ENTERPRISE geUPSTraps-third
    VARIABLES  { trapArg  }
    DESCRIPTION
            "An input condition is out of tolerance."
    ::= 6

upsAlarmOutputBad-third TRAP-TYPE
    ENTERPRISE geUPSTraps-third
    VARIABLES  { trapArg  }
    DESCRIPTION
            "An output condition (other than OutputOverload) is
            out of tolerance."
    ::= 7

upsAlarmOutputOverload-third TRAP-TYPE
    ENTERPRISE geUPSTraps-third
    VARIABLES  { trapArg , upsOutputPercentLoad-third }
    DESCRIPTION
            "The output load exceeds the UPS output capacity."
    ::= 8

upsAlarmOnBypass-third TRAP-TYPE
    ENTERPRISE geUPSTraps-third
    VARIABLES  { trapArg  }
    DESCRIPTION
            "The Bypass is presently engaged on the UPS."
    ::= 9

upsAlarmBypassBad-third TRAP-TYPE
    ENTERPRISE geUPSTraps-third
    VARIABLES  { trapArg  }
    DESCRIPTION
            "The Bypass is out of tolerance."
    ::= 10

upsAlarmOutputOffAsRequested-third TRAP-TYPE
    ENTERPRISE geUPSTraps-third
    VARIABLES  { trapArg  }
    DESCRIPTION
            "The UPS has shutdown as requested, i.e., the output
            is off."
    ::= 11

upsAlarmUpsOffAsRequested-third TRAP-TYPE
    ENTERPRISE geUPSTraps-third-third
    VARIABLES  { trapArg  }
    DESCRIPTION
            "The entire UPS has shutdown as commanded."
    ::= 12

upsAlarmChargerFailed-third TRAP-TYPE
    ENTERPRISE geUPSTraps-third
    VARIABLES  { trapArg  }
    DESCRIPTION
            "An uncorrected problem has been detected within the
            UPS charger subsystem."
    ::= 13

upsAlarmUpsOutputOff-third TRAP-TYPE
    ENTERPRISE geUPSTraps-third
    VARIABLES  { trapArg  }
    DESCRIPTION
            "The output of the UPS is in the off state."
    ::= 14

upsAlarmUpsSystemOff-third TRAP-TYPE
    ENTERPRISE geUPSTraps-third
    VARIABLES  { trapArg  }
    DESCRIPTION
            "The UPS system is in the off state."
    ::= 15

upsAlarmFanFailure-third TRAP-TYPE
    ENTERPRISE geUPSTraps-third
    VARIABLES  { trapArg  }
    DESCRIPTION
            "The failure of one or more fans in the UPS has been
            detected."
    ::= 16

upsAlarmFuseFailure-third TRAP-TYPE
    ENTERPRISE geUPSTraps-third
    VARIABLES  { trapArg  }
    DESCRIPTION
            "The failure of one or more fuses has been detected."
    ::= 17

upsAlarmGeneralFault-third TRAP-TYPE
    ENTERPRISE geUPSTraps-third
    VARIABLES  { trapArg  }
    DESCRIPTION
            "A general fault in the UPS has been detected."
    ::= 18

upsAlarmDiagnosticTestFailed-third TRAP-TYPE
    ENTERPRISE geUPSTraps-third
    VARIABLES  { trapArg  }
    DESCRIPTION
            "The result of the last diagnostic test indicates a
            failure."
    ::= 19

upsAlarmCommunicationsLost-third TRAP-TYPE
    ENTERPRISE geUPSTraps-third
    VARIABLES  { trapArg  }
    DESCRIPTION
            "A problem has been encountered in the communication
            between the agent and the UPS."
    ::= 20
    
upsAlarmAwaitingPower-third TRAP-TYPE
    ENTERPRISE geUPSTraps-third
    VARIABLES  { trapArg  }
    DESCRIPTION
            "The UPS output is off and the UPS is awaiting the
            return of the input power (*)."
    ::= 21    

upsAlarmShutdownPending-third TRAP-TYPE
    ENTERPRISE geUPSTraps-third
    VARIABLES  { trapArg , upsShutdownAfterDelay-third }
    DESCRIPTION
            "A upsShutdownAfterDelay countdown is underway."
    ::= 22

upsAlarmShutdownImminent-third TRAP-TYPE
    ENTERPRISE geUPSTraps-third
    VARIABLES  { trapArg  }
    DESCRIPTION
            "The UPS will turn off power to the load in less than
            5 seconds; this may be either a timed shutdown or a
            low battery shutdown."
    ::= 23

upsAlarmTestInProgress-third TRAP-TYPE
    ENTERPRISE geUPSTraps-third
    VARIABLES  { trapArg , upsTestId-third }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-third TRAP-TYPE
    ENTERPRISE geUPSTraps-third
    VARIABLES  { trapArg  }
    DESCRIPTION
            "A receptacle has been switched off."
    ::= 25

upsAlarmBatteryBadRestored-third TRAP-TYPE
    ENTERPRISE geUPSTraps-third
    VARIABLES  { trapArg  }
    DESCRIPTION
            "A Battery bad condition is restored."
    ::= 33

upsAlarmOnBatteryRestored-third TRAP-TYPE
    ENTERPRISE geUPSTraps-third
    VARIABLES  { trapArg  }
    DESCRIPTION
            "The UPS is drawing power from mains again."
    ::= 34

upsAlarmLowBatteryRestored-third TRAP-TYPE
    ENTERPRISE geUPSTraps-third
    VARIABLES  { trapArg  }
    DESCRIPTION
            "A Low Battery condition is restored."
    ::= 35

upsAlarmDepletedBatteryRestored-third TRAP-TYPE
    ENTERPRISE geUPSTraps-third
    VARIABLES  { trapArg  }
    DESCRIPTION
            "A Depleted Battery condition is restored."
    ::= 36

upsAlarmTempBadRestored-third TRAP-TYPE
    ENTERPRISE geUPSTraps-third
    VARIABLES  { trapArg  }
    DESCRIPTION
            "A bad temperature condition is restored."
    ::= 37

upsAlarmInputBadRestored-third TRAP-TYPE
    ENTERPRISE geUPSTraps-third
    VARIABLES  { trapArg  }
    DESCRIPTION
            "An input bad condition is restored."
    ::= 38

upsAlarmOutputBadRestored-third TRAP-TYPE
    ENTERPRISE geUPSTraps-third
    VARIABLES  { trapArg  }
    DESCRIPTION
            "An output bad condition is restored."
    ::= 39

upsAlarmOutputOverloadRestored-third TRAP-TYPE
    ENTERPRISE geUPSTraps-third
    VARIABLES  { trapArg  }
    DESCRIPTION
            "An output overload condition is restored."
    ::= 40

upsAlarmOnBypassRestored-third TRAP-TYPE
    ENTERPRISE geUPSTraps-third
    VARIABLES  { trapArg  }
    DESCRIPTION
            "An On Bypass condition is restored."
    ::= 41

upsAlarmBypassBadRestored-third TRAP-TYPE
    ENTERPRISE geUPSTraps-third
    VARIABLES  { trapArg  }
    DESCRIPTION
            "A Bypass bad condition is restored."
    ::= 42

upsAlarmOutputOffAsRequestedRestored-third TRAP-TYPE
    ENTERPRISE geUPSTraps-third
    VARIABLES  { trapArg  }
    DESCRIPTION
            "A request shutdown has been restored."
    ::= 43

upsAlarmUpsOffAsRequestedRestored-third TRAP-TYPE
    ENTERPRISE geUPSTraps-third-third
    VARIABLES  { trapArg  }
    DESCRIPTION
            "A entire UPS command has been restored."
    ::= 44

upsAlarmChargerFailedRestored-third TRAP-TYPE
    ENTERPRISE geUPSTraps-third
    VARIABLES  { trapArg  }
    DESCRIPTION
            "A Charger Failer condition is restored."
    ::= 45

upsAlarmUpsOutputOn-third TRAP-TYPE
    ENTERPRISE geUPSTraps-third
    VARIABLES  { trapArg  }
    DESCRIPTION
            "The output of the UPS switched in the on state."
    ::= 46

upsAlarmUpsSystemOn-third TRAP-TYPE
    ENTERPRISE geUPSTraps-third
    VARIABLES  { trapArg  }
    DESCRIPTION
            "The UPS system is switched in the on state."
    ::= 47

upsAlarmFanFailureRestored-third TRAP-TYPE
    ENTERPRISE geUPSTraps-third
    VARIABLES  { trapArg  }
    DESCRIPTION
            "A Fan failure condition is restored."
    ::= 48

upsAlarmFuseFailureRestored-third TRAP-TYPE
    ENTERPRISE geUPSTraps-third
    VARIABLES  { trapArg  }
    DESCRIPTION
            "A Fuse failure condition is restored."
    ::= 49

upsAlarmGeneralFaultRestored-third TRAP-TYPE
    ENTERPRISE geUPSTraps-third
    VARIABLES  { trapArg  }
    DESCRIPTION
            "A general fault is restored."
    ::= 50

upsAlarmDiagnosticTestFailedRestored-third TRAP-TYPE
    ENTERPRISE geUPSTraps-third
    VARIABLES  { trapArg  }
    DESCRIPTION
            "A last diagnostic test indicates a failure is 
            restored."
    ::= 51

upsAlarmCommunicationsLostRestored-third TRAP-TYPE
    ENTERPRISE geUPSTraps-third
    VARIABLES  { trapArg  }
    DESCRIPTION
            "A problem in the communication between the agent 
            and the UPS is restored."
    ::= 52
    
upsAlarmAwaitingPowerRestored-third TRAP-TYPE
    ENTERPRISE geUPSTraps-third
    VARIABLES  { trapArg  }
    DESCRIPTION
            "A awaiting power condition is restored (*)."
    ::= 53    

upsAlarmShutdownPendingRestored-third TRAP-TYPE
    ENTERPRISE geUPSTraps-third
    VARIABLES  { trapArg , upsShutdownAfterDelay-third }
    DESCRIPTION
            "A upsShutdownAfterDelay countdown is restored."
    ::= 54

upsAlarmShutdownImminentRestored-third TRAP-TYPE
    ENTERPRISE geUPSTraps-third
    VARIABLES  { trapArg  }
    DESCRIPTION
            "A shutdown imminent condition is restored."
    ::= 55

upsAlarmTestInProgressRestored-third TRAP-TYPE
    ENTERPRISE geUPSTraps-third
    VARIABLES  { trapArg , upsTestId-third }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-third TRAP-TYPE
    ENTERPRISE geUPSTraps-third
    VARIABLES  { trapArg  }
    DESCRIPTION
            "A measurement value reached a value below its low-level threshold."
    ::= 129

upsAlarmValueHigh-third TRAP-TYPE
    ENTERPRISE geUPSTraps-third
    VARIABLES  { trapArg  }
    DESCRIPTION
            "A measurement value reached a value higher than its high-level threshold."
    ::= 130

upsAlarmValueLowRestored-third TRAP-TYPE
    ENTERPRISE geUPSTraps-third
    VARIABLES  { trapArg  }
    DESCRIPTION
            "A ValueLow alarm condition is restored."
    ::= 133

upsAlarmValueHighRestored-third TRAP-TYPE
    ENTERPRISE geUPSTraps-third
    VARIABLES  { trapArg }
    DESCRIPTION
            "A ValueHigh alarm condition is restored."
    ::= 134

--
-- The Device Identification group. Fourth
--      All objects in this group except for upsIdentName and
--      upsIdentAttachedDevices are set at device initialization
--      and remain static.
--

upsIdentManufacturer-fourth OBJECT-TYPE
    SYNTAX     DisplayString (SIZE (0..31))
    MAX-ACCESS read-only
    STATUS     current
    DESCRIPTION
            "The name of the UPS manufacturer.(*)"
    ::= { upsIdent-fourth 1 }

upsIdentModel-fourth OBJECT-TYPE
    SYNTAX     DisplayString (SIZE (0..63))
    MAX-ACCESS read-only
    STATUS     current
    DESCRIPTION
            "The UPS Model designation.(*)"
    ::= { upsIdent-fourth 2 }

upsIdentUPSSoftwareVersion-fourth OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-fourth 3 }

upsIdentAgentSoftwareVersion-fourth OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-fourth 4 }

upsIdentName-fourth OBJECT-TYPE
    SYNTAX     DisplayString (SIZE(0..63))
    MAX-ACCESS read-write
    STATUS     current
    DESCRIPTION
            "A string identifying the UPS.  This object should be
            set by the administrator.(*)"
    ::= { upsIdent-fourth 5 }

upsIdentAttachedDevices-fourth OBJECT-TYPE
    SYNTAX     DisplayString (SIZE(0..63))
    MAX-ACCESS read-write
    STATUS     current
    DESCRIPTION
            "A string identifying the devices attached to the
            output(s) of the UPS.  This object should be set by
            the administrator.(*)"
    ::= { upsIdent-fourth 6 }

upsIdentUPSSerialNumber-fourth OBJECT-TYPE
    SYNTAX     DisplayString (SIZE(0..31))
    MAX-ACCESS read-only
    STATUS     current
    DESCRIPTION
            "The UPS serial number"
    ::= { upsIdent-fourth 7 }
				
upsIdentComProtVersion-fourth OBJECT-TYPE
    SYNTAX     DisplayString (SIZE(0..15))
    MAX-ACCESS read-only
    STATUS     current
    DESCRIPTION
            "The IMV communication protocol version"
    ::= { upsIdent-fourth 8 }	
		
upsIdentOperatingTime-fourth OBJECT-TYPE
    SYNTAX     NonNegativeInteger32
    UNITS      "seconds"
    MAX-ACCESS read-only
    STATUS     current
    DESCRIPTION
            "The present value of the operating time.
             total 'on' time since UPS manufactured"
    ::= { upsIdent-fourth 9 }	
				
--
-- Battery Group Generic
--

upsBatteryStatus-fourth OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-fourth 1 }

upsSecondsOnBattery-fourth OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-fourth 2 }

upsEstimatedMinutesRemaining-fourth OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-fourth 3 }

upsEstimatedChargeRemaining-fourth OBJECT-TYPE
    SYNTAX     Integer32 (0..100)
    UNITS      "percent"
    MAX-ACCESS read-only
    STATUS     current
    DESCRIPTION
            "An estimate of the battery charge remaining expressed
            as a percent of full charge.(*)"
    ::= { upsBattery-fourth 4 }

upsBatteryVoltage-fourth OBJECT-TYPE
    SYNTAX     NonNegativeInteger32
    UNITS      "0.1 Volt DC"
    MAX-ACCESS read-only
    STATUS     current
    DESCRIPTION
            "The magnitude of the present battery voltage.(*)"
    ::= { upsBattery-fourth 5 }

upsBatteryCurrent-fourth OBJECT-TYPE
    SYNTAX     Integer32
    UNITS      "0.1 Amp DC"
    MAX-ACCESS read-only
    STATUS     current
    DESCRIPTION
            "The present battery current.(*)"
    ::= { upsBattery-fourth 6 }

upsBatteryTemperature-fourth OBJECT-TYPE
    SYNTAX     Integer32
    UNITS      "degrees Centigrade"
    MAX-ACCESS read-only
    STATUS     current
    DESCRIPTION
            "The ambient temperature at or near the UPS Battery
            casing.(*)"
    ::= { upsBattery-fourth 7 }

--
-- Input Group
--

upsInputLineBads-fourth OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-fourth 1 }

upsInputNumLines-fourth OBJECT-TYPE
    SYNTAX     NonNegativeInteger32
    MAX-ACCESS read-only
    STATUS     current
    DESCRIPTION
            "The number of input lines utilized in this device.
            This variable indicates the number of rows in the
            input table.(*)"
    ::= { upsInput-fourth 2 }

upsInputTable-fourth OBJECT-TYPE
    SYNTAX     SEQUENCE OF UpsInputEntry-fourth
    MAX-ACCESS not-accessible
    STATUS     current
    DESCRIPTION
            "A list of input table entries.  The number of entries
            is given by the value of upsInputNumLines.(*)"
    ::= { upsInput-fourth 3 }

upsInputEntry-fourth OBJECT-TYPE
    SYNTAX     UpsInputEntry-fourth
    MAX-ACCESS not-accessible
    STATUS     current
    DESCRIPTION
            "An entry containing information applicable to a
            particular input line.(*)"
    INDEX { upsInputLineIndex-fourth }
    ::= { upsInputTable-fourth 1 }

UpsInputEntry-fourth ::= SEQUENCE {
    upsInputLineIndex-fourth   PositiveInteger32,
    upsInputFrequency-fourth   NonNegativeInteger32,
    upsInputVoltage-fourth     NonNegativeInteger32,
    upsInputCurrent-fourth     NonNegativeInteger32,
    upsInputTruePower-fourth   NonNegativeInteger32,
    upsInputVoltageMin-fourth  NonNegativeInteger32,
    upsInputVoltageMax-fourth  NonNegativeInteger32
}

upsInputLineIndex-fourth OBJECT-TYPE
    SYNTAX     PositiveInteger32
    MAX-ACCESS not-accessible
    STATUS     current
    DESCRIPTION
            "The input line identifier.(*)"
    ::= { upsInputEntry-fourth 1 }

upsInputFrequency-fourth OBJECT-TYPE
    SYNTAX     NonNegativeInteger32
    UNITS      "0.1 Hertz"
    MAX-ACCESS read-only
    STATUS     current
    DESCRIPTION
            "The present input frequency.(*)"
    ::= { upsInputEntry-fourth 2 }

upsInputVoltage-fourth OBJECT-TYPE
    SYNTAX     NonNegativeInteger32
    UNITS      "RMS Volts"
    MAX-ACCESS read-only
    STATUS     current
    DESCRIPTION
            "The magnitude of the present input voltage.(*)"
    ::= { upsInputEntry-fourth 3 }

upsInputCurrent-fourth OBJECT-TYPE
    SYNTAX     NonNegativeInteger32
    UNITS      "0.1 RMS Amp"
    MAX-ACCESS read-only
    STATUS     current
    DESCRIPTION
            "The magnitude of the present input current.(*)"
    ::= { upsInputEntry-fourth 4 }

upsInputTruePower-fourth OBJECT-TYPE
    SYNTAX     NonNegativeInteger32
    UNITS      "Watts"
    MAX-ACCESS read-only
    STATUS     current
    DESCRIPTION
            "The magnitude of the present input true power.(*)"
    ::= { upsInputEntry-fourth 5 }

upsInputVoltageMin-fourth OBJECT-TYPE
    SYNTAX     NonNegativeInteger32
    UNITS      "RMS Volts"
    MAX-ACCESS read-only
    STATUS     current
    DESCRIPTION
            "The lowest magnitude of the input voltage since last read out."
    ::= { upsInputEntry-fourth 6 }

upsInputVoltageMax-fourth OBJECT-TYPE
    SYNTAX     NonNegativeInteger32
    UNITS      "RMS Volts"
    MAX-ACCESS read-only
    STATUS     current
    DESCRIPTION
            "The highest magnitude of the input voltage since last read out."
    ::= { upsInputEntry-fourth 7 }

--
-- The Output group.
--

upsOutputSource-fourth OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-fourth 1 }

upsOutputFrequency-fourth OBJECT-TYPE
    SYNTAX     NonNegativeInteger32
    UNITS      "0.1 Hertz"
    MAX-ACCESS read-only
    STATUS     current
    DESCRIPTION
            "The present output frequency.(*)"
    ::= { upsOutput-fourth 2 }

upsOutputNumLines-fourth OBJECT-TYPE
    SYNTAX     NonNegativeInteger32
    MAX-ACCESS read-only
    STATUS     current
    DESCRIPTION
            "The number of output lines utilized in this device.
            This variable indicates the number of rows in the
            output table.(*)"
    ::= { upsOutput-fourth 3 }

upsOutputTable-fourth OBJECT-TYPE
    SYNTAX     SEQUENCE OF UpsOutputEntry-fourth
    MAX-ACCESS not-accessible
    STATUS     current
    DESCRIPTION
            "A list of output table entries.  The number of
            entries is given by the value of upsOutputNumLines.(*)"
    ::= { upsOutput-fourth 4 }

upsOutputEntry-fourth OBJECT-TYPE
    SYNTAX     UpsOutputEntry-fourth
    MAX-ACCESS not-accessible
    STATUS     current
    DESCRIPTION
            "An entry containing information applicable to a
            particular output line.(*)"
    INDEX { upsOutputLineIndex-fourth }
    ::= { upsOutputTable-fourth 1 }

UpsOutputEntry-fourth ::= SEQUENCE {
    upsOutputLineIndex-fourth   PositiveInteger32,
    upsOutputVoltage-fourth     NonNegativeInteger32,
    upsOutputCurrent-fourth     NonNegativeInteger32,
    upsOutputPower-fourth       NonNegativeInteger32,
    upsOutputPercentLoad-fourth Integer32
}

upsOutputLineIndex-fourth OBJECT-TYPE
    SYNTAX     PositiveInteger32
    MAX-ACCESS not-accessible
    STATUS     current
    DESCRIPTION
            "The output line identifier.(*)"
    ::= { upsOutputEntry-fourth 1 }

upsOutputVoltage-fourth OBJECT-TYPE
    SYNTAX     NonNegativeInteger32
    UNITS      "RMS Volts"
    MAX-ACCESS read-only
    STATUS     current
    DESCRIPTION
            "The present output voltage.(*)"
    ::= { upsOutputEntry-fourth 2 }

upsOutputCurrent-fourth OBJECT-TYPE
    SYNTAX     NonNegativeInteger32
    UNITS      "0.1 RMS Amp"
    MAX-ACCESS read-only
    STATUS     current
    DESCRIPTION
            "The present output current.(*)"
    ::= { upsOutputEntry-fourth 3 }

upsOutputPower-fourth OBJECT-TYPE
    SYNTAX     NonNegativeInteger32
    UNITS      "Watts"
    MAX-ACCESS read-only
    STATUS     current
    DESCRIPTION
            "The present output true power.(*)"
    ::= { upsOutputEntry-fourth 4 }

upsOutputPercentLoad-fourth OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-fourth 5 }

--
-- The Bypass group generic.
--

upsBypassFrequency-fourth OBJECT-TYPE
    SYNTAX     NonNegativeInteger32
    UNITS      "0.1 Hertz"
    MAX-ACCESS read-only
    STATUS     current
    DESCRIPTION
            "The present bypass frequency.(*)"
    ::= { upsBypass-fourth 1 }

upsBypassNumLines-fourth OBJECT-TYPE
    SYNTAX     NonNegativeInteger32
    MAX-ACCESS read-only
    STATUS     current
    DESCRIPTION
            "The number of bypass lines utilized in this device.
            This entry indicates the number of rows in the bypass
            table.(*)"
    ::= { upsBypass-fourth 2 }

upsBypassTable-fourth OBJECT-TYPE
    SYNTAX     SEQUENCE OF UpsBypassEntry-fourth
    MAX-ACCESS not-accessible
    STATUS     current
    DESCRIPTION
            "A list of bypass table entries.  The number of
            entries is given by the value of upsBypassNumLines.(*)"
    ::= { upsBypass-fourth 3 }

upsBypassEntry-fourth OBJECT-TYPE
    SYNTAX     UpsBypassEntry-fourth
    MAX-ACCESS not-accessible
    STATUS     current
    DESCRIPTION
            "An entry containing information applicable to a
            particular bypass input.(*)"
    INDEX { upsBypassLineIndex-fourth }
    ::= { upsBypassTable-fourth 1 }

UpsBypassEntry-fourth ::= SEQUENCE {
    upsBypassLineIndex-fourth  PositiveInteger32,
    upsBypassVoltage-fourth    NonNegativeInteger32,
    upsBypassCurrent-fourth    NonNegativeInteger32,
    upsBypassPower-fourth      NonNegativeInteger32
}

upsBypassLineIndex-fourth OBJECT-TYPE
    SYNTAX     PositiveInteger32
    MAX-ACCESS not-accessible
    STATUS     current
    DESCRIPTION
            "The bypass line identifier.(*)"
    ::= { upsBypassEntry-fourth 1 }

upsBypassVoltage-fourth OBJECT-TYPE
    SYNTAX     NonNegativeInteger32
    UNITS      "RMS Volts"
    MAX-ACCESS read-only
    STATUS     current
    DESCRIPTION
            "The present bypass voltage.(*)"
    ::= { upsBypassEntry-fourth 2 }

upsBypassCurrent-fourth OBJECT-TYPE
    SYNTAX     NonNegativeInteger32
    UNITS      "0.1 RMS Amp"
    MAX-ACCESS read-only
    STATUS     current
    DESCRIPTION
            "The present bypass current.(*)"
    ::= { upsBypassEntry-fourth 3 }

upsBypassPower-fourth OBJECT-TYPE
    SYNTAX     NonNegativeInteger32
    UNITS      "Watts"
    MAX-ACCESS read-only
    STATUS     current
    DESCRIPTION
            "The present true power conveyed by the bypass.(*)"
    ::= { upsBypassEntry-fourth 4 }

--
-- The Alarm group generic.
--

upsAlarmsPresent-fourth OBJECT-TYPE
    SYNTAX     Gauge32
    MAX-ACCESS read-only
    STATUS     current
    DESCRIPTION
            "The present number of active alarm conditions.(*)"
    ::= { upsAlarm-fourth 1 }

upsAlarmTable-fourth OBJECT-TYPE
    SYNTAX     SEQUENCE OF UpsAlarmEntry-fourth
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-fourth 2 }

upsAlarmEntry-fourth OBJECT-TYPE
    SYNTAX     UpsAlarmEntry-fourth
    MAX-ACCESS not-accessible
    STATUS     current
    DESCRIPTION
            "An entry containing information applicable to a
            particular alarm.(*)"
    INDEX { upsAlarmId-fourth }
    ::= { upsAlarmTable-fourth 1 }

UpsAlarmEntry-fourth ::= SEQUENCE {
    upsAlarmId-fourth          PositiveInteger32,
    upsAlarmDescr-fourth       AutonomousType,
    upsAlarmTime-fourth       TimeStamp
}

upsAlarmId-fourth OBJECT-TYPE
    SYNTAX     PositiveInteger32
    MAX-ACCESS not-accessible
    STATUS     current
    DESCRIPTION
            "A unique identifier for an alarm condition.  This
            value must remain constant.(*)"
    ::= { upsAlarmEntry-fourth 1 }

upsAlarmDescr-fourth OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-fourth 2 }

upsAlarmTime-fourth OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-fourth 3 }

--
-- Well known alarm conditions generic.
--

upsAlarmBatteryBad-fourth OBJECT-IDENTITY
    STATUS     current
    DESCRIPTION
            "One or more batteries have been determined to require
            replacement.(*)"
    ::= { upsWellKnownAlarms-fourth  1 }

upsAlarmOnBattery-fourth OBJECT-IDENTITY
    STATUS     current
    DESCRIPTION
            "The UPS is drawing power from the batteries.(*)"
    ::= { upsWellKnownAlarms-fourth  2 }

upsAlarmLowBattery-fourth OBJECT-IDENTITY
    STATUS     current
    DESCRIPTION
            "The remaining battery run-time is less than or equal
            to upsConfigLowBattTime.(*)"
    ::= { upsWellKnownAlarms-fourth  3 }

upsAlarmDepletedBattery-fourth OBJECT-IDENTITY
    STATUS     current
    DESCRIPTION
            "The UPS will be unable to sustain the present load
            when and if the utility power is lost.(*)"
    ::= { upsWellKnownAlarms-fourth  4 }

upsAlarmTempBad-fourth OBJECT-IDENTITY
    STATUS     current
    DESCRIPTION
            "A temperature is out of tolerance.(*)"
    ::= { upsWellKnownAlarms-fourth  5 }

upsAlarmInputBad-fourth OBJECT-IDENTITY
    STATUS     current
    DESCRIPTION
            "An input condition is out of tolerance.(*)"
    ::= { upsWellKnownAlarms-fourth  6 }

upsAlarmOutputBad-fourth OBJECT-IDENTITY
    STATUS     current
    DESCRIPTION
            "An output condition (other than OutputOverload) is
            out of tolerance.(*)"
    ::= { upsWellKnownAlarms-fourth  7 }

upsAlarmOutputOverload-fourth OBJECT-IDENTITY
    STATUS     current
    DESCRIPTION
            "The output load exceeds the UPS output capacity.(*)"
    ::= { upsWellKnownAlarms-fourth  8 }

upsAlarmOnBypass-fourth OBJECT-IDENTITY
    STATUS     current
    DESCRIPTION
            "The Bypass is presently engaged on the UPS.(*)"
    ::= { upsWellKnownAlarms-fourth  9 }

upsAlarmBypassBad-fourth OBJECT-IDENTITY
    STATUS     current
    DESCRIPTION
            "The Bypass is out of tolerance.(*)"
    ::= { upsWellKnownAlarms-fourth 10 }

upsAlarmOutputOffAsRequested-fourth OBJECT-IDENTITY
    STATUS     current
    DESCRIPTION
            "The UPS has shutdown as requested, i.e., the output
            is off.(*)"
    ::= { upsWellKnownAlarms-fourth 11 }

upsAlarmUpsOffAsRequested-fourth OBJECT-IDENTITY
    STATUS     current
    DESCRIPTION
            "The entire UPS has shutdown as commanded.(*)"
    ::= { upsWellKnownAlarms-fourth 12 }

upsAlarmChargerFailed-fourth OBJECT-IDENTITY
    STATUS     current
    DESCRIPTION
            "An uncorrected problem has been detected within the
            UPS charger subsystem.(*)"
    ::= { upsWellKnownAlarms-fourth 13 }

upsAlarmUpsOutputOff-fourth OBJECT-IDENTITY
    STATUS     current
    DESCRIPTION
            "The output of the UPS is in the off state.(*)"
    ::= { upsWellKnownAlarms-fourth 14 }

upsAlarmUpsSystemOff-fourth OBJECT-IDENTITY
    STATUS     current
    DESCRIPTION
            "The UPS system is in the off state.(*)"
    ::= { upsWellKnownAlarms-fourth 15 }

upsAlarmFanFailure-fourth OBJECT-IDENTITY
    STATUS     current
    DESCRIPTION
            "The failure of one or more fans in the UPS has been
            detected.(*)"
    ::= { upsWellKnownAlarms-fourth 16 }

upsAlarmFuseFailure-fourth OBJECT-IDENTITY
    STATUS     current
    DESCRIPTION
            "The failure of one or more fuses has been detected.(*)"
    ::= { upsWellKnownAlarms-fourth 17 }

upsAlarmGeneralFault-fourth OBJECT-IDENTITY
    STATUS     current
    DESCRIPTION
            "A general fault in the UPS has been detected.(*)"
    ::= { upsWellKnownAlarms-fourth 18 }

upsAlarmDiagnosticTestFailed-fourth OBJECT-IDENTITY
    STATUS     current
    DESCRIPTION
            "The result of the last diagnostic test indicates a
            failure.(*)"
    ::= { upsWellKnownAlarms-fourth 19 }

upsAlarmCommunicationsLost-fourth OBJECT-IDENTITY
    STATUS     current
    DESCRIPTION
            "A problem has been encountered in the communications
            between the agent and the UPS.(*)"
    ::= { upsWellKnownAlarms-fourth 20 }

upsAlarmAwaitingPower-fourth OBJECT-IDENTITY
    STATUS     current
    DESCRIPTION
            "The UPS output is off and the UPS is awaiting the
            return of input power.(*)"
    ::= { upsWellKnownAlarms-fourth 21 }

upsAlarmShutdownPending-fourth OBJECT-IDENTITY
    STATUS     current
    DESCRIPTION
            "A upsShutdownAfterDelay countdown is underway.(*)"
    ::= { upsWellKnownAlarms-fourth 22 }

upsAlarmShutdownImminent-fourth OBJECT-IDENTITY
    STATUS     current
    DESCRIPTION
            "The UPS will turn off power to the load in less than
            5 seconds; this may be either a timed shutdown or a
            low battery shutdown.(*)"
    ::= { upsWellKnownAlarms-fourth 23 }

upsAlarmTestInProgress-fourth OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-fourth 24 }

upsAlarmReceptacleOff-fourth OBJECT-IDENTITY
    STATUS     current
    DESCRIPTION
            "The receptacle are switch off    "
    ::= { upsWellKnownAlarms-fourth 25 }

upsAlarmMaskA-fourth OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-fourth 4 }

--
-- The Test Group generic
--

upsTestId-fourth OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-fourth 1 }

-- see [6] for more information on the semantics of objects with
-- syntax of TestAndIncr

upsTestSpinLock-fourth OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-fourth 2 }

upsTestResultsSummary-fourth OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-fourth 3 }

upsTestResultsDetail-fourth OBJECT-TYPE
    SYNTAX     DisplayString (SIZE (0..255))
    MAX-ACCESS read-only
    STATUS     current
    DESCRIPTION
            "Additional information about upsTestResultsSummary.
            If no additional information available, a zero length
            string is returned.(*)"
    ::= { upsTest-fourth 4 }

upsTestStartTime-fourth OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-fourth 5 }

upsTestElapsedTime-fourth OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-fourth 6 }

--
-- Well known tests generic.
--

upsTestNoTestsInitiated-fourth OBJECT-IDENTITY
    STATUS     current
    DESCRIPTION
            "No tests have been initiated and no test is in
            progress.(*)"
    ::= { upsWellKnownTests-fourth  1 }

upsTestAbortTestInProgress-fourth OBJECT-IDENTITY
    STATUS     current
    DESCRIPTION
            "The test in progress is to be aborted / the test in
            progress was aborted.(*)"
    ::= { upsWellKnownTests-fourth  2 }

upsTestGeneralSystemsTest-fourth OBJECT-IDENTITY
    STATUS     current
    DESCRIPTION
            "The manufacturer's standard test of UPS device
            systems.(*)"
    ::= { upsWellKnownTests-fourth  3 }

upsTestQuickBatteryTest-fourth OBJECT-IDENTITY
    STATUS     current
    DESCRIPTION
            "A test that is sufficient to determine if the battery
            needs replacement.(*)"
    ::= { upsWellKnownTests-fourth  4 }

upsTestDeepBatteryCalibration-fourth OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-fourth  5 }

--
-- The Control group generic.
--

upsShutdownType-fourth OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-fourth 1 }

upsShutdownAfterDelay-fourth OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-fourth 2 }

upsStartupAfterDelay-fourth OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-fourth 3 }

upsRebootWithDuration-fourth OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-fourth 4 }

upsAutoRestart-fourth OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-fourth 5 }

upsReceptaclesNum-fourth OBJECT-TYPE
    SYNTAX     NonNegativeInteger32
    MAX-ACCESS read-only
    STATUS     current
    DESCRIPTION
            "The number of receptacles utilized in this device.
            This entry indicates the number of rows in the receptacle
            table."
    ::= { upsControl-fourth 6 }

upsReceptacleTable-fourth OBJECT-TYPE
    SYNTAX     SEQUENCE OF UpsReceptacleEntry-fourth
    MAX-ACCESS not-accessible
    STATUS     current
    DESCRIPTION
            "A list of receptacle table entries.  The number of
            entries is given by the value of upsReceptacleNum."
    ::= { upsControl-fourth 7 }

upsReceptacleEntry-fourth OBJECT-TYPE
    SYNTAX     UpsReceptacleEntry-fourth
    MAX-ACCESS not-accessible
    STATUS     current
    DESCRIPTION
            "An entry containing information applicable to a
            particular receptacle."
    INDEX { upsReceptacleLineIndex-fourth }
    ::= { upsReceptacleTable-fourth 1 }

UpsReceptacleEntry-fourth ::= SEQUENCE {
    upsReceptacleLineIndex-fourth  PositiveInteger32,
    upsReceptacleOnOff-fourth      Integer32    
}

upsReceptacleLineIndex-fourth OBJECT-TYPE
    SYNTAX     PositiveInteger32
    MAX-ACCESS not-accessible
    STATUS     current
    DESCRIPTION
            "The receptacle line identifier."
    ::= { upsReceptacleEntry-fourth 1 }

upsReceptacleOnOff-fourth OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-fourth 2 }

upsUPSMode-fourth OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-fourth 8 }

upsRectifierOnOff-fourth OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-fourth 9 }

upsBatteryChargeMethod-fourth OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-fourth 10 }

upsInverterOnOff-fourth OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-fourth 11 }

upsBypassOnOff-fourth OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-fourth 12 }

upsLoadSource-fourth OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-fourth 13 }
	
--
-- The Configuration group generic.
--

upsConfigInputVoltage-fourth OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-fourth 1 }

upsConfigInputFreq-fourth OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-fourth 2 }

upsConfigOutputVoltage-fourth OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-fourth 3 }

upsConfigOutputFreq-fourth OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-fourth 4 }

upsConfigOutputVA-fourth OBJECT-TYPE
    SYNTAX     NonNegativeInteger32
    UNITS      "Volt-Amps"
    MAX-ACCESS read-only
    STATUS     current
    DESCRIPTION
            "The magnitude of the nominal Volt-Amp rating.(*)"
    ::= { upsConfig-fourth 5 }

upsConfigOutputPower-fourth OBJECT-TYPE
    SYNTAX     NonNegativeInteger32
    UNITS      "Watts"
    MAX-ACCESS read-only
    STATUS     current
    DESCRIPTION
            "The magnitude of the nominal true power rating.(*)"
    ::= { upsConfig-fourth 6 }

upsConfigLowBattTime-fourth OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-fourth 7 }

upsConfigAudibleStatus-fourth OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-fourth 8 }

upsConfigLowVoltageTransferPoint-fourth OBJECT-TYPE
    SYNTAX     NonNegativeInteger32
    UNITS      "RMS Volts"
    MAX-ACCESS read-write
    STATUS     current
    DESCRIPTION
            "The minimum input line voltage allowed before the UPS
            system transfers to battery backup.(*)"
    ::= { upsConfig-fourth 9 }

upsConfigHighVoltageTransferPoint-fourth OBJECT-TYPE
    SYNTAX     NonNegativeInteger32
    UNITS      "RMS Volts"
    MAX-ACCESS read-write
    STATUS     current
    DESCRIPTION
            "The maximum line voltage allowed before the UPS
            system transfers to battery backup.(*)"
    ::= { upsConfig-fourth 10 }

upsConfigBatteryCapacity-fourth OBJECT-TYPE
    SYNTAX     NonNegativeInteger32
    UNITS      "Amps Hours"
    MAX-ACCESS read-write
    STATUS     current
    DESCRIPTION
            "The installed battery capacity. This value is the 'factory'-value,
             not the value after calibration."
    ::= { upsConfig-fourth 11 }

upsConfigBatteryChargeCurrent-fourth OBJECT-TYPE
    SYNTAX     NonNegativeInteger32
    UNITS      "0.1 Amp DC"
    MAX-ACCESS read-write
    STATUS     current
    DESCRIPTION
            "The maximum battery charge current, including external chargers."
    ::= { upsConfig-fourth 12 }						

upsConfigNoLoadShutdown-fourth OBJECT-TYPE
    SYNTAX     Integer32 {
        disabled(1),
        enabled(2)
    }
    MAX-ACCESS read-write
    STATUS     current
    DESCRIPTION
            "Dis- or enable 'no load' shutdown from the contact interface."
    ::= { upsConfig-fourth 13 }
	
upsConfigStartDelay-fourth OBJECT-TYPE
    SYNTAX     PositiveInteger32
    UNITS      "minutes"				
    MAX-ACCESS read-write
    STATUS     current
    DESCRIPTION
            "Minimum required autonomy time before the UPS may perform an
             autorestart."
    ::= { upsConfig-fourth 14 }

--
-- The GetSet group generic.
--

upsEventGetNext-fourth OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-fourth 1 }

upsEventGetPrevious-fourth OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-fourth 2 }
				
upsEventSetStartingTimeStamp-fourth OBJECT-TYPE
    SYNTAX     NonNegativeInteger32
    MAX-ACCESS read-write
    STATUS     current
    DESCRIPTION
            "The timestamp which is used as starting point for downloading
             events from the UPS event buffer"
    ::= { upsGetSet-fourth 3 }				

upsEventRetreiveCurrentTimeStamp-fourth OBJECT-TYPE
    SYNTAX     NonNegativeInteger32
    MAX-ACCESS read-only
    STATUS     current
    DESCRIPTION
            "The current timestamp is retreived from the UPS"
    ::= { upsGetSet-fourth 4 }				

upsEventTableSize-fourth OBJECT-TYPE
    SYNTAX     NonNegativeInteger32
    MAX-ACCESS read-only
    STATUS     current
    DESCRIPTION
            "The number of entries in the event table.
            This object indicates the number of rows in the event table."
    ::= { upsGetSet-fourth 5 }

upsEventTable-fourth OBJECT-TYPE
    SYNTAX     SEQUENCE OF UpsEventEntry-fourth
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-fourth 6 }

upsEventEntry-fourth OBJECT-TYPE
    SYNTAX     UpsEventEntry-fourth
    MAX-ACCESS not-accessible
    STATUS     current
    DESCRIPTION
            "An entry containing information applicable to a
            particular event."
    INDEX { upsEventLineIndex-fourth }
    ::= { upsEventTable-fourth 1 }

UpsEventEntry-fourth ::= SEQUENCE {
    upsEventLineIndex-fourth PositiveInteger32,
    upsEventCode-fourth      Integer32,
    upsEventStatus-fourth    NonNegativeInteger32,
    upsEventTime-fourth      NonNegativeInteger32
}

upsEventLineIndex-fourth OBJECT-TYPE
    SYNTAX     PositiveInteger32
    MAX-ACCESS not-accessible
    STATUS     current
    DESCRIPTION
            "The event line identifier."
    ::= { upsEventEntry-fourth 1 }

upsEventCode-fourth OBJECT-TYPE
    SYNTAX     NonNegativeInteger32
    MAX-ACCESS read-only
    STATUS     current
    DESCRIPTION
            "The event code in numerical format."
    ::= { upsEventEntry-fourth 2 }

upsEventStatus-fourth OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-fourth 3 }

upsEventTime-fourth OBJECT-TYPE
    SYNTAX     NonNegativeInteger32
    MAX-ACCESS read-only
    STATUS     current
    DESCRIPTION
            "The timestamp of the moment the event was generated."
    ::= { upsEventEntry-fourth 4 }

upsParametersRead-fourth OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-fourth 7 }

upsParametersWrite-fourth OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-fourth 8 }

upsParametersStartAddress-fourth OBJECT-TYPE
    SYNTAX     NonNegativeInteger32
    MAX-ACCESS read-write
    STATUS     current
    DESCRIPTION
            "The address which is used as starting point for downloading
             parameters from the UPS"
    ::= { upsGetSet-fourth 9 }				

upsParameterTableSize-fourth OBJECT-TYPE
    SYNTAX     NonNegativeInteger32
    MAX-ACCESS read-only
    STATUS     current
    DESCRIPTION
            "The number of entries in the parameter table.
            This object indicates the number of rows in the parameter table."
    ::= { upsGetSet-fourth 10 }

upsParameterTable-fourth OBJECT-TYPE
    SYNTAX     SEQUENCE OF UpsParameterEntry-fourth
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-fourth 11 }

upsParameterEntry-fourth OBJECT-TYPE
    SYNTAX     UpsParameterEntry-fourth
    MAX-ACCESS not-accessible
    STATUS     current
    DESCRIPTION
            "An entry containing information applicable to a
            particular parameter."
    INDEX { upsParameterLineIndex-fourth }
    ::= { upsParameterTable-fourth 1 }

UpsParameterEntry-fourth ::= SEQUENCE {
    upsParameterLineIndex-fourth PositiveInteger32,
    upsParameterValue-fourth     Integer32   
}

upsParameterLineIndex-fourth OBJECT-TYPE
    SYNTAX     PositiveInteger32
    MAX-ACCESS not-accessible
    STATUS     current
    DESCRIPTION
            "The parameter line identifier."
    ::= { upsParameterEntry-fourth 1 }

upsParameterValue-fourth OBJECT-TYPE
    SYNTAX     Integer32
    MAX-ACCESS read-write
    STATUS     current
    DESCRIPTION
            "The parameter value in numerical format."
    ::= { upsParameterEntry-fourth 2 }

upsStatus-fourth OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-fourth 12 }

upsMainsStatisticsMBfail-fourth OBJECT-TYPE
    SYNTAX     NonNegativeInteger32
    MAX-ACCESS read-only
    STATUS     current
    DESCRIPTION
            "Count of main bypass failures (>200 ms), since UPS installation."
    ::= { upsGetSet-fourth 13 }

upsMainsStatisticsMRfail-fourth OBJECT-TYPE
    SYNTAX     NonNegativeInteger32
    MAX-ACCESS read-only
    STATUS     current
    DESCRIPTION
            "Count of mains rectifier failures (>200 ms), since UPS installation."
    ::= { upsGetSet-fourth 14 }
		
upsMainsStatisticsB2-fourth OBJECT-TYPE
    SYNTAX     NonNegativeInteger32
    MAX-ACCESS read-only
    STATUS     current
    DESCRIPTION
            "Count of transients on the mains bypass (0..2 ms), during the last 7 days."
    ::= { upsGetSet-fourth 15 }

upsMainsStatisticsB5-fourth OBJECT-TYPE
    SYNTAX     NonNegativeInteger32
    MAX-ACCESS read-only
    STATUS     current
    DESCRIPTION
            "Count of transients on the mains bypass (2..5 ms), during the last 7 days."
    ::= { upsGetSet-fourth 16 }

upsMainsStatisticsB10-fourth OBJECT-TYPE
    SYNTAX     NonNegativeInteger32
    MAX-ACCESS read-only
    STATUS     current
    DESCRIPTION
            "Count of transients on the mains bypass (5..10 ms), during the last 7 days."
    ::= { upsGetSet-fourth 17 }

upsMainsStatisticsB200-fourth OBJECT-TYPE
    SYNTAX     NonNegativeInteger32
    MAX-ACCESS read-only
    STATUS     current
    DESCRIPTION
            "Count of transients on the mains bypass (10..200 ms), during the last 7 days."
    ::= { upsGetSet-fourth 18 }

upsMainsStatisticsBypRel-fourth OBJECT-TYPE
    SYNTAX     NonNegativeInteger32
    MAX-ACCESS read-only
    STATUS     current
    DESCRIPTION
            "Bypass reliability degree [0..100%;255]. The value NOSUCHNAME means 'not available'."
    ::= { upsGetSet-fourth 19 }

upsTime-fourth OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-fourthERROR,              meaning 'command not supported'. It is possible to know which is the timestamp 
             format supported by the UPS, by issuing a read-command or by reading events, 
             which includes timestamps."
    ::= { upsGetSet-fourth 20 }

upsRequestPermission-fourth OBJECT-TYPE
    SYNTAX     DisplayString (SIZE(0..63))
    MAX-ACCESS write-only
    STATUS     current
    DESCRIPTION
            "An encrypted code is send to enable use of restricted write objects during
             a limited period of time."
    ::= { upsGetSet-fourth 21 }

upsEventGetCode-fourth OBJECT-TYPE
    SYNTAX     Integer32
    MAX-ACCESS write-only
    STATUS     current
    DESCRIPTION
            "The code which is used as starting point to downloading the events from the 
            UPS event buffer."
    ::= { upsGetSet-fourth 22 }    
    
upsEventSpinLock-fourth OBJECT-TYPE
    SYNTAX     TestAndIncr
    MAX-ACCESS read-write
    STATUS     current
    DESCRIPTION
            "A spin lock on the event subsystem. "

    ::= { upsGetSet-fourth 23 }
    
upsParameterSpinLock-fourth OBJECT-TYPE
    SYNTAX     TestAndIncr
    MAX-ACCESS read-write
    STATUS     current
    DESCRIPTION
            "A spin lock on the parameters subsystem. "

    ::= { upsGetSet-fourth 24 }

--
-- GE Trap group generic
--

upsAlarmBatteryBad-fourth TRAP-TYPE
    ENTERPRISE geUPSTraps-fourth
    VARIABLES  { trapArg  }
    DESCRIPTION
            "One or more batteries have been determined to require
            replacement."
    ::= 1

upsAlarmOnBattery-fourth TRAP-TYPE
    ENTERPRISE geUPSTraps-fourth
    VARIABLES  { trapArg , upsSecondsOnBattery-fourth  }
    DESCRIPTION
            "An On Battery condition is restored."
    ::= 2

upsAlarmLowBattery-fourth TRAP-TYPE
    ENTERPRISE geUPSTraps-fourth
    VARIABLES  { trapArg  }
    DESCRIPTION
            "The remaining battery run-time is less than or equal
            to upsConfigLowBattTime."
    ::= 3

upsAlarmDepletedBattery-fourth TRAP-TYPE
    ENTERPRISE geUPSTraps-fourth
    VARIABLES  { trapArg  }
    DESCRIPTION
            "The UPS will be unable to sustain the present load
            when and if the utility power is lost)"
    ::= 4

upsAlarmTempBad-fourth TRAP-TYPE
    ENTERPRISE geUPSTraps-fourth
    VARIABLES  { trapArg , upsBatteryTemperature }
    DESCRIPTION
            "A temperature is out of tolerance."
    ::= 5

upsAlarmInputBad-fourth TRAP-TYPE
    ENTERPRISE geUPSTraps-fourth
    VARIABLES  { trapArg  }
    DESCRIPTION
            "An input condition is out of tolerance."
    ::= 6

upsAlarmOutputBad-fourth TRAP-TYPE
    ENTERPRISE geUPSTraps-fourth
    VARIABLES  { trapArg  }
    DESCRIPTION
            "An output condition (other than OutputOverload) is
            out of tolerance."
    ::= 7

upsAlarmOutputOverload-fourth TRAP-TYPE
    ENTERPRISE geUPSTraps-fourth
    VARIABLES  { trapArg , upsOutputPercentLoad-fourth }
    DESCRIPTION
            "The output load exceeds the UPS output capacity."
    ::= 8

upsAlarmOnBypass-fourth TRAP-TYPE
    ENTERPRISE geUPSTraps-fourth
    VARIABLES  { trapArg  }
    DESCRIPTION
            "The Bypass is presently engaged on the UPS."
    ::= 9

upsAlarmBypassBad-fourth TRAP-TYPE
    ENTERPRISE geUPSTraps-fourth
    VARIABLES  { trapArg  }
    DESCRIPTION
            "The Bypass is out of tolerance."
    ::= 10

upsAlarmOutputOffAsRequested-fourth TRAP-TYPE
    ENTERPRISE geUPSTraps-fourth
    VARIABLES  { trapArg  }
    DESCRIPTION
            "The UPS has shutdown as requested, i.e., the output
            is off."
    ::= 11

upsAlarmUpsOffAsRequested-fourth TRAP-TYPE
    ENTERPRISE geUPSTraps-fourth-fourth
    VARIABLES  { trapArg  }
    DESCRIPTION
            "The entire UPS has shutdown as commanded."
    ::= 12

upsAlarmChargerFailed-fourth TRAP-TYPE
    ENTERPRISE geUPSTraps-fourth
    VARIABLES  { trapArg  }
    DESCRIPTION
            "An uncorrected problem has been detected within the
            UPS charger subsystem."
    ::= 13

upsAlarmUpsOutputOff-fourth TRAP-TYPE
    ENTERPRISE geUPSTraps-fourth
    VARIABLES  { trapArg  }
    DESCRIPTION
            "The output of the UPS is in the off state."
    ::= 14

upsAlarmUpsSystemOff-fourth TRAP-TYPE
    ENTERPRISE geUPSTraps-fourth
    VARIABLES  { trapArg  }
    DESCRIPTION
            "The UPS system is in the off state."
    ::= 15

upsAlarmFanFailure-fourth TRAP-TYPE
    ENTERPRISE geUPSTraps-fourth
    VARIABLES  { trapArg  }
    DESCRIPTION
            "The failure of one or more fans in the UPS has been
            detected."
    ::= 16

upsAlarmFuseFailure-fourth TRAP-TYPE
    ENTERPRISE geUPSTraps-fourth
    VARIABLES  { trapArg  }
    DESCRIPTION
            "The failure of one or more fuses has been detected."
    ::= 17

upsAlarmGeneralFault-fourth TRAP-TYPE
    ENTERPRISE geUPSTraps-fourth
    VARIABLES  { trapArg  }
    DESCRIPTION
            "A general fault in the UPS has been detected."
    ::= 18

upsAlarmDiagnosticTestFailed-fourth TRAP-TYPE
    ENTERPRISE geUPSTraps-fourth
    VARIABLES  { trapArg  }
    DESCRIPTION
            "The result of the last diagnostic test indicates a
            failure."
    ::= 19

upsAlarmCommunicationsLost-fourth TRAP-TYPE
    ENTERPRISE geUPSTraps-fourth
    VARIABLES  { trapArg  }
    DESCRIPTION
            "A problem has been encountered in the communication
            between the agent and the UPS."
    ::= 20
    
upsAlarmAwaitingPower-fourth TRAP-TYPE
    ENTERPRISE geUPSTraps-fourth
    VARIABLES  { trapArg  }
    DESCRIPTION
            "The UPS output is off and the UPS is awaiting the
            return of the input power (*)."
    ::= 21    

upsAlarmShutdownPending-fourth TRAP-TYPE
    ENTERPRISE geUPSTraps-fourth
    VARIABLES  { trapArg , upsShutdownAfterDelay-fourth }
    DESCRIPTION
            "A upsShutdownAfterDelay countdown is underway."
    ::= 22

upsAlarmShutdownImminent-fourth TRAP-TYPE
    ENTERPRISE geUPSTraps-fourth
    VARIABLES  { trapArg  }
    DESCRIPTION
            "The UPS will turn off power to the load in less than
            5 seconds; this may be either a timed shutdown or a
            low battery shutdown."
    ::= 23

upsAlarmTestInProgress-fourth TRAP-TYPE
    ENTERPRISE geUPSTraps-fourth
    VARIABLES  { trapArg , upsTestId-fourth }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-fourth TRAP-TYPE
    ENTERPRISE geUPSTraps-fourth
    VARIABLES  { trapArg  }
    DESCRIPTION
            "A receptacle has been switched off."
    ::= 25

upsAlarmBatteryBadRestored-fourth TRAP-TYPE
    ENTERPRISE geUPSTraps-fourth
    VARIABLES  { trapArg  }
    DESCRIPTION
            "A Battery bad condition is restored."
    ::= 33

upsAlarmOnBatteryRestored-fourth TRAP-TYPE
    ENTERPRISE geUPSTraps-fourth
    VARIABLES  { trapArg  }
    DESCRIPTION
            "The UPS is drawing power from mains again."
    ::= 34

upsAlarmLowBatteryRestored-fourth TRAP-TYPE
    ENTERPRISE geUPSTraps-fourth
    VARIABLES  { trapArg  }
    DESCRIPTION
            "A Low Battery condition is restored."
    ::= 35

upsAlarmDepletedBatteryRestored-fourth TRAP-TYPE
    ENTERPRISE geUPSTraps-fourth
    VARIABLES  { trapArg  }
    DESCRIPTION
            "A Depleted Battery condition is restored."
    ::= 36

upsAlarmTempBadRestored-fourth TRAP-TYPE
    ENTERPRISE geUPSTraps-fourth
    VARIABLES  { trapArg  }
    DESCRIPTION
            "A bad temperature condition is restored."
    ::= 37

upsAlarmInputBadRestored-fourth TRAP-TYPE
    ENTERPRISE geUPSTraps-fourth
    VARIABLES  { trapArg  }
    DESCRIPTION
            "An input bad condition is restored."
    ::= 38

upsAlarmOutputBadRestored-fourth TRAP-TYPE
    ENTERPRISE geUPSTraps-fourth
    VARIABLES  { trapArg  }
    DESCRIPTION
            "An output bad condition is restored."
    ::= 39

upsAlarmOutputOverloadRestored-fourth TRAP-TYPE
    ENTERPRISE geUPSTraps-fourth
    VARIABLES  { trapArg  }
    DESCRIPTION
            "An output overload condition is restored."
    ::= 40

upsAlarmOnBypassRestored-fourth TRAP-TYPE
    ENTERPRISE geUPSTraps-fourth
    VARIABLES  { trapArg  }
    DESCRIPTION
            "An On Bypass condition is restored."
    ::= 41

upsAlarmBypassBadRestored-fourth TRAP-TYPE
    ENTERPRISE geUPSTraps-fourth
    VARIABLES  { trapArg  }
    DESCRIPTION
            "A Bypass bad condition is restored."
    ::= 42

upsAlarmOutputOffAsRequestedRestored-fourth TRAP-TYPE
    ENTERPRISE geUPSTraps-fourth
    VARIABLES  { trapArg  }
    DESCRIPTION
            "A request shutdown has been restored."
    ::= 43

upsAlarmUpsOffAsRequestedRestored-fourth TRAP-TYPE
    ENTERPRISE geUPSTraps-fourth-fourth
    VARIABLES  { trapArg  }
    DESCRIPTION
            "A entire UPS command has been restored."
    ::= 44

upsAlarmChargerFailedRestored-fourth TRAP-TYPE
    ENTERPRISE geUPSTraps-fourth
    VARIABLES  { trapArg  }
    DESCRIPTION
            "A Charger Failer condition is restored."
    ::= 45

upsAlarmUpsOutputOn-fourth TRAP-TYPE
    ENTERPRISE geUPSTraps-fourth
    VARIABLES  { trapArg  }
    DESCRIPTION
            "The output of the UPS switched in the on state."
    ::= 46

upsAlarmUpsSystemOn-fourth TRAP-TYPE
    ENTERPRISE geUPSTraps-fourth
    VARIABLES  { trapArg  }
    DESCRIPTION
            "The UPS system is switched in the on state."
    ::= 47

upsAlarmFanFailureRestored-fourth TRAP-TYPE
    ENTERPRISE geUPSTraps-fourth
    VARIABLES  { trapArg  }
    DESCRIPTION
            "A Fan failure condition is restored."
    ::= 48

upsAlarmFuseFailureRestored-fourth TRAP-TYPE
    ENTERPRISE geUPSTraps-fourth
    VARIABLES  { trapArg  }
    DESCRIPTION
            "A Fuse failure condition is restored."
    ::= 49

upsAlarmGeneralFaultRestored-fourth TRAP-TYPE
    ENTERPRISE geUPSTraps-fourth
    VARIABLES  { trapArg  }
    DESCRIPTION
            "A general fault is restored."
    ::= 50

upsAlarmDiagnosticTestFailedRestored-fourth TRAP-TYPE
    ENTERPRISE geUPSTraps-fourth
    VARIABLES  { trapArg  }
    DESCRIPTION
            "A last diagnostic test indicates a failure is 
            restored."
    ::= 51

upsAlarmCommunicationsLostRestored-fourth TRAP-TYPE
    ENTERPRISE geUPSTraps-fourth
    VARIABLES  { trapArg  }
    DESCRIPTION
            "A problem in the communication between the agent 
            and the UPS is restored."
    ::= 52
    
upsAlarmAwaitingPowerRestored-fourth TRAP-TYPE
    ENTERPRISE geUPSTraps-fourth
    VARIABLES  { trapArg  }
    DESCRIPTION
            "A awaiting power condition is restored (*)."
    ::= 53    

upsAlarmShutdownPendingRestored-fourth TRAP-TYPE
    ENTERPRISE geUPSTraps-fourth
    VARIABLES  { trapArg , upsShutdownAfterDelay-fourth }
    DESCRIPTION
            "A upsShutdownAfterDelay countdown is restored."
    ::= 54

upsAlarmShutdownImminentRestored-fourth TRAP-TYPE
    ENTERPRISE geUPSTraps-fourth
    VARIABLES  { trapArg  }
    DESCRIPTION
            "A shutdown imminent condition is restored."
    ::= 55

upsAlarmTestInProgressRestored-fourth TRAP-TYPE
    ENTERPRISE geUPSTraps-fourth
    VARIABLES  { trapArg , upsTestId-fourth }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-fourth TRAP-TYPE
    ENTERPRISE geUPSTraps-fourth
    VARIABLES  { trapArg  }
    DESCRIPTION
            "A measurement value reached a value below its low-level threshold."
    ::= 129

upsAlarmValueHigh-fourth TRAP-TYPE
    ENTERPRISE geUPSTraps-fourth
    VARIABLES  { trapArg  }
    DESCRIPTION
            "A measurement value reached a value higher than its high-level threshold."
    ::= 130

upsAlarmValueLowRestored-fourth TRAP-TYPE
    ENTERPRISE geUPSTraps-fourth
    VARIABLES  { trapArg  }
    DESCRIPTION
            "A ValueLow alarm condition is restored."
    ::= 133

upsAlarmValueHighRestored-fourth TRAP-TYPE
    ENTERPRISE geUPSTraps-fourth
    VARIABLES  { trapArg }
    DESCRIPTION
            "A ValueHigh alarm condition is restored."
    ::= 134

--
-- The Device Identification group. Fifth
--      All objects in this group except for upsIdentName and
--      upsIdentAttachedDevices are set at device initialization
--      and remain static.
--

upsIdentManufacturer-fifth OBJECT-TYPE
    SYNTAX     DisplayString (SIZE (0..31))
    MAX-ACCESS read-only
    STATUS     current
    DESCRIPTION
            "The name of the UPS manufacturer.(*)"
    ::= { upsIdent-fifth 1 }

upsIdentModel-fifth OBJECT-TYPE
    SYNTAX     DisplayString (SIZE (0..63))
    MAX-ACCESS read-only
    STATUS     current
    DESCRIPTION
            "The UPS Model designation.(*)"
    ::= { upsIdent-fifth 2 }

upsIdentUPSSoftwareVersion-fifth OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-fifth 3 }

upsIdentAgentSoftwareVersion-fifth OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-fifth 4 }

upsIdentName-fifth OBJECT-TYPE
    SYNTAX     DisplayString (SIZE(0..63))
    MAX-ACCESS read-write
    STATUS     current
    DESCRIPTION
            "A string identifying the UPS.  This object should be
            set by the administrator.(*)"
    ::= { upsIdent-fifth 5 }

upsIdentAttachedDevices-fifth OBJECT-TYPE
    SYNTAX     DisplayString (SIZE(0..63))
    MAX-ACCESS read-write
    STATUS     current
    DESCRIPTION
            "A string identifying the devices attached to the
            output(s) of the UPS.  This object should be set by
            the administrator.(*)"
    ::= { upsIdent-fifth 6 }

upsIdentUPSSerialNumber-fifth OBJECT-TYPE
    SYNTAX     DisplayString (SIZE(0..31))
    MAX-ACCESS read-only
    STATUS     current
    DESCRIPTION
            "The UPS serial number"
    ::= { upsIdent-fifth 7 }
				
upsIdentComProtVersion-fifth OBJECT-TYPE
    SYNTAX     DisplayString (SIZE(0..15))
    MAX-ACCESS read-only
    STATUS     current
    DESCRIPTION
            "The IMV communication protocol version"
    ::= { upsIdent-fifth 8 }	
		
upsIdentOperatingTime-fifth OBJECT-TYPE
    SYNTAX     NonNegativeInteger32
    UNITS      "seconds"
    MAX-ACCESS read-only
    STATUS     current
    DESCRIPTION
            "The present value of the operating time.
             total 'on' time since UPS manufactured"
    ::= { upsIdent-fifth 9 }	
				
--
-- Battery Group Generic
--

upsBatteryStatus-fifth OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-fifth 1 }

upsSecondsOnBattery-fifth OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-fifth 2 }

upsEstimatedMinutesRemaining-fifth OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-fifth 3 }

upsEstimatedChargeRemaining-fifth OBJECT-TYPE
    SYNTAX     Integer32 (0..100)
    UNITS      "percent"
    MAX-ACCESS read-only
    STATUS     current
    DESCRIPTION
            "An estimate of the battery charge remaining expressed
            as a percent of full charge.(*)"
    ::= { upsBattery-fifth 4 }

upsBatteryVoltage-fifth OBJECT-TYPE
    SYNTAX     NonNegativeInteger32
    UNITS      "0.1 Volt DC"
    MAX-ACCESS read-only
    STATUS     current
    DESCRIPTION
            "The magnitude of the present battery voltage.(*)"
    ::= { upsBattery-fifth 5 }

upsBatteryCurrent-fifth OBJECT-TYPE
    SYNTAX     Integer32
    UNITS      "0.1 Amp DC"
    MAX-ACCESS read-only
    STATUS     current
    DESCRIPTION
            "The present battery current.(*)"
    ::= { upsBattery-fifth 6 }

upsBatteryTemperature-fifth OBJECT-TYPE
    SYNTAX     Integer32
    UNITS      "degrees Centigrade"
    MAX-ACCESS read-only
    STATUS     current
    DESCRIPTION
            "The ambient temperature at or near the UPS Battery
            casing.(*)"
    ::= { upsBattery-fifth 7 }

--
-- Input Group
--

upsInputLineBads-fifth OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-fifth 1 }

upsInputNumLines-fifth OBJECT-TYPE
    SYNTAX     NonNegativeInteger32
    MAX-ACCESS read-only
    STATUS     current
    DESCRIPTION
            "The number of input lines utilized in this device.
            This variable indicates the number of rows in the
            input table.(*)"
    ::= { upsInput-fifth 2 }

upsInputTable-fifth OBJECT-TYPE
    SYNTAX     SEQUENCE OF UpsInputEntry-fifth
    MAX-ACCESS not-accessible
    STATUS     current
    DESCRIPTION
            "A list of input table entries.  The number of entries
            is given by the value of upsInputNumLines.(*)"
    ::= { upsInput-fifth 3 }

upsInputEntry-fifth OBJECT-TYPE
    SYNTAX     UpsInputEntry-fifth
    MAX-ACCESS not-accessible
    STATUS     current
    DESCRIPTION
            "An entry containing information applicable to a
            particular input line.(*)"
    INDEX { upsInputLineIndex-fifth }
    ::= { upsInputTable-fifth 1 }

UpsInputEntry-fifth ::= SEQUENCE {
    upsInputLineIndex-fifth   PositiveInteger32,
    upsInputFrequency-fifth   NonNegativeInteger32,
    upsInputVoltage-fifth     NonNegativeInteger32,
    upsInputCurrent-fifth     NonNegativeInteger32,
    upsInputTruePower-fifth   NonNegativeInteger32,
    upsInputVoltageMin-fifth  NonNegativeInteger32,
    upsInputVoltageMax-fifth  NonNegativeInteger32
}

upsInputLineIndex-fifth OBJECT-TYPE
    SYNTAX     PositiveInteger32
    MAX-ACCESS not-accessible
    STATUS     current
    DESCRIPTION
            "The input line identifier.(*)"
    ::= { upsInputEntry-fifth 1 }

upsInputFrequency-fifth OBJECT-TYPE
    SYNTAX     NonNegativeInteger32
    UNITS      "0.1 Hertz"
    MAX-ACCESS read-only
    STATUS     current
    DESCRIPTION
            "The present input frequency.(*)"
    ::= { upsInputEntry-fifth 2 }

upsInputVoltage-fifth OBJECT-TYPE
    SYNTAX     NonNegativeInteger32
    UNITS      "RMS Volts"
    MAX-ACCESS read-only
    STATUS     current
    DESCRIPTION
            "The magnitude of the present input voltage.(*)"
    ::= { upsInputEntry-fifth 3 }

upsInputCurrent-fifth OBJECT-TYPE
    SYNTAX     NonNegativeInteger32
    UNITS      "0.1 RMS Amp"
    MAX-ACCESS read-only
    STATUS     current
    DESCRIPTION
            "The magnitude of the present input current.(*)"
    ::= { upsInputEntry-fifth 4 }

upsInputTruePower-fifth OBJECT-TYPE
    SYNTAX     NonNegativeInteger32
    UNITS      "Watts"
    MAX-ACCESS read-only
    STATUS     current
    DESCRIPTION
            "The magnitude of the present input true power.(*)"
    ::= { upsInputEntry-fifth 5 }

upsInputVoltageMin-fifth OBJECT-TYPE
    SYNTAX     NonNegativeInteger32
    UNITS      "RMS Volts"
    MAX-ACCESS read-only
    STATUS     current
    DESCRIPTION
            "The lowest magnitude of the input voltage since last read out."
    ::= { upsInputEntry-fifth 6 }

upsInputVoltageMax-fifth OBJECT-TYPE
    SYNTAX     NonNegativeInteger32
    UNITS      "RMS Volts"
    MAX-ACCESS read-only
    STATUS     current
    DESCRIPTION
            "The highest magnitude of the input voltage since last read out."
    ::= { upsInputEntry-fifth 7 }

--
-- The Output group.
--

upsOutputSource-fifth OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-fifth 1 }

upsOutputFrequency-fifth OBJECT-TYPE
    SYNTAX     NonNegativeInteger32
    UNITS      "0.1 Hertz"
    MAX-ACCESS read-only
    STATUS     current
    DESCRIPTION
            "The present output frequency.(*)"
    ::= { upsOutput-fifth 2 }

upsOutputNumLines-fifth OBJECT-TYPE
    SYNTAX     NonNegativeInteger32
    MAX-ACCESS read-only
    STATUS     current
    DESCRIPTION
            "The number of output lines utilized in this device.
            This variable indicates the number of rows in the
            output table.(*)"
    ::= { upsOutput-fifth 3 }

upsOutputTable-fifth OBJECT-TYPE
    SYNTAX     SEQUENCE OF UpsOutputEntry-fifth
    MAX-ACCESS not-accessible
    STATUS     current
    DESCRIPTION
            "A list of output table entries.  The number of
            entries is given by the value of upsOutputNumLines.(*)"
    ::= { upsOutput-fifth 4 }

upsOutputEntry-fifth OBJECT-TYPE
    SYNTAX     UpsOutputEntry-fifth
    MAX-ACCESS not-accessible
    STATUS     current
    DESCRIPTION
            "An entry containing information applicable to a
            particular output line.(*)"
    INDEX { upsOutputLineIndex-fifth }
    ::= { upsOutputTable-fifth 1 }

UpsOutputEntry-fifth ::= SEQUENCE {
    upsOutputLineIndex-fifth   PositiveInteger32,
    upsOutputVoltage-fifth     NonNegativeInteger32,
    upsOutputCurrent-fifth     NonNegativeInteger32,
    upsOutputPower-fifth       NonNegativeInteger32,
    upsOutputPercentLoad-fifth Integer32
}

upsOutputLineIndex-fifth OBJECT-TYPE
    SYNTAX     PositiveInteger32
    MAX-ACCESS not-accessible
    STATUS     current
    DESCRIPTION
            "The output line identifier.(*)"
    ::= { upsOutputEntry-fifth 1 }

upsOutputVoltage-fifth OBJECT-TYPE
    SYNTAX     NonNegativeInteger32
    UNITS      "RMS Volts"
    MAX-ACCESS read-only
    STATUS     current
    DESCRIPTION
            "The present output voltage.(*)"
    ::= { upsOutputEntry-fifth 2 }

upsOutputCurrent-fifth OBJECT-TYPE
    SYNTAX     NonNegativeInteger32
    UNITS      "0.1 RMS Amp"
    MAX-ACCESS read-only
    STATUS     current
    DESCRIPTION
            "The present output current.(*)"
    ::= { upsOutputEntry-fifth 3 }

upsOutputPower-fifth OBJECT-TYPE
    SYNTAX     NonNegativeInteger32
    UNITS      "Watts"
    MAX-ACCESS read-only
    STATUS     current
    DESCRIPTION
            "The present output true power.(*)"
    ::= { upsOutputEntry-fifth 4 }

upsOutputPercentLoad-fifth OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-fifth 5 }

--
-- The Bypass group generic.
--

upsBypassFrequency-fifth OBJECT-TYPE
    SYNTAX     NonNegativeInteger32
    UNITS      "0.1 Hertz"
    MAX-ACCESS read-only
    STATUS     current
    DESCRIPTION
            "The present bypass frequency.(*)"
    ::= { upsBypass-fifth 1 }

upsBypassNumLines-fifth OBJECT-TYPE
    SYNTAX     NonNegativeInteger32
    MAX-ACCESS read-only
    STATUS     current
    DESCRIPTION
            "The number of bypass lines utilized in this device.
            This entry indicates the number of rows in the bypass
            table.(*)"
    ::= { upsBypass-fifth 2 }

upsBypassTable-fifth OBJECT-TYPE
    SYNTAX     SEQUENCE OF UpsBypassEntry-fifth
    MAX-ACCESS not-accessible
    STATUS     current
    DESCRIPTION
            "A list of bypass table entries.  The number of
            entries is given by the value of upsBypassNumLines.(*)"
    ::= { upsBypass-fifth 3 }

upsBypassEntry-fifth OBJECT-TYPE
    SYNTAX     UpsBypassEntry-fifth
    MAX-ACCESS not-accessible
    STATUS     current
    DESCRIPTION
            "An entry containing information applicable to a
            particular bypass input.(*)"
    INDEX { upsBypassLineIndex-fifth }
    ::= { upsBypassTable-fifth 1 }

UpsBypassEntry-fifth ::= SEQUENCE {
    upsBypassLineIndex-fifth  PositiveInteger32,
    upsBypassVoltage-fifth    NonNegativeInteger32,
    upsBypassCurrent-fifth    NonNegativeInteger32,
    upsBypassPower-fifth      NonNegativeInteger32
}

upsBypassLineIndex-fifth OBJECT-TYPE
    SYNTAX     PositiveInteger32
    MAX-ACCESS not-accessible
    STATUS     current
    DESCRIPTION
            "The bypass line identifier.(*)"
    ::= { upsBypassEntry-fifth 1 }

upsBypassVoltage-fifth OBJECT-TYPE
    SYNTAX     NonNegativeInteger32
    UNITS      "RMS Volts"
    MAX-ACCESS read-only
    STATUS     current
    DESCRIPTION
            "The present bypass voltage.(*)"
    ::= { upsBypassEntry-fifth 2 }

upsBypassCurrent-fifth OBJECT-TYPE
    SYNTAX     NonNegativeInteger32
    UNITS      "0.1 RMS Amp"
    MAX-ACCESS read-only
    STATUS     current
    DESCRIPTION
            "The present bypass current.(*)"
    ::= { upsBypassEntry-fifth 3 }

upsBypassPower-fifth OBJECT-TYPE
    SYNTAX     NonNegativeInteger32
    UNITS      "Watts"
    MAX-ACCESS read-only
    STATUS     current
    DESCRIPTION
            "The present true power conveyed by the bypass.(*)"
    ::= { upsBypassEntry-fifth 4 }

--
-- The Alarm group generic.
--

upsAlarmsPresent-fifth OBJECT-TYPE
    SYNTAX     Gauge32
    MAX-ACCESS read-only
    STATUS     current
    DESCRIPTION
            "The present number of active alarm conditions.(*)"
    ::= { upsAlarm-fifth 1 }

upsAlarmTable-fifth OBJECT-TYPE
    SYNTAX     SEQUENCE OF UpsAlarmEntry-fifth
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-fifth 2 }

upsAlarmEntry-fifth OBJECT-TYPE
    SYNTAX     UpsAlarmEntry-fifth
    MAX-ACCESS not-accessible
    STATUS     current
    DESCRIPTION
            "An entry containing information applicable to a
            particular alarm.(*)"
    INDEX { upsAlarmId-fifth }
    ::= { upsAlarmTable-fifth 1 }

UpsAlarmEntry-fifth ::= SEQUENCE {
    upsAlarmId-fifth          PositiveInteger32,
    upsAlarmDescr-fifth       AutonomousType,
    upsAlarmTime-fifth       TimeStamp
}

upsAlarmId-fifth OBJECT-TYPE
    SYNTAX     PositiveInteger32
    MAX-ACCESS not-accessible
    STATUS     current
    DESCRIPTION
            "A unique identifier for an alarm condition.  This
            value must remain constant.(*)"
    ::= { upsAlarmEntry-fifth 1 }

upsAlarmDescr-fifth OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-fifth 2 }

upsAlarmTime-fifth OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-fifth 3 }

--
-- Well known alarm conditions generic.
--

upsAlarmBatteryBad-fifth OBJECT-IDENTITY
    STATUS     current
    DESCRIPTION
            "One or more batteries have been determined to require
            replacement.(*)"
    ::= { upsWellKnownAlarms-fifth  1 }

upsAlarmOnBattery-fifth OBJECT-IDENTITY
    STATUS     current
    DESCRIPTION
            "The UPS is drawing power from the batteries.(*)"
    ::= { upsWellKnownAlarms-fifth  2 }

upsAlarmLowBattery-fifth OBJECT-IDENTITY
    STATUS     current
    DESCRIPTION
            "The remaining battery run-time is less than or equal
            to upsConfigLowBattTime.(*)"
    ::= { upsWellKnownAlarms-fifth  3 }

upsAlarmDepletedBattery-fifth OBJECT-IDENTITY
    STATUS     current
    DESCRIPTION
            "The UPS will be unable to sustain the present load
            when and if the utility power is lost.(*)"
    ::= { upsWellKnownAlarms-fifth  4 }

upsAlarmTempBad-fifth OBJECT-IDENTITY
    STATUS     current
    DESCRIPTION
            "A temperature is out of tolerance.(*)"
    ::= { upsWellKnownAlarms-fifth  5 }

upsAlarmInputBad-fifth OBJECT-IDENTITY
    STATUS     current
    DESCRIPTION
            "An input condition is out of tolerance.(*)"
    ::= { upsWellKnownAlarms-fifth  6 }

upsAlarmOutputBad-fifth OBJECT-IDENTITY
    STATUS     current
    DESCRIPTION
            "An output condition (other than OutputOverload) is
            out of tolerance.(*)"
    ::= { upsWellKnownAlarms-fifth  7 }

upsAlarmOutputOverload-fifth OBJECT-IDENTITY
    STATUS     current
    DESCRIPTION
            "The output load exceeds the UPS output capacity.(*)"
    ::= { upsWellKnownAlarms-fifth  8 }

upsAlarmOnBypass-fifth OBJECT-IDENTITY
    STATUS     current
    DESCRIPTION
            "The Bypass is presently engaged on the UPS.(*)"
    ::= { upsWellKnownAlarms-fifth  9 }

upsAlarmBypassBad-fifth OBJECT-IDENTITY
    STATUS     current
    DESCRIPTION
            "The Bypass is out of tolerance.(*)"
    ::= { upsWellKnownAlarms-fifth 10 }

upsAlarmOutputOffAsRequested-fifth OBJECT-IDENTITY
    STATUS     current
    DESCRIPTION
            "The UPS has shutdown as requested, i.e., the output
            is off.(*)"
    ::= { upsWellKnownAlarms-fifth 11 }

upsAlarmUpsOffAsRequested-fifth OBJECT-IDENTITY
    STATUS     current
    DESCRIPTION
            "The entire UPS has shutdown as commanded.(*)"
    ::= { upsWellKnownAlarms-fifth 12 }

upsAlarmChargerFailed-fifth OBJECT-IDENTITY
    STATUS     current
    DESCRIPTION
            "An uncorrected problem has been detected within the
            UPS charger subsystem.(*)"
    ::= { upsWellKnownAlarms-fifth 13 }

upsAlarmUpsOutputOff-fifth OBJECT-IDENTITY
    STATUS     current
    DESCRIPTION
            "The output of the UPS is in the off state.(*)"
    ::= { upsWellKnownAlarms-fifth 14 }

upsAlarmUpsSystemOff-fifth OBJECT-IDENTITY
    STATUS     current
    DESCRIPTION
            "The UPS system is in the off state.(*)"
    ::= { upsWellKnownAlarms-fifth 15 }

upsAlarmFanFailure-fifth OBJECT-IDENTITY
    STATUS     current
    DESCRIPTION
            "The failure of one or more fans in the UPS has been
            detected.(*)"
    ::= { upsWellKnownAlarms-fifth 16 }

upsAlarmFuseFailure-fifth OBJECT-IDENTITY
    STATUS     current
    DESCRIPTION
            "The failure of one or more fuses has been detected.(*)"
    ::= { upsWellKnownAlarms-fifth 17 }

upsAlarmGeneralFault-fifth OBJECT-IDENTITY
    STATUS     current
    DESCRIPTION
            "A general fault in the UPS has been detected.(*)"
    ::= { upsWellKnownAlarms-fifth 18 }

upsAlarmDiagnosticTestFailed-fifth OBJECT-IDENTITY
    STATUS     current
    DESCRIPTION
            "The result of the last diagnostic test indicates a
            failure.(*)"
    ::= { upsWellKnownAlarms-fifth 19 }

upsAlarmCommunicationsLost-fifth OBJECT-IDENTITY
    STATUS     current
    DESCRIPTION
            "A problem has been encountered in the communications
            between the agent and the UPS.(*)"
    ::= { upsWellKnownAlarms-fifth 20 }

upsAlarmAwaitingPower-fifth OBJECT-IDENTITY
    STATUS     current
    DESCRIPTION
            "The UPS output is off and the UPS is awaiting the
            return of input power.(*)"
    ::= { upsWellKnownAlarms-fifth 21 }

upsAlarmShutdownPending-fifth OBJECT-IDENTITY
    STATUS     current
    DESCRIPTION
            "A upsShutdownAfterDelay countdown is underway.(*)"
    ::= { upsWellKnownAlarms-fifth 22 }

upsAlarmShutdownImminent-fifth OBJECT-IDENTITY
    STATUS     current
    DESCRIPTION
            "The UPS will turn off power to the load in less than
            5 seconds; this may be either a timed shutdown or a
            low battery shutdown.(*)"
    ::= { upsWellKnownAlarms-fifth 23 }

upsAlarmTestInProgress-fifth OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-fifth 24 }

upsAlarmReceptacleOff-fifth OBJECT-IDENTITY
    STATUS     current
    DESCRIPTION
            "The receptacle are switch off    "
    ::= { upsWellKnownAlarms-fifth 25 }

upsAlarmMaskA-fifth OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-fifth 4 }

--
-- The Test Group generic
--

upsTestId-fifth OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-fifth 1 }

-- see [6] for more information on the semantics of objects with
-- syntax of TestAndIncr

upsTestSpinLock-fifth OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-fifth 2 }

upsTestResultsSummary-fifth OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-fifth 3 }

upsTestResultsDetail-fifth OBJECT-TYPE
    SYNTAX     DisplayString (SIZE (0..255))
    MAX-ACCESS read-only
    STATUS     current
    DESCRIPTION
            "Additional information about upsTestResultsSummary.
            If no additional information available, a zero length
            string is returned.(*)"
    ::= { upsTest-fifth 4 }

upsTestStartTime-fifth OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-fifth 5 }

upsTestElapsedTime-fifth OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-fifth 6 }

--
-- Well known tests generic.
--

upsTestNoTestsInitiated-fifth OBJECT-IDENTITY
    STATUS     current
    DESCRIPTION
            "No tests have been initiated and no test is in
            progress.(*)"
    ::= { upsWellKnownTests-fifth  1 }

upsTestAbortTestInProgress-fifth OBJECT-IDENTITY
    STATUS     current
    DESCRIPTION
            "The test in progress is to be aborted / the test in
            progress was aborted.(*)"
    ::= { upsWellKnownTests-fifth  2 }

upsTestGeneralSystemsTest-fifth OBJECT-IDENTITY
    STATUS     current
    DESCRIPTION
            "The manufacturer's standard test of UPS device
            systems.(*)"
    ::= { upsWellKnownTests-fifth  3 }

upsTestQuickBatteryTest-fifth OBJECT-IDENTITY
    STATUS     current
    DESCRIPTION
            "A test that is sufficient to determine if the battery
            needs replacement.(*)"
    ::= { upsWellKnownTests-fifth  4 }

upsTestDeepBatteryCalibration-fifth OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-fifth  5 }

--
-- The Control group generic.
--

upsShutdownType-fifth OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-fifth 1 }

upsShutdownAfterDelay-fifth OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-fifth 2 }

upsStartupAfterDelay-fifth OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-fifth 3 }

upsRebootWithDuration-fifth OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-fifth 4 }

upsAutoRestart-fifth OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-fifth 5 }

upsReceptaclesNum-fifth OBJECT-TYPE
    SYNTAX     NonNegativeInteger32
    MAX-ACCESS read-only
    STATUS     current
    DESCRIPTION
            "The number of receptacles utilized in this device.
            This entry indicates the number of rows in the receptacle
            table."
    ::= { upsControl-fifth 6 }

upsReceptacleTable-fifth OBJECT-TYPE
    SYNTAX     SEQUENCE OF UpsReceptacleEntry-fifth
    MAX-ACCESS not-accessible
    STATUS     current
    DESCRIPTION
            "A list of receptacle table entries.  The number of
            entries is given by the value of upsReceptacleNum."
    ::= { upsControl-fifth 7 }

upsReceptacleEntry-fifth OBJECT-TYPE
    SYNTAX     UpsReceptacleEntry-fifth
    MAX-ACCESS not-accessible
    STATUS     current
    DESCRIPTION
            "An entry containing information applicable to a
            particular receptacle."
    INDEX { upsReceptacleLineIndex-fifth }
    ::= { upsReceptacleTable-fifth 1 }

UpsReceptacleEntry-fifth ::= SEQUENCE {
    upsReceptacleLineIndex-fifth  PositiveInteger32,
    upsReceptacleOnOff-fifth      Integer32    
}

upsReceptacleLineIndex-fifth OBJECT-TYPE
    SYNTAX     PositiveInteger32
    MAX-ACCESS not-accessible
    STATUS     current
    DESCRIPTION
            "The receptacle line identifier."
    ::= { upsReceptacleEntry-fifth 1 }

upsReceptacleOnOff-fifth OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-fifth 2 }

upsUPSMode-fifth OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-fifth 8 }

upsRectifierOnOff-fifth OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-fifth 9 }

upsBatteryChargeMethod-fifth OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-fifth 10 }

upsInverterOnOff-fifth OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-fifth 11 }

upsBypassOnOff-fifth OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-fifth 12 }

upsLoadSource-fifth OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-fifth 13 }
	
--
-- The Configuration group generic.
--

upsConfigInputVoltage-fifth OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-fifth 1 }

upsConfigInputFreq-fifth OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-fifth 2 }

upsConfigOutputVoltage-fifth OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-fifth 3 }

upsConfigOutputFreq-fifth OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-fifth 4 }

upsConfigOutputVA-fifth OBJECT-TYPE
    SYNTAX     NonNegativeInteger32
    UNITS      "Volt-Amps"
    MAX-ACCESS read-only
    STATUS     current
    DESCRIPTION
            "The magnitude of the nominal Volt-Amp rating.(*)"
    ::= { upsConfig-fifth 5 }

upsConfigOutputPower-fifth OBJECT-TYPE
    SYNTAX     NonNegativeInteger32
    UNITS      "Watts"
    MAX-ACCESS read-only
    STATUS     current
    DESCRIPTION
            "The magnitude of the nominal true power rating.(*)"
    ::= { upsConfig-fifth 6 }

upsConfigLowBattTime-fifth OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-fifth 7 }

upsConfigAudibleStatus-fifth OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-fifth 8 }

upsConfigLowVoltageTransferPoint-fifth OBJECT-TYPE
    SYNTAX     NonNegativeInteger32
    UNITS      "RMS Volts"
    MAX-ACCESS read-write
    STATUS     current
    DESCRIPTION
            "The minimum input line voltage allowed before the UPS
            system transfers to battery backup.(*)"
    ::= { upsConfig-fifth 9 }

upsConfigHighVoltageTransferPoint-fifth OBJECT-TYPE
    SYNTAX     NonNegativeInteger32
    UNITS      "RMS Volts"
    MAX-ACCESS read-write
    STATUS     current
    DESCRIPTION
            "The maximum line voltage allowed before the UPS
            system transfers to battery backup.(*)"
    ::= { upsConfig-fifth 10 }

upsConfigBatteryCapacity-fifth OBJECT-TYPE
    SYNTAX     NonNegativeInteger32
    UNITS      "Amps Hours"
    MAX-ACCESS read-write
    STATUS     current
    DESCRIPTION
            "The installed battery capacity. This value is the 'factory'-value,
             not the value after calibration."
    ::= { upsConfig-fifth 11 }

upsConfigBatteryChargeCurrent-fifth OBJECT-TYPE
    SYNTAX     NonNegativeInteger32
    UNITS      "0.1 Amp DC"
    MAX-ACCESS read-write
    STATUS     current
    DESCRIPTION
            "The maximum battery charge current, including external chargers."
    ::= { upsConfig-fifth 12 }						

upsConfigNoLoadShutdown-fifth OBJECT-TYPE
    SYNTAX     Integer32 {
        disabled(1),
        enabled(2)
    }
    MAX-ACCESS read-write
    STATUS     current
    DESCRIPTION
            "Dis- or enable 'no load' shutdown from the contact interface."
    ::= { upsConfig-fifth 13 }
	
upsConfigStartDelay-fifth OBJECT-TYPE
    SYNTAX     PositiveInteger32
    UNITS      "minutes"				
    MAX-ACCESS read-write
    STATUS     current
    DESCRIPTION
            "Minimum required autonomy time before the UPS may perform an
             autorestart."
    ::= { upsConfig-fifth 14 }

--
-- The GetSet group generic.
--

upsEventGetNext-fifth OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-fifth 1 }

upsEventGetPrevious-fifth OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-fifth 2 }
				
upsEventSetStartingTimeStamp-fifth OBJECT-TYPE
    SYNTAX     NonNegativeInteger32
    MAX-ACCESS read-write
    STATUS     current
    DESCRIPTION
            "The timestamp which is used as starting point for downloading
             events from the UPS event buffer"
    ::= { upsGetSet-fifth 3 }				

upsEventRetreiveCurrentTimeStamp-fifth OBJECT-TYPE
    SYNTAX     NonNegativeInteger32
    MAX-ACCESS read-only
    STATUS     current
    DESCRIPTION
            "The current timestamp is retreived from the UPS"
    ::= { upsGetSet-fifth 4 }				

upsEventTableSize-fifth OBJECT-TYPE
    SYNTAX     NonNegativeInteger32
    MAX-ACCESS read-only
    STATUS     current
    DESCRIPTION
            "The number of entries in the event table.
            This object indicates the number of rows in the event table."
    ::= { upsGetSet-fifth 5 }

upsEventTable-fifth OBJECT-TYPE
    SYNTAX     SEQUENCE OF UpsEventEntry-fifth
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-fifth 6 }

upsEventEntry-fifth OBJECT-TYPE
    SYNTAX     UpsEventEntry-fifth
    MAX-ACCESS not-accessible
    STATUS     current
    DESCRIPTION
            "An entry containing information applicable to a
            particular event."
    INDEX { upsEventLineIndex-fifth }
    ::= { upsEventTable-fifth 1 }

UpsEventEntry-fifth ::= SEQUENCE {
    upsEventLineIndex-fifth PositiveInteger32,
    upsEventCode-fifth      Integer32,
    upsEventStatus-fifth    NonNegativeInteger32,
    upsEventTime-fifth      NonNegativeInteger32
}

upsEventLineIndex-fifth OBJECT-TYPE
    SYNTAX     PositiveInteger32
    MAX-ACCESS not-accessible
    STATUS     current
    DESCRIPTION
            "The event line identifier."
    ::= { upsEventEntry-fifth 1 }

upsEventCode-fifth OBJECT-TYPE
    SYNTAX     NonNegativeInteger32
    MAX-ACCESS read-only
    STATUS     current
    DESCRIPTION
            "The event code in numerical format."
    ::= { upsEventEntry-fifth 2 }

upsEventStatus-fifth OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-fifth 3 }

upsEventTime-fifth OBJECT-TYPE
    SYNTAX     NonNegativeInteger32
    MAX-ACCESS read-only
    STATUS     current
    DESCRIPTION
            "The timestamp of the moment the event was generated."
    ::= { upsEventEntry-fifth 4 }

upsParametersRead-fifth OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-fifth 7 }

upsParametersWrite-fifth OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-fifth 8 }

upsParametersStartAddress-fifth OBJECT-TYPE
    SYNTAX     NonNegativeInteger32
    MAX-ACCESS read-write
    STATUS     current
    DESCRIPTION
            "The address which is used as starting point for downloading
             parameters from the UPS"
    ::= { upsGetSet-fifth 9 }				

upsParameterTableSize-fifth OBJECT-TYPE
    SYNTAX     NonNegativeInteger32
    MAX-ACCESS read-only
    STATUS     current
    DESCRIPTION
            "The number of entries in the parameter table.
            This object indicates the number of rows in the parameter table."
    ::= { upsGetSet-fifth 10 }

upsParameterTable-fifth OBJECT-TYPE
    SYNTAX     SEQUENCE OF UpsParameterEntry-fifth
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-fifth 11 }

upsParameterEntry-fifth OBJECT-TYPE
    SYNTAX     UpsParameterEntry-fifth
    MAX-ACCESS not-accessible
    STATUS     current
    DESCRIPTION
            "An entry containing information applicable to a
            particular parameter."
    INDEX { upsParameterLineIndex-fifth }
    ::= { upsParameterTable-fifth 1 }

UpsParameterEntry-fifth ::= SEQUENCE {
    upsParameterLineIndex-fifth PositiveInteger32,
    upsParameterValue-fifth     Integer32   
}

upsParameterLineIndex-fifth OBJECT-TYPE
    SYNTAX     PositiveInteger32
    MAX-ACCESS not-accessible
    STATUS     current
    DESCRIPTION
            "The parameter line identifier."
    ::= { upsParameterEntry-fifth 1 }

upsParameterValue-fifth OBJECT-TYPE
    SYNTAX     Integer32
    MAX-ACCESS read-write
    STATUS     current
    DESCRIPTION
            "The parameter value in numerical format."
    ::= { upsParameterEntry-fifth 2 }

upsStatus-fifth OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-fifth 12 }

upsMainsStatisticsMBfail-fifth OBJECT-TYPE
    SYNTAX     NonNegativeInteger32
    MAX-ACCESS read-only
    STATUS     current
    DESCRIPTION
            "Count of main bypass failures (>200 ms), since UPS installation."
    ::= { upsGetSet-fifth 13 }

upsMainsStatisticsMRfail-fifth OBJECT-TYPE
    SYNTAX     NonNegativeInteger32
    MAX-ACCESS read-only
    STATUS     current
    DESCRIPTION
            "Count of mains rectifier failures (>200 ms), since UPS installation."
    ::= { upsGetSet-fifth 14 }
		
upsMainsStatisticsB2-fifth OBJECT-TYPE
    SYNTAX     NonNegativeInteger32
    MAX-ACCESS read-only
    STATUS     current
    DESCRIPTION
            "Count of transients on the mains bypass (0..2 ms), during the last 7 days."
    ::= { upsGetSet-fifth 15 }

upsMainsStatisticsB5-fifth OBJECT-TYPE
    SYNTAX     NonNegativeInteger32
    MAX-ACCESS read-only
    STATUS     current
    DESCRIPTION
            "Count of transients on the mains bypass (2..5 ms), during the last 7 days."
    ::= { upsGetSet-fifth 16 }

upsMainsStatisticsB10-fifth OBJECT-TYPE
    SYNTAX     NonNegativeInteger32
    MAX-ACCESS read-only
    STATUS     current
    DESCRIPTION
            "Count of transients on the mains bypass (5..10 ms), during the last 7 days."
    ::= { upsGetSet-fifth 17 }

upsMainsStatisticsB200-fifth OBJECT-TYPE
    SYNTAX     NonNegativeInteger32
    MAX-ACCESS read-only
    STATUS     current
    DESCRIPTION
            "Count of transients on the mains bypass (10..200 ms), during the last 7 days."
    ::= { upsGetSet-fifth 18 }

upsMainsStatisticsBypRel-fifth OBJECT-TYPE
    SYNTAX     NonNegativeInteger32
    MAX-ACCESS read-only
    STATUS     current
    DESCRIPTION
            "Bypass reliability degree [0..100%;255]. The value NOSUCHNAME means 'not available'."
    ::= { upsGetSet-fifth 19 }

upsTime-fifth OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-fifthERROR,              meaning 'command not supported'. It is possible to know which is the timestamp 
             format supported by the UPS, by issuing a read-command or by reading events, 
             which includes timestamps."
    ::= { upsGetSet-fifth 20 }

upsRequestPermission-fifth OBJECT-TYPE
    SYNTAX     DisplayString (SIZE(0..63))
    MAX-ACCESS write-only
    STATUS     current
    DESCRIPTION
            "An encrypted code is send to enable use of restricted write objects during
             a limited period of time."
    ::= { upsGetSet-fifth 21 }

upsEventGetCode-fifth OBJECT-TYPE
    SYNTAX     Integer32
    MAX-ACCESS write-only
    STATUS     current
    DESCRIPTION
            "The code which is used as starting point to downloading the events from the 
            UPS event buffer."
    ::= { upsGetSet-fifth 22 }    
    
upsEventSpinLock-fifth OBJECT-TYPE
    SYNTAX     TestAndIncr
    MAX-ACCESS read-write
    STATUS     current
    DESCRIPTION
            "A spin lock on the event subsystem. "

    ::= { upsGetSet-fifth 23 }
    
upsParameterSpinLock-fifth OBJECT-TYPE
    SYNTAX     TestAndIncr
    MAX-ACCESS read-write
    STATUS     current
    DESCRIPTION
            "A spin lock on the parameters subsystem. "

    ::= { upsGetSet-fifth 24 }

--
-- GE Trap group generic
--

upsAlarmBatteryBad-fifth TRAP-TYPE
    ENTERPRISE geUPSTraps-fifth
    VARIABLES  { trapArg  }
    DESCRIPTION
            "One or more batteries have been determined to require
            replacement."
    ::= 1

upsAlarmOnBattery-fifth TRAP-TYPE
    ENTERPRISE geUPSTraps-fifth
    VARIABLES  { trapArg , upsSecondsOnBattery-fifth  }
    DESCRIPTION
            "An On Battery condition is restored."
    ::= 2

upsAlarmLowBattery-fifth TRAP-TYPE
    ENTERPRISE geUPSTraps-fifth
    VARIABLES  { trapArg  }
    DESCRIPTION
            "The remaining battery run-time is less than or equal
            to upsConfigLowBattTime."
    ::= 3

upsAlarmDepletedBattery-fifth TRAP-TYPE
    ENTERPRISE geUPSTraps-fifth
    VARIABLES  { trapArg  }
    DESCRIPTION
            "The UPS will be unable to sustain the present load
            when and if the utility power is lost)"
    ::= 4

upsAlarmTempBad-fifth TRAP-TYPE
    ENTERPRISE geUPSTraps-fifth
    VARIABLES  { trapArg , upsBatteryTemperature }
    DESCRIPTION
            "A temperature is out of tolerance."
    ::= 5

upsAlarmInputBad-fifth TRAP-TYPE
    ENTERPRISE geUPSTraps-fifth
    VARIABLES  { trapArg  }
    DESCRIPTION
            "An input condition is out of tolerance."
    ::= 6

upsAlarmOutputBad-fifth TRAP-TYPE
    ENTERPRISE geUPSTraps-fifth
    VARIABLES  { trapArg  }
    DESCRIPTION
            "An output condition (other than OutputOverload) is
            out of tolerance."
    ::= 7

upsAlarmOutputOverload-fifth TRAP-TYPE
    ENTERPRISE geUPSTraps-fifth
    VARIABLES  { trapArg , upsOutputPercentLoad-fifth }
    DESCRIPTION
            "The output load exceeds the UPS output capacity."
    ::= 8

upsAlarmOnBypass-fifth TRAP-TYPE
    ENTERPRISE geUPSTraps-fifth
    VARIABLES  { trapArg  }
    DESCRIPTION
            "The Bypass is presently engaged on the UPS."
    ::= 9

upsAlarmBypassBad-fifth TRAP-TYPE
    ENTERPRISE geUPSTraps-fifth
    VARIABLES  { trapArg  }
    DESCRIPTION
            "The Bypass is out of tolerance."
    ::= 10

upsAlarmOutputOffAsRequested-fifth TRAP-TYPE
    ENTERPRISE geUPSTraps-fifth
    VARIABLES  { trapArg  }
    DESCRIPTION
            "The UPS has shutdown as requested, i.e., the output
            is off."
    ::= 11

upsAlarmUpsOffAsRequested-fifth TRAP-TYPE
    ENTERPRISE geUPSTraps-fifth-fifth
    VARIABLES  { trapArg  }
    DESCRIPTION
            "The entire UPS has shutdown as commanded."
    ::= 12

upsAlarmChargerFailed-fifth TRAP-TYPE
    ENTERPRISE geUPSTraps-fifth
    VARIABLES  { trapArg  }
    DESCRIPTION
            "An uncorrected problem has been detected within the
            UPS charger subsystem."
    ::= 13

upsAlarmUpsOutputOff-fifth TRAP-TYPE
    ENTERPRISE geUPSTraps-fifth
    VARIABLES  { trapArg  }
    DESCRIPTION
            "The output of the UPS is in the off state."
    ::= 14

upsAlarmUpsSystemOff-fifth TRAP-TYPE
    ENTERPRISE geUPSTraps-fifth
    VARIABLES  { trapArg  }
    DESCRIPTION
            "The UPS system is in the off state."
    ::= 15

upsAlarmFanFailure-fifth TRAP-TYPE
    ENTERPRISE geUPSTraps-fifth
    VARIABLES  { trapArg  }
    DESCRIPTION
            "The failure of one or more fans in the UPS has been
            detected."
    ::= 16

upsAlarmFuseFailure-fifth TRAP-TYPE
    ENTERPRISE geUPSTraps-fifth
    VARIABLES  { trapArg  }
    DESCRIPTION
            "The failure of one or more fuses has been detected."
    ::= 17

upsAlarmGeneralFault-fifth TRAP-TYPE
    ENTERPRISE geUPSTraps-fifth
    VARIABLES  { trapArg  }
    DESCRIPTION
            "A general fault in the UPS has been detected."
    ::= 18

upsAlarmDiagnosticTestFailed-fifth TRAP-TYPE
    ENTERPRISE geUPSTraps-fifth
    VARIABLES  { trapArg  }
    DESCRIPTION
            "The result of the last diagnostic test indicates a
            failure."
    ::= 19

upsAlarmCommunicationsLost-fifth TRAP-TYPE
    ENTERPRISE geUPSTraps-fifth
    VARIABLES  { trapArg  }
    DESCRIPTION
            "A problem has been encountered in the communication
            between the agent and the UPS."
    ::= 20
    
upsAlarmAwaitingPower-fifth TRAP-TYPE
    ENTERPRISE geUPSTraps-fifth
    VARIABLES  { trapArg  }
    DESCRIPTION
            "The UPS output is off and the UPS is awaiting the
            return of the input power (*)."
    ::= 21    

upsAlarmShutdownPending-fifth TRAP-TYPE
    ENTERPRISE geUPSTraps-fifth
    VARIABLES  { trapArg , upsShutdownAfterDelay-fifth }
    DESCRIPTION
            "A upsShutdownAfterDelay countdown is underway."
    ::= 22

upsAlarmShutdownImminent-fifth TRAP-TYPE
    ENTERPRISE geUPSTraps-fifth
    VARIABLES  { trapArg  }
    DESCRIPTION
            "The UPS will turn off power to the load in less than
            5 seconds; this may be either a timed shutdown or a
            low battery shutdown."
    ::= 23

upsAlarmTestInProgress-fifth TRAP-TYPE
    ENTERPRISE geUPSTraps-fifth
    VARIABLES  { trapArg , upsTestId-fifth }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-fifth TRAP-TYPE
    ENTERPRISE geUPSTraps-fifth
    VARIABLES  { trapArg  }
    DESCRIPTION
            "A receptacle has been switched off."
    ::= 25

upsAlarmBatteryBadRestored-fifth TRAP-TYPE
    ENTERPRISE geUPSTraps-fifth
    VARIABLES  { trapArg  }
    DESCRIPTION
            "A Battery bad condition is restored."
    ::= 33

upsAlarmOnBatteryRestored-fifth TRAP-TYPE
    ENTERPRISE geUPSTraps-fifth
    VARIABLES  { trapArg  }
    DESCRIPTION
            "The UPS is drawing power from mains again."
    ::= 34

upsAlarmLowBatteryRestored-fifth TRAP-TYPE
    ENTERPRISE geUPSTraps-fifth
    VARIABLES  { trapArg  }
    DESCRIPTION
            "A Low Battery condition is restored."
    ::= 35

upsAlarmDepletedBatteryRestored-fifth TRAP-TYPE
    ENTERPRISE geUPSTraps-fifth
    VARIABLES  { trapArg  }
    DESCRIPTION
            "A Depleted Battery condition is restored."
    ::= 36

upsAlarmTempBadRestored-fifth TRAP-TYPE
    ENTERPRISE geUPSTraps-fifth
    VARIABLES  { trapArg  }
    DESCRIPTION
            "A bad temperature condition is restored."
    ::= 37

upsAlarmInputBadRestored-fifth TRAP-TYPE
    ENTERPRISE geUPSTraps-fifth
    VARIABLES  { trapArg  }
    DESCRIPTION
            "An input bad condition is restored."
    ::= 38

upsAlarmOutputBadRestored-fifth TRAP-TYPE
    ENTERPRISE geUPSTraps-fifth
    VARIABLES  { trapArg  }
    DESCRIPTION
            "An output bad condition is restored."
    ::= 39

upsAlarmOutputOverloadRestored-fifth TRAP-TYPE
    ENTERPRISE geUPSTraps-fifth
    VARIABLES  { trapArg  }
    DESCRIPTION
            "An output overload condition is restored."
    ::= 40

upsAlarmOnBypassRestored-fifth TRAP-TYPE
    ENTERPRISE geUPSTraps-fifth
    VARIABLES  { trapArg  }
    DESCRIPTION
            "An On Bypass condition is restored."
    ::= 41

upsAlarmBypassBadRestored-fifth TRAP-TYPE
    ENTERPRISE geUPSTraps-fifth
    VARIABLES  { trapArg  }
    DESCRIPTION
            "A Bypass bad condition is restored."
    ::= 42

upsAlarmOutputOffAsRequestedRestored-fifth TRAP-TYPE
    ENTERPRISE geUPSTraps-fifth
    VARIABLES  { trapArg  }
    DESCRIPTION
            "A request shutdown has been restored."
    ::= 43

upsAlarmUpsOffAsRequestedRestored-fifth TRAP-TYPE
    ENTERPRISE geUPSTraps-fifth-fifth
    VARIABLES  { trapArg  }
    DESCRIPTION
            "A entire UPS command has been restored."
    ::= 44

upsAlarmChargerFailedRestored-fifth TRAP-TYPE
    ENTERPRISE geUPSTraps-fifth
    VARIABLES  { trapArg  }
    DESCRIPTION
            "A Charger Failer condition is restored."
    ::= 45

upsAlarmUpsOutputOn-fifth TRAP-TYPE
    ENTERPRISE geUPSTraps-fifth
    VARIABLES  { trapArg  }
    DESCRIPTION
            "The output of the UPS switched in the on state."
    ::= 46

upsAlarmUpsSystemOn-fifth TRAP-TYPE
    ENTERPRISE geUPSTraps-fifth
    VARIABLES  { trapArg  }
    DESCRIPTION
            "The UPS system is switched in the on state."
    ::= 47

upsAlarmFanFailureRestored-fifth TRAP-TYPE
    ENTERPRISE geUPSTraps-fifth
    VARIABLES  { trapArg  }
    DESCRIPTION
            "A Fan failure condition is restored."
    ::= 48

upsAlarmFuseFailureRestored-fifth TRAP-TYPE
    ENTERPRISE geUPSTraps-fifth
    VARIABLES  { trapArg  }
    DESCRIPTION
            "A Fuse failure condition is restored."
    ::= 49

upsAlarmGeneralFaultRestored-fifth TRAP-TYPE
    ENTERPRISE geUPSTraps-fifth
    VARIABLES  { trapArg  }
    DESCRIPTION
            "A general fault is restored."
    ::= 50

upsAlarmDiagnosticTestFailedRestored-fifth TRAP-TYPE
    ENTERPRISE geUPSTraps-fifth
    VARIABLES  { trapArg  }
    DESCRIPTION
            "A last diagnostic test indicates a failure is 
            restored."
    ::= 51

upsAlarmCommunicationsLostRestored-fifth TRAP-TYPE
    ENTERPRISE geUPSTraps-fifth
    VARIABLES  { trapArg  }
    DESCRIPTION
            "A problem in the communication between the agent 
            and the UPS is restored."
    ::= 52
    
upsAlarmAwaitingPowerRestored-fifth TRAP-TYPE
    ENTERPRISE geUPSTraps-fifth
    VARIABLES  { trapArg  }
    DESCRIPTION
            "A awaiting power condition is restored (*)."
    ::= 53    

upsAlarmShutdownPendingRestored-fifth TRAP-TYPE
    ENTERPRISE geUPSTraps-fifth
    VARIABLES  { trapArg , upsShutdownAfterDelay-fifth }
    DESCRIPTION
            "A upsShutdownAfterDelay countdown is restored."
    ::= 54

upsAlarmShutdownImminentRestored-fifth TRAP-TYPE
    ENTERPRISE geUPSTraps-fifth
    VARIABLES  { trapArg  }
    DESCRIPTION
            "A shutdown imminent condition is restored."
    ::= 55

upsAlarmTestInProgressRestored-fifth TRAP-TYPE
    ENTERPRISE geUPSTraps-fifth
    VARIABLES  { trapArg , upsTestId-fifth }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-fifth TRAP-TYPE
    ENTERPRISE geUPSTraps-fifth
    VARIABLES  { trapArg  }
    DESCRIPTION
            "A measurement value reached a value below its low-level threshold."
    ::= 129

upsAlarmValueHigh-fifth TRAP-TYPE
    ENTERPRISE geUPSTraps-fifth
    VARIABLES  { trapArg  }
    DESCRIPTION
            "A measurement value reached a value higher than its high-level threshold."
    ::= 130

upsAlarmValueLowRestored-fifth TRAP-TYPE
    ENTERPRISE geUPSTraps-fifth
    VARIABLES  { trapArg  }
    DESCRIPTION
            "A ValueLow alarm condition is restored."
    ::= 133

upsAlarmValueHighRestored-fifth TRAP-TYPE
    ENTERPRISE geUPSTraps-fifth
    VARIABLES  { trapArg }
    DESCRIPTION
            "A ValueHigh alarm condition is restored."
    ::= 134

--
-- The Device Identification group. Sixth
--      All objects in this group except for upsIdentName and
--      upsIdentAttachedDevices are set at device initialization
--      and remain static.
--

upsIdentManufacturer-sixth OBJECT-TYPE
    SYNTAX     DisplayString (SIZE (0..31))
    MAX-ACCESS read-only
    STATUS     current
    DESCRIPTION
            "The name of the UPS manufacturer.(*)"
    ::= { upsIdent-sixth 1 }

upsIdentModel-sixth OBJECT-TYPE
    SYNTAX     DisplayString (SIZE (0..63))
    MAX-ACCESS read-only
    STATUS     current
    DESCRIPTION
            "The UPS Model designation.(*)"
    ::= { upsIdent-sixth 2 }

upsIdentUPSSoftwareVersion-sixth OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-sixth 3 }

upsIdentAgentSoftwareVersion-sixth OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-sixth 4 }

upsIdentName-sixth OBJECT-TYPE
    SYNTAX     DisplayString (SIZE(0..63))
    MAX-ACCESS read-write
    STATUS     current
    DESCRIPTION
            "A string identifying the UPS.  This object should be
            set by the administrator.(*)"
    ::= { upsIdent-sixth 5 }

upsIdentAttachedDevices-sixth OBJECT-TYPE
    SYNTAX     DisplayString (SIZE(0..63))
    MAX-ACCESS read-write
    STATUS     current
    DESCRIPTION
            "A string identifying the devices attached to the
            output(s) of the UPS.  This object should be set by
            the administrator.(*)"
    ::= { upsIdent-sixth 6 }

upsIdentUPSSerialNumber-sixth OBJECT-TYPE
    SYNTAX     DisplayString (SIZE(0..31))
    MAX-ACCESS read-only
    STATUS     current
    DESCRIPTION
            "The UPS serial number"
    ::= { upsIdent-sixth 7 }
				
upsIdentComProtVersion-sixth OBJECT-TYPE
    SYNTAX     DisplayString (SIZE(0..15))
    MAX-ACCESS read-only
    STATUS     current
    DESCRIPTION
            "The IMV communication protocol version"
    ::= { upsIdent-sixth 8 }	
		
upsIdentOperatingTime-sixth OBJECT-TYPE
    SYNTAX     NonNegativeInteger32
    UNITS      "seconds"
    MAX-ACCESS read-only
    STATUS     current
    DESCRIPTION
            "The present value of the operating time.
             total 'on' time since UPS manufactured"
    ::= { upsIdent-sixth 9 }	
				
--
-- Battery Group Generic
--

upsBatteryStatus-sixth OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-sixth 1 }

upsSecondsOnBattery-sixth OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-sixth 2 }

upsEstimatedMinutesRemaining-sixth OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-sixth 3 }

upsEstimatedChargeRemaining-sixth OBJECT-TYPE
    SYNTAX     Integer32 (0..100)
    UNITS      "percent"
    MAX-ACCESS read-only
    STATUS     current
    DESCRIPTION
            "An estimate of the battery charge remaining expressed
            as a percent of full charge.(*)"
    ::= { upsBattery-sixth 4 }

upsBatteryVoltage-sixth OBJECT-TYPE
    SYNTAX     NonNegativeInteger32
    UNITS      "0.1 Volt DC"
    MAX-ACCESS read-only
    STATUS     current
    DESCRIPTION
            "The magnitude of the present battery voltage.(*)"
    ::= { upsBattery-sixth 5 }

upsBatteryCurrent-sixth OBJECT-TYPE
    SYNTAX     Integer32
    UNITS      "0.1 Amp DC"
    MAX-ACCESS read-only
    STATUS     current
    DESCRIPTION
            "The present battery current.(*)"
    ::= { upsBattery-sixth 6 }

upsBatteryTemperature-sixth OBJECT-TYPE
    SYNTAX     Integer32
    UNITS      "degrees Centigrade"
    MAX-ACCESS read-only
    STATUS     current
    DESCRIPTION
            "The ambient temperature at or near the UPS Battery
            casing.(*)"
    ::= { upsBattery-sixth 7 }

--
-- Input Group
--

upsInputLineBads-sixth OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-sixth 1 }

upsInputNumLines-sixth OBJECT-TYPE
    SYNTAX     NonNegativeInteger32
    MAX-ACCESS read-only
    STATUS     current
    DESCRIPTION
            "The number of input lines utilized in this device.
            This variable indicates the number of rows in the
            input table.(*)"
    ::= { upsInput-sixth 2 }

upsInputTable-sixth OBJECT-TYPE
    SYNTAX     SEQUENCE OF UpsInputEntry-sixth
    MAX-ACCESS not-accessible
    STATUS     current
    DESCRIPTION
            "A list of input table entries.  The number of entries
            is given by the value of upsInputNumLines.(*)"
    ::= { upsInput-sixth 3 }

upsInputEntry-sixth OBJECT-TYPE
    SYNTAX     UpsInputEntry-sixth
    MAX-ACCESS not-accessible
    STATUS     current
    DESCRIPTION
            "An entry containing information applicable to a
            particular input line.(*)"
    INDEX { upsInputLineIndex-sixth }
    ::= { upsInputTable-sixth 1 }

UpsInputEntry-sixth ::= SEQUENCE {
    upsInputLineIndex-sixth   PositiveInteger32,
    upsInputFrequency-sixth   NonNegativeInteger32,
    upsInputVoltage-sixth     NonNegativeInteger32,
    upsInputCurrent-sixth     NonNegativeInteger32,
    upsInputTruePower-sixth   NonNegativeInteger32,
    upsInputVoltageMin-sixth  NonNegativeInteger32,
    upsInputVoltageMax-sixth  NonNegativeInteger32
}

upsInputLineIndex-sixth OBJECT-TYPE
    SYNTAX     PositiveInteger32
    MAX-ACCESS not-accessible
    STATUS     current
    DESCRIPTION
            "The input line identifier.(*)"
    ::= { upsInputEntry-sixth 1 }

upsInputFrequency-sixth OBJECT-TYPE
    SYNTAX     NonNegativeInteger32
    UNITS      "0.1 Hertz"
    MAX-ACCESS read-only
    STATUS     current
    DESCRIPTION
            "The present input frequency.(*)"
    ::= { upsInputEntry-sixth 2 }

upsInputVoltage-sixth OBJECT-TYPE
    SYNTAX     NonNegativeInteger32
    UNITS      "RMS Volts"
    MAX-ACCESS read-only
    STATUS     current
    DESCRIPTION
            "The magnitude of the present input voltage.(*)"
    ::= { upsInputEntry-sixth 3 }

upsInputCurrent-sixth OBJECT-TYPE
    SYNTAX     NonNegativeInteger32
    UNITS      "0.1 RMS Amp"
    MAX-ACCESS read-only
    STATUS     current
    DESCRIPTION
            "The magnitude of the present input current.(*)"
    ::= { upsInputEntry-sixth 4 }

upsInputTruePower-sixth OBJECT-TYPE
    SYNTAX     NonNegativeInteger32
    UNITS      "Watts"
    MAX-ACCESS read-only
    STATUS     current
    DESCRIPTION
            "The magnitude of the present input true power.(*)"
    ::= { upsInputEntry-sixth 5 }

upsInputVoltageMin-sixth OBJECT-TYPE
    SYNTAX     NonNegativeInteger32
    UNITS      "RMS Volts"
    MAX-ACCESS read-only
    STATUS     current
    DESCRIPTION
            "The lowest magnitude of the input voltage since last read out."
    ::= { upsInputEntry-sixth 6 }

upsInputVoltageMax-sixth OBJECT-TYPE
    SYNTAX     NonNegativeInteger32
    UNITS      "RMS Volts"
    MAX-ACCESS read-only
    STATUS     current
    DESCRIPTION
            "The highest magnitude of the input voltage since last read out."
    ::= { upsInputEntry-sixth 7 }

--
-- The Output group.
--

upsOutputSource-sixth OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-sixth 1 }

upsOutputFrequency-sixth OBJECT-TYPE
    SYNTAX     NonNegativeInteger32
    UNITS      "0.1 Hertz"
    MAX-ACCESS read-only
    STATUS     current
    DESCRIPTION
            "The present output frequency.(*)"
    ::= { upsOutput-sixth 2 }

upsOutputNumLines-sixth OBJECT-TYPE
    SYNTAX     NonNegativeInteger32
    MAX-ACCESS read-only
    STATUS     current
    DESCRIPTION
            "The number of output lines utilized in this device.
            This variable indicates the number of rows in the
            output table.(*)"
    ::= { upsOutput-sixth 3 }

upsOutputTable-sixth OBJECT-TYPE
    SYNTAX     SEQUENCE OF UpsOutputEntry-sixth
    MAX-ACCESS not-accessible
    STATUS     current
    DESCRIPTION
            "A list of output table entries.  The number of
            entries is given by the value of upsOutputNumLines.(*)"
    ::= { upsOutput-sixth 4 }

upsOutputEntry-sixth OBJECT-TYPE
    SYNTAX     UpsOutputEntry-sixth
    MAX-ACCESS not-accessible
    STATUS     current
    DESCRIPTION
            "An entry containing information applicable to a
            particular output line.(*)"
    INDEX { upsOutputLineIndex-sixth }
    ::= { upsOutputTable-sixth 1 }

UpsOutputEntry-sixth ::= SEQUENCE {
    upsOutputLineIndex-sixth   PositiveInteger32,
    upsOutputVoltage-sixth     NonNegativeInteger32,
    upsOutputCurrent-sixth     NonNegativeInteger32,
    upsOutputPower-sixth       NonNegativeInteger32,
    upsOutputPercentLoad-sixth Integer32
}

upsOutputLineIndex-sixth OBJECT-TYPE
    SYNTAX     PositiveInteger32
    MAX-ACCESS not-accessible
    STATUS     current
    DESCRIPTION
            "The output line identifier.(*)"
    ::= { upsOutputEntry-sixth 1 }

upsOutputVoltage-sixth OBJECT-TYPE
    SYNTAX     NonNegativeInteger32
    UNITS      "RMS Volts"
    MAX-ACCESS read-only
    STATUS     current
    DESCRIPTION
            "The present output voltage.(*)"
    ::= { upsOutputEntry-sixth 2 }

upsOutputCurrent-sixth OBJECT-TYPE
    SYNTAX     NonNegativeInteger32
    UNITS      "0.1 RMS Amp"
    MAX-ACCESS read-only
    STATUS     current
    DESCRIPTION
            "The present output current.(*)"
    ::= { upsOutputEntry-sixth 3 }

upsOutputPower-sixth OBJECT-TYPE
    SYNTAX     NonNegativeInteger32
    UNITS      "Watts"
    MAX-ACCESS read-only
    STATUS     current
    DESCRIPTION
            "The present output true power.(*)"
    ::= { upsOutputEntry-sixth 4 }

upsOutputPercentLoad-sixth OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-sixth 5 }

--
-- The Bypass group generic.
--

upsBypassFrequency-sixth OBJECT-TYPE
    SYNTAX     NonNegativeInteger32
    UNITS      "0.1 Hertz"
    MAX-ACCESS read-only
    STATUS     current
    DESCRIPTION
            "The present bypass frequency.(*)"
    ::= { upsBypass-sixth 1 }

upsBypassNumLines-sixth OBJECT-TYPE
    SYNTAX     NonNegativeInteger32
    MAX-ACCESS read-only
    STATUS     current
    DESCRIPTION
            "The number of bypass lines utilized in this device.
            This entry indicates the number of rows in the bypass
            table.(*)"
    ::= { upsBypass-sixth 2 }

upsBypassTable-sixth OBJECT-TYPE
    SYNTAX     SEQUENCE OF UpsBypassEntry-sixth
    MAX-ACCESS not-accessible
    STATUS     current
    DESCRIPTION
            "A list of bypass table entries.  The number of
            entries is given by the value of upsBypassNumLines.(*)"
    ::= { upsBypass-sixth 3 }

upsBypassEntry-sixth OBJECT-TYPE
    SYNTAX     UpsBypassEntry-sixth
    MAX-ACCESS not-accessible
    STATUS     current
    DESCRIPTION
            "An entry containing information applicable to a
            particular bypass input.(*)"
    INDEX { upsBypassLineIndex-sixth }
    ::= { upsBypassTable-sixth 1 }

UpsBypassEntry-sixth ::= SEQUENCE {
    upsBypassLineIndex-sixth  PositiveInteger32,
    upsBypassVoltage-sixth    NonNegativeInteger32,
    upsBypassCurrent-sixth    NonNegativeInteger32,
    upsBypassPower-sixth      NonNegativeInteger32
}

upsBypassLineIndex-sixth OBJECT-TYPE
    SYNTAX     PositiveInteger32
    MAX-ACCESS not-accessible
    STATUS     current
    DESCRIPTION
            "The bypass line identifier.(*)"
    ::= { upsBypassEntry-sixth 1 }

upsBypassVoltage-sixth OBJECT-TYPE
    SYNTAX     NonNegativeInteger32
    UNITS      "RMS Volts"
    MAX-ACCESS read-only
    STATUS     current
    DESCRIPTION
            "The present bypass voltage.(*)"
    ::= { upsBypassEntry-sixth 2 }

upsBypassCurrent-sixth OBJECT-TYPE
    SYNTAX     NonNegativeInteger32
    UNITS      "0.1 RMS Amp"
    MAX-ACCESS read-only
    STATUS     current
    DESCRIPTION
            "The present bypass current.(*)"
    ::= { upsBypassEntry-sixth 3 }

upsBypassPower-sixth OBJECT-TYPE
    SYNTAX     NonNegativeInteger32
    UNITS      "Watts"
    MAX-ACCESS read-only
    STATUS     current
    DESCRIPTION
            "The present true power conveyed by the bypass.(*)"
    ::= { upsBypassEntry-sixth 4 }

--
-- The Alarm group generic.
--

upsAlarmsPresent-sixth OBJECT-TYPE
    SYNTAX     Gauge32
    MAX-ACCESS read-only
    STATUS     current
    DESCRIPTION
            "The present number of active alarm conditions.(*)"
    ::= { upsAlarm-sixth 1 }

upsAlarmTable-sixth OBJECT-TYPE
    SYNTAX     SEQUENCE OF UpsAlarmEntry-sixth
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-sixth 2 }

upsAlarmEntry-sixth OBJECT-TYPE
    SYNTAX     UpsAlarmEntry-sixth
    MAX-ACCESS not-accessible
    STATUS     current
    DESCRIPTION
            "An entry containing information applicable to a
            particular alarm.(*)"
    INDEX { upsAlarmId-sixth }
    ::= { upsAlarmTable-sixth 1 }

UpsAlarmEntry-sixth ::= SEQUENCE {
    upsAlarmId-sixth          PositiveInteger32,
    upsAlarmDescr-sixth       AutonomousType,
    upsAlarmTime-sixth       TimeStamp
}

upsAlarmId-sixth OBJECT-TYPE
    SYNTAX     PositiveInteger32
    MAX-ACCESS not-accessible
    STATUS     current
    DESCRIPTION
            "A unique identifier for an alarm condition.  This
            value must remain constant.(*)"
    ::= { upsAlarmEntry-sixth 1 }

upsAlarmDescr-sixth OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-sixth 2 }

upsAlarmTime-sixth OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-sixth 3 }

--
-- Well known alarm conditions generic.
--

upsAlarmBatteryBad-sixth OBJECT-IDENTITY
    STATUS     current
    DESCRIPTION
            "One or more batteries have been determined to require
            replacement.(*)"
    ::= { upsWellKnownAlarms-sixth  1 }

upsAlarmOnBattery-sixth OBJECT-IDENTITY
    STATUS     current
    DESCRIPTION
            "The UPS is drawing power from the batteries.(*)"
    ::= { upsWellKnownAlarms-sixth  2 }

upsAlarmLowBattery-sixth OBJECT-IDENTITY
    STATUS     current
    DESCRIPTION
            "The remaining battery run-time is less than or equal
            to upsConfigLowBattTime.(*)"
    ::= { upsWellKnownAlarms-sixth  3 }

upsAlarmDepletedBattery-sixth OBJECT-IDENTITY
    STATUS     current
    DESCRIPTION
            "The UPS will be unable to sustain the present load
            when and if the utility power is lost.(*)"
    ::= { upsWellKnownAlarms-sixth  4 }

upsAlarmTempBad-sixth OBJECT-IDENTITY
    STATUS     current
    DESCRIPTION
            "A temperature is out of tolerance.(*)"
    ::= { upsWellKnownAlarms-sixth  5 }

upsAlarmInputBad-sixth OBJECT-IDENTITY
    STATUS     current
    DESCRIPTION
            "An input condition is out of tolerance.(*)"
    ::= { upsWellKnownAlarms-sixth  6 }

upsAlarmOutputBad-sixth OBJECT-IDENTITY
    STATUS     current
    DESCRIPTION
            "An output condition (other than OutputOverload) is
            out of tolerance.(*)"
    ::= { upsWellKnownAlarms-sixth  7 }

upsAlarmOutputOverload-sixth OBJECT-IDENTITY
    STATUS     current
    DESCRIPTION
            "The output load exceeds the UPS output capacity.(*)"
    ::= { upsWellKnownAlarms-sixth  8 }

upsAlarmOnBypass-sixth OBJECT-IDENTITY
    STATUS     current
    DESCRIPTION
            "The Bypass is presently engaged on the UPS.(*)"
    ::= { upsWellKnownAlarms-sixth  9 }

upsAlarmBypassBad-sixth OBJECT-IDENTITY
    STATUS     current
    DESCRIPTION
            "The Bypass is out of tolerance.(*)"
    ::= { upsWellKnownAlarms-sixth 10 }

upsAlarmOutputOffAsRequested-sixth OBJECT-IDENTITY
    STATUS     current
    DESCRIPTION
            "The UPS has shutdown as requested, i.e., the output
            is off.(*)"
    ::= { upsWellKnownAlarms-sixth 11 }

upsAlarmUpsOffAsRequested-sixth OBJECT-IDENTITY
    STATUS     current
    DESCRIPTION
            "The entire UPS has shutdown as commanded.(*)"
    ::= { upsWellKnownAlarms-sixth 12 }

upsAlarmChargerFailed-sixth OBJECT-IDENTITY
    STATUS     current
    DESCRIPTION
            "An uncorrected problem has been detected within the
            UPS charger subsystem.(*)"
    ::= { upsWellKnownAlarms-sixth 13 }

upsAlarmUpsOutputOff-sixth OBJECT-IDENTITY
    STATUS     current
    DESCRIPTION
            "The output of the UPS is in the off state.(*)"
    ::= { upsWellKnownAlarms-sixth 14 }

upsAlarmUpsSystemOff-sixth OBJECT-IDENTITY
    STATUS     current
    DESCRIPTION
            "The UPS system is in the off state.(*)"
    ::= { upsWellKnownAlarms-sixth 15 }

upsAlarmFanFailure-sixth OBJECT-IDENTITY
    STATUS     current
    DESCRIPTION
            "The failure of one or more fans in the UPS has been
            detected.(*)"
    ::= { upsWellKnownAlarms-sixth 16 }

upsAlarmFuseFailure-sixth OBJECT-IDENTITY
    STATUS     current
    DESCRIPTION
            "The failure of one or more fuses has been detected.(*)"
    ::= { upsWellKnownAlarms-sixth 17 }

upsAlarmGeneralFault-sixth OBJECT-IDENTITY
    STATUS     current
    DESCRIPTION
            "A general fault in the UPS has been detected.(*)"
    ::= { upsWellKnownAlarms-sixth 18 }

upsAlarmDiagnosticTestFailed-sixth OBJECT-IDENTITY
    STATUS     current
    DESCRIPTION
            "The result of the last diagnostic test indicates a
            failure.(*)"
    ::= { upsWellKnownAlarms-sixth 19 }

upsAlarmCommunicationsLost-sixth OBJECT-IDENTITY
    STATUS     current
    DESCRIPTION
            "A problem has been encountered in the communications
            between the agent and the UPS.(*)"
    ::= { upsWellKnownAlarms-sixth 20 }

upsAlarmAwaitingPower-sixth OBJECT-IDENTITY
    STATUS     current
    DESCRIPTION
            "The UPS output is off and the UPS is awaiting the
            return of input power.(*)"
    ::= { upsWellKnownAlarms-sixth 21 }

upsAlarmShutdownPending-sixth OBJECT-IDENTITY
    STATUS     current
    DESCRIPTION
            "A upsShutdownAfterDelay countdown is underway.(*)"
    ::= { upsWellKnownAlarms-sixth 22 }

upsAlarmShutdownImminent-sixth OBJECT-IDENTITY
    STATUS     current
    DESCRIPTION
            "The UPS will turn off power to the load in less than
            5 seconds; this may be either a timed shutdown or a
            low battery shutdown.(*)"
    ::= { upsWellKnownAlarms-sixth 23 }

upsAlarmTestInProgress-sixth OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-sixth 24 }

upsAlarmReceptacleOff-sixth OBJECT-IDENTITY
    STATUS     current
    DESCRIPTION
            "The receptacle are switch off    "
    ::= { upsWellKnownAlarms-sixth 25 }

upsAlarmMaskA-sixth OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-sixth 4 }

--
-- The Test Group generic
--

upsTestId-sixth OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-sixth 1 }

-- see [6] for more information on the semantics of objects with
-- syntax of TestAndIncr

upsTestSpinLock-sixth OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-sixth 2 }

upsTestResultsSummary-sixth OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-sixth 3 }

upsTestResultsDetail-sixth OBJECT-TYPE
    SYNTAX     DisplayString (SIZE (0..255))
    MAX-ACCESS read-only
    STATUS     current
    DESCRIPTION
            "Additional information about upsTestResultsSummary.
            If no additional information available, a zero length
            string is returned.(*)"
    ::= { upsTest-sixth 4 }

upsTestStartTime-sixth OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-sixth 5 }

upsTestElapsedTime-sixth OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-sixth 6 }

--
-- Well known tests generic.
--

upsTestNoTestsInitiated-sixth OBJECT-IDENTITY
    STATUS     current
    DESCRIPTION
            "No tests have been initiated and no test is in
            progress.(*)"
    ::= { upsWellKnownTests-sixth  1 }

upsTestAbortTestInProgress-sixth OBJECT-IDENTITY
    STATUS     current
    DESCRIPTION
            "The test in progress is to be aborted / the test in
            progress was aborted.(*)"
    ::= { upsWellKnownTests-sixth  2 }

upsTestGeneralSystemsTest-sixth OBJECT-IDENTITY
    STATUS     current
    DESCRIPTION
            "The manufacturer's standard test of UPS device
            systems.(*)"
    ::= { upsWellKnownTests-sixth  3 }

upsTestQuickBatteryTest-sixth OBJECT-IDENTITY
    STATUS     current
    DESCRIPTION
            "A test that is sufficient to determine if the battery
            needs replacement.(*)"
    ::= { upsWellKnownTests-sixth  4 }

upsTestDeepBatteryCalibration-sixth OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-sixth  5 }

--
-- The Control group generic.
--

upsShutdownType-sixth OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-sixth 1 }

upsShutdownAfterDelay-sixth OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-sixth 2 }

upsStartupAfterDelay-sixth OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-sixth 3 }

upsRebootWithDuration-sixth OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-sixth 4 }

upsAutoRestart-sixth OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-sixth 5 }

upsReceptaclesNum-sixth OBJECT-TYPE
    SYNTAX     NonNegativeInteger32
    MAX-ACCESS read-only
    STATUS     current
    DESCRIPTION
            "The number of receptacles utilized in this device.
            This entry indicates the number of rows in the receptacle
            table."
    ::= { upsControl-sixth 6 }

upsReceptacleTable-sixth OBJECT-TYPE
    SYNTAX     SEQUENCE OF UpsReceptacleEntry-sixth
    MAX-ACCESS not-accessible
    STATUS     current
    DESCRIPTION
            "A list of receptacle table entries.  The number of
            entries is given by the value of upsReceptacleNum."
    ::= { upsControl-sixth 7 }

upsReceptacleEntry-sixth OBJECT-TYPE
    SYNTAX     UpsReceptacleEntry-sixth
    MAX-ACCESS not-accessible
    STATUS     current
    DESCRIPTION
            "An entry containing information applicable to a
            particular receptacle."
    INDEX { upsReceptacleLineIndex-sixth }
    ::= { upsReceptacleTable-sixth 1 }

UpsReceptacleEntry-sixth ::= SEQUENCE {
    upsReceptacleLineIndex-sixth  PositiveInteger32,
    upsReceptacleOnOff-sixth      Integer32    
}

upsReceptacleLineIndex-sixth OBJECT-TYPE
    SYNTAX     PositiveInteger32
    MAX-ACCESS not-accessible
    STATUS     current
    DESCRIPTION
            "The receptacle line identifier."
    ::= { upsReceptacleEntry-sixth 1 }

upsReceptacleOnOff-sixth OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-sixth 2 }

upsUPSMode-sixth OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-sixth 8 }

upsRectifierOnOff-sixth OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-sixth 9 }

upsBatteryChargeMethod-sixth OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-sixth 10 }

upsInverterOnOff-sixth OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-sixth 11 }

upsBypassOnOff-sixth OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-sixth 12 }

upsLoadSource-sixth OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-sixth 13 }
	
--
-- The Configuration group generic.
--

upsConfigInputVoltage-sixth OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-sixth 1 }

upsConfigInputFreq-sixth OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-sixth 2 }

upsConfigOutputVoltage-sixth OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-sixth 3 }

upsConfigOutputFreq-sixth OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-sixth 4 }

upsConfigOutputVA-sixth OBJECT-TYPE
    SYNTAX     NonNegativeInteger32
    UNITS      "Volt-Amps"
    MAX-ACCESS read-only
    STATUS     current
    DESCRIPTION
            "The magnitude of the nominal Volt-Amp rating.(*)"
    ::= { upsConfig-sixth 5 }

upsConfigOutputPower-sixth OBJECT-TYPE
    SYNTAX     NonNegativeInteger32
    UNITS      "Watts"
    MAX-ACCESS read-only
    STATUS     current
    DESCRIPTION
            "The magnitude of the nominal true power rating.(*)"
    ::= { upsConfig-sixth 6 }

upsConfigLowBattTime-sixth OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-sixth 7 }

upsConfigAudibleStatus-sixth OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-sixth 8 }

upsConfigLowVoltageTransferPoint-sixth OBJECT-TYPE
    SYNTAX     NonNegativeInteger32
    UNITS      "RMS Volts"
    MAX-ACCESS read-write
    STATUS     current
    DESCRIPTION
            "The minimum input line voltage allowed before the UPS
            system transfers to battery backup.(*)"
    ::= { upsConfig-sixth 9 }

upsConfigHighVoltageTransferPoint-sixth OBJECT-TYPE
    SYNTAX     NonNegativeInteger32
    UNITS      "RMS Volts"
    MAX-ACCESS read-write
    STATUS     current
    DESCRIPTION
            "The maximum line voltage allowed before the UPS
            system transfers to battery backup.(*)"
    ::= { upsConfig-sixth 10 }

upsConfigBatteryCapacity-sixth OBJECT-TYPE
    SYNTAX     NonNegativeInteger32
    UNITS      "Amps Hours"
    MAX-ACCESS read-write
    STATUS     current
    DESCRIPTION
            "The installed battery capacity. This value is the 'factory'-value,
             not the value after calibration."
    ::= { upsConfig-sixth 11 }

upsConfigBatteryChargeCurrent-sixth OBJECT-TYPE
    SYNTAX     NonNegativeInteger32
    UNITS      "0.1 Amp DC"
    MAX-ACCESS read-write
    STATUS     current
    DESCRIPTION
            "The maximum battery charge current, including external chargers."
    ::= { upsConfig-sixth 12 }						

upsConfigNoLoadShutdown-sixth OBJECT-TYPE
    SYNTAX     Integer32 {
        disabled(1),
        enabled(2)
    }
    MAX-ACCESS read-write
    STATUS     current
    DESCRIPTION
            "Dis- or enable 'no load' shutdown from the contact interface."
    ::= { upsConfig-sixth 13 }
	
upsConfigStartDelay-sixth OBJECT-TYPE
    SYNTAX     PositiveInteger32
    UNITS      "minutes"				
    MAX-ACCESS read-write
    STATUS     current
    DESCRIPTION
            "Minimum required autonomy time before the UPS may perform an
             autorestart."
    ::= { upsConfig-sixth 14 }

--
-- The GetSet group generic.
--

upsEventGetNext-sixth OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-sixth 1 }

upsEventGetPrevious-sixth OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-sixth 2 }
				
upsEventSetStartingTimeStamp-sixth OBJECT-TYPE
    SYNTAX     NonNegativeInteger32
    MAX-ACCESS read-write
    STATUS     current
    DESCRIPTION
            "The timestamp which is used as starting point for downloading
             events from the UPS event buffer"
    ::= { upsGetSet-sixth 3 }				

upsEventRetreiveCurrentTimeStamp-sixth OBJECT-TYPE
    SYNTAX     NonNegativeInteger32
    MAX-ACCESS read-only
    STATUS     current
    DESCRIPTION
            "The current timestamp is retreived from the UPS"
    ::= { upsGetSet-sixth 4 }				

upsEventTableSize-sixth OBJECT-TYPE
    SYNTAX     NonNegativeInteger32
    MAX-ACCESS read-only
    STATUS     current
    DESCRIPTION
            "The number of entries in the event table.
            This object indicates the number of rows in the event table."
    ::= { upsGetSet-sixth 5 }

upsEventTable-sixth OBJECT-TYPE
    SYNTAX     SEQUENCE OF UpsEventEntry-sixth
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-sixth 6 }

upsEventEntry-sixth OBJECT-TYPE
    SYNTAX     UpsEventEntry-sixth
    MAX-ACCESS not-accessible
    STATUS     current
    DESCRIPTION
            "An entry containing information applicable to a
            particular event."
    INDEX { upsEventLineIndex-sixth }
    ::= { upsEventTable-sixth 1 }

UpsEventEntry-sixth ::= SEQUENCE {
    upsEventLineIndex-sixth PositiveInteger32,
    upsEventCode-sixth      Integer32,
    upsEventStatus-sixth    NonNegativeInteger32,
    upsEventTime-sixth      NonNegativeInteger32
}

upsEventLineIndex-sixth OBJECT-TYPE
    SYNTAX     PositiveInteger32
    MAX-ACCESS not-accessible
    STATUS     current
    DESCRIPTION
            "The event line identifier."
    ::= { upsEventEntry-sixth 1 }

upsEventCode-sixth OBJECT-TYPE
    SYNTAX     NonNegativeInteger32
    MAX-ACCESS read-only
    STATUS     current
    DESCRIPTION
            "The event code in numerical format."
    ::= { upsEventEntry-sixth 2 }

upsEventStatus-sixth OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-sixth 3 }

upsEventTime-sixth OBJECT-TYPE
    SYNTAX     NonNegativeInteger32
    MAX-ACCESS read-only
    STATUS     current
    DESCRIPTION
            "The timestamp of the moment the event was generated."
    ::= { upsEventEntry-sixth 4 }

upsParametersRead-sixth OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-sixth 7 }

upsParametersWrite-sixth OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-sixth 8 }

upsParametersStartAddress-sixth OBJECT-TYPE
    SYNTAX     NonNegativeInteger32
    MAX-ACCESS read-write
    STATUS     current
    DESCRIPTION
            "The address which is used as starting point for downloading
             parameters from the UPS"
    ::= { upsGetSet-sixth 9 }				

upsParameterTableSize-sixth OBJECT-TYPE
    SYNTAX     NonNegativeInteger32
    MAX-ACCESS read-only
    STATUS     current
    DESCRIPTION
            "The number of entries in the parameter table.
            This object indicates the number of rows in the parameter table."
    ::= { upsGetSet-sixth 10 }

upsParameterTable-sixth OBJECT-TYPE
    SYNTAX     SEQUENCE OF UpsParameterEntry-sixth
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-sixth 11 }

upsParameterEntry-sixth OBJECT-TYPE
    SYNTAX     UpsParameterEntry-sixth
    MAX-ACCESS not-accessible
    STATUS     current
    DESCRIPTION
            "An entry containing information applicable to a
            particular parameter."
    INDEX { upsParameterLineIndex-sixth }
    ::= { upsParameterTable-sixth 1 }

UpsParameterEntry-sixth ::= SEQUENCE {
    upsParameterLineIndex-sixth PositiveInteger32,
    upsParameterValue-sixth     Integer32   
}

upsParameterLineIndex-sixth OBJECT-TYPE
    SYNTAX     PositiveInteger32
    MAX-ACCESS not-accessible
    STATUS     current
    DESCRIPTION
            "The parameter line identifier."
    ::= { upsParameterEntry-sixth 1 }

upsParameterValue-sixth OBJECT-TYPE
    SYNTAX     Integer32
    MAX-ACCESS read-write
    STATUS     current
    DESCRIPTION
            "The parameter value in numerical format."
    ::= { upsParameterEntry-sixth 2 }

upsStatus-sixth OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-sixth 12 }

upsMainsStatisticsMBfail-sixth OBJECT-TYPE
    SYNTAX     NonNegativeInteger32
    MAX-ACCESS read-only
    STATUS     current
    DESCRIPTION
            "Count of main bypass failures (>200 ms), since UPS installation."
    ::= { upsGetSet-sixth 13 }

upsMainsStatisticsMRfail-sixth OBJECT-TYPE
    SYNTAX     NonNegativeInteger32
    MAX-ACCESS read-only
    STATUS     current
    DESCRIPTION
            "Count of mains rectifier failures (>200 ms), since UPS installation."
    ::= { upsGetSet-sixth 14 }
		
upsMainsStatisticsB2-sixth OBJECT-TYPE
    SYNTAX     NonNegativeInteger32
    MAX-ACCESS read-only
    STATUS     current
    DESCRIPTION
            "Count of transients on the mains bypass (0..2 ms), during the last 7 days."
    ::= { upsGetSet-sixth 15 }

upsMainsStatisticsB5-sixth OBJECT-TYPE
    SYNTAX     NonNegativeInteger32
    MAX-ACCESS read-only
    STATUS     current
    DESCRIPTION
            "Count of transients on the mains bypass (2..5 ms), during the last 7 days."
    ::= { upsGetSet-sixth 16 }

upsMainsStatisticsB10-sixth OBJECT-TYPE
    SYNTAX     NonNegativeInteger32
    MAX-ACCESS read-only
    STATUS     current
    DESCRIPTION
            "Count of transients on the mains bypass (5..10 ms), during the last 7 days."
    ::= { upsGetSet-sixth 17 }

upsMainsStatisticsB200-sixth OBJECT-TYPE
    SYNTAX     NonNegativeInteger32
    MAX-ACCESS read-only
    STATUS     current
    DESCRIPTION
            "Count of transients on the mains bypass (10..200 ms), during the last 7 days."
    ::= { upsGetSet-sixth 18 }

upsMainsStatisticsBypRel-sixth OBJECT-TYPE
    SYNTAX     NonNegativeInteger32
    MAX-ACCESS read-only
    STATUS     current
    DESCRIPTION
            "Bypass reliability degree [0..100%;255]. The value NOSUCHNAME means 'not available'."
    ::= { upsGetSet-sixth 19 }

upsTime-sixth OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-sixthERROR,              meaning 'command not supported'. It is possible to know which is the timestamp 
             format supported by the UPS, by issuing a read-command or by reading events, 
             which includes timestamps."
    ::= { upsGetSet-sixth 20 }

upsRequestPermission-sixth OBJECT-TYPE
    SYNTAX     DisplayString (SIZE(0..63))
    MAX-ACCESS write-only
    STATUS     current
    DESCRIPTION
            "An encrypted code is send to enable use of restricted write objects during
             a limited period of time."
    ::= { upsGetSet-sixth 21 }
    
upsEventGetCode-sixth OBJECT-TYPE
    SYNTAX     Integer32
    MAX-ACCESS write-only
    STATUS     current
    DESCRIPTION
            "The code which is used as starting point to downloading the events from the 
            UPS event buffer."
    ::= { upsGetSet-sixth 22 }    
    
upsEventSpinLock-sixth OBJECT-TYPE
    SYNTAX     TestAndIncr
    MAX-ACCESS read-write
    STATUS     current
    DESCRIPTION
            "A spin lock on the event subsystem. "

    ::= { upsGetSet-sixth 23 }
    
upsParameterSpinLock-sixth OBJECT-TYPE
    SYNTAX     TestAndIncr
    MAX-ACCESS read-write
    STATUS     current
    DESCRIPTION
            "A spin lock on the parameters subsystem. "

    ::= { upsGetSet-sixth 24 }

--
-- GE Trap group generic
--

upsAlarmBatteryBad-sixth TRAP-TYPE
    ENTERPRISE geUPSTraps-sixth
    VARIABLES  { trapArg  }
    DESCRIPTION
            "One or more batteries have been determined to require
            replacement."
    ::= 1

upsAlarmOnBattery-sixth TRAP-TYPE
    ENTERPRISE geUPSTraps-sixth
    VARIABLES  { trapArg , upsSecondsOnBattery-sixth  }
    DESCRIPTION
            "An On Battery condition is restored."
    ::= 2

upsAlarmLowBattery-sixth TRAP-TYPE
    ENTERPRISE geUPSTraps-sixth
    VARIABLES  { trapArg  }
    DESCRIPTION
            "The remaining battery run-time is less than or equal
            to upsConfigLowBattTime."
    ::= 3

upsAlarmDepletedBattery-sixth TRAP-TYPE
    ENTERPRISE geUPSTraps-sixth
    VARIABLES  { trapArg  }
    DESCRIPTION
            "The UPS will be unable to sustain the present load
            when and if the utility power is lost)"
    ::= 4

upsAlarmTempBad-sixth TRAP-TYPE
    ENTERPRISE geUPSTraps-sixth
    VARIABLES  { trapArg , upsBatteryTemperature }
    DESCRIPTION
            "A temperature is out of tolerance."
    ::= 5

upsAlarmInputBad-sixth TRAP-TYPE
    ENTERPRISE geUPSTraps-sixth
    VARIABLES  { trapArg  }
    DESCRIPTION
            "An input condition is out of tolerance."
    ::= 6

upsAlarmOutputBad-sixth TRAP-TYPE
    ENTERPRISE geUPSTraps-sixth
    VARIABLES  { trapArg  }
    DESCRIPTION
            "An output condition (other than OutputOverload) is
            out of tolerance."
    ::= 7

upsAlarmOutputOverload-sixth TRAP-TYPE
    ENTERPRISE geUPSTraps-sixth
    VARIABLES  { trapArg , upsOutputPercentLoad-sixth }
    DESCRIPTION
            "The output load exceeds the UPS output capacity."
    ::= 8

upsAlarmOnBypass-sixth TRAP-TYPE
    ENTERPRISE geUPSTraps-sixth
    VARIABLES  { trapArg  }
    DESCRIPTION
            "The Bypass is presently engaged on the UPS."
    ::= 9

upsAlarmBypassBad-sixth TRAP-TYPE
    ENTERPRISE geUPSTraps-sixth
    VARIABLES  { trapArg  }
    DESCRIPTION
            "The Bypass is out of tolerance."
    ::= 10

upsAlarmOutputOffAsRequested-sixth TRAP-TYPE
    ENTERPRISE geUPSTraps-sixth
    VARIABLES  { trapArg  }
    DESCRIPTION
            "The UPS has shutdown as requested, i.e., the output
            is off."
    ::= 11

upsAlarmUpsOffAsRequested-sixth TRAP-TYPE
    ENTERPRISE geUPSTraps-sixth-sixth
    VARIABLES  { trapArg  }
    DESCRIPTION
            "The entire UPS has shutdown as commanded."
    ::= 12

upsAlarmChargerFailed-sixth TRAP-TYPE
    ENTERPRISE geUPSTraps-sixth
    VARIABLES  { trapArg  }
    DESCRIPTION
            "An uncorrected problem has been detected within the
            UPS charger subsystem."
    ::= 13

upsAlarmUpsOutputOff-sixth TRAP-TYPE
    ENTERPRISE geUPSTraps-sixth
    VARIABLES  { trapArg  }
    DESCRIPTION
            "The output of the UPS is in the off state."
    ::= 14

upsAlarmUpsSystemOff-sixth TRAP-TYPE
    ENTERPRISE geUPSTraps-sixth
    VARIABLES  { trapArg  }
    DESCRIPTION
            "The UPS system is in the off state."
    ::= 15

upsAlarmFanFailure-sixth TRAP-TYPE
    ENTERPRISE geUPSTraps-sixth
    VARIABLES  { trapArg  }
    DESCRIPTION
            "The failure of one or more fans in the UPS has been
            detected."
    ::= 16

upsAlarmFuseFailure-sixth TRAP-TYPE
    ENTERPRISE geUPSTraps-sixth
    VARIABLES  { trapArg  }
    DESCRIPTION
            "The failure of one or more fuses has been detected."
    ::= 17

upsAlarmGeneralFault-sixth TRAP-TYPE
    ENTERPRISE geUPSTraps-sixth
    VARIABLES  { trapArg  }
    DESCRIPTION
            "A general fault in the UPS has been detected."
    ::= 18

upsAlarmDiagnosticTestFailed-sixth TRAP-TYPE
    ENTERPRISE geUPSTraps-sixth
    VARIABLES  { trapArg  }
    DESCRIPTION
            "The result of the last diagnostic test indicates a
            failure."
    ::= 19

upsAlarmCommunicationsLost-sixth TRAP-TYPE
    ENTERPRISE geUPSTraps-sixth
    VARIABLES  { trapArg  }
    DESCRIPTION
            "A problem has been encountered in the communication
            between the agent and the UPS."
    ::= 20
    
upsAlarmAwaitingPower-sixth TRAP-TYPE
    ENTERPRISE geUPSTraps-sixth
    VARIABLES  { trapArg  }
    DESCRIPTION
            "The UPS output is off and the UPS is awaiting the
            return of the input power (*)."
    ::= 21    

upsAlarmShutdownPending-sixth TRAP-TYPE
    ENTERPRISE geUPSTraps-sixth
    VARIABLES  { trapArg , upsShutdownAfterDelay-sixth }
    DESCRIPTION
            "A upsShutdownAfterDelay countdown is underway."
    ::= 22

upsAlarmShutdownImminent-sixth TRAP-TYPE
    ENTERPRISE geUPSTraps-sixth
    VARIABLES  { trapArg  }
    DESCRIPTION
            "The UPS will turn off power to the load in less than
            5 seconds; this may be either a timed shutdown or a
            low battery shutdown."
    ::= 23

upsAlarmTestInProgress-sixth TRAP-TYPE
    ENTERPRISE geUPSTraps-sixth
    VARIABLES  { trapArg , upsTestId-sixth }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-sixth TRAP-TYPE
    ENTERPRISE geUPSTraps-sixth
    VARIABLES  { trapArg  }
    DESCRIPTION
            "A receptacle has been switched off."
    ::= 25

upsAlarmBatteryBadRestored-sixth TRAP-TYPE
    ENTERPRISE geUPSTraps-sixth
    VARIABLES  { trapArg  }
    DESCRIPTION
            "A Battery bad condition is restored."
    ::= 33

upsAlarmOnBatteryRestored-sixth TRAP-TYPE
    ENTERPRISE geUPSTraps-sixth
    VARIABLES  { trapArg  }
    DESCRIPTION
            "The UPS is drawing power from mains again."
    ::= 34

upsAlarmLowBatteryRestored-sixth TRAP-TYPE
    ENTERPRISE geUPSTraps-sixth
    VARIABLES  { trapArg  }
    DESCRIPTION
            "A Low Battery condition is restored."
    ::= 35

upsAlarmDepletedBatteryRestored-sixth TRAP-TYPE
    ENTERPRISE geUPSTraps-sixth
    VARIABLES  { trapArg  }
    DESCRIPTION
            "A Depleted Battery condition is restored."
    ::= 36

upsAlarmTempBadRestored-sixth TRAP-TYPE
    ENTERPRISE geUPSTraps-sixth
    VARIABLES  { trapArg  }
    DESCRIPTION
            "A bad temperature condition is restored."
    ::= 37

upsAlarmInputBadRestored-sixth TRAP-TYPE
    ENTERPRISE geUPSTraps-sixth
    VARIABLES  { trapArg  }
    DESCRIPTION
            "An input bad condition is restored."
    ::= 38

upsAlarmOutputBadRestored-sixth TRAP-TYPE
    ENTERPRISE geUPSTraps-sixth
    VARIABLES  { trapArg  }
    DESCRIPTION
            "An output bad condition is restored."
    ::= 39

upsAlarmOutputOverloadRestored-sixth TRAP-TYPE
    ENTERPRISE geUPSTraps-sixth
    VARIABLES  { trapArg  }
    DESCRIPTION
            "An output overload condition is restored."
    ::= 40

upsAlarmOnBypassRestored-sixth TRAP-TYPE
    ENTERPRISE geUPSTraps-sixth
    VARIABLES  { trapArg  }
    DESCRIPTION
            "An On Bypass condition is restored."
    ::= 41

upsAlarmBypassBadRestored-sixth TRAP-TYPE
    ENTERPRISE geUPSTraps-sixth
    VARIABLES  { trapArg  }
    DESCRIPTION
            "A Bypass bad condition is restored."
    ::= 42

upsAlarmOutputOffAsRequestedRestored-sixth TRAP-TYPE
    ENTERPRISE geUPSTraps-sixth
    VARIABLES  { trapArg  }
    DESCRIPTION
            "A request shutdown has been restored."
    ::= 43

upsAlarmUpsOffAsRequestedRestored-sixth TRAP-TYPE
    ENTERPRISE geUPSTraps-sixth-sixth
    VARIABLES  { trapArg  }
    DESCRIPTION
            "A entire UPS command has been restored."
    ::= 44

upsAlarmChargerFailedRestored-sixth TRAP-TYPE
    ENTERPRISE geUPSTraps-sixth
    VARIABLES  { trapArg  }
    DESCRIPTION
            "A Charger Failer condition is restored."
    ::= 45

upsAlarmUpsOutputOn-sixth TRAP-TYPE
    ENTERPRISE geUPSTraps-sixth
    VARIABLES  { trapArg  }
    DESCRIPTION
            "The output of the UPS switched in the on state."
    ::= 46

upsAlarmUpsSystemOn-sixth TRAP-TYPE
    ENTERPRISE geUPSTraps-sixth
    VARIABLES  { trapArg  }
    DESCRIPTION
            "The UPS system is switched in the on state."
    ::= 47

upsAlarmFanFailureRestored-sixth TRAP-TYPE
    ENTERPRISE geUPSTraps-sixth
    VARIABLES  { trapArg  }
    DESCRIPTION
            "A Fan failure condition is restored."
    ::= 48

upsAlarmFuseFailureRestored-sixth TRAP-TYPE
    ENTERPRISE geUPSTraps-sixth
    VARIABLES  { trapArg  }
    DESCRIPTION
            "A Fuse failure condition is restored."
    ::= 49

upsAlarmGeneralFaultRestored-sixth TRAP-TYPE
    ENTERPRISE geUPSTraps-sixth
    VARIABLES  { trapArg  }
    DESCRIPTION
            "A general fault is restored."
    ::= 50

upsAlarmDiagnosticTestFailedRestored-sixth TRAP-TYPE
    ENTERPRISE geUPSTraps-sixth
    VARIABLES  { trapArg  }
    DESCRIPTION
            "A last diagnostic test indicates a failure is 
            restored."
    ::= 51

upsAlarmCommunicationsLostRestored-sixth TRAP-TYPE
    ENTERPRISE geUPSTraps-sixth
    VARIABLES  { trapArg  }
    DESCRIPTION
            "A problem in the communication between the agent 
            and the UPS is restored."
    ::= 52
    
upsAlarmAwaitingPowerRestored-sixth TRAP-TYPE
    ENTERPRISE geUPSTraps-sixth
    VARIABLES  { trapArg  }
    DESCRIPTION
            "A awaiting power condition is restored (*)."
    ::= 53    

upsAlarmShutdownPendingRestored-sixth TRAP-TYPE
    ENTERPRISE geUPSTraps-sixth
    VARIABLES  { trapArg , upsShutdownAfterDelay-sixth }
    DESCRIPTION
            "A upsShutdownAfterDelay countdown is restored."
    ::= 54

upsAlarmShutdownImminentRestored-sixth TRAP-TYPE
    ENTERPRISE geUPSTraps-sixth
    VARIABLES  { trapArg  }
    DESCRIPTION
            "A shutdown imminent condition is restored."
    ::= 55

upsAlarmTestInProgressRestored-sixth TRAP-TYPE
    ENTERPRISE geUPSTraps-sixth
    VARIABLES  { trapArg , upsTestId-sixth }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-sixth TRAP-TYPE
    ENTERPRISE geUPSTraps-sixth
    VARIABLES  { trapArg  }
    DESCRIPTION
            "A measurement value reached a value below its low-level threshold."
    ::= 129

upsAlarmValueHigh-sixth TRAP-TYPE
    ENTERPRISE geUPSTraps-sixth
    VARIABLES  { trapArg  }
    DESCRIPTION
            "A measurement value reached a value higher than its high-level threshold."
    ::= 130

upsAlarmValueLowRestored-sixth TRAP-TYPE
    ENTERPRISE geUPSTraps-sixth
    VARIABLES  { trapArg  }
    DESCRIPTION
            "A ValueLow alarm condition is restored."
    ::= 133

upsAlarmValueHighRestored-sixth TRAP-TYPE
    ENTERPRISE geUPSTraps-sixth
    VARIABLES  { trapArg }
    DESCRIPTION
            "A ValueHigh alarm condition is restored."
    ::= 134


--
-- The Device Identification group. Seventh
--      All objects in this group except for upsIdentName and
--      upsIdentAttachedDevices are set at device initialization
--      and remain static.
--

upsIdentManufacturer-seventh OBJECT-TYPE
    SYNTAX     DisplayString (SIZE (0..31))
    MAX-ACCESS read-only
    STATUS     current
    DESCRIPTION
            "The name of the UPS manufacturer.(*)"
    ::= { upsIdent-seventh 1 }

upsIdentModel-seventh OBJECT-TYPE
    SYNTAX     DisplayString (SIZE (0..63))
    MAX-ACCESS read-only
    STATUS     current
    DESCRIPTION
            "The UPS Model designation.(*)"
    ::= { upsIdent-seventh 2 }

upsIdentUPSSoftwareVersion-seventh OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-seventh 3 }

upsIdentAgentSoftwareVersion-seventh OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-seventh 4 }

upsIdentName-seventh OBJECT-TYPE
    SYNTAX     DisplayString (SIZE(0..63))
    MAX-ACCESS read-write
    STATUS     current
    DESCRIPTION
            "A string identifying the UPS.  This object should be
            set by the administrator.(*)"
    ::= { upsIdent-seventh 5 }

upsIdentAttachedDevices-seventh OBJECT-TYPE
    SYNTAX     DisplayString (SIZE(0..63))
    MAX-ACCESS read-write
    STATUS     current
    DESCRIPTION
            "A string identifying the devices attached to the
            output(s) of the UPS.  This object should be set by
            the administrator.(*)"
    ::= { upsIdent-seventh 6 }

upsIdentUPSSerialNumber-seventh OBJECT-TYPE
    SYNTAX     DisplayString (SIZE(0..31))
    MAX-ACCESS read-only
    STATUS     current
    DESCRIPTION
            "The UPS serial number"
    ::= { upsIdent-seventh 7 }
				
upsIdentComProtVersion-seventh OBJECT-TYPE
    SYNTAX     DisplayString (SIZE(0..15))
    MAX-ACCESS read-only
    STATUS     current
    DESCRIPTION
            "The IMV communication protocol version"
    ::= { upsIdent-seventh 8 }	
		
upsIdentOperatingTime-seventh OBJECT-TYPE
    SYNTAX     NonNegativeInteger32
    UNITS      "seconds"
    MAX-ACCESS read-only
    STATUS     current
    DESCRIPTION
            "The present value of the operating time.
             total 'on' time since UPS manufactured"
    ::= { upsIdent-seventh 9 }	
				
--
-- Battery Group Generic
--

upsBatteryStatus-seventh OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-seventh 1 }

upsSecondsOnBattery-seventh OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-seventh 2 }

upsEstimatedMinutesRemaining-seventh OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-seventh 3 }

upsEstimatedChargeRemaining-seventh OBJECT-TYPE
    SYNTAX     Integer32 (0..100)
    UNITS      "percent"
    MAX-ACCESS read-only
    STATUS     current
    DESCRIPTION
            "An estimate of the battery charge remaining expressed
            as a percent of full charge.(*)"
    ::= { upsBattery-seventh 4 }

upsBatteryVoltage-seventh OBJECT-TYPE
    SYNTAX     NonNegativeInteger32
    UNITS      "0.1 Volt DC"
    MAX-ACCESS read-only
    STATUS     current
    DESCRIPTION
            "The magnitude of the present battery voltage.(*)"
    ::= { upsBattery-seventh 5 }

upsBatteryCurrent-seventh OBJECT-TYPE
    SYNTAX     Integer32
    UNITS      "0.1 Amp DC"
    MAX-ACCESS read-only
    STATUS     current
    DESCRIPTION
            "The present battery current.(*)"
    ::= { upsBattery-seventh 6 }

upsBatteryTemperature-seventh OBJECT-TYPE
    SYNTAX     Integer32
    UNITS      "degrees Centigrade"
    MAX-ACCESS read-only
    STATUS     current
    DESCRIPTION
            "The ambient temperature at or near the UPS Battery
            casing.(*)"
    ::= { upsBattery-seventh 7 }

--
-- Input Group
--

upsInputLineBads-seventh OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-seventh 1 }

upsInputNumLines-seventh OBJECT-TYPE
    SYNTAX     NonNegativeInteger32
    MAX-ACCESS read-only
    STATUS     current
    DESCRIPTION
            "The number of input lines utilized in this device.
            This variable indicates the number of rows in the
            input table.(*)"
    ::= { upsInput-seventh 2 }

upsInputTable-seventh OBJECT-TYPE
    SYNTAX     SEQUENCE OF UpsInputEntry-seventh
    MAX-ACCESS not-accessible
    STATUS     current
    DESCRIPTION
            "A list of input table entries.  The number of entries
            is given by the value of upsInputNumLines.(*)"
    ::= { upsInput-seventh 3 }

upsInputEntry-seventh OBJECT-TYPE
    SYNTAX     UpsInputEntry-seventh
    MAX-ACCESS not-accessible
    STATUS     current
    DESCRIPTION
            "An entry containing information applicable to a
            particular input line.(*)"
    INDEX { upsInputLineIndex-seventh }
    ::= { upsInputTable-seventh 1 }

UpsInputEntry-seventh ::= SEQUENCE {
    upsInputLineIndex-seventh   PositiveInteger32,
    upsInputFrequency-seventh   NonNegativeInteger32,
    upsInputVoltage-seventh     NonNegativeInteger32,
    upsInputCurrent-seventh     NonNegativeInteger32,
    upsInputTruePower-seventh   NonNegativeInteger32,
    upsInputVoltageMin-seventh  NonNegativeInteger32,
    upsInputVoltageMax-seventh  NonNegativeInteger32
}

upsInputLineIndex-seventh OBJECT-TYPE
    SYNTAX     PositiveInteger32
    MAX-ACCESS not-accessible
    STATUS     current
    DESCRIPTION
            "The input line identifier.(*)"
    ::= { upsInputEntry-seventh 1 }

upsInputFrequency-seventh OBJECT-TYPE
    SYNTAX     NonNegativeInteger32
    UNITS      "0.1 Hertz"
    MAX-ACCESS read-only
    STATUS     current
    DESCRIPTION
            "The present input frequency.(*)"
    ::= { upsInputEntry-seventh 2 }

upsInputVoltage-seventh OBJECT-TYPE
    SYNTAX     NonNegativeInteger32
    UNITS      "RMS Volts"
    MAX-ACCESS read-only
    STATUS     current
    DESCRIPTION
            "The magnitude of the present input voltage.(*)"
    ::= { upsInputEntry-seventh 3 }

upsInputCurrent-seventh OBJECT-TYPE
    SYNTAX     NonNegativeInteger32
    UNITS      "0.1 RMS Amp"
    MAX-ACCESS read-only
    STATUS     current
    DESCRIPTION
            "The magnitude of the present input current.(*)"
    ::= { upsInputEntry-seventh 4 }

upsInputTruePower-seventh OBJECT-TYPE
    SYNTAX     NonNegativeInteger32
    UNITS      "Watts"
    MAX-ACCESS read-only
    STATUS     current
    DESCRIPTION
            "The magnitude of the present input true power.(*)"
    ::= { upsInputEntry-seventh 5 }

upsInputVoltageMin-seventh OBJECT-TYPE
    SYNTAX     NonNegativeInteger32
    UNITS      "RMS Volts"
    MAX-ACCESS read-only
    STATUS     current
    DESCRIPTION
            "The lowest magnitude of the input voltage since last read out."
    ::= { upsInputEntry-seventh 6 }

upsInputVoltageMax-seventh OBJECT-TYPE
    SYNTAX     NonNegativeInteger32
    UNITS      "RMS Volts"
    MAX-ACCESS read-only
    STATUS     current
    DESCRIPTION
            "The highest magnitude of the input voltage since last read out."
    ::= { upsInputEntry-seventh 7 }

--
-- The Output group.
--

upsOutputSource-seventh OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-seventh 1 }

upsOutputFrequency-seventh OBJECT-TYPE
    SYNTAX     NonNegativeInteger32
    UNITS      "0.1 Hertz"
    MAX-ACCESS read-only
    STATUS     current
    DESCRIPTION
            "The present output frequency.(*)"
    ::= { upsOutput-seventh 2 }

upsOutputNumLines-seventh OBJECT-TYPE
    SYNTAX     NonNegativeInteger32
    MAX-ACCESS read-only
    STATUS     current
    DESCRIPTION
            "The number of output lines utilized in this device.
            This variable indicates the number of rows in the
            output table.(*)"
    ::= { upsOutput-seventh 3 }

upsOutputTable-seventh OBJECT-TYPE
    SYNTAX     SEQUENCE OF UpsOutputEntry-seventh
    MAX-ACCESS not-accessible
    STATUS     current
    DESCRIPTION
            "A list of output table entries.  The number of
            entries is given by the value of upsOutputNumLines.(*)"
    ::= { upsOutput-seventh 4 }

upsOutputEntry-seventh OBJECT-TYPE
    SYNTAX     UpsOutputEntry-seventh
    MAX-ACCESS not-accessible
    STATUS     current
    DESCRIPTION
            "An entry containing information applicable to a
            particular output line.(*)"
    INDEX { upsOutputLineIndex-seventh }
    ::= { upsOutputTable-seventh 1 }

UpsOutputEntry-seventh ::= SEQUENCE {
    upsOutputLineIndex-seventh   PositiveInteger32,
    upsOutputVoltage-seventh     NonNegativeInteger32,
    upsOutputCurrent-seventh     NonNegativeInteger32,
    upsOutputPower-seventh       NonNegativeInteger32,
    upsOutputPercentLoad-seventh Integer32
}

upsOutputLineIndex-seventh OBJECT-TYPE
    SYNTAX     PositiveInteger32
    MAX-ACCESS not-accessible
    STATUS     current
    DESCRIPTION
            "The output line identifier.(*)"
    ::= { upsOutputEntry-seventh 1 }

upsOutputVoltage-seventh OBJECT-TYPE
    SYNTAX     NonNegativeInteger32
    UNITS      "RMS Volts"
    MAX-ACCESS read-only
    STATUS     current
    DESCRIPTION
            "The present output voltage.(*)"
    ::= { upsOutputEntry-seventh 2 }

upsOutputCurrent-seventh OBJECT-TYPE
    SYNTAX     NonNegativeInteger32
    UNITS      "0.1 RMS Amp"
    MAX-ACCESS read-only
    STATUS     current
    DESCRIPTION
            "The present output current.(*)"
    ::= { upsOutputEntry-seventh 3 }

upsOutputPower-seventh OBJECT-TYPE
    SYNTAX     NonNegativeInteger32
    UNITS      "Watts"
    MAX-ACCESS read-only
    STATUS     current
    DESCRIPTION
            "The present output true power.(*)"
    ::= { upsOutputEntry-seventh 4 }

upsOutputPercentLoad-seventh OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-seventh 5 }

--
-- The Bypass group generic.
--

upsBypassFrequency-seventh OBJECT-TYPE
    SYNTAX     NonNegativeInteger32
    UNITS      "0.1 Hertz"
    MAX-ACCESS read-only
    STATUS     current
    DESCRIPTION
            "The present bypass frequency.(*)"
    ::= { upsBypass-seventh 1 }

upsBypassNumLines-seventh OBJECT-TYPE
    SYNTAX     NonNegativeInteger32
    MAX-ACCESS read-only
    STATUS     current
    DESCRIPTION
            "The number of bypass lines utilized in this device.
            This entry indicates the number of rows in the bypass
            table.(*)"
    ::= { upsBypass-seventh 2 }

upsBypassTable-seventh OBJECT-TYPE
    SYNTAX     SEQUENCE OF UpsBypassEntry-seventh
    MAX-ACCESS not-accessible
    STATUS     current
    DESCRIPTION
            "A list of bypass table entries.  The number of
            entries is given by the value of upsBypassNumLines.(*)"
    ::= { upsBypass-seventh 3 }

upsBypassEntry-seventh OBJECT-TYPE
    SYNTAX     UpsBypassEntry-seventh
    MAX-ACCESS not-accessible
    STATUS     current
    DESCRIPTION
            "An entry containing information applicable to a
            particular bypass input.(*)"
    INDEX { upsBypassLineIndex-seventh }
    ::= { upsBypassTable-seventh 1 }

UpsBypassEntry-seventh ::= SEQUENCE {
    upsBypassLineIndex-seventh  PositiveInteger32,
    upsBypassVoltage-seventh    NonNegativeInteger32,
    upsBypassCurrent-seventh    NonNegativeInteger32,
    upsBypassPower-seventh      NonNegativeInteger32
}

upsBypassLineIndex-seventh OBJECT-TYPE
    SYNTAX     PositiveInteger32
    MAX-ACCESS not-accessible
    STATUS     current
    DESCRIPTION
            "The bypass line identifier.(*)"
    ::= { upsBypassEntry-seventh 1 }

upsBypassVoltage-seventh OBJECT-TYPE
    SYNTAX     NonNegativeInteger32
    UNITS      "RMS Volts"
    MAX-ACCESS read-only
    STATUS     current
    DESCRIPTION
            "The present bypass voltage.(*)"
    ::= { upsBypassEntry-seventh 2 }

upsBypassCurrent-seventh OBJECT-TYPE
    SYNTAX     NonNegativeInteger32
    UNITS      "0.1 RMS Amp"
    MAX-ACCESS read-only
    STATUS     current
    DESCRIPTION
            "The present bypass current.(*)"
    ::= { upsBypassEntry-seventh 3 }

upsBypassPower-seventh OBJECT-TYPE
    SYNTAX     NonNegativeInteger32
    UNITS      "Watts"
    MAX-ACCESS read-only
    STATUS     current
    DESCRIPTION
            "The present true power conveyed by the bypass.(*)"
    ::= { upsBypassEntry-seventh 4 }

--
-- The Alarm group generic.
--

upsAlarmsPresent-seventh OBJECT-TYPE
    SYNTAX     Gauge32
    MAX-ACCESS read-only
    STATUS     current
    DESCRIPTION
            "The present number of active alarm conditions.(*)"
    ::= { upsAlarm-seventh 1 }

upsAlarmTable-seventh OBJECT-TYPE
    SYNTAX     SEQUENCE OF UpsAlarmEntry-seventh
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-seventh 2 }

upsAlarmEntry-seventh OBJECT-TYPE
    SYNTAX     UpsAlarmEntry-seventh
    MAX-ACCESS not-accessible
    STATUS     current
    DESCRIPTION
            "An entry containing information applicable to a
            particular alarm.(*)"
    INDEX { upsAlarmId-seventh }
    ::= { upsAlarmTable-seventh 1 }

UpsAlarmEntry-seventh ::= SEQUENCE {
    upsAlarmId-seventh          PositiveInteger32,
    upsAlarmDescr-seventh       AutonomousType,
    upsAlarmTime-seventh       TimeStamp
}

upsAlarmId-seventh OBJECT-TYPE
    SYNTAX     PositiveInteger32
    MAX-ACCESS not-accessible
    STATUS     current
    DESCRIPTION
            "A unique identifier for an alarm condition.  This
            value must remain constant.(*)"
    ::= { upsAlarmEntry-seventh 1 }

upsAlarmDescr-seventh OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-seventh 2 }

upsAlarmTime-seventh OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-seventh 3 }

--
-- Well known alarm conditions generic.
--

upsAlarmBatteryBad-seventh OBJECT-IDENTITY
    STATUS     current
    DESCRIPTION
            "One or more batteries have been determined to require
            replacement.(*)"
    ::= { upsWellKnownAlarms-seventh  1 }

upsAlarmOnBattery-seventh OBJECT-IDENTITY
    STATUS     current
    DESCRIPTION
            "The UPS is drawing power from the batteries.(*)"
    ::= { upsWellKnownAlarms-seventh  2 }

upsAlarmLowBattery-seventh OBJECT-IDENTITY
    STATUS     current
    DESCRIPTION
            "The remaining battery run-time is less than or equal
            to upsConfigLowBattTime.(*)"
    ::= { upsWellKnownAlarms-seventh  3 }

upsAlarmDepletedBattery-seventh OBJECT-IDENTITY
    STATUS     current
    DESCRIPTION
            "The UPS will be unable to sustain the present load
            when and if the utility power is lost.(*)"
    ::= { upsWellKnownAlarms-seventh  4 }

upsAlarmTempBad-seventh OBJECT-IDENTITY
    STATUS     current
    DESCRIPTION
            "A temperature is out of tolerance.(*)"
    ::= { upsWellKnownAlarms-seventh  5 }

upsAlarmInputBad-seventh OBJECT-IDENTITY
    STATUS     current
    DESCRIPTION
            "An input condition is out of tolerance.(*)"
    ::= { upsWellKnownAlarms-seventh  6 }

upsAlarmOutputBad-seventh OBJECT-IDENTITY
    STATUS     current
    DESCRIPTION
            "An output condition (other than OutputOverload) is
            out of tolerance.(*)"
    ::= { upsWellKnownAlarms-seventh  7 }

upsAlarmOutputOverload-seventh OBJECT-IDENTITY
    STATUS     current
    DESCRIPTION
            "The output load exceeds the UPS output capacity.(*)"
    ::= { upsWellKnownAlarms-seventh  8 }

upsAlarmOnBypass-seventh OBJECT-IDENTITY
    STATUS     current
    DESCRIPTION
            "The Bypass is presently engaged on the UPS.(*)"
    ::= { upsWellKnownAlarms-seventh  9 }

upsAlarmBypassBad-seventh OBJECT-IDENTITY
    STATUS     current
    DESCRIPTION
            "The Bypass is out of tolerance.(*)"
    ::= { upsWellKnownAlarms-seventh 10 }

upsAlarmOutputOffAsRequested-seventh OBJECT-IDENTITY
    STATUS     current
    DESCRIPTION
            "The UPS has shutdown as requested, i.e., the output
            is off.(*)"
    ::= { upsWellKnownAlarms-seventh 11 }

upsAlarmUpsOffAsRequested-seventh OBJECT-IDENTITY
    STATUS     current
    DESCRIPTION
            "The entire UPS has shutdown as commanded.(*)"
    ::= { upsWellKnownAlarms-seventh 12 }

upsAlarmChargerFailed-seventh OBJECT-IDENTITY
    STATUS     current
    DESCRIPTION
            "An uncorrected problem has been detected within the
            UPS charger subsystem.(*)"
    ::= { upsWellKnownAlarms-seventh 13 }

upsAlarmUpsOutputOff-seventh OBJECT-IDENTITY
    STATUS     current
    DESCRIPTION
            "The output of the UPS is in the off state.(*)"
    ::= { upsWellKnownAlarms-seventh 14 }

upsAlarmUpsSystemOff-seventh OBJECT-IDENTITY
    STATUS     current
    DESCRIPTION
            "The UPS system is in the off state.(*)"
    ::= { upsWellKnownAlarms-seventh 15 }

upsAlarmFanFailure-seventh OBJECT-IDENTITY
    STATUS     current
    DESCRIPTION
            "The failure of one or more fans in the UPS has been
            detected.(*)"
    ::= { upsWellKnownAlarms-seventh 16 }

upsAlarmFuseFailure-seventh OBJECT-IDENTITY
    STATUS     current
    DESCRIPTION
            "The failure of one or more fuses has been detected.(*)"
    ::= { upsWellKnownAlarms-seventh 17 }

upsAlarmGeneralFault-seventh OBJECT-IDENTITY
    STATUS     current
    DESCRIPTION
            "A general fault in the UPS has been detected.(*)"
    ::= { upsWellKnownAlarms-seventh 18 }

upsAlarmDiagnosticTestFailed-seventh OBJECT-IDENTITY
    STATUS     current
    DESCRIPTION
            "The result of the last diagnostic test indicates a
            failure.(*)"
    ::= { upsWellKnownAlarms-seventh 19 }

upsAlarmCommunicationsLost-seventh OBJECT-IDENTITY
    STATUS     current
    DESCRIPTION
            "A problem has been encountered in the communications
            between the agent and the UPS.(*)"
    ::= { upsWellKnownAlarms-seventh 20 }

upsAlarmAwaitingPower-seventh OBJECT-IDENTITY
    STATUS     current
    DESCRIPTION
            "The UPS output is off and the UPS is awaiting the
            return of input power.(*)"
    ::= { upsWellKnownAlarms-seventh 21 }

upsAlarmShutdownPending-seventh OBJECT-IDENTITY
    STATUS     current
    DESCRIPTION
            "A upsShutdownAfterDelay countdown is underway.(*)"
    ::= { upsWellKnownAlarms-seventh 22 }

upsAlarmShutdownImminent-seventh OBJECT-IDENTITY
    STATUS     current
    DESCRIPTION
            "The UPS will turn off power to the load in less than
            5 seconds; this may be either a timed shutdown or a
            low battery shutdown.(*)"
    ::= { upsWellKnownAlarms-seventh 23 }

upsAlarmTestInProgress-seventh OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-seventh 24 }

upsAlarmReceptacleOff-seventh OBJECT-IDENTITY
    STATUS     current
    DESCRIPTION
            "The receptacle are switch off    "
    ::= { upsWellKnownAlarms-seventh 25 }

upsAlarmMaskA-seventh OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-seventh 4 }

--
-- The Test Group generic
--

upsTestId-seventh OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-seventh 1 }

-- see [6] for more information on the semantics of objects with
-- syntax of TestAndIncr

upsTestSpinLock-seventh OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-seventh 2 }

upsTestResultsSummary-seventh OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-seventh 3 }

upsTestResultsDetail-seventh OBJECT-TYPE
    SYNTAX     DisplayString (SIZE (0..255))
    MAX-ACCESS read-only
    STATUS     current
    DESCRIPTION
            "Additional information about upsTestResultsSummary.
            If no additional information available, a zero length
            string is returned.(*)"
    ::= { upsTest-seventh 4 }

upsTestStartTime-seventh OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-seventh 5 }

upsTestElapsedTime-seventh OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-seventh 6 }

--
-- Well known tests generic.
--

upsTestNoTestsInitiated-seventh OBJECT-IDENTITY
    STATUS     current
    DESCRIPTION
            "No tests have been initiated and no test is in
            progress.(*)"
    ::= { upsWellKnownTests-seventh  1 }

upsTestAbortTestInProgress-seventh OBJECT-IDENTITY
    STATUS     current
    DESCRIPTION
            "The test in progress is to be aborted / the test in
            progress was aborted.(*)"
    ::= { upsWellKnownTests-seventh  2 }

upsTestGeneralSystemsTest-seventh OBJECT-IDENTITY
    STATUS     current
    DESCRIPTION
            "The manufacturer's standard test of UPS device
            systems.(*)"
    ::= { upsWellKnownTests-seventh  3 }

upsTestQuickBatteryTest-seventh OBJECT-IDENTITY
    STATUS     current
    DESCRIPTION
            "A test that is sufficient to determine if the battery
            needs replacement.(*)"
    ::= { upsWellKnownTests-seventh  4 }

upsTestDeepBatteryCalibration-seventh OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-seventh  5 }

--
-- The Control group generic.
--

upsShutdownType-seventh OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-seventh 1 }

upsShutdownAfterDelay-seventh OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-seventh 2 }

upsStartupAfterDelay-seventh OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-seventh 3 }

upsRebootWithDuration-seventh OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-seventh 4 }

upsAutoRestart-seventh OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-seventh 5 }

upsReceptaclesNum-seventh OBJECT-TYPE
    SYNTAX     NonNegativeInteger32
    MAX-ACCESS read-only
    STATUS     current
    DESCRIPTION
            "The number of receptacles utilized in this device.
            This entry indicates the number of rows in the receptacle
            table."
    ::= { upsControl-seventh 6 }

upsReceptacleTable-seventh OBJECT-TYPE
    SYNTAX     SEQUENCE OF UpsReceptacleEntry-seventh
    MAX-ACCESS not-accessible
    STATUS     current
    DESCRIPTION
            "A list of receptacle table entries.  The number of
            entries is given by the value of upsReceptacleNum."
    ::= { upsControl-seventh 7 }

upsReceptacleEntry-seventh OBJECT-TYPE
    SYNTAX     UpsReceptacleEntry-seventh
    MAX-ACCESS not-accessible
    STATUS     current
    DESCRIPTION
            "An entry containing information applicable to a
            particular receptacle."
    INDEX { upsReceptacleLineIndex-seventh }
    ::= { upsReceptacleTable-seventh 1 }

UpsReceptacleEntry-seventh ::= SEQUENCE {
    upsReceptacleLineIndex-seventh  PositiveInteger32,
    upsReceptacleOnOff-seventh      Integer32    
}

upsReceptacleLineIndex-seventh OBJECT-TYPE
    SYNTAX     PositiveInteger32
    MAX-ACCESS not-accessible
    STATUS     current
    DESCRIPTION
            "The receptacle line identifier."
    ::= { upsReceptacleEntry-seventh 1 }

upsReceptacleOnOff-seventh OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-seventh 2 }

upsUPSMode-seventh OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-seventh 8 }

upsRectifierOnOff-seventh OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-seventh 9 }

upsBatteryChargeMethod-seventh OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-seventh 10 }

upsInverterOnOff-seventh OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-seventh 11 }

upsBypassOnOff-seventh OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-seventh 12 }

upsLoadSource-seventh OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-seventh 13 }
	
--
-- The Configuration group generic.
--

upsConfigInputVoltage-seventh OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-seventh 1 }

upsConfigInputFreq-seventh OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-seventh 2 }

upsConfigOutputVoltage-seventh OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-seventh 3 }

upsConfigOutputFreq-seventh OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-seventh 4 }

upsConfigOutputVA-seventh OBJECT-TYPE
    SYNTAX     NonNegativeInteger32
    UNITS      "Volt-Amps"
    MAX-ACCESS read-only
    STATUS     current
    DESCRIPTION
            "The magnitude of the nominal Volt-Amp rating.(*)"
    ::= { upsConfig-seventh 5 }

upsConfigOutputPower-seventh OBJECT-TYPE
    SYNTAX     NonNegativeInteger32
    UNITS      "Watts"
    MAX-ACCESS read-only
    STATUS     current
    DESCRIPTION
            "The magnitude of the nominal true power rating.(*)"
    ::= { upsConfig-seventh 6 }

upsConfigLowBattTime-seventh OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-seventh 7 }

upsConfigAudibleStatus-seventh OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-seventh 8 }

upsConfigLowVoltageTransferPoint-seventh OBJECT-TYPE
    SYNTAX     NonNegativeInteger32
    UNITS      "RMS Volts"
    MAX-ACCESS read-write
    STATUS     current
    DESCRIPTION
            "The minimum input line voltage allowed before the UPS
            system transfers to battery backup.(*)"
    ::= { upsConfig-seventh 9 }

upsConfigHighVoltageTransferPoint-seventh OBJECT-TYPE
    SYNTAX     NonNegativeInteger32
    UNITS      "RMS Volts"
    MAX-ACCESS read-write
    STATUS     current
    DESCRIPTION
            "The maximum line voltage allowed before the UPS
            system transfers to battery backup.(*)"
    ::= { upsConfig-seventh 10 }

upsConfigBatteryCapacity-seventh OBJECT-TYPE
    SYNTAX     NonNegativeInteger32
    UNITS      "Amps Hours"
    MAX-ACCESS read-write
    STATUS     current
    DESCRIPTION
            "The installed battery capacity. This value is the 'factory'-value,
             not the value after calibration."
    ::= { upsConfig-seventh 11 }

upsConfigBatteryChargeCurrent-seventh OBJECT-TYPE
    SYNTAX     NonNegativeInteger32
    UNITS      "0.1 Amp DC"
    MAX-ACCESS read-write
    STATUS     current
    DESCRIPTION
            "The maximum battery charge current, including external chargers."
    ::= { upsConfig-seventh 12 }						

upsConfigNoLoadShutdown-seventh OBJECT-TYPE
    SYNTAX     Integer32 {
        disabled(1),
        enabled(2)
    }
    MAX-ACCESS read-write
    STATUS     current
    DESCRIPTION
            "Dis- or enable 'no load' shutdown from the contact interface."
    ::= { upsConfig-seventh 13 }
	
upsConfigStartDelay-seventh OBJECT-TYPE
    SYNTAX     PositiveInteger32
    UNITS      "minutes"				
    MAX-ACCESS read-write
    STATUS     current
    DESCRIPTION
            "Minimum required autonomy time before the UPS may perform an
             autorestart."
    ::= { upsConfig-seventh 14 }

--
-- The GetSet group generic.
--

upsEventGetNext-seventh OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-seventh 1 }

upsEventGetPrevious-seventh OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-seventh 2 }
				
upsEventSetStartingTimeStamp-seventh OBJECT-TYPE
    SYNTAX     NonNegativeInteger32
    MAX-ACCESS read-write
    STATUS     current
    DESCRIPTION
            "The timestamp which is used as starting point for downloading
             events from the UPS event buffer"
    ::= { upsGetSet-seventh 3 }				

upsEventRetreiveCurrentTimeStamp-seventh OBJECT-TYPE
    SYNTAX     NonNegativeInteger32
    MAX-ACCESS read-only
    STATUS     current
    DESCRIPTION
            "The current timestamp is retreived from the UPS"
    ::= { upsGetSet-seventh 4 }				

upsEventTableSize-seventh OBJECT-TYPE
    SYNTAX     NonNegativeInteger32
    MAX-ACCESS read-only
    STATUS     current
    DESCRIPTION
            "The number of entries in the event table.
            This object indicates the number of rows in the event table."
    ::= { upsGetSet-seventh 5 }

upsEventTable-seventh OBJECT-TYPE
    SYNTAX     SEQUENCE OF UpsEventEntry-seventh
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-seventh 6 }

upsEventEntry-seventh OBJECT-TYPE
    SYNTAX     UpsEventEntry-seventh
    MAX-ACCESS not-accessible
    STATUS     current
    DESCRIPTION
            "An entry containing information applicable to a
            particular event."
    INDEX { upsEventLineIndex-seventh }
    ::= { upsEventTable-seventh 1 }

UpsEventEntry-seventh ::= SEQUENCE {
    upsEventLineIndex-seventh PositiveInteger32,
    upsEventCode-seventh      Integer32,
    upsEventStatus-seventh    NonNegativeInteger32,
    upsEventTime-seventh      NonNegativeInteger32
}

upsEventLineIndex-seventh OBJECT-TYPE
    SYNTAX     PositiveInteger32
    MAX-ACCESS not-accessible
    STATUS     current
    DESCRIPTION
            "The event line identifier."
    ::= { upsEventEntry-seventh 1 }

upsEventCode-seventh OBJECT-TYPE
    SYNTAX     NonNegativeInteger32
    MAX-ACCESS read-only
    STATUS     current
    DESCRIPTION
            "The event code in numerical format."
    ::= { upsEventEntry-seventh 2 }

upsEventStatus-seventh OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-seventh 3 }

upsEventTime-seventh OBJECT-TYPE
    SYNTAX     NonNegativeInteger32
    MAX-ACCESS read-only
    STATUS     current
    DESCRIPTION
            "The timestamp of the moment the event was generated."
    ::= { upsEventEntry-seventh 4 }

upsParametersRead-seventh OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-seventh 7 }

upsParametersWrite-seventh OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-seventh 8 }

upsParametersStartAddress-seventh OBJECT-TYPE
    SYNTAX     NonNegativeInteger32
    MAX-ACCESS read-write
    STATUS     current
    DESCRIPTION
            "The address which is used as starting point for downloading
             parameters from the UPS"
    ::= { upsGetSet-seventh 9 }				

upsParameterTableSize-seventh OBJECT-TYPE
    SYNTAX     NonNegativeInteger32
    MAX-ACCESS read-only
    STATUS     current
    DESCRIPTION
            "The number of entries in the parameter table.
            This object indicates the number of rows in the parameter table."
    ::= { upsGetSet-seventh 10 }

upsParameterTable-seventh OBJECT-TYPE
    SYNTAX     SEQUENCE OF UpsParameterEntry-seventh
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-seventh 11 }

upsParameterEntry-seventh OBJECT-TYPE
    SYNTAX     UpsParameterEntry-seventh
    MAX-ACCESS not-accessible
    STATUS     current
    DESCRIPTION
            "An entry containing information applicable to a
            particular parameter."
    INDEX { upsParameterLineIndex-seventh }
    ::= { upsParameterTable-seventh 1 }

UpsParameterEntry-seventh ::= SEQUENCE {
    upsParameterLineIndex-seventh PositiveInteger32,
    upsParameterValue-seventh     Integer32   
}

upsParameterLineIndex-seventh OBJECT-TYPE
    SYNTAX     PositiveInteger32
    MAX-ACCESS not-accessible
    STATUS     current
    DESCRIPTION
            "The parameter line identifier."
    ::= { upsParameterEntry-seventh 1 }

upsParameterValue-seventh OBJECT-TYPE
    SYNTAX     Integer32
    MAX-ACCESS read-write
    STATUS     current
    DESCRIPTION
            "The parameter value in numerical format."
    ::= { upsParameterEntry-seventh 2 }

upsStatus-seventh OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-seventh 12 }

upsMainsStatisticsMBfail-seventh OBJECT-TYPE
    SYNTAX     NonNegativeInteger32
    MAX-ACCESS read-only
    STATUS     current
    DESCRIPTION
            "Count of main bypass failures (>200 ms), since UPS installation."
    ::= { upsGetSet-seventh 13 }

upsMainsStatisticsMRfail-seventh OBJECT-TYPE
    SYNTAX     NonNegativeInteger32
    MAX-ACCESS read-only
    STATUS     current
    DESCRIPTION
            "Count of mains rectifier failures (>200 ms), since UPS installation."
    ::= { upsGetSet-seventh 14 }
		
upsMainsStatisticsB2-seventh OBJECT-TYPE
    SYNTAX     NonNegativeInteger32
    MAX-ACCESS read-only
    STATUS     current
    DESCRIPTION
            "Count of transients on the mains bypass (0..2 ms), during the last 7 days."
    ::= { upsGetSet-seventh 15 }

upsMainsStatisticsB5-seventh OBJECT-TYPE
    SYNTAX     NonNegativeInteger32
    MAX-ACCESS read-only
    STATUS     current
    DESCRIPTION
            "Count of transients on the mains bypass (2..5 ms), during the last 7 days."
    ::= { upsGetSet-seventh 16 }

upsMainsStatisticsB10-seventh OBJECT-TYPE
    SYNTAX     NonNegativeInteger32
    MAX-ACCESS read-only
    STATUS     current
    DESCRIPTION
            "Count of transients on the mains bypass (5..10 ms), during the last 7 days."
    ::= { upsGetSet-seventh 17 }

upsMainsStatisticsB200-seventh OBJECT-TYPE
    SYNTAX     NonNegativeInteger32
    MAX-ACCESS read-only
    STATUS     current
    DESCRIPTION
            "Count of transients on the mains bypass (10..200 ms), during the last 7 days."
    ::= { upsGetSet-seventh 18 }

upsMainsStatisticsBypRel-seventh OBJECT-TYPE
    SYNTAX     NonNegativeInteger32
    MAX-ACCESS read-only
    STATUS     current
    DESCRIPTION
            "Bypass reliability degree [0..100%;255]. The value NOSUCHNAME means 'not available'."
    ::= { upsGetSet-seventh 19 }

upsTime-seventh OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-seventhERROR, 
             meaning 'command not supported'. It is possible to know which is the timestamp 
             format supported by the UPS, by issuing a read-command or by reading events, 
             which includes timestamps."
    ::= { upsGetSet-seventh 20 }

upsRequestPermission-seventh OBJECT-TYPE
    SYNTAX     DisplayString (SIZE(0..63))
    MAX-ACCESS write-only
    STATUS     current
    DESCRIPTION
            "An encrypted code is send to enable use of restricted write objects during
             a limited period of time."
    ::= { upsGetSet-seventh 21 }

upsEventGetCode-seventh OBJECT-TYPE
    SYNTAX     Integer32
    MAX-ACCESS write-only
    STATUS     current
    DESCRIPTION
            "The code which is used as starting point to downloading the events from the 
            UPS event buffer."
    ::= { upsGetSet-seventh 22 }    
    
upsEventSpinLock-seventh OBJECT-TYPE
    SYNTAX     TestAndIncr
    MAX-ACCESS read-write
    STATUS     current
    DESCRIPTION
            "A spin lock on the event subsystem. "

    ::= { upsGetSet-seventh 23 }
    
upsParameterSpinLock-seventh OBJECT-TYPE
    SYNTAX     TestAndIncr
    MAX-ACCESS read-write
    STATUS     current
    DESCRIPTION
            "A spin lock on the parameters subsystem. "

    ::= { upsGetSet-seventh 24 }

--
-- GE Trap group generic
--

upsAlarmBatteryBad-seventh TRAP-TYPE
    ENTERPRISE geUPSTraps-seventh
    VARIABLES  { trapArg  }
    DESCRIPTION
            "One or more batteries have been determined to require
            replacement."
    ::= 1

upsAlarmOnBattery-seventh TRAP-TYPE
    ENTERPRISE geUPSTraps-seventh
    VARIABLES  { trapArg , upsSecondsOnBattery-seventh  }
    DESCRIPTION
            "An On Battery condition is restored."
    ::= 2

upsAlarmLowBattery-seventh TRAP-TYPE
    ENTERPRISE geUPSTraps-seventh
    VARIABLES  { trapArg  }
    DESCRIPTION
            "The remaining battery run-time is less than or equal
            to upsConfigLowBattTime."
    ::= 3

upsAlarmDepletedBattery-seventh TRAP-TYPE
    ENTERPRISE geUPSTraps-seventh
    VARIABLES  { trapArg  }
    DESCRIPTION
            "The UPS will be unable to sustain the present load
            when and if the utility power is lost)"
    ::= 4

upsAlarmTempBad-seventh TRAP-TYPE
    ENTERPRISE geUPSTraps-seventh
    VARIABLES  { trapArg , upsBatteryTemperature }
    DESCRIPTION
            "A temperature is out of tolerance."
    ::= 5

upsAlarmInputBad-seventh TRAP-TYPE
    ENTERPRISE geUPSTraps-seventh
    VARIABLES  { trapArg  }
    DESCRIPTION
            "An input condition is out of tolerance."
    ::= 6

upsAlarmOutputBad-seventh TRAP-TYPE
    ENTERPRISE geUPSTraps-seventh
    VARIABLES  { trapArg  }
    DESCRIPTION
            "An output condition (other than OutputOverload) is
            out of tolerance."
    ::= 7

upsAlarmOutputOverload-seventh TRAP-TYPE
    ENTERPRISE geUPSTraps-seventh
    VARIABLES  { trapArg , upsOutputPercentLoad-seventh }
    DESCRIPTION
            "The output load exceeds the UPS output capacity."
    ::= 8

upsAlarmOnBypass-seventh TRAP-TYPE
    ENTERPRISE geUPSTraps-seventh
    VARIABLES  { trapArg  }
    DESCRIPTION
            "The Bypass is presently engaged on the UPS."
    ::= 9

upsAlarmBypassBad-seventh TRAP-TYPE
    ENTERPRISE geUPSTraps-seventh
    VARIABLES  { trapArg  }
    DESCRIPTION
            "The Bypass is out of tolerance."
    ::= 10

upsAlarmOutputOffAsRequested-seventh TRAP-TYPE
    ENTERPRISE geUPSTraps-seventh
    VARIABLES  { trapArg  }
    DESCRIPTION
            "The UPS has shutdown as requested, i.e., the output
            is off."
    ::= 11

upsAlarmUpsOffAsRequested-seventh TRAP-TYPE
    ENTERPRISE geUPSTraps-seventh-seventh
    VARIABLES  { trapArg  }
    DESCRIPTION
            "The entire UPS has shutdown as commanded."
    ::= 12

upsAlarmChargerFailed-seventh TRAP-TYPE
    ENTERPRISE geUPSTraps-seventh
    VARIABLES  { trapArg  }
    DESCRIPTION
            "An uncorrected problem has been detected within the
            UPS charger subsystem."
    ::= 13

upsAlarmUpsOutputOff-seventh TRAP-TYPE
    ENTERPRISE geUPSTraps-seventh
    VARIABLES  { trapArg  }
    DESCRIPTION
            "The output of the UPS is in the off state."
    ::= 14

upsAlarmUpsSystemOff-seventh TRAP-TYPE
    ENTERPRISE geUPSTraps-seventh
    VARIABLES  { trapArg  }
    DESCRIPTION
            "The UPS system is in the off state."
    ::= 15

upsAlarmFanFailure-seventh TRAP-TYPE
    ENTERPRISE geUPSTraps-seventh
    VARIABLES  { trapArg  }
    DESCRIPTION
            "The failure of one or more fans in the UPS has been
            detected."
    ::= 16

upsAlarmFuseFailure-seventh TRAP-TYPE
    ENTERPRISE geUPSTraps-seventh
    VARIABLES  { trapArg  }
    DESCRIPTION
            "The failure of one or more fuses has been detected."
    ::= 17

upsAlarmGeneralFault-seventh TRAP-TYPE
    ENTERPRISE geUPSTraps-seventh
    VARIABLES  { trapArg  }
    DESCRIPTION
            "A general fault in the UPS has been detected."
    ::= 18

upsAlarmDiagnosticTestFailed-seventh TRAP-TYPE
    ENTERPRISE geUPSTraps-seventh
    VARIABLES  { trapArg  }
    DESCRIPTION
            "The result of the last diagnostic test indicates a
            failure."
    ::= 19

upsAlarmCommunicationsLost-seventh TRAP-TYPE
    ENTERPRISE geUPSTraps-seventh
    VARIABLES  { trapArg  }
    DESCRIPTION
            "A problem has been encountered in the communication
            between the agent and the UPS."
    ::= 20
    
upsAlarmAwaitingPower-seventh TRAP-TYPE
    ENTERPRISE geUPSTraps-seventh
    VARIABLES  { trapArg  }
    DESCRIPTION
            "The UPS output is off and the UPS is awaiting the
            return of the input power (*)."
    ::= 21    

upsAlarmShutdownPending-seventh TRAP-TYPE
    ENTERPRISE geUPSTraps-seventh
    VARIABLES  { trapArg , upsShutdownAfterDelay-seventh }
    DESCRIPTION
            "A upsShutdownAfterDelay countdown is underway."
    ::= 22

upsAlarmShutdownImminent-seventh TRAP-TYPE
    ENTERPRISE geUPSTraps-seventh
    VARIABLES  { trapArg  }
    DESCRIPTION
            "The UPS will turn off power to the load in less than
            5 seconds; this may be either a timed shutdown or a
            low battery shutdown."
    ::= 23

upsAlarmTestInProgress-seventh TRAP-TYPE
    ENTERPRISE geUPSTraps-seventh
    VARIABLES  { trapArg , upsTestId-seventh }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-seventh TRAP-TYPE
    ENTERPRISE geUPSTraps-seventh
    VARIABLES  { trapArg  }
    DESCRIPTION
            "A receptacle has been switched off."
    ::= 25

upsAlarmBatteryBadRestored-seventh TRAP-TYPE
    ENTERPRISE geUPSTraps-seventh
    VARIABLES  { trapArg  }
    DESCRIPTION
            "A Battery bad condition is restored."
    ::= 33

upsAlarmOnBatteryRestored-seventh TRAP-TYPE
    ENTERPRISE geUPSTraps-seventh
    VARIABLES  { trapArg  }
    DESCRIPTION
            "The UPS is drawing power from mains again."
    ::= 34

upsAlarmLowBatteryRestored-seventh TRAP-TYPE
    ENTERPRISE geUPSTraps-seventh
    VARIABLES  { trapArg  }
    DESCRIPTION
            "A Low Battery condition is restored."
    ::= 35

upsAlarmDepletedBatteryRestored-seventh TRAP-TYPE
    ENTERPRISE geUPSTraps-seventh
    VARIABLES  { trapArg  }
    DESCRIPTION
            "A Depleted Battery condition is restored."
    ::= 36

upsAlarmTempBadRestored-seventh TRAP-TYPE
    ENTERPRISE geUPSTraps-seventh
    VARIABLES  { trapArg  }
    DESCRIPTION
            "A bad temperature condition is restored."
    ::= 37

upsAlarmInputBadRestored-seventh TRAP-TYPE
    ENTERPRISE geUPSTraps-seventh
    VARIABLES  { trapArg  }
    DESCRIPTION
            "An input bad condition is restored."
    ::= 38

upsAlarmOutputBadRestored-seventh TRAP-TYPE
    ENTERPRISE geUPSTraps-seventh
    VARIABLES  { trapArg  }
    DESCRIPTION
            "An output bad condition is restored."
    ::= 39

upsAlarmOutputOverloadRestored-seventh TRAP-TYPE
    ENTERPRISE geUPSTraps-seventh
    VARIABLES  { trapArg  }
    DESCRIPTION
            "An output overload condition is restored."
    ::= 40

upsAlarmOnBypassRestored-seventh TRAP-TYPE
    ENTERPRISE geUPSTraps-seventh
    VARIABLES  { trapArg  }
    DESCRIPTION
            "An On Bypass condition is restored."
    ::= 41

upsAlarmBypassBadRestored-seventh TRAP-TYPE
    ENTERPRISE geUPSTraps-seventh
    VARIABLES  { trapArg  }
    DESCRIPTION
            "A Bypass bad condition is restored."
    ::= 42

upsAlarmOutputOffAsRequestedRestored-seventh TRAP-TYPE
    ENTERPRISE geUPSTraps-seventh
    VARIABLES  { trapArg  }
    DESCRIPTION
            "A request shutdown has been restored."
    ::= 43

upsAlarmUpsOffAsRequestedRestored-seventh TRAP-TYPE
    ENTERPRISE geUPSTraps-seventh-seventh
    VARIABLES  { trapArg  }
    DESCRIPTION
            "A entire UPS command has been restored."
    ::= 44

upsAlarmChargerFailedRestored-seventh TRAP-TYPE
    ENTERPRISE geUPSTraps-seventh
    VARIABLES  { trapArg  }
    DESCRIPTION
            "A Charger Failer condition is restored."
    ::= 45

upsAlarmUpsOutputOn-seventh TRAP-TYPE
    ENTERPRISE geUPSTraps-seventh
    VARIABLES  { trapArg  }
    DESCRIPTION
            "The output of the UPS switched in the on state."
    ::= 46

upsAlarmUpsSystemOn-seventh TRAP-TYPE
    ENTERPRISE geUPSTraps-seventh
    VARIABLES  { trapArg  }
    DESCRIPTION
            "The UPS system is switched in the on state."
    ::= 47

upsAlarmFanFailureRestored-seventh TRAP-TYPE
    ENTERPRISE geUPSTraps-seventh
    VARIABLES  { trapArg  }
    DESCRIPTION
            "A Fan failure condition is restored."
    ::= 48

upsAlarmFuseFailureRestored-seventh TRAP-TYPE
    ENTERPRISE geUPSTraps-seventh
    VARIABLES  { trapArg  }
    DESCRIPTION
            "A Fuse failure condition is restored."
    ::= 49

upsAlarmGeneralFaultRestored-seventh TRAP-TYPE
    ENTERPRISE geUPSTraps-seventh
    VARIABLES  { trapArg  }
    DESCRIPTION
            "A general fault is restored."
    ::= 50

upsAlarmDiagnosticTestFailedRestored-seventh TRAP-TYPE
    ENTERPRISE geUPSTraps-seventh
    VARIABLES  { trapArg  }
    DESCRIPTION
            "A last diagnostic test indicates a failure is 
            restored."
    ::= 51

upsAlarmCommunicationsLostRestored-seventh TRAP-TYPE
    ENTERPRISE geUPSTraps-seventh
    VARIABLES  { trapArg  }
    DESCRIPTION
            "A problem in the communication between the agent 
            and the UPS is restored."
    ::= 52
    
upsAlarmAwaitingPowerRestored-seventh TRAP-TYPE
    ENTERPRISE geUPSTraps-seventh
    VARIABLES  { trapArg  }
    DESCRIPTION
            "A awaiting power condition is restored (*)."
    ::= 53    

upsAlarmShutdownPendingRestored-seventh TRAP-TYPE
    ENTERPRISE geUPSTraps-seventh
    VARIABLES  { trapArg , upsShutdownAfterDelay-seventh }
    DESCRIPTION
            "A upsShutdownAfterDelay countdown is restored."
    ::= 54

upsAlarmShutdownImminentRestored-seventh TRAP-TYPE
    ENTERPRISE geUPSTraps-seventh
    VARIABLES  { trapArg  }
    DESCRIPTION
            "A shutdown imminent condition is restored."
    ::= 55

upsAlarmTestInProgressRestored-seventh TRAP-TYPE
    ENTERPRISE geUPSTraps-seventh
    VARIABLES  { trapArg , upsTestId-seventh }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-seventh TRAP-TYPE
    ENTERPRISE geUPSTraps-seventh
    VARIABLES  { trapArg  }
    DESCRIPTION
            "A measurement value reached a value below its low-level threshold."
    ::= 129

upsAlarmValueHigh-seventh TRAP-TYPE
    ENTERPRISE geUPSTraps-seventh
    VARIABLES  { trapArg  }
    DESCRIPTION
            "A measurement value reached a value higher than its high-level threshold."
    ::= 130

upsAlarmValueLowRestored-seventh TRAP-TYPE
    ENTERPRISE geUPSTraps-seventh
    VARIABLES  { trapArg  }
    DESCRIPTION
            "A ValueLow alarm condition is restored."
    ::= 133

upsAlarmValueHighRestored-seventh TRAP-TYPE
    ENTERPRISE geUPSTraps-seventh
    VARIABLES  { trapArg }
    DESCRIPTION
            "A ValueHigh alarm condition is restored."
    ::= 134

--
-- The Device Identification group. Eighth
--      All objects in this group except for upsIdentName and
--      upsIdentAttachedDevices are set at device initialization
--      and remain static.
--

upsIdentManufacturer-eighth OBJECT-TYPE
    SYNTAX     DisplayString (SIZE (0..31))
    MAX-ACCESS read-only
    STATUS     current
    DESCRIPTION
            "The name of the UPS manufacturer.(*)"
    ::= { upsIdent-eighth 1 }

upsIdentModel-eighth OBJECT-TYPE
    SYNTAX     DisplayString (SIZE (0..63))
    MAX-ACCESS read-only
    STATUS     current
    DESCRIPTION
            "The UPS Model designation.(*)"
    ::= { upsIdent-eighth 2 }

upsIdentUPSSoftwareVersion-eighth OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-eighth 3 }

upsIdentAgentSoftwareVersion-eighth OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-eighth 4 }

upsIdentName-eighth OBJECT-TYPE
    SYNTAX     DisplayString (SIZE(0..63))
    MAX-ACCESS read-write
    STATUS     current
    DESCRIPTION
            "A string identifying the UPS.  This object should be
            set by the administrator.(*)"
    ::= { upsIdent-eighth 5 }

upsIdentAttachedDevices-eighth OBJECT-TYPE
    SYNTAX     DisplayString (SIZE(0..63))
    MAX-ACCESS read-write
    STATUS     current
    DESCRIPTION
            "A string identifying the devices attached to the
            output(s) of the UPS.  This object should be set by
            the administrator.(*)"
    ::= { upsIdent-eighth 6 }

upsIdentUPSSerialNumber-eighth OBJECT-TYPE
    SYNTAX     DisplayString (SIZE(0..31))
    MAX-ACCESS read-only
    STATUS     current
    DESCRIPTION
            "The UPS serial number"
    ::= { upsIdent-eighth 7 }
				
upsIdentComProtVersion-eighth OBJECT-TYPE
    SYNTAX     DisplayString (SIZE(0..15))
    MAX-ACCESS read-only
    STATUS     current
    DESCRIPTION
            "The IMV communication protocol version"
    ::= { upsIdent-eighth 8 }	
		
upsIdentOperatingTime-eighth OBJECT-TYPE
    SYNTAX     NonNegativeInteger32
    UNITS      "seconds"
    MAX-ACCESS read-only
    STATUS     current
    DESCRIPTION
            "The present value of the operating time.
             total 'on' time since UPS manufactured"
    ::= { upsIdent-eighth 9 }	
				
--
-- Battery Group Generic
--

upsBatteryStatus-eighth OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-eighth 1 }

upsSecondsOnBattery-eighth OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-eighth 2 }

upsEstimatedMinutesRemaining-eighth OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-eighth 3 }

upsEstimatedChargeRemaining-eighth OBJECT-TYPE
    SYNTAX     Integer32 (0..100)
    UNITS      "percent"
    MAX-ACCESS read-only
    STATUS     current
    DESCRIPTION
            "An estimate of the battery charge remaining expressed
            as a percent of full charge.(*)"
    ::= { upsBattery-eighth 4 }

upsBatteryVoltage-eighth OBJECT-TYPE
    SYNTAX     NonNegativeInteger32
    UNITS      "0.1 Volt DC"
    MAX-ACCESS read-only
    STATUS     current
    DESCRIPTION
            "The magnitude of the present battery voltage.(*)"
    ::= { upsBattery-eighth 5 }

upsBatteryCurrent-eighth OBJECT-TYPE
    SYNTAX     Integer32
    UNITS      "0.1 Amp DC"
    MAX-ACCESS read-only
    STATUS     current
    DESCRIPTION
            "The present battery current.(*)"
    ::= { upsBattery-eighth 6 }

upsBatteryTemperature-eighth OBJECT-TYPE
    SYNTAX     Integer32
    UNITS      "degrees Centigrade"
    MAX-ACCESS read-only
    STATUS     current
    DESCRIPTION
            "The ambient temperature at or near the UPS Battery
            casing.(*)"
    ::= { upsBattery-eighth 7 }

--
-- Input Group
--

upsInputLineBads-eighth OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-eighth 1 }

upsInputNumLines-eighth OBJECT-TYPE
    SYNTAX     NonNegativeInteger32
    MAX-ACCESS read-only
    STATUS     current
    DESCRIPTION
            "The number of input lines utilized in this device.
            This variable indicates the number of rows in the
            input table.(*)"
    ::= { upsInput-eighth 2 }

upsInputTable-eighth OBJECT-TYPE
    SYNTAX     SEQUENCE OF UpsInputEntry-eighth
    MAX-ACCESS not-accessible
    STATUS     current
    DESCRIPTION
            "A list of input table entries.  The number of entries
            is given by the value of upsInputNumLines.(*)"
    ::= { upsInput-eighth 3 }

upsInputEntry-eighth OBJECT-TYPE
    SYNTAX     UpsInputEntry-eighth
    MAX-ACCESS not-accessible
    STATUS     current
    DESCRIPTION
            "An entry containing information applicable to a
            particular input line.(*)"
    INDEX { upsInputLineIndex-eighth }
    ::= { upsInputTable-eighth 1 }

UpsInputEntry-eighth ::= SEQUENCE {
    upsInputLineIndex-eighth   PositiveInteger32,
    upsInputFrequency-eighth   NonNegativeInteger32,
    upsInputVoltage-eighth     NonNegativeInteger32,
    upsInputCurrent-eighth     NonNegativeInteger32,
    upsInputTruePower-eighth   NonNegativeInteger32,
    upsInputVoltageMin-eighth  NonNegativeInteger32,
    upsInputVoltageMax-eighth  NonNegativeInteger32
}

upsInputLineIndex-eighth OBJECT-TYPE
    SYNTAX     PositiveInteger32
    MAX-ACCESS not-accessible
    STATUS     current
    DESCRIPTION
            "The input line identifier.(*)"
    ::= { upsInputEntry-eighth 1 }

upsInputFrequency-eighth OBJECT-TYPE
    SYNTAX     NonNegativeInteger32
    UNITS      "0.1 Hertz"
    MAX-ACCESS read-only
    STATUS     current
    DESCRIPTION
            "The present input frequency.(*)"
    ::= { upsInputEntry-eighth 2 }

upsInputVoltage-eighth OBJECT-TYPE
    SYNTAX     NonNegativeInteger32
    UNITS      "RMS Volts"
    MAX-ACCESS read-only
    STATUS     current
    DESCRIPTION
            "The magnitude of the present input voltage.(*)"
    ::= { upsInputEntry-eighth 3 }

upsInputCurrent-eighth OBJECT-TYPE
    SYNTAX     NonNegativeInteger32
    UNITS      "0.1 RMS Amp"
    MAX-ACCESS read-only
    STATUS     current
    DESCRIPTION
            "The magnitude of the present input current.(*)"
    ::= { upsInputEntry-eighth 4 }

upsInputTruePower-eighth OBJECT-TYPE
    SYNTAX     NonNegativeInteger32
    UNITS      "Watts"
    MAX-ACCESS read-only
    STATUS     current
    DESCRIPTION
            "The magnitude of the present input true power.(*)"
    ::= { upsInputEntry-eighth 5 }

upsInputVoltageMin-eighth OBJECT-TYPE
    SYNTAX     NonNegativeInteger32
    UNITS      "RMS Volts"
    MAX-ACCESS read-only
    STATUS     current
    DESCRIPTION
            "The lowest magnitude of the input voltage since last read out."
    ::= { upsInputEntry-eighth 6 }

upsInputVoltageMax-eighth OBJECT-TYPE
    SYNTAX     NonNegativeInteger32
    UNITS      "RMS Volts"
    MAX-ACCESS read-only
    STATUS     current
    DESCRIPTION
            "The highest magnitude of the input voltage since last read out."
    ::= { upsInputEntry-eighth 7 }

--
-- The Output group.
--

upsOutputSource-eighth OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-eighth 1 }

upsOutputFrequency-eighth OBJECT-TYPE
    SYNTAX     NonNegativeInteger32
    UNITS      "0.1 Hertz"
    MAX-ACCESS read-only
    STATUS     current
    DESCRIPTION
            "The present output frequency.(*)"
    ::= { upsOutput-eighth 2 }

upsOutputNumLines-eighth OBJECT-TYPE
    SYNTAX     NonNegativeInteger32
    MAX-ACCESS read-only
    STATUS     current
    DESCRIPTION
            "The number of output lines utilized in this device.
            This variable indicates the number of rows in the
            output table.(*)"
    ::= { upsOutput-eighth 3 }

upsOutputTable-eighth OBJECT-TYPE
    SYNTAX     SEQUENCE OF UpsOutputEntry-eighth
    MAX-ACCESS not-accessible
    STATUS     current
    DESCRIPTION
            "A list of output table entries.  The number of
            entries is given by the value of upsOutputNumLines.(*)"
    ::= { upsOutput-eighth 4 }

upsOutputEntry-eighth OBJECT-TYPE
    SYNTAX     UpsOutputEntry-eighth
    MAX-ACCESS not-accessible
    STATUS     current
    DESCRIPTION
            "An entry containing information applicable to a
            particular output line.(*)"
    INDEX { upsOutputLineIndex-eighth }
    ::= { upsOutputTable-eighth 1 }

UpsOutputEntry-eighth ::= SEQUENCE {
    upsOutputLineIndex-eighth   PositiveInteger32,
    upsOutputVoltage-eighth     NonNegativeInteger32,
    upsOutputCurrent-eighth     NonNegativeInteger32,
    upsOutputPower-eighth       NonNegativeInteger32,
    upsOutputPercentLoad-eighth Integer32
}

upsOutputLineIndex-eighth OBJECT-TYPE
    SYNTAX     PositiveInteger32
    MAX-ACCESS not-accessible
    STATUS     current
    DESCRIPTION
            "The output line identifier.(*)"
    ::= { upsOutputEntry-eighth 1 }

upsOutputVoltage-eighth OBJECT-TYPE
    SYNTAX     NonNegativeInteger32
    UNITS      "RMS Volts"
    MAX-ACCESS read-only
    STATUS     current
    DESCRIPTION
            "The present output voltage.(*)"
    ::= { upsOutputEntry-eighth 2 }

upsOutputCurrent-eighth OBJECT-TYPE
    SYNTAX     NonNegativeInteger32
    UNITS      "0.1 RMS Amp"
    MAX-ACCESS read-only
    STATUS     current
    DESCRIPTION
            "The present output current.(*)"
    ::= { upsOutputEntry-eighth 3 }

upsOutputPower-eighth OBJECT-TYPE
    SYNTAX     NonNegativeInteger32
    UNITS      "Watts"
    MAX-ACCESS read-only
    STATUS     current
    DESCRIPTION
            "The present output true power.(*)"
    ::= { upsOutputEntry-eighth 4 }

upsOutputPercentLoad-eighth OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-eighth 5 }

--
-- The Bypass group generic.
--

upsBypassFrequency-eighth OBJECT-TYPE
    SYNTAX     NonNegativeInteger32
    UNITS      "0.1 Hertz"
    MAX-ACCESS read-only
    STATUS     current
    DESCRIPTION
            "The present bypass frequency.(*)"
    ::= { upsBypass-eighth 1 }

upsBypassNumLines-eighth OBJECT-TYPE
    SYNTAX     NonNegativeInteger32
    MAX-ACCESS read-only
    STATUS     current
    DESCRIPTION
            "The number of bypass lines utilized in this device.
            This entry indicates the number of rows in the bypass
            table.(*)"
    ::= { upsBypass-eighth 2 }

upsBypassTable-eighth OBJECT-TYPE
    SYNTAX     SEQUENCE OF UpsBypassEntry-eighth
    MAX-ACCESS not-accessible
    STATUS     current
    DESCRIPTION
            "A list of bypass table entries.  The number of
            entries is given by the value of upsBypassNumLines.(*)"
    ::= { upsBypass-eighth 3 }

upsBypassEntry-eighth OBJECT-TYPE
    SYNTAX     UpsBypassEntry-eighth
    MAX-ACCESS not-accessible
    STATUS     current
    DESCRIPTION
            "An entry containing information applicable to a
            particular bypass input.(*)"
    INDEX { upsBypassLineIndex-eighth }
    ::= { upsBypassTable-eighth 1 }

UpsBypassEntry-eighth ::= SEQUENCE {
    upsBypassLineIndex-eighth  PositiveInteger32,
    upsBypassVoltage-eighth    NonNegativeInteger32,
    upsBypassCurrent-eighth    NonNegativeInteger32,
    upsBypassPower-eighth      NonNegativeInteger32
}

upsBypassLineIndex-eighth OBJECT-TYPE
    SYNTAX     PositiveInteger32
    MAX-ACCESS not-accessible
    STATUS     current
    DESCRIPTION
            "The bypass line identifier.(*)"
    ::= { upsBypassEntry-eighth 1 }

upsBypassVoltage-eighth OBJECT-TYPE
    SYNTAX     NonNegativeInteger32
    UNITS      "RMS Volts"
    MAX-ACCESS read-only
    STATUS     current
    DESCRIPTION
            "The present bypass voltage.(*)"
    ::= { upsBypassEntry-eighth 2 }

upsBypassCurrent-eighth OBJECT-TYPE
    SYNTAX     NonNegativeInteger32
    UNITS      "0.1 RMS Amp"
    MAX-ACCESS read-only
    STATUS     current
    DESCRIPTION
            "The present bypass current.(*)"
    ::= { upsBypassEntry-eighth 3 }

upsBypassPower-eighth OBJECT-TYPE
    SYNTAX     NonNegativeInteger32
    UNITS      "Watts"
    MAX-ACCESS read-only
    STATUS     current
    DESCRIPTION
            "The present true power conveyed by the bypass.(*)"
    ::= { upsBypassEntry-eighth 4 }

--
-- The Alarm group generic.
--

upsAlarmsPresent-eighth OBJECT-TYPE
    SYNTAX     Gauge32
    MAX-ACCESS read-only
    STATUS     current
    DESCRIPTION
            "The present number of active alarm conditions.(*)"
    ::= { upsAlarm-eighth 1 }

upsAlarmTable-eighth OBJECT-TYPE
    SYNTAX     SEQUENCE OF UpsAlarmEntry-eighth
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-eighth 2 }

upsAlarmEntry-eighth OBJECT-TYPE
    SYNTAX     UpsAlarmEntry-eighth
    MAX-ACCESS not-accessible
    STATUS     current
    DESCRIPTION
            "An entry containing information applicable to a
            particular alarm.(*)"
    INDEX { upsAlarmId-eighth }
    ::= { upsAlarmTable-eighth 1 }

UpsAlarmEntry-eighth ::= SEQUENCE {
    upsAlarmId-eighth          PositiveInteger32,
    upsAlarmDescr-eighth       AutonomousType,
    upsAlarmTime-eighth       TimeStamp
}

upsAlarmId-eighth OBJECT-TYPE
    SYNTAX     PositiveInteger32
    MAX-ACCESS not-accessible
    STATUS     current
    DESCRIPTION
            "A unique identifier for an alarm condition.  This
            value must remain constant.(*)"
    ::= { upsAlarmEntry-eighth 1 }

upsAlarmDescr-eighth OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-eighth 2 }

upsAlarmTime-eighth OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-eighth 3 }

--
-- Well known alarm conditions generic.
--

upsAlarmBatteryBad-eighth OBJECT-IDENTITY
    STATUS     current
    DESCRIPTION
            "One or more batteries have been determined to require
            replacement.(*)"
    ::= { upsWellKnownAlarms-eighth  1 }

upsAlarmOnBattery-eighth OBJECT-IDENTITY
    STATUS     current
    DESCRIPTION
            "The UPS is drawing power from the batteries.(*)"
    ::= { upsWellKnownAlarms-eighth  2 }

upsAlarmLowBattery-eighth OBJECT-IDENTITY
    STATUS     current
    DESCRIPTION
            "The remaining battery run-time is less than or equal
            to upsConfigLowBattTime.(*)"
    ::= { upsWellKnownAlarms-eighth  3 }

upsAlarmDepletedBattery-eighth OBJECT-IDENTITY
    STATUS     current
    DESCRIPTION
            "The UPS will be unable to sustain the present load
            when and if the utility power is lost.(*)"
    ::= { upsWellKnownAlarms-eighth  4 }

upsAlarmTempBad-eighth OBJECT-IDENTITY
    STATUS     current
    DESCRIPTION
            "A temperature is out of tolerance.(*)"
    ::= { upsWellKnownAlarms-eighth  5 }

upsAlarmInputBad-eighth OBJECT-IDENTITY
    STATUS     current
    DESCRIPTION
            "An input condition is out of tolerance.(*)"
    ::= { upsWellKnownAlarms-eighth  6 }

upsAlarmOutputBad-eighth OBJECT-IDENTITY
    STATUS     current
    DESCRIPTION
            "An output condition (other than OutputOverload) is
            out of tolerance.(*)"
    ::= { upsWellKnownAlarms-eighth  7 }

upsAlarmOutputOverload-eighth OBJECT-IDENTITY
    STATUS     current
    DESCRIPTION
            "The output load exceeds the UPS output capacity.(*)"
    ::= { upsWellKnownAlarms-eighth  8 }

upsAlarmOnBypass-eighth OBJECT-IDENTITY
    STATUS     current
    DESCRIPTION
            "The Bypass is presently engaged on the UPS.(*)"
    ::= { upsWellKnownAlarms-eighth  9 }

upsAlarmBypassBad-eighth OBJECT-IDENTITY
    STATUS     current
    DESCRIPTION
            "The Bypass is out of tolerance.(*)"
    ::= { upsWellKnownAlarms-eighth 10 }

upsAlarmOutputOffAsRequested-eighth OBJECT-IDENTITY
    STATUS     current
    DESCRIPTION
            "The UPS has shutdown as requested, i.e., the output
            is off.(*)"
    ::= { upsWellKnownAlarms-eighth 11 }

upsAlarmUpsOffAsRequested-eighth OBJECT-IDENTITY
    STATUS     current
    DESCRIPTION
            "The entire UPS has shutdown as commanded.(*)"
    ::= { upsWellKnownAlarms-eighth 12 }

upsAlarmChargerFailed-eighth OBJECT-IDENTITY
    STATUS     current
    DESCRIPTION
            "An uncorrected problem has been detected within the
            UPS charger subsystem.(*)"
    ::= { upsWellKnownAlarms-eighth 13 }

upsAlarmUpsOutputOff-eighth OBJECT-IDENTITY
    STATUS     current
    DESCRIPTION
            "The output of the UPS is in the off state.(*)"
    ::= { upsWellKnownAlarms-eighth 14 }

upsAlarmUpsSystemOff-eighth OBJECT-IDENTITY
    STATUS     current
    DESCRIPTION
            "The UPS system is in the off state.(*)"
    ::= { upsWellKnownAlarms-eighth 15 }

upsAlarmFanFailure-eighth OBJECT-IDENTITY
    STATUS     current
    DESCRIPTION
            "The failure of one or more fans in the UPS has been
            detected.(*)"
    ::= { upsWellKnownAlarms-eighth 16 }

upsAlarmFuseFailure-eighth OBJECT-IDENTITY
    STATUS     current
    DESCRIPTION
            "The failure of one or more fuses has been detected.(*)"
    ::= { upsWellKnownAlarms-eighth 17 }

upsAlarmGeneralFault-eighth OBJECT-IDENTITY
    STATUS     current
    DESCRIPTION
            "A general fault in the UPS has been detected.(*)"
    ::= { upsWellKnownAlarms-eighth 18 }

upsAlarmDiagnosticTestFailed-eighth OBJECT-IDENTITY
    STATUS     current
    DESCRIPTION
            "The result of the last diagnostic test indicates a
            failure.(*)"
    ::= { upsWellKnownAlarms-eighth 19 }

upsAlarmCommunicationsLost-eighth OBJECT-IDENTITY
    STATUS     current
    DESCRIPTION
            "A problem has been encountered in the communications
            between the agent and the UPS.(*)"
    ::= { upsWellKnownAlarms-eighth 20 }

upsAlarmAwaitingPower-eighth OBJECT-IDENTITY
    STATUS     current
    DESCRIPTION
            "The UPS output is off and the UPS is awaiting the
            return of input power.(*)"
    ::= { upsWellKnownAlarms-eighth 21 }

upsAlarmShutdownPending-eighth OBJECT-IDENTITY
    STATUS     current
    DESCRIPTION
            "A upsShutdownAfterDelay countdown is underway.(*)"
    ::= { upsWellKnownAlarms-eighth 22 }

upsAlarmShutdownImminent-eighth OBJECT-IDENTITY
    STATUS     current
    DESCRIPTION
            "The UPS will turn off power to the load in less than
            5 seconds; this may be either a timed shutdown or a
            low battery shutdown.(*)"
    ::= { upsWellKnownAlarms-eighth 23 }

upsAlarmTestInProgress-eighth OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-eighth 24 }

upsAlarmReceptacleOff-eighth OBJECT-IDENTITY
    STATUS     current
    DESCRIPTION
            "The receptacle are switch off    "
    ::= { upsWellKnownAlarms-eighth 25 }

upsAlarmMaskA-eighth OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-eighth 4 }

--
-- The Test Group generic
--

upsTestId-eighth OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-eighth 1 }

-- see [6] for more information on the semantics of objects with
-- syntax of TestAndIncr

upsTestSpinLock-eighth OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-eighth 2 }

upsTestResultsSummary-eighth OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-eighth 3 }

upsTestResultsDetail-eighth OBJECT-TYPE
    SYNTAX     DisplayString (SIZE (0..255))
    MAX-ACCESS read-only
    STATUS     current
    DESCRIPTION
            "Additional information about upsTestResultsSummary.
            If no additional information available, a zero length
            string is returned.(*)"
    ::= { upsTest-eighth 4 }

upsTestStartTime-eighth OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-eighth 5 }

upsTestElapsedTime-eighth OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-eighth 6 }

--
-- Well known tests generic.
--

upsTestNoTestsInitiated-eighth OBJECT-IDENTITY
    STATUS     current
    DESCRIPTION
            "No tests have been initiated and no test is in
            progress.(*)"
    ::= { upsWellKnownTests-eighth  1 }

upsTestAbortTestInProgress-eighth OBJECT-IDENTITY
    STATUS     current
    DESCRIPTION
            "The test in progress is to be aborted / the test in
            progress was aborted.(*)"
    ::= { upsWellKnownTests-eighth  2 }

upsTestGeneralSystemsTest-eighth OBJECT-IDENTITY
    STATUS     current
    DESCRIPTION
            "The manufacturer's standard test of UPS device
            systems.(*)"
    ::= { upsWellKnownTests-eighth  3 }

upsTestQuickBatteryTest-eighth OBJECT-IDENTITY
    STATUS     current
    DESCRIPTION
            "A test that is sufficient to determine if the battery
            needs replacement.(*)"
    ::= { upsWellKnownTests-eighth  4 }

upsTestDeepBatteryCalibration-eighth OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-eighth  5 }

--
-- The Control group generic.
--

upsShutdownType-eighth OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-eighth 1 }

upsShutdownAfterDelay-eighth OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-eighth 2 }

upsStartupAfterDelay-eighth OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-eighth 3 }

upsRebootWithDuration-eighth OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-eighth 4 }

upsAutoRestart-eighth OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-eighth 5 }

upsReceptaclesNum-eighth OBJECT-TYPE
    SYNTAX     NonNegativeInteger32
    MAX-ACCESS read-only
    STATUS     current
    DESCRIPTION
            "The number of receptacles utilized in this device.
            This entry indicates the number of rows in the receptacle
            table."
    ::= { upsControl-eighth 6 }

upsReceptacleTable-eighth OBJECT-TYPE
    SYNTAX     SEQUENCE OF UpsReceptacleEntry-eighth
    MAX-ACCESS not-accessible
    STATUS     current
    DESCRIPTION
            "A list of receptacle table entries.  The number of
            entries is given by the value of upsReceptacleNum."
    ::= { upsControl-eighth 7 }

upsReceptacleEntry-eighth OBJECT-TYPE
    SYNTAX     UpsReceptacleEntry-eighth
    MAX-ACCESS not-accessible
    STATUS     current
    DESCRIPTION
            "An entry containing information applicable to a
            particular receptacle."
    INDEX { upsReceptacleLineIndex-eighth }
    ::= { upsReceptacleTable-eighth 1 }

UpsReceptacleEntry-eighth ::= SEQUENCE {
    upsReceptacleLineIndex-eighth  PositiveInteger32,
    upsReceptacleOnOff-eighth      Integer32    
}

upsReceptacleLineIndex-eighth OBJECT-TYPE
    SYNTAX     PositiveInteger32
    MAX-ACCESS not-accessible
    STATUS     current
    DESCRIPTION
            "The receptacle line identifier."
    ::= { upsReceptacleEntry-eighth 1 }

upsReceptacleOnOff-eighth OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-eighth 2 }

upsUPSMode-eighth OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-eighth 8 }

upsRectifierOnOff-eighth OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-eighth 9 }

upsBatteryChargeMethod-eighth OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-eighth 10 }

upsInverterOnOff-eighth OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-eighth 11 }

upsBypassOnOff-eighth OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-eighth 12 }

upsLoadSource-eighth OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-eighth 13 }
	
--
-- The Configuration group generic.
--

upsConfigInputVoltage-eighth OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-eighth 1 }

upsConfigInputFreq-eighth OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-eighth 2 }

upsConfigOutputVoltage-eighth OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-eighth 3 }

upsConfigOutputFreq-eighth OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-eighth 4 }

upsConfigOutputVA-eighth OBJECT-TYPE
    SYNTAX     NonNegativeInteger32
    UNITS      "Volt-Amps"
    MAX-ACCESS read-only
    STATUS     current
    DESCRIPTION
            "The magnitude of the nominal Volt-Amp rating.(*)"
    ::= { upsConfig-eighth 5 }

upsConfigOutputPower-eighth OBJECT-TYPE
    SYNTAX     NonNegativeInteger32
    UNITS      "Watts"
    MAX-ACCESS read-only
    STATUS     current
    DESCRIPTION
            "The magnitude of the nominal true power rating.(*)"
    ::= { upsConfig-eighth 6 }

upsConfigLowBattTime-eighth OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-eighth 7 }

upsConfigAudibleStatus-eighth OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-eighth 8 }

upsConfigLowVoltageTransferPoint-eighth OBJECT-TYPE
    SYNTAX     NonNegativeInteger32
    UNITS      "RMS Volts"
    MAX-ACCESS read-write
    STATUS     current
    DESCRIPTION
            "The minimum input line voltage allowed before the UPS
            system transfers to battery backup.(*)"
    ::= { upsConfig-eighth 9 }

upsConfigHighVoltageTransferPoint-eighth OBJECT-TYPE
    SYNTAX     NonNegativeInteger32
    UNITS      "RMS Volts"
    MAX-ACCESS read-write
    STATUS     current
    DESCRIPTION
            "The maximum line voltage allowed before the UPS
            system transfers to battery backup.(*)"
    ::= { upsConfig-eighth 10 }

upsConfigBatteryCapacity-eighth OBJECT-TYPE
    SYNTAX     NonNegativeInteger32
    UNITS      "Amps Hours"
    MAX-ACCESS read-write
    STATUS     current
    DESCRIPTION
            "The installed battery capacity. This value is the 'factory'-value,
             not the value after calibration."
    ::= { upsConfig-eighth 11 }

upsConfigBatteryChargeCurrent-eighth OBJECT-TYPE
    SYNTAX     NonNegativeInteger32
    UNITS      "0.1 Amp DC"
    MAX-ACCESS read-write
    STATUS     current
    DESCRIPTION
            "The maximum battery charge current, including external chargers."
    ::= { upsConfig-eighth 12 }						

upsConfigNoLoadShutdown-eighth OBJECT-TYPE
    SYNTAX     Integer32 {
        disabled(1),
        enabled(2)
    }
    MAX-ACCESS read-write
    STATUS     current
    DESCRIPTION
            "Dis- or enable 'no load' shutdown from the contact interface."
    ::= { upsConfig-eighth 13 }
	
upsConfigStartDelay-eighth OBJECT-TYPE
    SYNTAX     PositiveInteger32
    UNITS      "minutes"				
    MAX-ACCESS read-write
    STATUS     current
    DESCRIPTION
            "Minimum required autonomy time before the UPS may perform an
             autorestart."
    ::= { upsConfig-eighth 14 }

--
-- The GetSet group generic.
--

upsEventGetNext-eighth OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-eighth 1 }

upsEventGetPrevious-eighth OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-eighth 2 }
				
upsEventSetStartingTimeStamp-eighth OBJECT-TYPE
    SYNTAX     NonNegativeInteger32
    MAX-ACCESS read-write
    STATUS     current
    DESCRIPTION
            "The timestamp which is used as starting point for downloading
             events from the UPS event buffer"
    ::= { upsGetSet-eighth 3 }				

upsEventRetreiveCurrentTimeStamp-eighth OBJECT-TYPE
    SYNTAX     NonNegativeInteger32
    MAX-ACCESS read-only
    STATUS     current
    DESCRIPTION
            "The current timestamp is retreived from the UPS"
    ::= { upsGetSet-eighth 4 }				

upsEventTableSize-eighth OBJECT-TYPE
    SYNTAX     NonNegativeInteger32
    MAX-ACCESS read-only
    STATUS     current
    DESCRIPTION
            "The number of entries in the event table.
            This object indicates the number of rows in the event table."
    ::= { upsGetSet-eighth 5 }

upsEventTable-eighth OBJECT-TYPE
    SYNTAX     SEQUENCE OF UpsEventEntry-eighth
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-eighth 6 }

upsEventEntry-eighth OBJECT-TYPE
    SYNTAX     UpsEventEntry-eighth
    MAX-ACCESS not-accessible
    STATUS     current
    DESCRIPTION
            "An entry containing information applicable to a
            particular event."
    INDEX { upsEventLineIndex-eighth }
    ::= { upsEventTable-eighth 1 }

UpsEventEntry-eighth ::= SEQUENCE {
    upsEventLineIndex-eighth PositiveInteger32,
    upsEventCode-eighth      Integer32,
    upsEventStatus-eighth    NonNegativeInteger32,
    upsEventTime-eighth      NonNegativeInteger32
}

upsEventLineIndex-eighth OBJECT-TYPE
    SYNTAX     PositiveInteger32
    MAX-ACCESS not-accessible
    STATUS     current
    DESCRIPTION
            "The event line identifier."
    ::= { upsEventEntry-eighth 1 }

upsEventCode-eighth OBJECT-TYPE
    SYNTAX     NonNegativeInteger32
    MAX-ACCESS read-only
    STATUS     current
    DESCRIPTION
            "The event code in numerical format."
    ::= { upsEventEntry-eighth 2 }

upsEventStatus-eighth OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-eighth 3 }

upsEventTime-eighth OBJECT-TYPE
    SYNTAX     NonNegativeInteger32
    MAX-ACCESS read-only
    STATUS     current
    DESCRIPTION
            "The timestamp of the moment the event was generated."
    ::= { upsEventEntry-eighth 4 }

upsParametersRead-eighth OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-eighth 7 }

upsParametersWrite-eighth OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-eighth 8 }

upsParametersStartAddress-eighth OBJECT-TYPE
    SYNTAX     NonNegativeInteger32
    MAX-ACCESS read-write
    STATUS     current
    DESCRIPTION
            "The address which is used as starting point for downloading
             parameters from the UPS"
    ::= { upsGetSet-eighth 9 }				

upsParameterTableSize-eighth OBJECT-TYPE
    SYNTAX     NonNegativeInteger32
    MAX-ACCESS read-only
    STATUS     current
    DESCRIPTION
            "The number of entries in the parameter table.
            This object indicates the number of rows in the parameter table."
    ::= { upsGetSet-eighth 10 }

upsParameterTable-eighth OBJECT-TYPE
    SYNTAX     SEQUENCE OF UpsParameterEntry-eighth
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-eighth 11 }

upsParameterEntry-eighth OBJECT-TYPE
    SYNTAX     UpsParameterEntry-eighth
    MAX-ACCESS not-accessible
    STATUS     current
    DESCRIPTION
            "An entry containing information applicable to a
            particular parameter."
    INDEX { upsParameterLineIndex-eighth }
    ::= { upsParameterTable-eighth 1 }

UpsParameterEntry-eighth ::= SEQUENCE {
    upsParameterLineIndex-eighth PositiveInteger32,
    upsParameterValue-eighth     Integer32   
}

upsParameterLineIndex-eighth OBJECT-TYPE
    SYNTAX     PositiveInteger32
    MAX-ACCESS not-accessible
    STATUS     current
    DESCRIPTION
            "The parameter line identifier."
    ::= { upsParameterEntry-eighth 1 }

upsParameterValue-eighth OBJECT-TYPE
    SYNTAX     Integer32
    MAX-ACCESS read-write
    STATUS     current
    DESCRIPTION
            "The parameter value in numerical format."
    ::= { upsParameterEntry-eighth 2 }

upsStatus-eighth OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-eighth 12 }

upsMainsStatisticsMBfail-eighth OBJECT-TYPE
    SYNTAX     NonNegativeInteger32
    MAX-ACCESS read-only
    STATUS     current
    DESCRIPTION
            "Count of main bypass failures (>200 ms), since UPS installation."
    ::= { upsGetSet-eighth 13 }

upsMainsStatisticsMRfail-eighth OBJECT-TYPE
    SYNTAX     NonNegativeInteger32
    MAX-ACCESS read-only
    STATUS     current
    DESCRIPTION
            "Count of mains rectifier failures (>200 ms), since UPS installation."
    ::= { upsGetSet-eighth 14 }
		
upsMainsStatisticsB2-eighth OBJECT-TYPE
    SYNTAX     NonNegativeInteger32
    MAX-ACCESS read-only
    STATUS     current
    DESCRIPTION
            "Count of transients on the mains bypass (0..2 ms), during the last 7 days."
    ::= { upsGetSet-eighth 15 }

upsMainsStatisticsB5-eighth OBJECT-TYPE
    SYNTAX     NonNegativeInteger32
    MAX-ACCESS read-only
    STATUS     current
    DESCRIPTION
            "Count of transients on the mains bypass (2..5 ms), during the last 7 days."
    ::= { upsGetSet-eighth 16 }

upsMainsStatisticsB10-eighth OBJECT-TYPE
    SYNTAX     NonNegativeInteger32
    MAX-ACCESS read-only
    STATUS     current
    DESCRIPTION
            "Count of transients on the mains bypass (5..10 ms), during the last 7 days."
    ::= { upsGetSet-eighth 17 }

upsMainsStatisticsB200-eighth OBJECT-TYPE
    SYNTAX     NonNegativeInteger32
    MAX-ACCESS read-only
    STATUS     current
    DESCRIPTION
            "Count of transients on the mains bypass (10..200 ms), during the last 7 days."
    ::= { upsGetSet-eighth 18 }

upsMainsStatisticsBypRel-eighth OBJECT-TYPE
    SYNTAX     NonNegativeInteger32
    MAX-ACCESS read-only
    STATUS     current
    DESCRIPTION
            "Bypass reliability degree [0..100%;255]. The value NOSUCHNAME means 'not available'."
    ::= { upsGetSet-eighth 19 }

upsTime-eighth OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-eighthERROR,              meaning 'command not supported'. It is possible to know which is the timestamp 
             format supported by the UPS, by issuing a read-command or by reading events, 
             which includes timestamps."
    ::= { upsGetSet-eighth 20 }

upsRequestPermission-eighth OBJECT-TYPE
    SYNTAX     DisplayString (SIZE(0..63))
    MAX-ACCESS write-only
    STATUS     current
    DESCRIPTION
            "An encrypted code is send to enable use of restricted write objects during
             a limited period of time."
    ::= { upsGetSet-eighth 21 }
    
upsEventGetCode-eighth OBJECT-TYPE
    SYNTAX     Integer32
    MAX-ACCESS write-only
    STATUS     current
    DESCRIPTION
            "The code which is used as starting point to downloading the events from the 
            UPS event buffer."
    ::= { upsGetSet-eighth 22 }    
    
upsEventSpinLock-eighth OBJECT-TYPE
    SYNTAX     TestAndIncr
    MAX-ACCESS read-write
    STATUS     current
    DESCRIPTION
            "A spin lock on the event subsystem. "

    ::= { upsGetSet-eighth 23 }
    
upsParameterSpinLock-eighth OBJECT-TYPE
    SYNTAX     TestAndIncr
    MAX-ACCESS read-write
    STATUS     current
    DESCRIPTION
            "A spin lock on the parameters subsystem. "

    ::= { upsGetSet-eighth 24 }


--
-- GE Trap group generic
--

upsAlarmBatteryBad-eighth TRAP-TYPE
    ENTERPRISE geUPSTraps-eighth
    VARIABLES  { trapArg  }
    DESCRIPTION
            "One or more batteries have been determined to require
            replacement."
    ::= 1

upsAlarmOnBattery-eighth TRAP-TYPE
    ENTERPRISE geUPSTraps-eighth
    VARIABLES  { trapArg , upsSecondsOnBattery-eighth  }
    DESCRIPTION
            "An On Battery condition is restored."
    ::= 2

upsAlarmLowBattery-eighth TRAP-TYPE
    ENTERPRISE geUPSTraps-eighth
    VARIABLES  { trapArg  }
    DESCRIPTION
            "The remaining battery run-time is less than or equal
            to upsConfigLowBattTime."
    ::= 3

upsAlarmDepletedBattery-eighth TRAP-TYPE
    ENTERPRISE geUPSTraps-eighth
    VARIABLES  { trapArg  }
    DESCRIPTION
            "The UPS will be unable to sustain the present load
            when and if the utility power is lost)"
    ::= 4

upsAlarmTempBad-eighth TRAP-TYPE
    ENTERPRISE geUPSTraps-eighth
    VARIABLES  { trapArg , upsBatteryTemperature }
    DESCRIPTION
            "A temperature is out of tolerance."
    ::= 5

upsAlarmInputBad-eighth TRAP-TYPE
    ENTERPRISE geUPSTraps-eighth
    VARIABLES  { trapArg  }
    DESCRIPTION
            "An input condition is out of tolerance."
    ::= 6

upsAlarmOutputBad-eighth TRAP-TYPE
    ENTERPRISE geUPSTraps-eighth
    VARIABLES  { trapArg  }
    DESCRIPTION
            "An output condition (other than OutputOverload) is
            out of tolerance."
    ::= 7

upsAlarmOutputOverload-eighth TRAP-TYPE
    ENTERPRISE geUPSTraps-eighth
    VARIABLES  { trapArg , upsOutputPercentLoad-eighth }
    DESCRIPTION
            "The output load exceeds the UPS output capacity."
    ::= 8

upsAlarmOnBypass-eighth TRAP-TYPE
    ENTERPRISE geUPSTraps-eighth
    VARIABLES  { trapArg  }
    DESCRIPTION
            "The Bypass is presently engaged on the UPS."
    ::= 9

upsAlarmBypassBad-eighth TRAP-TYPE
    ENTERPRISE geUPSTraps-eighth
    VARIABLES  { trapArg  }
    DESCRIPTION
            "The Bypass is out of tolerance."
    ::= 10

upsAlarmOutputOffAsRequested-eighth TRAP-TYPE
    ENTERPRISE geUPSTraps-eighth
    VARIABLES  { trapArg  }
    DESCRIPTION
            "The UPS has shutdown as requested, i.e., the output
            is off."
    ::= 11

upsAlarmUpsOffAsRequested-eighth TRAP-TYPE
    ENTERPRISE geUPSTraps-eighth-eighth
    VARIABLES  { trapArg  }
    DESCRIPTION
            "The entire UPS has shutdown as commanded."
    ::= 12

upsAlarmChargerFailed-eighth TRAP-TYPE
    ENTERPRISE geUPSTraps-eighth
    VARIABLES  { trapArg  }
    DESCRIPTION
            "An uncorrected problem has been detected within the
            UPS charger subsystem."
    ::= 13

upsAlarmUpsOutputOff-eighth TRAP-TYPE
    ENTERPRISE geUPSTraps-eighth
    VARIABLES  { trapArg  }
    DESCRIPTION
            "The output of the UPS is in the off state."
    ::= 14

upsAlarmUpsSystemOff-eighth TRAP-TYPE
    ENTERPRISE geUPSTraps-eighth
    VARIABLES  { trapArg  }
    DESCRIPTION
            "The UPS system is in the off state."
    ::= 15

upsAlarmFanFailure-eighth TRAP-TYPE
    ENTERPRISE geUPSTraps-eighth
    VARIABLES  { trapArg  }
    DESCRIPTION
            "The failure of one or more fans in the UPS has been
            detected."
    ::= 16

upsAlarmFuseFailure-eighth TRAP-TYPE
    ENTERPRISE geUPSTraps-eighth
    VARIABLES  { trapArg  }
    DESCRIPTION
            "The failure of one or more fuses has been detected."
    ::= 17

upsAlarmGeneralFault-eighth TRAP-TYPE
    ENTERPRISE geUPSTraps-eighth
    VARIABLES  { trapArg  }
    DESCRIPTION
            "A general fault in the UPS has been detected."
    ::= 18

upsAlarmDiagnosticTestFailed-eighth TRAP-TYPE
    ENTERPRISE geUPSTraps-eighth
    VARIABLES  { trapArg  }
    DESCRIPTION
            "The result of the last diagnostic test indicates a
            failure."
    ::= 19

upsAlarmCommunicationsLost-eighth TRAP-TYPE
    ENTERPRISE geUPSTraps-eighth
    VARIABLES  { trapArg  }
    DESCRIPTION
            "A problem has been encountered in the communication
            between the agent and the UPS."
    ::= 20
    
upsAlarmAwaitingPower-eighth TRAP-TYPE
    ENTERPRISE geUPSTraps-eighth
    VARIABLES  { trapArg  }
    DESCRIPTION
            "The UPS output is off and the UPS is awaiting the
            return of the input power (*)."
    ::= 21    

upsAlarmShutdownPending-eighth TRAP-TYPE
    ENTERPRISE geUPSTraps-eighth
    VARIABLES  { trapArg , upsShutdownAfterDelay-eighth }
    DESCRIPTION
            "A upsShutdownAfterDelay countdown is underway."
    ::= 22

upsAlarmShutdownImminent-eighth TRAP-TYPE
    ENTERPRISE geUPSTraps-eighth
    VARIABLES  { trapArg  }
    DESCRIPTION
            "The UPS will turn off power to the load in less than
            5 seconds; this may be either a timed shutdown or a
            low battery shutdown."
    ::= 23

upsAlarmTestInProgress-eighth TRAP-TYPE
    ENTERPRISE geUPSTraps-eighth
    VARIABLES  { trapArg , upsTestId-eighth }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-eighth TRAP-TYPE
    ENTERPRISE geUPSTraps-eighth
    VARIABLES  { trapArg  }
    DESCRIPTION
            "A receptacle has been switched off."
    ::= 25

upsAlarmBatteryBadRestored-eighth TRAP-TYPE
    ENTERPRISE geUPSTraps-eighth
    VARIABLES  { trapArg  }
    DESCRIPTION
            "A Battery bad condition is restored."
    ::= 33

upsAlarmOnBatteryRestored-eighth TRAP-TYPE
    ENTERPRISE geUPSTraps-eighth
    VARIABLES  { trapArg  }
    DESCRIPTION
            "The UPS is drawing power from mains again."
    ::= 34

upsAlarmLowBatteryRestored-eighth TRAP-TYPE
    ENTERPRISE geUPSTraps-eighth
    VARIABLES  { trapArg  }
    DESCRIPTION
            "A Low Battery condition is restored."
    ::= 35

upsAlarmDepletedBatteryRestored-eighth TRAP-TYPE
    ENTERPRISE geUPSTraps-eighth
    VARIABLES  { trapArg  }
    DESCRIPTION
            "A Depleted Battery condition is restored."
    ::= 36

upsAlarmTempBadRestored-eighth TRAP-TYPE
    ENTERPRISE geUPSTraps-eighth
    VARIABLES  { trapArg  }
    DESCRIPTION
            "A bad temperature condition is restored."
    ::= 37

upsAlarmInputBadRestored-eighth TRAP-TYPE
    ENTERPRISE geUPSTraps-eighth
    VARIABLES  { trapArg  }
    DESCRIPTION
            "An input bad condition is restored."
    ::= 38

upsAlarmOutputBadRestored-eighth TRAP-TYPE
    ENTERPRISE geUPSTraps-eighth
    VARIABLES  { trapArg  }
    DESCRIPTION
            "An output bad condition is restored."
    ::= 39

upsAlarmOutputOverloadRestored-eighth TRAP-TYPE
    ENTERPRISE geUPSTraps-eighth
    VARIABLES  { trapArg  }
    DESCRIPTION
            "An output overload condition is restored."
    ::= 40

upsAlarmOnBypassRestored-eighth TRAP-TYPE
    ENTERPRISE geUPSTraps-eighth
    VARIABLES  { trapArg  }
    DESCRIPTION
            "An On Bypass condition is restored."
    ::= 41

upsAlarmBypassBadRestored-eighth TRAP-TYPE
    ENTERPRISE geUPSTraps-eighth
    VARIABLES  { trapArg  }
    DESCRIPTION
            "A Bypass bad condition is restored."
    ::= 42

upsAlarmOutputOffAsRequestedRestored-eighth TRAP-TYPE
    ENTERPRISE geUPSTraps-eighth
    VARIABLES  { trapArg  }
    DESCRIPTION
            "A request shutdown has been restored."
    ::= 43

upsAlarmUpsOffAsRequestedRestored-eighth TRAP-TYPE
    ENTERPRISE geUPSTraps-eighth-eighth
    VARIABLES  { trapArg  }
    DESCRIPTION
            "A entire UPS command has been restored."
    ::= 44

upsAlarmChargerFailedRestored-eighth TRAP-TYPE
    ENTERPRISE geUPSTraps-eighth
    VARIABLES  { trapArg  }
    DESCRIPTION
            "A Charger Failer condition is restored."
    ::= 45

upsAlarmUpsOutputOn-eighth TRAP-TYPE
    ENTERPRISE geUPSTraps-eighth
    VARIABLES  { trapArg  }
    DESCRIPTION
            "The output of the UPS switched in the on state."
    ::= 46

upsAlarmUpsSystemOn-eighth TRAP-TYPE
    ENTERPRISE geUPSTraps-eighth
    VARIABLES  { trapArg  }
    DESCRIPTION
            "The UPS system is switched in the on state."
    ::= 47

upsAlarmFanFailureRestored-eighth TRAP-TYPE
    ENTERPRISE geUPSTraps-eighth
    VARIABLES  { trapArg  }
    DESCRIPTION
            "A Fan failure condition is restored."
    ::= 48

upsAlarmFuseFailureRestored-eighth TRAP-TYPE
    ENTERPRISE geUPSTraps-eighth
    VARIABLES  { trapArg  }
    DESCRIPTION
            "A Fuse failure condition is restored."
    ::= 49

upsAlarmGeneralFaultRestored-eighth TRAP-TYPE
    ENTERPRISE geUPSTraps-eighth
    VARIABLES  { trapArg  }
    DESCRIPTION
            "A general fault is restored."
    ::= 50

upsAlarmDiagnosticTestFailedRestored-eighth TRAP-TYPE
    ENTERPRISE geUPSTraps-eighth
    VARIABLES  { trapArg  }
    DESCRIPTION
            "A last diagnostic test indicates a failure is 
            restored."
    ::= 51

upsAlarmCommunicationsLostRestored-eighth TRAP-TYPE
    ENTERPRISE geUPSTraps-eighth
    VARIABLES  { trapArg  }
    DESCRIPTION
            "A problem in the communication between the agent 
            and the UPS is restored."
    ::= 52
    
upsAlarmAwaitingPowerRestored-eighth TRAP-TYPE
    ENTERPRISE geUPSTraps-eighth
    VARIABLES  { trapArg  }
    DESCRIPTION
            "A awaiting power condition is restored (*)."
    ::= 53    

upsAlarmShutdownPendingRestored-eighth TRAP-TYPE
    ENTERPRISE geUPSTraps-eighth
    VARIABLES  { trapArg , upsShutdownAfterDelay-eighth }
    DESCRIPTION
            "A upsShutdownAfterDelay countdown is restored."
    ::= 54

upsAlarmShutdownImminentRestored-eighth TRAP-TYPE
    ENTERPRISE geUPSTraps-eighth
    VARIABLES  { trapArg  }
    DESCRIPTION
            "A shutdown imminent condition is restored."
    ::= 55

upsAlarmTestInProgressRestored-eighth TRAP-TYPE
    ENTERPRISE geUPSTraps-eighth
    VARIABLES  { trapArg , upsTestId-eighth }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-eighth TRAP-TYPE
    ENTERPRISE geUPSTraps-eighth
    VARIABLES  { trapArg  }
    DESCRIPTION
            "A measurement value reached a value below its low-level threshold."
    ::= 129

upsAlarmValueHigh-eighth TRAP-TYPE
    ENTERPRISE geUPSTraps-eighth
    VARIABLES  { trapArg  }
    DESCRIPTION
            "A measurement value reached a value higher than its high-level threshold."
    ::= 130

upsAlarmValueLowRestored-eighth TRAP-TYPE
    ENTERPRISE geUPSTraps-eighth
    VARIABLES  { trapArg  }
    DESCRIPTION
            "A ValueLow alarm condition is restored."
    ::= 133

upsAlarmValueHighRestored-eighth TRAP-TYPE
    ENTERPRISE geUPSTraps-eighth
    VARIABLES  { trapArg }
    DESCRIPTION
            "A ValueHigh alarm condition is restored."
    ::= 134
























END
