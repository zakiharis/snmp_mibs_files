GE-SINGLEUPS DEFINITIONS ::= BEGIN

IMPORTS
        
       MODULE-IDENTITY, OBJECT-TYPE, NOTIFICATION-TYPE,
       OBJECT-IDENTITY, Counter32, Gauge32, Integer32,enterprises, IpAddress
       FROM SNMPv2-SMI
       DisplayString, TimeStamp, TimeInterval, TestAndIncr,
         AutonomousType, TEXTUAL-CONVENTION
           FROM SNMPv2-TC;		
              
PositiveInteger32 ::= TEXTUAL-CONVENTION
       DISPLAY-HINT "d"
       STATUS       current
       DESCRIPTION
               "This data type is a non-zero and non-negative value."
       SYNTAX       Integer32 (1..2147483647)

              
NonNegativeInteger32 ::= TEXTUAL-CONVENTION
       DISPLAY-HINT "d"
       STATUS       current
       DESCRIPTION
               "This data type is a non-negative value."
       SYNTAX       Integer32 (0..2147483647)

imv                     OBJECT IDENTIFIER ::=  { enterprises 818 }

geHardware             OBJECT IDENTIFIER ::=  { imv 1 }
geSoftware             OBJECT IDENTIFIER ::=  { imv 2 }
geAgent                OBJECT IDENTIFIER ::=  { imv 3 }

geUPS                  OBJECT IDENTIFIER ::=  { geHardware 1 }

-- The following list is not really a table, but can be implemented as one in the software.
-- The complete UPS section is simply too large to fit in a pre-defined table.
-- The solution: 
-- * All objects are defined for geGenericUPS
-- * All individual UPSs of parallel systems can be reached by their respective sequence
--   number as reflected in below list in stead of the geGenericUPS objects.

geGenericUPS           OBJECT IDENTIFIER ::=  { geUPS 10 }
                                              
-- Generic UPS --
                                              
upsIdent-gen                OBJECT IDENTIFIER ::=  { geGenericUPS 1 }
upsBattery-gen              OBJECT IDENTIFIER ::=  { geGenericUPS 2 }
upsInput-gen                OBJECT IDENTIFIER ::=  { geGenericUPS 3 }
upsOutput-gen               OBJECT IDENTIFIER ::=  { geGenericUPS 4 }
upsBypass-gen               OBJECT IDENTIFIER ::=  { geGenericUPS 5 }
upsAlarm-gen                OBJECT IDENTIFIER ::=  { geGenericUPS 6 }
upsWellKnownAlarms-gen      OBJECT IDENTIFIER ::=  { upsAlarm-gen 3 }
upsTest-gen                 OBJECT IDENTIFIER ::=  { geGenericUPS 7 }
upsWellKnownTests-gen       OBJECT IDENTIFIER ::=  { upsTest-gen 7 }
upsControl-gen              OBJECT IDENTIFIER ::=  { geGenericUPS 8 }
upsConfig-gen               OBJECT IDENTIFIER ::=  { geGenericUPS 9 }
upsGetSet-gen               OBJECT IDENTIFIER ::=  { geGenericUPS 10 }
geUPSTraps-gen             OBJECT IDENTIFIER ::=  { geGenericUPS 11 }


----
-- Environtmental card --
----

geEnvironmental        OBJECT IDENTIFIER ::=  { geHardware 2 }

ioInterface-First       OBJECT IDENTIFIER ::=  { geEnvironmental 1 }
ioInterface-Second      OBJECT IDENTIFIER ::=  { geEnvironmental 2 }
ioInterface-Third       OBJECT IDENTIFIER ::=  { geEnvironmental 3 }
ioInterface-Fourth      OBJECT IDENTIFIER ::=  { geEnvironmental 4 }
ioInterface-Fifth       OBJECT IDENTIFIER ::=  { geEnvironmental 5 }
ioInterface-Sixth       OBJECT IDENTIFIER ::=  { geEnvironmental 6 }
ioInterface-Seventh     OBJECT IDENTIFIER ::=  { geEnvironmental 7 }
ioInterface-Eighth      OBJECT IDENTIFIER ::=  { geEnvironmental 8 }

-- First Environmental card --

ioInterfaceInputLine-First     OBJECT IDENTIFIER ::=  { ioInterface-First 1 }
ioInterfaceOutputLine-First    OBJECT IDENTIFIER ::=  { ioInterface-First 2 }
ioInterfaceAnalogueLine-First  OBJECT IDENTIFIER ::=  { ioInterface-First 3 }
ioInterfaceTraps-First         OBJECT IDENTIFIER ::=  { ioInterface-First 4 }

-- Second Environmental card --

ioInterfaceInputLine-Second     OBJECT IDENTIFIER ::=  { ioInterface-Second 1 }
ioInterfaceOutputLine-Second    OBJECT IDENTIFIER ::=  { ioInterface-Second 2 }
ioInterfaceAnalogueLine-Second  OBJECT IDENTIFIER ::=  { ioInterface-Second 3 }
ioInterfaceTraps-Second         OBJECT IDENTIFIER ::=  { ioInterface-Second 4 }

-- Third Environmental card --

ioInterfaceInputLine-Third     OBJECT IDENTIFIER ::=  { ioInterface-Third 1 }
ioInterfaceOutputLine-Third    OBJECT IDENTIFIER ::=  { ioInterface-Third 2 }
ioInterfaceAnalogueLine-Third  OBJECT IDENTIFIER ::=  { ioInterface-Third 3 }
ioInterfaceTraps-Third         OBJECT IDENTIFIER ::=  { ioInterface-Third 4 }

-- Fourth Environmental card --

ioInterfaceInputLine-Fourth     OBJECT IDENTIFIER ::=  { ioInterface-Fourth 1 }
ioInterfaceOutputLine-Fourth    OBJECT IDENTIFIER ::=  { ioInterface-Fourth 2 }
ioInterfaceAnalogueLine-Fourth  OBJECT IDENTIFIER ::=  { ioInterface-Fourth 3 }
ioInterfaceTraps-Fourth         OBJECT IDENTIFIER ::=  { ioInterface-Fourth 4 }

-- Fifth Environmental card --

ioInterfaceInputLine-Fifth     OBJECT IDENTIFIER ::=  { ioInterface-Fifth 1 }
ioInterfaceOutputLine-Fifth    OBJECT IDENTIFIER ::=  { ioInterface-Fifth 2 }
ioInterfaceAnalogueLine-Fifth  OBJECT IDENTIFIER ::=  { ioInterface-Fifth 3 }
ioInterfaceTraps-Fifth         OBJECT IDENTIFIER ::=  { ioInterface-Fifth 4 }

-- Sixth Environmental card --

ioInterfaceInputLine-Sixth     OBJECT IDENTIFIER ::=  { ioInterface-Sixth 1 }
ioInterfaceOutputLine-Sixth    OBJECT IDENTIFIER ::=  { ioInterface-Sixth 2 }
ioInterfaceAnalogueLine-Sixth  OBJECT IDENTIFIER ::=  { ioInterface-Sixth 3 }
ioInterfaceTraps-Sixth         OBJECT IDENTIFIER ::=  { ioInterface-Sixth 4 }

-- Seventh Environmental card --

ioInterfaceInputLine-Seventh     OBJECT IDENTIFIER ::=  { ioInterface-Seventh 1 }
ioInterfaceOutputLine-Seventh    OBJECT IDENTIFIER ::=  { ioInterface-Seventh 2 }
ioInterfaceAnalogueLine-Seventh  OBJECT IDENTIFIER ::=  { ioInterface-Seventh 3 }
ioInterfaceTraps-Seventh         OBJECT IDENTIFIER ::=  { ioInterface-Seventh 4 }

-- Eighth Environmental card --

ioInterfaceInputLine-Eighth     OBJECT IDENTIFIER ::=  { ioInterface-Eighth 1 }
ioInterfaceOutputLine-Eighth    OBJECT IDENTIFIER ::=  { ioInterface-Eighth 2 }
ioInterfaceAnalogueLine-Eighth  OBJECT IDENTIFIER ::=  { ioInterface-Eighth 3 }
ioInterfaceTraps-Eighth         OBJECT IDENTIFIER ::=  { ioInterface-Eighth 4 }

--
-- Modem --
--

geModem                OBJECT IDENTIFIER ::=  { geHardware 3 }

--
-- Device --
--

geDevices              OBJECT IDENTIFIER ::=  { geHardware 100 }
geDevicesDescriptions  OBJECT IDENTIFIER ::=  { geDevices 1 }

advSNMPWebIntCard       OBJECT IDENTIFIER ::=  { geDevicesDescriptions 1 }
snmpWebIntCard          OBJECT IDENTIFIER ::=  { geDevicesDescriptions 2 }
snmpWebIntBox           OBJECT IDENTIFIER ::=  { geDevicesDescriptions 3 }
snmpSWPFAgent           OBJECT IDENTIFIER ::=  { geDevicesDescriptions 4 }
snmpSWJUMPAgent         OBJECT IDENTIFIER ::=  { geDevicesDescriptions 5 }

--
-- Client --
--

geClient               OBJECT IDENTIFIER ::=  { geSoftware 1 }
          
--
-- Agent --
--
          
geAgentConfig          OBJECT IDENTIFIER ::=  { geAgent 1 }
geAgentTraps           OBJECT IDENTIFIER ::=  { geAgent 2 }

--
-- The GE UPS group
--

geDiscoveredUPSsMask OBJECT-TYPE
    SYNTAX     Integer32
    MAX-ACCESS read-only
    STATUS     current
    DESCRIPTION
            "Reading this variable returns bit mask indicating which 
            UPSs in a parallel system are alive. Management 
            software should poll only these UPSs on their snmp
            branches 11-18 as follows:

              1  FirstUPS alive
              2  SecondUPS alive
              4  ThirdUPS alive
              8  FourthUPS alive
             16  FifthUPS alive
             32  SixthUPS alive
             64  SeventhUPS alive
            128  EigthUPS alive

            Since the management software should always monitor
            the GenericUPS branch (10), this value has no meaning 
            for single upses (which provide values on that snmp 
            branch), and should be set to zero in that case."
    ::= { geUPS 1 }

geRequestPacket OBJECT-TYPE
    SYNTAX     DisplayString (SIZE (0..63))
    MAX-ACCESS read-write 
    STATUS     current
    DESCRIPTION
            "Put the string, formatted as a IMV/CP4 packet, directly to internally RS485 bus. 
	This OID could be used for accede directly to the internally RS485 bus from a remote place."
    ::= { geUPS 2 }

geReplyPacket OBJECT-TYPE
    SYNTAX     DisplayString (SIZE (0..63))
    MAX-ACCESS read-only
    STATUS     current
    DESCRIPTION
            "Contain the reply of the IMV/CP4 request packet sent using the OID geRequestPacket. 
	Every time that a write command has be made at the OID ge RequestPacket, the value of this OID is erased."
    ::= { geUPS 3 }



--
-- The Device Identification group. Generic
--      All objects in this group except for upsIdentName and
--      upsIdentAttachedDevices are set at device initialization
--      and remain static.
--

upsIdentManufacturer-gen OBJECT-TYPE
    SYNTAX     DisplayString (SIZE (0..31))
    MAX-ACCESS read-only
    STATUS     current
    DESCRIPTION
            "The name of the UPS manufacturer.(*)"
    ::= { upsIdent-gen 1 }

upsIdentModel-gen OBJECT-TYPE
    SYNTAX     DisplayString (SIZE (0..63))
    MAX-ACCESS read-only
    STATUS     current
    DESCRIPTION
            "The UPS Model designation.(*)"
    ::= { upsIdent-gen 2 }

upsIdentUPSSoftwareVersion-gen OBJECT-TYPE
    SYNTAX     DisplayString (SIZE (0..63))
    MAX-ACCESS read-only
    STATUS     current
    DESCRIPTION
            "The UPS firmware/software version(s).  This variable
            may or may not have the same value as
            upsIdentAgentSoftwareVersion in some implementations.(*)"
    ::= { upsIdent-gen 3 }

upsIdentAgentSoftwareVersion-gen OBJECT-TYPE
    SYNTAX     DisplayString (SIZE (0..63))
    MAX-ACCESS read-only
    STATUS     current
    DESCRIPTION
            "The UPS agent software version.  This variable may or
            may not have the same value as
            upsIdentUPSSoftwareVersion in some implementations.(*)"
    ::= { upsIdent-gen 4 }

upsIdentName-gen OBJECT-TYPE
    SYNTAX     DisplayString (SIZE(0..63))
    MAX-ACCESS read-write
    STATUS     current
    DESCRIPTION
            "A string identifying the UPS.  This object should be
            set by the administrator.(*)"
    ::= { upsIdent-gen 5 }

upsIdentAttachedDevices-gen OBJECT-TYPE
    SYNTAX     DisplayString (SIZE(0..63))
    MAX-ACCESS read-write
    STATUS     current
    DESCRIPTION
            "A string identifying the devices attached to the
            output(s) of the UPS.  This object should be set by
            the administrator.(*)"
    ::= { upsIdent-gen 6 }

upsIdentUPSSerialNumber-gen OBJECT-TYPE
    SYNTAX     DisplayString (SIZE(0..31))
    MAX-ACCESS read-only
    STATUS     current
    DESCRIPTION
            "The UPS serial number"
    ::= { upsIdent-gen 7 }
				
upsIdentComProtVersion-gen OBJECT-TYPE
    SYNTAX     DisplayString (SIZE(0..15))
    MAX-ACCESS read-only
    STATUS     current
    DESCRIPTION
            "The IMV communication protocol version"
    ::= { upsIdent-gen 8 }	
		
upsIdentOperatingTime-gen OBJECT-TYPE
    SYNTAX     NonNegativeInteger32
    UNITS      "seconds"
    MAX-ACCESS read-only
    STATUS     current
    DESCRIPTION
            "The present value of the operating time.
             total 'on' time since UPS manufactured"
    ::= { upsIdent-gen 9 }	
				
--
-- Battery Group Generic
--

upsBatteryStatus-gen OBJECT-TYPE
    SYNTAX     Integer32 {
        unknown(1),
        batteryNormal(2),
        batteryLow(3),
        batteryDepleted(4)
    }
    MAX-ACCESS read-only
    STATUS     current
    DESCRIPTION
            "The indication of the capacity remaining in the UPS
            system's batteries.   A value of batteryNormal
            indicates that the remaining run-time is greater than
            upsConfigLowBattTime.  A value of batteryLow indicates
            that the remaining battery run-time is less than or
            equal to upsConfigLowBattTime.  A value of
            batteryDepleted indicates that the UPS will be unable
            to sustain the present load when and if the utility
            power is lost (including the possibility that the
            utility power is currently absent and the UPS is
            unable to sustain the output).(*)"
    ::= { upsBattery-gen 1 }

upsSecondsOnBattery-gen OBJECT-TYPE
    SYNTAX     NonNegativeInteger32
    UNITS      "seconds"
    MAX-ACCESS read-only
    STATUS     current
    DESCRIPTION
            "If the unit is on battery power, the elapsed time
            since the UPS last switched to battery power, or the
            time since the network management subsystem was last
            restarted, whichever is less.  Zero shall be returned
            if the unit is not on battery power.(*)"
    ::= { upsBattery-gen 2 }

upsEstimatedMinutesRemaining-gen OBJECT-TYPE
    SYNTAX     PositiveInteger32
    UNITS      "minutes"
    MAX-ACCESS read-only
    STATUS     current
    DESCRIPTION
            "An estimate of the time to battery charge depletion
            under the present load conditions if the utility power
            is off and remains off, or if it were to be lost and
            remain off.(*)"
    ::= { upsBattery-gen 3 }

upsEstimatedChargeRemaining-gen OBJECT-TYPE
    SYNTAX     Integer32 (0..100)
    UNITS      "percent"
    MAX-ACCESS read-only
    STATUS     current
    DESCRIPTION
            "An estimate of the battery charge remaining expressed
            as a percent of full charge.(*)"
    ::= { upsBattery-gen 4 }

upsBatteryVoltage-gen OBJECT-TYPE
    SYNTAX     NonNegativeInteger32
    UNITS      "0.1 Volt DC"
    MAX-ACCESS read-only
    STATUS     current
    DESCRIPTION
            "The magnitude of the present battery voltage.(*)"
    ::= { upsBattery-gen 5 }

upsBatteryCurrent-gen OBJECT-TYPE
    SYNTAX     Integer32
    UNITS      "0.1 Amp DC"
    MAX-ACCESS read-only
    STATUS     current
    DESCRIPTION
            "The present battery current.(*)"
    ::= { upsBattery-gen 6 }

upsBatteryTemperature-gen OBJECT-TYPE
    SYNTAX     Integer32
    UNITS      "degrees Centigrade"
    MAX-ACCESS read-only
    STATUS     current
    DESCRIPTION
            "The ambient temperature at or near the UPS Battery
            casing.(*)"
    ::= { upsBattery-gen 7 }

--
-- Input Group
--

upsInputLineBads-gen OBJECT-TYPE
    SYNTAX     Counter32
    MAX-ACCESS read-only
    STATUS     current
    DESCRIPTION
            "A count of the number of times the input entered an
            out-of-tolerance condition as defined by the
            manufacturer.  This count is incremented by one each
            time the input transitions from zero out-of-tolerance
            lines to one or more input lines out-of-tolerance.(*)"
    ::= { upsInput-gen 1 }

upsInputNumLines-gen OBJECT-TYPE
    SYNTAX     NonNegativeInteger32
    MAX-ACCESS read-only
    STATUS     current
    DESCRIPTION
            "The number of input lines utilized in this device.
            This variable indicates the number of rows in the
            input table.(*)"
    ::= { upsInput-gen 2 }

upsInputTable-gen OBJECT-TYPE
    SYNTAX     SEQUENCE OF UpsInputEntry-gen
    MAX-ACCESS not-accessible
    STATUS     current
    DESCRIPTION
            "A list of input table entries.  The number of entries
            is given by the value of upsInputNumLines.(*)"
    ::= { upsInput-gen 3 }

upsInputEntry-gen OBJECT-TYPE
    SYNTAX     UpsInputEntry-gen
    MAX-ACCESS not-accessible
    STATUS     current
    DESCRIPTION
            "An entry containing information applicable to a
            particular input line.(*)"
    INDEX { upsInputLineIndex-gen }
    ::= { upsInputTable-gen 1 }

UpsInputEntry-gen ::= SEQUENCE {
    upsInputLineIndex-gen   PositiveInteger32,
    upsInputFrequency-gen   NonNegativeInteger32,
    upsInputVoltage-gen     NonNegativeInteger32,
    upsInputCurrent-gen     NonNegativeInteger32,
    upsInputTruePower-gen   NonNegativeInteger32,
    upsInputVoltageMin-gen  NonNegativeInteger32,
    upsInputVoltageMax-gen  NonNegativeInteger32
}

upsInputLineIndex-gen OBJECT-TYPE
    SYNTAX     PositiveInteger32
    MAX-ACCESS not-accessible
    STATUS     current
    DESCRIPTION
            "The input line identifier.(*)"
    ::= { upsInputEntry-gen 1 }

upsInputFrequency-gen OBJECT-TYPE
    SYNTAX     NonNegativeInteger32
    UNITS      "0.1 Hertz"
    MAX-ACCESS read-only
    STATUS     current
    DESCRIPTION
            "The present input frequency.(*)"
    ::= { upsInputEntry-gen 2 }

upsInputVoltage-gen OBJECT-TYPE
    SYNTAX     NonNegativeInteger32
    UNITS      "RMS Volts"
    MAX-ACCESS read-only
    STATUS     current
    DESCRIPTION
            "The magnitude of the present input voltage.(*)"
    ::= { upsInputEntry-gen 3 }

upsInputCurrent-gen OBJECT-TYPE
    SYNTAX     NonNegativeInteger32
    UNITS      "0.1 RMS Amp"
    MAX-ACCESS read-only
    STATUS     current
    DESCRIPTION
            "The magnitude of the present input current.(*)"
    ::= { upsInputEntry-gen 4 }

upsInputTruePower-gen OBJECT-TYPE
    SYNTAX     NonNegativeInteger32
    UNITS      "Watts"
    MAX-ACCESS read-only
    STATUS     current
    DESCRIPTION
            "The magnitude of the present input true power.(*)"
    ::= { upsInputEntry-gen 5 }

upsInputVoltageMin-gen OBJECT-TYPE
    SYNTAX     NonNegativeInteger32
    UNITS      "RMS Volts"
    MAX-ACCESS read-only
    STATUS     current
    DESCRIPTION
            "The lowest magnitude of the input voltage since last read out."
    ::= { upsInputEntry-gen 6 }

upsInputVoltageMax-gen OBJECT-TYPE
    SYNTAX     NonNegativeInteger32
    UNITS      "RMS Volts"
    MAX-ACCESS read-only
    STATUS     current
    DESCRIPTION
            "The highest magnitude of the input voltage since last read out."
    ::= { upsInputEntry-gen 7 }

--
-- The Output group.
--

upsOutputSource-gen OBJECT-TYPE
    SYNTAX     Integer32 {
        other(1),
        none(2),
        normal(3),
        bypass(4),
        battery(5),
        booster(6),
        reducer(7)
    }
    MAX-ACCESS read-only
    STATUS     current
    DESCRIPTION
            "The present source of output power.  The enumeration
            none(2) indicates that there is no source of output
            power (and therefore no output power), for example,
            the system has opened the output breaker.(*)"
    ::= { upsOutput-gen 1 }

upsOutputFrequency-gen OBJECT-TYPE
    SYNTAX     NonNegativeInteger32
    UNITS      "0.1 Hertz"
    MAX-ACCESS read-only
    STATUS     current
    DESCRIPTION
            "The present output frequency.(*)"
    ::= { upsOutput-gen 2 }

upsOutputNumLines-gen OBJECT-TYPE
    SYNTAX     NonNegativeInteger32
    MAX-ACCESS read-only
    STATUS     current
    DESCRIPTION
            "The number of output lines utilized in this device.
            This variable indicates the number of rows in the
            output table.(*)"
    ::= { upsOutput-gen 3 }

upsOutputTable-gen OBJECT-TYPE
    SYNTAX     SEQUENCE OF UpsOutputEntry-gen
    MAX-ACCESS not-accessible
    STATUS     current
    DESCRIPTION
            "A list of output table entries.  The number of
            entries is given by the value of upsOutputNumLines.(*)"
    ::= { upsOutput-gen 4 }

upsOutputEntry-gen OBJECT-TYPE
    SYNTAX     UpsOutputEntry-gen
    MAX-ACCESS not-accessible
    STATUS     current
    DESCRIPTION
            "An entry containing information applicable to a
            particular output line.(*)"
    INDEX { upsOutputLineIndex-gen }
    ::= { upsOutputTable-gen 1 }

UpsOutputEntry-gen ::= SEQUENCE {
    upsOutputLineIndex-gen   PositiveInteger32,
    upsOutputVoltage-gen     NonNegativeInteger32,
    upsOutputCurrent-gen     NonNegativeInteger32,
    upsOutputPower-gen       NonNegativeInteger32,
    upsOutputPercentLoad-gen Integer32
}

upsOutputLineIndex-gen OBJECT-TYPE
    SYNTAX     PositiveInteger32
    MAX-ACCESS not-accessible
    STATUS     current
    DESCRIPTION
            "The output line identifier.(*)"
    ::= { upsOutputEntry-gen 1 }

upsOutputVoltage-gen OBJECT-TYPE
    SYNTAX     NonNegativeInteger32
    UNITS      "RMS Volts"
    MAX-ACCESS read-only
    STATUS     current
    DESCRIPTION
            "The present output voltage.(*)"
    ::= { upsOutputEntry-gen 2 }

upsOutputCurrent-gen OBJECT-TYPE
    SYNTAX     NonNegativeInteger32
    UNITS      "0.1 RMS Amp"
    MAX-ACCESS read-only
    STATUS     current
    DESCRIPTION
            "The present output current.(*)"
    ::= { upsOutputEntry-gen 3 }

upsOutputPower-gen OBJECT-TYPE
    SYNTAX     NonNegativeInteger32
    UNITS      "Watts"
    MAX-ACCESS read-only
    STATUS     current
    DESCRIPTION
            "The present output true power.(*)"
    ::= { upsOutputEntry-gen 4 }

upsOutputPercentLoad-gen OBJECT-TYPE
    SYNTAX     Integer32 (0..200)
    UNITS      "percent"
    MAX-ACCESS read-only
    STATUS     current
    DESCRIPTION
            "The percentage of the UPS power capacity presently
            being used on this output line, i.e., the greater of
            the percent load of true power capacity and the
            percent load of VA.(*)"
    ::= { upsOutputEntry-gen 5 }

--
-- The Bypass group generic.
--

upsBypassFrequency-gen OBJECT-TYPE
    SYNTAX     NonNegativeInteger32
    UNITS      "0.1 Hertz"
    MAX-ACCESS read-only
    STATUS     current
    DESCRIPTION
            "The present bypass frequency.(*)"
    ::= { upsBypass-gen 1 }

upsBypassNumLines-gen OBJECT-TYPE
    SYNTAX     NonNegativeInteger32
    MAX-ACCESS read-only
    STATUS     current
    DESCRIPTION
            "The number of bypass lines utilized in this device.
            This entry indicates the number of rows in the bypass
            table.(*)"
    ::= { upsBypass-gen 2 }

upsBypassTable-gen OBJECT-TYPE
    SYNTAX     SEQUENCE OF UpsBypassEntry-gen
    MAX-ACCESS not-accessible
    STATUS     current
    DESCRIPTION
            "A list of bypass table entries.  The number of
            entries is given by the value of upsBypassNumLines.(*)"
    ::= { upsBypass-gen 3 }

upsBypassEntry-gen OBJECT-TYPE
    SYNTAX     UpsBypassEntry-gen
    MAX-ACCESS not-accessible
    STATUS     current
    DESCRIPTION
            "An entry containing information applicable to a
            particular bypass input.(*)"
    INDEX { upsBypassLineIndex-gen }
    ::= { upsBypassTable-gen 1 }

UpsBypassEntry-gen ::= SEQUENCE {
    upsBypassLineIndex-gen  PositiveInteger32,
    upsBypassVoltage-gen    NonNegativeInteger32,
    upsBypassCurrent-gen    NonNegativeInteger32,
    upsBypassPower-gen      NonNegativeInteger32
}

upsBypassLineIndex-gen OBJECT-TYPE
    SYNTAX     PositiveInteger32
    MAX-ACCESS not-accessible
    STATUS     current
    DESCRIPTION
            "The bypass line identifier.(*)"
    ::= { upsBypassEntry-gen 1 }

upsBypassVoltage-gen OBJECT-TYPE
    SYNTAX     NonNegativeInteger32
    UNITS      "RMS Volts"
    MAX-ACCESS read-only
    STATUS     current
    DESCRIPTION
            "The present bypass voltage.(*)"
    ::= { upsBypassEntry-gen 2 }

upsBypassCurrent-gen OBJECT-TYPE
    SYNTAX     NonNegativeInteger32
    UNITS      "0.1 RMS Amp"
    MAX-ACCESS read-only
    STATUS     current
    DESCRIPTION
            "The present bypass current.(*)"
    ::= { upsBypassEntry-gen 3 }

upsBypassPower-gen OBJECT-TYPE
    SYNTAX     NonNegativeInteger32
    UNITS      "Watts"
    MAX-ACCESS read-only
    STATUS     current
    DESCRIPTION
            "The present true power conveyed by the bypass.(*)"
    ::= { upsBypassEntry-gen 4 }

--
-- The Alarm group generic.
--

upsAlarmsPresent-gen OBJECT-TYPE
    SYNTAX     Gauge32
    MAX-ACCESS read-only
    STATUS     current
    DESCRIPTION
            "The present number of active alarm conditions.(*)"
    ::= { upsAlarm-gen 1 }

upsAlarmTable-gen OBJECT-TYPE
    SYNTAX     SEQUENCE OF UpsAlarmEntry-gen
    MAX-ACCESS not-accessible
    STATUS     current
    DESCRIPTION
            "A list of alarm table entries.  The table contains
            zero, one, or many rows at any moment, depending upon
            the number of alarm conditions in effect.  The table
            is initially empty at agent startup.  The agent
            creates a row in the table each time a condition is
            detected and deletes that row when that condition no
            longer pertains.  The agent creates the first row with
            upsAlarmId equal to 1, and increments the value of
            upsAlarmId each time a new row is created, wrapping to
            the first free value greater than or equal to 1 when
            the maximum value of upsAlarmId would otherwise be
            exceeded.  Consequently, after multiple operations,
            the table may become sparse, e.g., containing entries
            for rows 95, 100, 101, and 203 and the entries should
            not be assumed to be in chronological order because
            upsAlarmId might have wrapped.

            Alarms are named by an AutonomousType (OBJECT
            IDENTIFIER), upsAlarmDescr, to allow a single table to
            reflect well known alarms plus alarms defined by a
            particular implementation, i.e., as documented in the
            private enterprise MIB definition for the device.  No
            two rows will have the same value of upsAlarmDescr,
            since alarms define conditions.  In order to meet this
            requirement, care should be taken in the definition of
            alarm conditions to insure that a system cannot enter
            the same condition multiple times simultaneously.

            The number of rows in the table at any given time is
            reflected by the value of upsAlarmsPresent.(*)"
    ::= { upsAlarm-gen 2 }

upsAlarmEntry-gen OBJECT-TYPE
    SYNTAX     UpsAlarmEntry-gen
    MAX-ACCESS not-accessible
    STATUS     current
    DESCRIPTION
            "An entry containing information applicable to a
            particular alarm.(*)"
    INDEX { upsAlarmId-gen }
    ::= { upsAlarmTable-gen 1 }

UpsAlarmEntry-gen ::= SEQUENCE {
    upsAlarmId-gen          PositiveInteger32,
    upsAlarmDescr-gen       AutonomousType,
    upsAlarmTime-gen       TimeStamp
}

upsAlarmId-gen OBJECT-TYPE
    SYNTAX     PositiveInteger32
    MAX-ACCESS not-accessible
    STATUS     current
    DESCRIPTION
            "A unique identifier for an alarm condition.  This
            value must remain constant.(*)"
    ::= { upsAlarmEntry-gen 1 }

upsAlarmDescr-gen OBJECT-TYPE
    SYNTAX     AutonomousType
    MAX-ACCESS read-only
    STATUS     current
    DESCRIPTION
            "A reference to an alarm description object.  The
            object referenced should not be accessible, but rather
            be used to provide a unique description of the alarm
            condition.(*)"
    ::= { upsAlarmEntry-gen 2 }

upsAlarmTime-gen OBJECT-TYPE
    SYNTAX     TimeStamp
    MAX-ACCESS read-only
    STATUS     current
    DESCRIPTION
            "The value of sysUpTime when the alarm condition was
            detected.  If the alarm condition was detected at the
            time of agent startup and presumably existed before
            agent startup, the value of upsAlarmTime shall equal
            0.(*)"
    ::= { upsAlarmEntry-gen 3 }

--
-- Well known alarm conditions generic.
--

upsAlarmBatteryBad-gen OBJECT-IDENTITY
    STATUS     current
    DESCRIPTION
            "One or more batteries have been determined to require
            replacement.(*)"
    ::= { upsWellKnownAlarms-gen  1 }

upsAlarmOnBattery-gen OBJECT-IDENTITY
    STATUS     current
    DESCRIPTION
            "The UPS is drawing power from the batteries.(*)"
    ::= { upsWellKnownAlarms-gen  2 }

upsAlarmLowBattery-gen OBJECT-IDENTITY
    STATUS     current
    DESCRIPTION
            "The remaining battery run-time is less than or equal
            to upsConfigLowBattTime.(*)"
    ::= { upsWellKnownAlarms-gen  3 }

upsAlarmDepletedBattery-gen OBJECT-IDENTITY
    STATUS     current
    DESCRIPTION
            "The UPS will be unable to sustain the present load
            when and if the utility power is lost.(*)"
    ::= { upsWellKnownAlarms-gen  4 }

upsAlarmTempBad-gen OBJECT-IDENTITY
    STATUS     current
    DESCRIPTION
            "A temperature is out of tolerance.(*)"
    ::= { upsWellKnownAlarms-gen  5 }

upsAlarmInputBad-gen OBJECT-IDENTITY
    STATUS     current
    DESCRIPTION
            "An input condition is out of tolerance.(*)"
    ::= { upsWellKnownAlarms-gen  6 }

upsAlarmOutputBad-gen OBJECT-IDENTITY
    STATUS     current
    DESCRIPTION
            "An output condition (other than OutputOverload) is
            out of tolerance.(*)"
    ::= { upsWellKnownAlarms-gen  7 }

upsAlarmOutputOverload-gen OBJECT-IDENTITY
    STATUS     current
    DESCRIPTION
            "The output load exceeds the UPS output capacity.(*)"
    ::= { upsWellKnownAlarms-gen  8 }

upsAlarmOnBypass-gen OBJECT-IDENTITY
    STATUS     current
    DESCRIPTION
            "The Bypass is presently engaged on the UPS.(*)"
    ::= { upsWellKnownAlarms-gen  9 }

upsAlarmBypassBad-gen OBJECT-IDENTITY
    STATUS     current
    DESCRIPTION
            "The Bypass is out of tolerance.(*)"
    ::= { upsWellKnownAlarms-gen 10 }

upsAlarmOutputOffAsRequested-gen OBJECT-IDENTITY
    STATUS     current
    DESCRIPTION
            "The UPS has shutdown as requested, i.e., the output
            is off.(*)"
    ::= { upsWellKnownAlarms-gen 11 }

upsAlarmUpsOffAsRequested-gen OBJECT-IDENTITY
    STATUS     current
    DESCRIPTION
            "The entire UPS has shutdown as commanded.(*)"
    ::= { upsWellKnownAlarms-gen 12 }

upsAlarmChargerFailed-gen OBJECT-IDENTITY
    STATUS     current
    DESCRIPTION
            "An uncorrected problem has been detected within the
            UPS charger subsystem.(*)"
    ::= { upsWellKnownAlarms-gen 13 }

upsAlarmUpsOutputOff-gen OBJECT-IDENTITY
    STATUS     current
    DESCRIPTION
            "The output of the UPS is in the off state.(*)"
    ::= { upsWellKnownAlarms-gen 14 }

upsAlarmUpsSystemOff-gen OBJECT-IDENTITY
    STATUS     current
    DESCRIPTION
            "The UPS system is in the off state.(*)"
    ::= { upsWellKnownAlarms-gen 15 }

upsAlarmFanFailure-gen OBJECT-IDENTITY
    STATUS     current
    DESCRIPTION
            "The failure of one or more fans in the UPS has been
            detected.(*)"
    ::= { upsWellKnownAlarms-gen 16 }

upsAlarmFuseFailure-gen OBJECT-IDENTITY
    STATUS     current
    DESCRIPTION
            "The failure of one or more fuses has been detected.(*)"
    ::= { upsWellKnownAlarms-gen 17 }

upsAlarmGeneralFault-gen OBJECT-IDENTITY
    STATUS     current
    DESCRIPTION
            "A general fault in the UPS has been detected.(*)"
    ::= { upsWellKnownAlarms-gen 18 }

upsAlarmDiagnosticTestFailed-gen OBJECT-IDENTITY
    STATUS     current
    DESCRIPTION
            "The result of the last diagnostic test indicates a
            failure.(*)"
    ::= { upsWellKnownAlarms-gen 19 }

upsAlarmCommunicationsLost-gen OBJECT-IDENTITY
    STATUS     current
    DESCRIPTION
            "A problem has been encountered in the communications
            between the agent and the UPS.(*)"
    ::= { upsWellKnownAlarms-gen 20 }

upsAlarmAwaitingPower-gen OBJECT-IDENTITY
    STATUS     current
    DESCRIPTION
            "The UPS output is off and the UPS is awaiting the
            return of input power.(*)"
    ::= { upsWellKnownAlarms-gen 21 }

upsAlarmShutdownPending-gen OBJECT-IDENTITY
    STATUS     current
    DESCRIPTION
            "A upsShutdownAfterDelay countdown is underway.(*)"
    ::= { upsWellKnownAlarms-gen 22 }

upsAlarmShutdownImminent-gen OBJECT-IDENTITY
    STATUS     current
    DESCRIPTION
            "The UPS will turn off power to the load in less than
            5 seconds; this may be either a timed shutdown or a
            low battery shutdown.(*)"
    ::= { upsWellKnownAlarms-gen 23 }

upsAlarmTestInProgress-gen OBJECT-IDENTITY
    STATUS     current
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY.(*)"
    ::= { upsWellKnownAlarms-gen 24 }

upsAlarmReceptacleOff-gen OBJECT-IDENTITY
    STATUS     current
    DESCRIPTION
            "The receptacle are switch off    "
    ::= { upsWellKnownAlarms-gen 25 }

upsAlarmMaskA-gen OBJECT-TYPE
    SYNTAX     NonNegativeInteger32
    MAX-ACCESS read-only
    STATUS     current
    DESCRIPTION
            "Specifies which alarm can be handled by the UPS.
            The 'Mask' parameter is a Long Integer32. The meaning
            of every bit is the same as for the 'upsAlarmGroupA'
            command. A bit having value=1 indicates that the
            corresponding alarm is handled by the UPS."
    ::= { upsAlarm-gen 4 }

--
-- The Test Group generic
--

upsTestId-gen OBJECT-TYPE
    SYNTAX     OBJECT IDENTIFIER
    MAX-ACCESS read-write
    STATUS     current
    DESCRIPTION
            "The test is named by an OBJECT IDENTIFIER which
            allows a standard mechanism for the initiation of
            tests, including the well known tests identified in
            this document as well as those introduced by a
            particular implementation, i.e., as documented in the
            private enterprise MIB definition for the device.

            Setting this variable initiates the named test. Sets
            to this variable require the presence of
            upsTestSpinLock in the same SNMP message.

            The set request will be rejected with an appropriate
            error message if the requested test cannot be
            performed, including attempts to start a test when
            another test is already in progress.  The status of
            the current or last test is maintained in
            upsTestResultsSummary. Tests in progress may be
            aborted by setting the upsTestId variable to
            upsTestAbortTestInProgress.

            Read operations return the value of the name of the
            test in progress if a test is in progress or the name
            of the last test performed if no test is in progress,
            unless no test has been run, in which case the well
            known value upsTestNoTestsInitiated is returned.(*)"
    ::= { upsTest-gen 1 }

-- see [6] for more information on the semantics of objects with
-- syntax of TestAndIncr

upsTestSpinLock-gen OBJECT-TYPE
    SYNTAX     TestAndIncr
    MAX-ACCESS read-write
    STATUS     current
    DESCRIPTION
            "A spin lock on the test subsystem.  The spinlock is
            used as follows.

            Before starting a test, a manager-station should make
            sure that a test is not in progress as follows:

                try-again:
                  get (upsTestSpinLock)
                  while (upsTestResultsSummary == inProgress) {
                    /* loop while a test is running for another
            manager */
                    short delay
                    get (upsTestSpinLock)
                  }
                  lock-value = upsTestSpinLock
                  /* no test in progress, start the test */
                  set (upsTestSpinLock = lock-value, upsTestId =
            requested-test)
                  if (error-index == 1) { /* (upsTestSpinLock
            failed) */
                    /* if problem is not access control, then
                        some other manager slipped in ahead of us
            */
                    goto try-again
                  }
                  if (error-index == 2) { /* (upsTestId) */
                    /* cannot perform the test */
                    give up
                  }
                  /* test started ok */
                  /* wait for test completion by polling
            upsTestResultsSummary */
                  get (upsTestSpinLock, upsTestResultsSummary,
            upsTestResultsDetail)
                  while (upsTestResultsSummary == inProgress) {
                    short delay
                    get (upsTestSpinLock, upsTestResultsSummary,
            upsTestResultsDetail)
                  }
                  /* when test completes, retrieve any additional
            test results */
                  /* if upsTestSpinLock == lock-value + 1, then
            these are our test */
                  /* results (as opposed to another manager's */
                  The initial value of upsTestSpinLock at agent
            initialization shall
                  be 1.(*)"
    ::= { upsTest-gen 2 }

upsTestResultsSummary-gen OBJECT-TYPE
    SYNTAX     Integer32 {
        donePass(1),
        doneWarning(2),
        doneError(3),
        aborted(4),
        inProgress(5),
        noTestsInitiated(6)
    }
    MAX-ACCESS read-only
    STATUS     current
    DESCRIPTION
            "The results of the current or last UPS diagnostics
            test performed.  The values for donePass(1),
            doneWarning(2), and doneError(3) indicate that the
            test completed either successfully, with a warning, or
            with an error, respectively.  The value aborted(4) is
            returned for tests which are aborted by setting the
            value of upsTestId to upsTestAbortTestInProgress.
            Tests which have not yet concluded are indicated by
            inProgress(5).  The value noTestsInitiated(6)
            indicates that no previous test results are available,
            such as is the case when no tests have been run since
            the last reinitialization of the network management
            subsystem and the system has no provision for non-
            volatile storage of test results.(*)"
    ::= { upsTest-gen 3 }

upsTestResultsDetail-gen OBJECT-TYPE
    SYNTAX     DisplayString (SIZE (0..255))
    MAX-ACCESS read-only
    STATUS     current
    DESCRIPTION
            "Additional information about upsTestResultsSummary.
            If no additional information available, a zero length
            string is returned.(*)"
    ::= { upsTest-gen 4 }

upsTestStartTime-gen OBJECT-TYPE
    SYNTAX     TimeStamp
    MAX-ACCESS read-only
    STATUS     current
    DESCRIPTION
            "The value of sysUpTime at the time the test in
            progress was initiated, or, if no test is in progress,
            the time the previous test was initiated.  If the
            value of upsTestResultsSummary is noTestsInitiated(6),
            upsTestStartTime has the value 0.(*)"
    ::= { upsTest-gen 5 }

upsTestElapsedTime-gen OBJECT-TYPE
    SYNTAX     TimeInterval
    MAX-ACCESS read-only
    STATUS     current
    DESCRIPTION
            "The amount of time, in TimeTicks, since the test in
            progress was initiated, or, if no test is in progress,
            the previous test took to complete.  If the value of
            upsTestResultsSummary is noTestsInitiated(6),
            upsTestElapsedTime has the value 0.(*)"
    ::= { upsTest-gen 6 }

--
-- Well known tests generic.
--

upsTestNoTestsInitiated-gen OBJECT-IDENTITY
    STATUS     current
    DESCRIPTION
            "No tests have been initiated and no test is in
            progress.(*)"
    ::= { upsWellKnownTests-gen  1 }

upsTestAbortTestInProgress-gen OBJECT-IDENTITY
    STATUS     current
    DESCRIPTION
            "The test in progress is to be aborted / the test in
            progress was aborted.(*)"
    ::= { upsWellKnownTests-gen  2 }

upsTestGeneralSystemsTest-gen OBJECT-IDENTITY
    STATUS     current
    DESCRIPTION
            "The manufacturer's standard test of UPS device
            systems.(*)"
    ::= { upsWellKnownTests-gen  3 }

upsTestQuickBatteryTest-gen OBJECT-IDENTITY
    STATUS     current
    DESCRIPTION
            "A test that is sufficient to determine if the battery
            needs replacement.(*)"
    ::= { upsWellKnownTests-gen  4 }

upsTestDeepBatteryCalibration-gen OBJECT-IDENTITY
    STATUS     current
    DESCRIPTION
            "The system is placed on battery to a discharge level,
            set by the manufacturer, sufficient to determine
            battery replacement and battery run-time with a high
            degree of confidence.  WARNING:  this test will leave
            the battery in a low charge state and will require
            time for recharging to a level sufficient to provide
            normal battery duration for the protected load.(*)"
    ::= { upsWellKnownTests-gen  5 }

--
-- The Control group generic.
--

upsShutdownType-gen OBJECT-TYPE
    SYNTAX     Integer32 {
        output(1),
        system(2)
    }
    MAX-ACCESS read-write
    STATUS     current
    DESCRIPTION
            "This object determines the nature of the action to be
            taken at the time when the countdown of the
            upsShutdownAfterDelay and upsRebootWithDuration
            objects reaches zero.

            Setting this object to output(1) indicates that
            shutdown requests should cause only the output of the
            UPS to turn off.  Setting this object to system(2)
            indicates that shutdown requests will cause the entire
            UPS system to turn off.(*)"
    ::= { upsControl-gen 1 }

upsShutdownAfterDelay-gen OBJECT-TYPE
    SYNTAX     Integer32 (-1..2147483648)
    UNITS      "seconds"
    MAX-ACCESS read-write
    STATUS     current
    DESCRIPTION
            "Setting this object will shutdown (i.e., turn off)
            either the UPS output or the UPS system (as determined
            by the value of upsShutdownType at the time of
            shutdown) after the indicated number of seconds, or
            less if the UPS batteries become depleted. Setting
            this object to 0 will cause the shutdown to occur
            immediately.  Setting this object to -1 will abort the
            countdown.  If the system is already in the desired
            state at the time the countdown reaches 0, then
            nothing will happen.  That is, there is no additional
            action at that time if upsShutdownType = system and
            the system is already off.  Similarly, there is no
            additional action at that time if upsShutdownType =
            output and the output is already off.  When read,
            upsShutdownAfterDelay will return the number of
            seconds remaining until shutdown, or -1 if no shutdown
            countdown is in effect.  On some systems, if the agent
            is restarted while a shutdown countdown is in effect,
            the countdown may be aborted.  Sets to this object
            override any upsShutdownAfterDelay already in effect.(*)"
    ::= { upsControl-gen 2 }

upsStartupAfterDelay-gen OBJECT-TYPE
    SYNTAX     Integer32 (-1..2147483648)
    UNITS      "seconds"
    MAX-ACCESS read-write
    STATUS     current
    DESCRIPTION
            "Setting this object will start the output after the
            indicated number of seconds, including starting the
            UPS, if necessary.  Setting this object to 0 will
            cause the startup to occur immediately.  Setting this
            object to -1 will abort the countdown.  If the output
            is already on at the time the countdown reaches 0,
            then nothing will happen.  Sets to this object
            override the effect of any upsStartupAfterDelay
            countdown or upsRebootWithDuration countdown in
            progress.  When read, upsStartupAfterDelay will return
            the number of seconds until startup, or -1 if no
            startup countdown is in effect.  If the countdown
            expires during a utility failure, the startup shall
            not occur until the utility power is restored.  On
            some systems, if the agent is restarted while a
            startup countdown is in effect, the countdown is
            aborted.(*)"
    ::= { upsControl-gen 3 }

upsRebootWithDuration-gen OBJECT-TYPE
    SYNTAX     Integer32 (-1..300)
    UNITS      "seconds"
    MAX-ACCESS read-write
    STATUS     current
    DESCRIPTION
            "Setting this object will immediately shutdown (i.e.,
            turn off) either the UPS output or the UPS system (as
            determined by the value of upsShutdownType at the time
            of shutdown) for a period equal to the indicated
            number of seconds, after which time the output will be
            started, including starting the UPS, if necessary.  If
            the number of seconds required to perform the request
            is greater than the requested duration, then the
            requested shutdown and startup cycle shall be
            performed in the minimum time possible, but in no case
            shall this require more than the requested duration
            plus 60 seconds.  When read, upsRebootWithDuration
            shall return the number of seconds remaining in the
            countdown, or -1 if no countdown is in progress.  If
            the startup should occur during a utility failure, the
            startup shall not occur until the utility power is
            restored.(*)"
    ::= { upsControl-gen 4 }

upsAutoRestart-gen OBJECT-TYPE
    SYNTAX     Integer32 {
        on(1),
        off(2)
    }
    MAX-ACCESS read-write
    STATUS     current
    DESCRIPTION
            "Setting this object to 'on' will cause the UPS system
            to restart after a shutdown if the shutdown occurred
            during a power loss as a result of either a
            upsShutdownAfterDelay or an internal battery depleted
            condition.  Setting this object to 'off' will prevent
            the UPS system from restarting after a shutdown until
            an operator manually or remotely explicitly restarts
            it.  If the UPS is in a startup or reboot countdown,
            then the UPS will not restart until that delay has
            been satisfied.(*)"
    ::= { upsControl-gen 5 }

upsReceptaclesNum-gen OBJECT-TYPE
    SYNTAX     NonNegativeInteger32
    MAX-ACCESS read-only
    STATUS     current
    DESCRIPTION
            "The number of receptacles utilized in this device.
            This entry indicates the number of rows in the receptacle
            table."
    ::= { upsControl-gen 6 }

upsReceptacleTable-gen OBJECT-TYPE
    SYNTAX     SEQUENCE OF UpsReceptacleEntry-gen
    MAX-ACCESS not-accessible
    STATUS     current
    DESCRIPTION
            "A list of receptacle table entries.  The number of
            entries is given by the value of upsReceptacleNum."
    ::= { upsControl-gen 7 }

upsReceptacleEntry-gen OBJECT-TYPE
    SYNTAX     UpsReceptacleEntry-gen
    MAX-ACCESS not-accessible
    STATUS     current
    DESCRIPTION
            "An entry containing information applicable to a
            particular receptacle."
    INDEX { upsReceptacleLineIndex-gen }
    ::= { upsReceptacleTable-gen 1 }

UpsReceptacleEntry-gen ::= SEQUENCE {
    upsReceptacleLineIndex-gen  PositiveInteger32,
    upsReceptacleOnOff-gen      Integer32    
}

upsReceptacleLineIndex-gen OBJECT-TYPE
    SYNTAX     PositiveInteger32
    MAX-ACCESS not-accessible
    STATUS     current
    DESCRIPTION
            "The receptacle line identifier."
    ::= { upsReceptacleEntry-gen 1 }

upsReceptacleOnOff-gen OBJECT-TYPE
    SYNTAX     Integer32 {
        on(1),
        off(2)
    }
    MAX-ACCESS read-write
    STATUS     current
    DESCRIPTION
            "The present state of the receptacle. Setting this 
             object to 'on' will cause the receptacle to be turned
             on. Setting this object to 'off' will turn the
             receptacle off. If the receptacle is already in the
             desired state nothing will happen. After an
             autorestart (see upsAutoRestart) the receptacle will
             be on."
    ::= { upsReceptacleEntry-gen 2 }

upsUPSMode-gen OBJECT-TYPE
    SYNTAX     Integer32 {
        off-line(1),
        on-line(2),
        ecomode(3)
    }
    MAX-ACCESS read-write
    STATUS     current
    DESCRIPTION
            "The operation mode off the UPS. Off-line indicates a
            mode in which the input power is transferred to the
            output directly or via a step-up or step-down
            transformer. On-line mode indicates a mode in which 
            the output power is regenerated through some convertor.
            the operating mode of the UPS may be fixed, or may be
            selectable (e.g. an on-line UPS with ecomode)"
    ::= { upsControl-gen 8 }

upsRectifierOnOff-gen OBJECT-TYPE
    SYNTAX     Integer32 {
        on(1),
        off(2)
    }
    MAX-ACCESS read-write
    STATUS     current
    DESCRIPTION
            "The present state of the rectifier. Setting this 
             object to 'on' will cause the rectifier to be turned
             on. Setting this object to 'off' will turn the
             rectifier off. If the rectifier is already in the
             desired state nothing will happen. "
    ::= { upsControl-gen 9 }

upsBatteryChargeMethod-gen OBJECT-TYPE
    SYNTAX     Integer32 {
        normal-charge(1),
        boost-charge(2)
    }
    MAX-ACCESS read-write
    STATUS     current
    DESCRIPTION
            "The present state of the charge method. Setting this 
             object to 'Normal charge' will cause the battery to be 
             charged using the normal method. Setting this object to 
             'Boost charge' will charge the battery in boost mode. 
             If the charge method is already in the desired state 
             nothing will happen. "
    ::= { upsControl-gen 10 }

upsInverterOnOff-gen OBJECT-TYPE
    SYNTAX     Integer32 {
        on(1),
        off(2)
    }
    MAX-ACCESS read-write
    STATUS     current
    DESCRIPTION
            "The present state of the inverter. Setting this 
             object to 'on' will cause the inverter to be turned
             on. Setting this object to 'off' will turn the
             inverter off. If the inverter is already in the
             desired state nothing will happen. "
    ::= { upsControl-gen 11 }

upsBypassOnOff-gen OBJECT-TYPE
    SYNTAX     Integer32 {
        on(1),
        off(2)
    }
    MAX-ACCESS read-write
    STATUS     current
    DESCRIPTION
            "The present state of the bypass. Setting this 
             object to 'on' will cause the bypass to be activated.
             Setting this object to 'off' will deactivate the
             bypass. If the UPS is already in the
             desired state nothing will happen. "
    ::= { upsControl-gen 12 }

upsLoadSource-gen OBJECT-TYPE
    SYNTAX     Integer32 {
        on-bypass(1),
        on-Inverter(2),
        on-Detour(3),
        load-Off(4),
        other (5)
    }
    MAX-ACCESS read-write
    STATUS     current
    DESCRIPTION
            "The present source of the load. Setting this 
             object to 'On bypass' will cause the load to be 
             supplied by the bypass.
             Setting this object to 'On inverter' will cause the 
             load to be supplied by the inverter.
             If the load is already supplied by the desired 
             source nothing will happen. "
    ::= { upsControl-gen 13 }
	
--
-- The Configuration group generic.
--

upsConfigInputVoltage-gen OBJECT-TYPE
    SYNTAX     NonNegativeInteger32
    UNITS      "RMS Volts"
    MAX-ACCESS read-write
    STATUS     current
    DESCRIPTION
            "The magnitude of the nominal input voltage.  On those
            systems which support read-write access to this
            object, if there is an attempt to set this variable to
            a value that is not supported, the request must be
            rejected and the agent shall respond with an
            appropriate error message, i.e., badValue for SNMPv1,
            or inconsistentValue for SNMPv2.(*)"
    ::= { upsConfig-gen 1 }

upsConfigInputFreq-gen OBJECT-TYPE
    SYNTAX     NonNegativeInteger32
    UNITS      "0.1 Hertz"
    MAX-ACCESS read-write
    STATUS     current
    DESCRIPTION
            "The nominal input frequency.  On those systems which
            support read-write access to this object, if there is
            an attempt to set this variable to a value that is not
            supported, the request must be rejected and the agent
            shall respond with an appropriate error message, i.e.,
            badValue for SNMPv1, or inconsistentValue for SNMPv2.(*)"
    ::= { upsConfig-gen 2 }

upsConfigOutputVoltage-gen OBJECT-TYPE
    SYNTAX     NonNegativeInteger32
    UNITS      "RMS Volts"
    MAX-ACCESS read-write
    STATUS     current
    DESCRIPTION
            "The magnitude of the nominal output voltage.  On
            those systems which support read-write access to this
            object, if there is an attempt to set this variable to
            a value that is not supported, the request must be
            rejected and the agent shall respond with an
            appropriate error message, i.e., badValue for SNMPv1,
            or inconsistentValue for SNMPv2.(*)"
    ::= { upsConfig-gen 3 }

upsConfigOutputFreq-gen OBJECT-TYPE
    SYNTAX     NonNegativeInteger32
    UNITS      "0.1 Hertz"
    MAX-ACCESS read-write
    STATUS     current
    DESCRIPTION
            "The nominal output frequency.  On those systems which
            support read-write access to this object, if there is
            an attempt to set this variable to a value that is not
            supported, the request must be rejected and the agent
            shall respond with an appropriate error message, i.e.,
            badValue for SNMPv1, or inconsistentValue for SNMPv2.(*)"
    ::= { upsConfig-gen 4 }

upsConfigOutputVA-gen OBJECT-TYPE
    SYNTAX     NonNegativeInteger32
    UNITS      "Volt-Amps"
    MAX-ACCESS read-only
    STATUS     current
    DESCRIPTION
            "The magnitude of the nominal Volt-Amp rating.(*)"
    ::= { upsConfig-gen 5 }

upsConfigOutputPower-gen OBJECT-TYPE
    SYNTAX     NonNegativeInteger32
    UNITS      "Watts"
    MAX-ACCESS read-only
    STATUS     current
    DESCRIPTION
            "The magnitude of the nominal true power rating.(*)"
    ::= { upsConfig-gen 6 }

upsConfigLowBattTime-gen OBJECT-TYPE
    SYNTAX     NonNegativeInteger32
    UNITS      "minutes"
    MAX-ACCESS read-write
    STATUS     current
    DESCRIPTION
            "The value of upsEstimatedMinutesRemaining at which a
            lowBattery condition is declared.  For agents which
            support only discrete (discontinuous) values, then the
            agent shall round up to the next supported value.  If
            the requested value is larger than the largest
            supported value, then the largest supported value
            shall be selected.(*)"
    ::= { upsConfig-gen 7 }

upsConfigAudibleStatus-gen OBJECT-TYPE
    SYNTAX     Integer32 {
        disabled(1),
        enabled(2),
        muted(3)
    }
    MAX-ACCESS read-write
    STATUS     current
    DESCRIPTION
            "The requested state of the audible alarm.  When in
            the disabled state, the audible alarm should never
            sound.  The enabled state is self-describing.  Setting
            this object to muted(3) when the audible alarm is
            sounding shall temporarily silence the alarm.  It will
            remain muted until it would normally stop sounding and
            the value returned for read operations during this
            period shall equal muted(3).  At the end of this
            period, the value shall revert to enabled(2).  Writes
            of the value muted(3) when the audible alarm is not
            sounding shall be accepted but otherwise shall have no
            effect.(*)"
    ::= { upsConfig-gen 8 }

upsConfigLowVoltageTransferPoint-gen OBJECT-TYPE
    SYNTAX     NonNegativeInteger32
    UNITS      "RMS Volts"
    MAX-ACCESS read-write
    STATUS     current
    DESCRIPTION
            "The minimum input line voltage allowed before the UPS
            system transfers to battery backup.(*)"
    ::= { upsConfig-gen 9 }

upsConfigHighVoltageTransferPoint-gen OBJECT-TYPE
    SYNTAX     NonNegativeInteger32
    UNITS      "RMS Volts"
    MAX-ACCESS read-write
    STATUS     current
    DESCRIPTION
            "The maximum line voltage allowed before the UPS
            system transfers to battery backup.(*)"
    ::= { upsConfig-gen 10 }

upsConfigBatteryCapacity-gen OBJECT-TYPE
    SYNTAX     NonNegativeInteger32
    UNITS      "Amps Hours"
    MAX-ACCESS read-write
    STATUS     current
    DESCRIPTION
            "The installed battery capacity. This value is the 'factory'-value,
             not the value after calibration."
    ::= { upsConfig-gen 11 }

upsConfigBatteryChargeCurrent-gen OBJECT-TYPE
    SYNTAX     NonNegativeInteger32
    UNITS      "0.1 Amp DC"
    MAX-ACCESS read-write
    STATUS     current
    DESCRIPTION
            "The maximum battery charge current, including external chargers."
    ::= { upsConfig-gen 12 }						

upsConfigNoLoadShutdown-gen OBJECT-TYPE
    SYNTAX     Integer32 {
        disabled(1),
        enabled(2)
    }
    MAX-ACCESS read-write
    STATUS     current
    DESCRIPTION
            "Dis- or enable 'no load' shutdown from the contact interface."
    ::= { upsConfig-gen 13 }
	
upsConfigStartDelay-gen OBJECT-TYPE
    SYNTAX     PositiveInteger32
    UNITS      "minutes"				
    MAX-ACCESS read-write
    STATUS     current
    DESCRIPTION
            "Minimum required autonomy time before the UPS may perform an
             autorestart."
    ::= { upsConfig-gen 14 }

--
-- The GetSet group generic.
--

upsEventGetNext-gen OBJECT-TYPE
    SYNTAX     PositiveInteger32 (1..10)
    MAX-ACCESS read-write
    STATUS     current
    DESCRIPTION
            "The number of events to retreive from the UPS event buffer.
            When this object is set the EventTable will be filled with the
            requested number of entries. The value upsEventSetStartingTimeStamp
            will be used as the start value of the table with the lowest index number."
    ::= { upsGetSet-gen 1 }

upsEventGetPrevious-gen OBJECT-TYPE
    SYNTAX     PositiveInteger32 (1..10)
    MAX-ACCESS read-write
    STATUS     current
    DESCRIPTION
            "The number of events to retreive from the UPS event buffer.
            When this object is set the EventTable will be filled with the
            requested number of entries. The value upsEventLastTime will
            be used as the last value of the table with the highest index number.

            Returns SNMP-NOSUCHNAME for UPSs that don't support this command."
    ::= { upsGetSet-gen 2 }
				
upsEventSetStartingTimeStamp-gen OBJECT-TYPE
    SYNTAX     NonNegativeInteger32
    MAX-ACCESS read-write
    STATUS     current
    DESCRIPTION
            "The timestamp which is used as starting point for downloading
             events from the UPS event buffer"
    ::= { upsGetSet-gen 3 }				

upsEventRetreiveCurrentTimeStamp-gen OBJECT-TYPE
    SYNTAX     NonNegativeInteger32
    MAX-ACCESS read-only
    STATUS     current
    DESCRIPTION
            "The current timestamp is retreived from the UPS"
    ::= { upsGetSet-gen 4 }				

upsEventTableSize-gen OBJECT-TYPE
    SYNTAX     NonNegativeInteger32
    MAX-ACCESS read-only
    STATUS     current
    DESCRIPTION
            "The number of entries in the event table.
            This object indicates the number of rows in the event table."
    ::= { upsGetSet-gen 5 }

upsEventTable-gen OBJECT-TYPE
    SYNTAX     SEQUENCE OF UpsEventEntry-gen
    MAX-ACCESS not-accessible
    STATUS     current
    DESCRIPTION
            "A list of event table entries.  The number of entries is always
            10, and the value of upsEventTableSize gives the number of valid
            entries from the begging of the table.  Invalid entries return 0.

            To prevent problems with simultaneous queries from several agents,
            these values MUST be accessed using several PDUs in the
            same SNMP message (<number> is (1..10)):

            PDU-SET upsSetStartingTimeStamp <time> 
            PDU-SET upsEventGetNext <number>
            PDU-GET upsEventTableSize
            PDU-GET upsEventCode,upsEventStatus,upsEventTime 1
            PDU-GET upsEventCode,upsEventStatus,upsEventTime 2
            ..
            PDU-GET upsEventCode,upsEventStatus,upsEventTime <number>

            The table is read up to requested number of events and the
            management software afterwards decides which entries are
            valid, as indicated by the upsEventTableSize.
            "
    ::= { upsGetSet-gen 6 }

upsEventEntry-gen OBJECT-TYPE
    SYNTAX     UpsEventEntry-gen
    MAX-ACCESS not-accessible
    STATUS     current
    DESCRIPTION
            "An entry containing information applicable to a
            particular event."
    INDEX { upsEventLineIndex-gen }
    ::= { upsEventTable-gen 1 }

UpsEventEntry-gen ::= SEQUENCE {
    upsEventLineIndex-gen PositiveInteger32,
    upsEventCode-gen      Integer32,
    upsEventStatus-gen    NonNegativeInteger32,
    upsEventTime-gen      NonNegativeInteger32
}

upsEventLineIndex-gen OBJECT-TYPE
    SYNTAX     PositiveInteger32
    MAX-ACCESS not-accessible
    STATUS     current
    DESCRIPTION
            "The event line identifier."
    ::= { upsEventEntry-gen 1 }

upsEventCode-gen OBJECT-TYPE
    SYNTAX     NonNegativeInteger32
    MAX-ACCESS read-only
    STATUS     current
    DESCRIPTION
            "The event code in numerical format."
    ::= { upsEventEntry-gen 2 }

upsEventStatus-gen OBJECT-TYPE
    SYNTAX     NonNegativeInteger32
    MAX-ACCESS read-only
    STATUS     current
    DESCRIPTION
            "The status of the UPS at the moment that the event was generated.
             The format is specified at the 'upsStatus' command.
             If the UPS is not able to deliver status information, then
             SNMP-NOSUCHNAME is returned."
    ::= { upsEventEntry-gen 3 }

upsEventTime-gen OBJECT-TYPE
    SYNTAX     NonNegativeInteger32
    MAX-ACCESS read-only
    STATUS     current
    DESCRIPTION
            "The timestamp of the moment the event was generated."
    ::= { upsEventEntry-gen 4 }

upsParametersRead-gen OBJECT-TYPE
    SYNTAX     PositiveInteger32 (1..16)
    MAX-ACCESS read-write
    STATUS     current
    DESCRIPTION
            "The number of parameters to retreive from the UPS.
            When this object is set the ParameterTable will be filled with the
            requested number of entries. The value upsParametersStartAddress
            will be used as the start value of the table with the lowest index 
            number."
    ::= { upsGetSet-gen 7 }

upsParametersWrite-gen OBJECT-TYPE
    SYNTAX     PositiveInteger32 (1..16)
    MAX-ACCESS read-write
    STATUS     current
    DESCRIPTION
            "The number of parameters to write to the UPS.
            When this object is set the ParameterTable will be send to the ups. 
            The value upsParametersStartAddress will be used for the first value 
            of the table with the lowest index number."
    ::= { upsGetSet-gen 8 }

upsParametersStartAddress-gen OBJECT-TYPE
    SYNTAX     NonNegativeInteger32
    MAX-ACCESS read-write
    STATUS     current
    DESCRIPTION
            "The address which is used as starting point for downloading
             parameters from the UPS"
    ::= { upsGetSet-gen 9 }				

upsParameterTableSize-gen OBJECT-TYPE
    SYNTAX     NonNegativeInteger32
    MAX-ACCESS read-only
    STATUS     current
    DESCRIPTION
            "The number of entries in the parameter table.
            This object indicates the number of rows in the parameter table."
    ::= { upsGetSet-gen 10 }

upsParameterTable-gen OBJECT-TYPE
    SYNTAX     SEQUENCE OF UpsParameterEntry-gen
    MAX-ACCESS not-accessible
    STATUS     current
    DESCRIPTION
            "A list of parameter entries. The number of entries is always
            16, and the value of upsParameterTableSize gives the number of valid
            entries from the begging of the table. Invalid entries return 0.

            To prevent problems with simultaneous queries from several agents,
            these values MUST be accessed using several PDUs in the
            same SNMP message (<number> is (1..16)):

            Read sequence:

            PDU-SET upsSetStartingAddress <addr>
            PDU-SET upsParametersRead <number>
            PDU-GET upsParameterTableSize
            PDU-GET upsParameterValue 1
            PDU-GET upsParameterValue 2
            ..
            PDU-GET upsParameterValue <number>

            The table is read up to requested number of events and the
            management software afterwards decides which entries are
            valid, as indicated by the upsParameterTableSize.

            Write sequence:

            PDU-SET upsSetStartingAddress <addr>
            PDU-SET upsParameterValue 1
            PDU-SET upsParameterValue 2
            ..
            PDU-SET upsParameterValue <number>
            PDU-SET upsParametersWrite <number>
            "
    ::= { upsGetSet-gen 11 }

upsParameterEntry-gen OBJECT-TYPE
    SYNTAX     UpsParameterEntry-gen
    MAX-ACCESS not-accessible
    STATUS     current
    DESCRIPTION
            "An entry containing information applicable to a
            particular parameter."
    INDEX { upsParameterLineIndex-gen }
    ::= { upsParameterTable-gen 1 }

UpsParameterEntry-gen ::= SEQUENCE {
    upsParameterLineIndex-gen PositiveInteger32,
    upsParameterValue-gen     Integer32   
}

upsParameterLineIndex-gen OBJECT-TYPE
    SYNTAX     PositiveInteger32
    MAX-ACCESS not-accessible
    STATUS     current
    DESCRIPTION
            "The parameter line identifier."
    ::= { upsParameterEntry-gen 1 }

upsParameterValue-gen OBJECT-TYPE
    SYNTAX     Integer32
    MAX-ACCESS read-write
    STATUS     current
    DESCRIPTION
            "The parameter value in numerical format."
    ::= { upsParameterEntry-gen 2 }

upsStatus-gen OBJECT-TYPE
    SYNTAX     NonNegativeInteger32
    MAX-ACCESS read-only
    STATUS     current
    DESCRIPTION
            "The global UPS status is returned. Every bit reflects a specific 
             status condition. Unused bits returns as 0. The status value can 
             also be found on other commands. The value SNMP-NOSUCHNAME means 
             'invalid status' or 'status value non available'.

Status	1		0001h	upsStatusEcomodeIsOn
	2		0002h	upsStatusBatteryIsCharging
	4		0004h	upsStatusBatteryIsDischarging
	8		0008h	upsStatusAlarmIsActive
	16	0010h	upsStatusRectifierIsOn
	32	0020h	upsStatusLowBattery
	64	0040h	upsStatusOnBypass
	128	0080h	upsStatusMainsBypassOK
	256	0100h	upsStatusMainsRectifierOK
	512	0200h	upsStatusDetourIsOn
	1024	0400h	upsStatusAcousticAlarmIsOn
	2048	0800h	- (not used.)
	4096	1000h	upsStatusInverterIsOn
	8192	2000h	upsStatusNotInParallel (Q1 open)
	16384	4000h	upsStatusResetLoadOff
        32768	8000h	upsStatusLoadOff "
    ::= { upsGetSet-gen 12 }

upsMainsStatisticsMBfail-gen OBJECT-TYPE
    SYNTAX     NonNegativeInteger32
    MAX-ACCESS read-only
    STATUS     current
    DESCRIPTION
            "Count of main bypass failures (>200 ms), since UPS installation."
    ::= { upsGetSet-gen 13 }

upsMainsStatisticsMRfail-gen OBJECT-TYPE
    SYNTAX     NonNegativeInteger32
    MAX-ACCESS read-only
    STATUS     current
    DESCRIPTION
            "Count of mains rectifier failures (>200 ms), since UPS installation."
    ::= { upsGetSet-gen 14 }
		
upsMainsStatisticsB2-gen OBJECT-TYPE
    SYNTAX     NonNegativeInteger32
    MAX-ACCESS read-only
    STATUS     current
    DESCRIPTION
            "Count of transients on the mains bypass (0..2 ms), during the last 7 days."
    ::= { upsGetSet-gen 15 }

upsMainsStatisticsB5-gen OBJECT-TYPE
    SYNTAX     NonNegativeInteger32
    MAX-ACCESS read-only
    STATUS     current
    DESCRIPTION
            "Count of transients on the mains bypass (2..5 ms), during the last 7 days."
    ::= { upsGetSet-gen 16 }

upsMainsStatisticsB10-gen OBJECT-TYPE
    SYNTAX     NonNegativeInteger32
    MAX-ACCESS read-only
    STATUS     current
    DESCRIPTION
            "Count of transients on the mains bypass (5..10 ms), during the last 7 days."
    ::= { upsGetSet-gen 17 }

upsMainsStatisticsB200-gen OBJECT-TYPE
    SYNTAX     NonNegativeInteger32
    MAX-ACCESS read-only
    STATUS     current
    DESCRIPTION
            "Count of transients on the mains bypass (10..200 ms), during the last 7 days."
    ::= { upsGetSet-gen 18 }

upsMainsStatisticsBypRel-gen OBJECT-TYPE
    SYNTAX     NonNegativeInteger32
    MAX-ACCESS read-only
    STATUS     current
    DESCRIPTION
            "Bypass reliability degree [0..100%;255]. The value NOSUCHNAME means 'not available'."
    ::= { upsGetSet-gen 19 }

upsTime-gen OBJECT-TYPE
    SYNTAX     NonNegativeInteger32
    MAX-ACCESS read-write
    STATUS     current
    DESCRIPTION
            "The current timestamp (or real-time) of the UPS. For the format, 
             see 'Timestamp' specifications. The write-command has to comply with the 
             correct timestamp format expected by the UPS (counter value or real-time-clock 
             value). Missing to doing so will result in a SNMP-genERROR, 
             meaning 'command not supported'. It is possible to know which is the timestamp 
             format supported by the UPS, by issuing a read-command or by reading events, 
             which includes timestamps."
    ::= { upsGetSet-gen 20 }

upsRequestPermission-gen OBJECT-TYPE
    SYNTAX     DisplayString (SIZE(0..63))
    MAX-ACCESS write-only
    STATUS     current
    DESCRIPTION
            "An encrypted code is send to enable use of restricted write objects during
             a limited period of time."
    ::= { upsGetSet-gen 21 }
    
upsEventGetCode-gen OBJECT-TYPE
    SYNTAX     Integer32
    MAX-ACCESS write-only
    STATUS     current
    DESCRIPTION
            "The code which is used as starting point to downloading the events from the 
            UPS event buffer."
    ::= { upsGetSet-gen 22 }    
    
upsEventSpinLock-gen OBJECT-TYPE
    SYNTAX     TestAndIncr
    MAX-ACCESS read-write
    STATUS     current
    DESCRIPTION
            "A spin lock on the event subsystem. "

    ::= { upsGetSet-gen 23 }
    
upsParameterSpinLock-gen OBJECT-TYPE
    SYNTAX     TestAndIncr
    MAX-ACCESS read-write
    STATUS     current
    DESCRIPTION
            "A spin lock on the parameters subsystem. "

    ::= { upsGetSet-gen 24 }


--
-- GE Trap group generic
--

upsAlarmBatteryBad-gen TRAP-TYPE
    ENTERPRISE geUPSTraps-gen
    VARIABLES  { trapArg  }
    DESCRIPTION
            "One or more batteries have been determined to require
            replacement."
    ::= 1

upsAlarmOnBattery-gen TRAP-TYPE
    ENTERPRISE geUPSTraps-gen
    VARIABLES  { trapArg , upsSecondsOnBattery-gen  }
    DESCRIPTION
            "An On Battery condition is restored."
    ::= 2

upsAlarmLowBattery-gen TRAP-TYPE
    ENTERPRISE geUPSTraps-gen
    VARIABLES  { trapArg  }
    DESCRIPTION
            "The remaining battery run-time is less than or equal
            to upsConfigLowBattTime."
    ::= 3

upsAlarmDepletedBattery-gen TRAP-TYPE
    ENTERPRISE geUPSTraps-gen
    VARIABLES  { trapArg  }
    DESCRIPTION
            "The UPS will be unable to sustain the present load
            when and if the utility power is lost)"
    ::= 4

upsAlarmTempBad-gen TRAP-TYPE
    ENTERPRISE geUPSTraps-gen
    VARIABLES  { trapArg , upsBatteryTemperature }
    DESCRIPTION
            "A temperature is out of tolerance."
    ::= 5

upsAlarmInputBad-gen TRAP-TYPE
    ENTERPRISE geUPSTraps-gen
    VARIABLES  { trapArg  }
    DESCRIPTION
            "An input condition is out of tolerance."
    ::= 6

upsAlarmOutputBad-gen TRAP-TYPE
    ENTERPRISE geUPSTraps-gen
    VARIABLES  { trapArg  }
    DESCRIPTION
            "An output condition (other than OutputOverload) is
            out of tolerance."
    ::= 7

upsAlarmOutputOverload-gen TRAP-TYPE
    ENTERPRISE geUPSTraps-gen
    VARIABLES  { trapArg , upsOutputPercentLoad-gen }
    DESCRIPTION
            "The output load exceeds the UPS output capacity."
    ::= 8

upsAlarmOnBypass-gen TRAP-TYPE
    ENTERPRISE geUPSTraps-gen
    VARIABLES  { trapArg  }
    DESCRIPTION
            "The Bypass is presently engaged on the UPS."
    ::= 9

upsAlarmBypassBad-gen TRAP-TYPE
    ENTERPRISE geUPSTraps-gen
    VARIABLES  { trapArg  }
    DESCRIPTION
            "The Bypass is out of tolerance."
    ::= 10

upsAlarmOutputOffAsRequested-gen TRAP-TYPE
    ENTERPRISE geUPSTraps-gen
    VARIABLES  { trapArg  }
    DESCRIPTION
            "The UPS has shutdown as requested, i.e., the output
            is off."
    ::= 11

upsAlarmUpsOffAsRequested-gen TRAP-TYPE
    ENTERPRISE geUPSTraps-gen-gen
    VARIABLES  { trapArg  }
    DESCRIPTION
            "The entire UPS has shutdown as commanded."
    ::= 12

upsAlarmChargerFailed-gen TRAP-TYPE
    ENTERPRISE geUPSTraps-gen
    VARIABLES  { trapArg  }
    DESCRIPTION
            "An uncorrected problem has been detected within the
            UPS charger subsystem."
    ::= 13

upsAlarmUpsOutputOff-gen TRAP-TYPE
    ENTERPRISE geUPSTraps-gen
    VARIABLES  { trapArg  }
    DESCRIPTION
            "The output of the UPS is in the off state."
    ::= 14

upsAlarmUpsSystemOff-gen TRAP-TYPE
    ENTERPRISE geUPSTraps-gen
    VARIABLES  { trapArg  }
    DESCRIPTION
            "The UPS system is in the off state."
    ::= 15

upsAlarmFanFailure-gen TRAP-TYPE
    ENTERPRISE geUPSTraps-gen
    VARIABLES  { trapArg  }
    DESCRIPTION
            "The failure of one or more fans in the UPS has been
            detected."
    ::= 16

upsAlarmFuseFailure-gen TRAP-TYPE
    ENTERPRISE geUPSTraps-gen
    VARIABLES  { trapArg  }
    DESCRIPTION
            "The failure of one or more fuses has been detected."
    ::= 17

upsAlarmGeneralFault-gen TRAP-TYPE
    ENTERPRISE geUPSTraps-gen
    VARIABLES  { trapArg  }
    DESCRIPTION
            "A general fault in the UPS has been detected."
    ::= 18

upsAlarmDiagnosticTestFailed-gen TRAP-TYPE
    ENTERPRISE geUPSTraps-gen
    VARIABLES  { trapArg  }
    DESCRIPTION
            "The result of the last diagnostic test indicates a
            failure."
    ::= 19

upsAlarmCommunicationsLost-gen TRAP-TYPE
    ENTERPRISE geUPSTraps-gen
    VARIABLES  { trapArg  }
    DESCRIPTION
            "A problem has been encountered in the communication
            between the agent and the UPS."
    ::= 20
    
upsAlarmAwaitingPower-gen TRAP-TYPE
    ENTERPRISE geUPSTraps-gen
    VARIABLES  { trapArg  }
    DESCRIPTION
            "The UPS output is off and the UPS is awaiting the
            return of the input power (*)."
    ::= 21    

upsAlarmShutdownPending-gen TRAP-TYPE
    ENTERPRISE geUPSTraps-gen
    VARIABLES  { trapArg , upsShutdownAfterDelay-gen }
    DESCRIPTION
            "A upsShutdownAfterDelay countdown is underway."
    ::= 22

upsAlarmShutdownImminent-gen TRAP-TYPE
    ENTERPRISE geUPSTraps-gen
    VARIABLES  { trapArg  }
    DESCRIPTION
            "The UPS will turn off power to the load in less than
            5 seconds; this may be either a timed shutdown or a
            low battery shutdown."
    ::= 23

upsAlarmTestInProgress-gen TRAP-TYPE
    ENTERPRISE geUPSTraps-gen
    VARIABLES  { trapArg , upsTestId-gen }
    DESCRIPTION
            "A test is in progress, as initiated and indicated by
            the Test Group.  Tests initiated via other
            implementation-specific mechanisms can indicate the
            presence of the testing in the alarm table, if
            desired, via a OBJECT-IDENTITY macro in the MIB
            document specific to that implementation and are
            outside the scope of this OBJECT-IDENTITY."
    ::= 24

upsAlarmReceptacleOff-gen TRAP-TYPE
    ENTERPRISE geUPSTraps-gen
    VARIABLES  { trapArg  }
    DESCRIPTION
            "A receptacle has been switched off."
    ::= 25

upsAlarmBatteryBadRestored-gen TRAP-TYPE
    ENTERPRISE geUPSTraps-gen
    VARIABLES  { trapArg  }
    DESCRIPTION
            "A Battery bad condition is restored."
    ::= 33

upsAlarmOnBatteryRestored-gen TRAP-TYPE
    ENTERPRISE geUPSTraps-gen
    VARIABLES  { trapArg  }
    DESCRIPTION
            "The UPS is drawing power from mains again."
    ::= 34

upsAlarmLowBatteryRestored-gen TRAP-TYPE
    ENTERPRISE geUPSTraps-gen
    VARIABLES  { trapArg  }
    DESCRIPTION
            "A Low Battery condition is restored."
    ::= 35

upsAlarmDepletedBatteryRestored-gen TRAP-TYPE
    ENTERPRISE geUPSTraps-gen
    VARIABLES  { trapArg  }
    DESCRIPTION
            "A Depleted Battery condition is restored."
    ::= 36

upsAlarmTempBadRestored-gen TRAP-TYPE
    ENTERPRISE geUPSTraps-gen
    VARIABLES  { trapArg  }
    DESCRIPTION
            "A bad temperature condition is restored."
    ::= 37

upsAlarmInputBadRestored-gen TRAP-TYPE
    ENTERPRISE geUPSTraps-gen
    VARIABLES  { trapArg  }
    DESCRIPTION
            "An input bad condition is restored."
    ::= 38

upsAlarmOutputBadRestored-gen TRAP-TYPE
    ENTERPRISE geUPSTraps-gen
    VARIABLES  { trapArg  }
    DESCRIPTION
            "An output bad condition is restored."
    ::= 39

upsAlarmOutputOverloadRestored-gen TRAP-TYPE
    ENTERPRISE geUPSTraps-gen
    VARIABLES  { trapArg  }
    DESCRIPTION
            "An output overload condition is restored."
    ::= 40

upsAlarmOnBypassRestored-gen TRAP-TYPE
    ENTERPRISE geUPSTraps-gen
    VARIABLES  { trapArg  }
    DESCRIPTION
            "An On Bypass condition is restored."
    ::= 41

upsAlarmBypassBadRestored-gen TRAP-TYPE
    ENTERPRISE geUPSTraps-gen
    VARIABLES  { trapArg  }
    DESCRIPTION
            "A Bypass bad condition is restored."
    ::= 42

upsAlarmOutputOffAsRequestedRestored-gen TRAP-TYPE
    ENTERPRISE geUPSTraps-gen
    VARIABLES  { trapArg  }
    DESCRIPTION
            "A request shutdown has been restored."
    ::= 43

upsAlarmUpsOffAsRequestedRestored-gen TRAP-TYPE
    ENTERPRISE geUPSTraps-gen-gen
    VARIABLES  { trapArg  }
    DESCRIPTION
            "A entire UPS command has been restored."
    ::= 44

upsAlarmChargerFailedRestored-gen TRAP-TYPE
    ENTERPRISE geUPSTraps-gen
    VARIABLES  { trapArg  }
    DESCRIPTION
            "A Charger Failer condition is restored."
    ::= 45

upsAlarmUpsOutputOn-gen TRAP-TYPE
    ENTERPRISE geUPSTraps-gen
    VARIABLES  { trapArg  }
    DESCRIPTION
            "The output of the UPS switched in the on state."
    ::= 46

upsAlarmUpsSystemOn-gen TRAP-TYPE
    ENTERPRISE geUPSTraps-gen
    VARIABLES  { trapArg  }
    DESCRIPTION
            "The UPS system is switched in the on state."
    ::= 47

upsAlarmFanFailureRestored-gen TRAP-TYPE
    ENTERPRISE geUPSTraps-gen
    VARIABLES  { trapArg  }
    DESCRIPTION
            "A Fan failure condition is restored."
    ::= 48

upsAlarmFuseFailureRestored-gen TRAP-TYPE
    ENTERPRISE geUPSTraps-gen
    VARIABLES  { trapArg  }
    DESCRIPTION
            "A Fuse failure condition is restored."
    ::= 49

upsAlarmGeneralFaultRestored-gen TRAP-TYPE
    ENTERPRISE geUPSTraps-gen
    VARIABLES  { trapArg  }
    DESCRIPTION
            "A general fault is restored."
    ::= 50

upsAlarmDiagnosticTestFailedRestored-gen TRAP-TYPE
    ENTERPRISE geUPSTraps-gen
    VARIABLES  { trapArg  }
    DESCRIPTION
            "A last diagnostic test indicates a failure is 
            restored."
    ::= 51

upsAlarmCommunicationsLostRestored-gen TRAP-TYPE
    ENTERPRISE geUPSTraps-gen
    VARIABLES  { trapArg  }
    DESCRIPTION
            "A problem in the communication between the agent 
            and the UPS is restored."
    ::= 52
    
upsAlarmAwaitingPowerRestored-gen TRAP-TYPE
    ENTERPRISE geUPSTraps-gen
    VARIABLES  { trapArg  }
    DESCRIPTION
            "A awaiting power condition is restored (*)."
    ::= 53    

upsAlarmShutdownPendingRestored-gen TRAP-TYPE
    ENTERPRISE geUPSTraps-gen
    VARIABLES  { trapArg , upsShutdownAfterDelay-gen }
    DESCRIPTION
            "A upsShutdownAfterDelay countdown is restored."
    ::= 54

upsAlarmShutdownImminentRestored-gen TRAP-TYPE
    ENTERPRISE geUPSTraps-gen
    VARIABLES  { trapArg  }
    DESCRIPTION
            "A shutdown imminent condition is restored."
    ::= 55

upsAlarmTestInProgressRestored-gen TRAP-TYPE
    ENTERPRISE geUPSTraps-gen
    VARIABLES  { trapArg , upsTestId-gen }
    DESCRIPTION
            "The test is in progress is terminated."
    ::= 56

upsAlarmReceptacleOn TRAP-TYPE
    ENTERPRISE geUPSTraps
    VARIABLES  { trapArg  }
    DESCRIPTION
            "A receptacle has been switched on."
    ::= 57

upsAlarmValueLow-gen TRAP-TYPE
    ENTERPRISE geUPSTraps-gen
    VARIABLES  { trapArg  }
    DESCRIPTION
            "A measurement value reached a value below its low-level threshold."
    ::= 129

upsAlarmValueHigh-gen TRAP-TYPE
    ENTERPRISE geUPSTraps-gen
    VARIABLES  { trapArg  }
    DESCRIPTION
            "A measurement value reached a value higher than its high-level threshold."
    ::= 130

upsAlarmValueLowRestored-gen TRAP-TYPE
    ENTERPRISE geUPSTraps-gen
    VARIABLES  { trapArg  }
    DESCRIPTION
            "A ValueLow alarm condition is restored."
    ::= 133

upsAlarmValueHighRestored-gen TRAP-TYPE
    ENTERPRISE geUPSTraps-gen
    VARIABLES  { trapArg }
    DESCRIPTION
            "A ValueHigh alarm condition is restored."
    ::= 134






--
-- First Environmental cards/boxes handing dry contact and/or analogue signals
--


--
-- Input lines group
--

ioInterfaceNumInputs-First OBJECT-TYPE
    SYNTAX     NonNegativeInteger32
    MAX-ACCESS read-only
    STATUS     current
    DESCRIPTION
            "The number of input lines utilized in this device.
            This entry indicates the number of rows in the input
            table."
    ::= { ioInterfaceInputLine-First 1 }

ioInterfaceInputTable-First OBJECT-TYPE
    SYNTAX     SEQUENCE OF IoInterfaceInputEntry-First
    MAX-ACCESS not-accessible
    STATUS     current
    DESCRIPTION
            "A list of input line table entries.  The number of
            entries is given by the value of ioInterfaceNumInputs."
    ::= { ioInterfaceInputLine-First 2 }

ioInterfaceInputEntry-First OBJECT-TYPE
    SYNTAX     IoInterfaceInputEntry-First
    MAX-ACCESS not-accessible
    STATUS     current
    DESCRIPTION
            "An entry containing information applicable to a
            particular input line."
    INDEX { ioInterfaceInputLineIndex-First }
    ::= { ioInterfaceInputTable-First 1 }

IoInterfaceInputEntry-First ::= SEQUENCE {
    ioInterfaceInputLineIndex-First    PositiveInteger32,
    ioInterfaceInputDescription-First  DisplayString,
    ioInterfaceInputStatus-First       Integer32,
    ioInterfaceEdgeMode-First	       Integer32,
    ioInterfaceAlarmMask-First         Integer32
}

ioInterfaceInputLineIndex-First OBJECT-TYPE
    SYNTAX     PositiveInteger32
    MAX-ACCESS not-accessible
    STATUS     current
    DESCRIPTION
            "The input line identifier."
    ::= { ioInterfaceInputEntry-First 1 }

ioInterfaceInputDescription-First OBJECT-TYPE
    SYNTAX     DisplayString (SIZE(0..63))
    MAX-ACCESS read-write
    STATUS     current
    DESCRIPTION
            "A description of the alarm monitored by this input line."
    ::= { ioInterfaceInputEntry-First 2 }

ioInterfaceInputStatus-First OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-First 3 }

ioInterfaceEdgeMode-First OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-First 4 }

 ioInterfaceAlarmMask-First OBJECT-TYPE
    SYNTAX     Integer32 {
        inactive(0),
        active(1) 
    }
    MAX-ACCESS read-write
    STATUS     current
    DESCRIPTION
            "Alarm functionality for the input line can be set active or
             inactive."
    ::= { ioInterfaceInputEntry-First 5 }

 ioInterfaceAlarmDelay-First OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputLine-First 3 }

--
-- Output lines group
--

ioInterfaceNumOutput-First OBJECT-TYPE
    SYNTAX     NonNegativeInteger32
    MAX-ACCESS read-only
    STATUS     current
    DESCRIPTION
            "The number of output lines utilized by this device.
            This entry indicates the number of rows in the output
            line table."
    ::= { ioInterfaceOutputLine-First 1 }

ioInterfaceOutputTable-First OBJECT-TYPE
    SYNTAX     SEQUENCE OF IoInterfaceOutputEntry-First
    MAX-ACCESS not-accessible
    STATUS     current
    DESCRIPTION
            "A list of output line table entries.  The number of
            entries is given by the value of ioInterfaceNumOutputs."
    ::= { ioInterfaceOutputLine-First 2 }

ioInterfaceOutputEntry-First OBJECT-TYPE
    SYNTAX     IoInterfaceOutputEntry-First
    MAX-ACCESS not-accessible
    STATUS     current
    DESCRIPTION
            "An entry containing information applicable to a
            particular output line."
    INDEX { ioInterfaceOutputLineIndex-First }
    ::= { ioInterfaceOutputTable-First 1 }

IoInterfaceOutputEntry-First ::= SEQUENCE {
    ioInterfaceOutputLineIndex-First    PositiveInteger32,
    ioInterfaceOutputDescription-First  DisplayString,
    ioInterfaceOutputStatus-First       Integer32
}

ioInterfaceOutputLineIndex-First OBJECT-TYPE
    SYNTAX     PositiveInteger32
    MAX-ACCESS not-accessible
    STATUS     current
    DESCRIPTION
            "The output line identifier."
    ::= { ioInterfaceOutputEntry-First 1 }

ioInterfaceOutputDescription-First OBJECT-TYPE
    SYNTAX     DisplayString (SIZE(0..63))
    MAX-ACCESS read-write
    STATUS     current
    DESCRIPTION
            "A description of the alarm monitored by this output line."
    ::= { ioInterfaceOutputEntry-First 2 }

ioInterfaceOutputStatus-First OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-First 3 }

--
-- Analogue lines group
--

ioInterfaceNumAnalogue-First OBJECT-TYPE
    SYNTAX     NonNegativeInteger32
    MAX-ACCESS read-only
    STATUS     current
    DESCRIPTION
            "The number of analogue lines utilized by this device.
            This entry indicates the number of rows in the analogue
            line table."
    ::= { ioInterfaceAnalogueLine-First 1 }

ioInterfaceAnalogueTable-First OBJECT-TYPE
    SYNTAX     SEQUENCE OF IoInterfaceAnalogueEntry-First
    MAX-ACCESS not-accessible
    STATUS     current
    DESCRIPTION
            "A list of analogue line table entries.  The number of
            entries is given by the value of ioInterfaceNumAnalogue."
    ::= { ioInterfaceAnalogueLine-First 2 }

ioInterfaceAnalogueEntry-First OBJECT-TYPE
    SYNTAX     IoInterfaceAnalogueEntry-First
    MAX-ACCESS not-accessible
    STATUS     current
    DESCRIPTION
            "An entry containing information applicable to a
            particular analogue line."
    INDEX { ioInterfaceAnalogueLineInde-First }
    ::= { ioInterfaceAnalogueTable-First 1 }

IoInterfaceAnalogueEntry-First::= SEQUENCE {
    ioInterfaceAnalogueLineIndex-First     PositiveInteger32,
    ioInterfaceAnalogueDescription-First   DisplayString,
    ioInterfaceAnalogueStatus-First        Integer32,
    ioInterfaceAnalogueLowThreshold-First  Integer32,
    ioInterfaceAnalogueHighThreshold-First Integer32,
    ioInterfaceAnalogueResetLowThreshold-First Integer32,
    ioInterfaceAnalogueResetHighThreshold-First Integer32
}

ioInterfaceAnalogueLineIndex-First OBJECT-TYPE
    SYNTAX     PositiveInteger32
    MAX-ACCESS not-accessible
    STATUS     current
    DESCRIPTION
            "The analogue line identifier."
    ::= { ioInterfaceAnalogueEntry-First 1 }

ioInterfaceAnalogueDescription-First OBJECT-TYPE
    SYNTAX     DisplayString (SIZE(0..63))
    MAX-ACCESS read-write
    STATUS     current
    DESCRIPTION
            "A description of the alarm monitored by this analogue line."
    ::= { ioInterfaceAnalogueEntry-First 2 }

ioInterfaceAnalogueStatus-First OBJECT-TYPE
    SYNTAX     Integer32
    MAX-ACCESS read-only
    STATUS     current
    DESCRIPTION
            "Read analogue value 1, when the board support such functionality"
    ::= { ioInterfaceAnalogueEntry-First 3 }

 ioInterfaceAnalogueLowThreshold-First OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-First 4 }

 ioInterfaceAnalogueHighThreshold-First OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-First 5 }
    
    
 ioInterfaceAnalogueResetLowThreshold-First OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-First 6 }

 ioInterfaceAnalogueResetHighThreshold-First OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-First 7 }

--
-- ioInterface trap group
--

ioAlarmGenericChange-First TRAP-TYPE
    ENTERPRISE ioInterfaceTraps-First
    VARIABLES  { trapArg  }
    DESCRIPTION
            "An generic change of a digital input/digital output/analog input has become active."
    ::= 1

--
-- Second Environmental cards/boxes handing dry contact and/or analogue signals
--


--
-- Input lines group
--

ioInterfaceNumInputs-Second OBJECT-TYPE
    SYNTAX     NonNegativeInteger32
    MAX-ACCESS read-only
    STATUS     current
    DESCRIPTION
            "The number of input lines utilized in this device.
            This entry indicates the number of rows in the input
            table."
    ::= { ioInterfaceInputLine-Second 1 }

ioInterfaceInputTable-Second OBJECT-TYPE
    SYNTAX     SEQUENCE OF IoInterfaceInputEntry-Second
    MAX-ACCESS not-accessible
    STATUS     current
    DESCRIPTION
            "A list of input line table entries.  The number of
            entries is given by the value of ioInterfaceNumInputs."
    ::= { ioInterfaceInputLine-Second 2 }

ioInterfaceInputEntry-Second OBJECT-TYPE
    SYNTAX     IoInterfaceInputEntry-Second
    MAX-ACCESS not-accessible
    STATUS     current
    DESCRIPTION
            "An entry containing information applicable to a
            particular input line."
    INDEX { ioInterfaceInputLineIndex-Second }
    ::= { ioInterfaceInputTable-Second 1 }

IoInterfaceInputEntry-Second ::= SEQUENCE {
    ioInterfaceInputLineIndex-Second    PositiveInteger32,
    ioInterfaceInputDescription-Second  DisplayString,
    ioInterfaceInputStatus-Second       Integer32,
    ioInterfaceEdgeMode-Second          Integer32,
    ioInterfaceAlarmMask-Second         Integer32,
    ioInterfaceAlarmDelay-Second        NonNegativeInteger32
}

ioInterfaceInputLineIndex-Second OBJECT-TYPE
    SYNTAX     PositiveInteger32
    MAX-ACCESS not-accessible
    STATUS     current
    DESCRIPTION
            "The input line identifier."
    ::= { ioInterfaceInputEntry-Second 1 }

ioInterfaceInputDescription-Second OBJECT-TYPE
    SYNTAX     DisplayString (SIZE(0..63))
    MAX-ACCESS read-write
    STATUS     current
    DESCRIPTION
            "A description of the alarm monitored by this input line."
    ::= { ioInterfaceInputEntry-Second 2 }

ioInterfaceInputStatus-Second OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Second 3 }

ioInterfaceEdgeMode-Second OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Second 4 }

 ioInterfaceAlarmMask-Second OBJECT-TYPE
    SYNTAX     Integer32 {
        inactive(0),
        active(1) 
    }
    MAX-ACCESS read-write
    STATUS     current
    DESCRIPTION
            "Alarm functionality for the input line can be set active or
             inactive."
    ::= { ioInterfaceInputEntry-Second 5 }

 ioInterfaceAlarmDelay-Second OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Second 6 }

--
-- Output lines group
--

ioInterfaceNumOutput-Second OBJECT-TYPE
    SYNTAX     NonNegativeInteger32
    MAX-ACCESS read-only
    STATUS     current
    DESCRIPTION
            "The number of output lines utilized by this device.
            This entry indicates the number of rows in the output
            line table."
    ::= { ioInterfaceOutputLine-Second 1 }

ioInterfaceOutputTable-Second OBJECT-TYPE
    SYNTAX     SEQUENCE OF IoInterfaceOutputEntry-Second
    MAX-ACCESS not-accessible
    STATUS     current
    DESCRIPTION
            "A list of output line table entries.  The number of
            entries is given by the value of ioInterfaceNumOutputs."
    ::= { ioInterfaceOutputLine-Second 2 }

ioInterfaceOutputEntry-Second OBJECT-TYPE
    SYNTAX     IoInterfaceOutputEntry-Second
    MAX-ACCESS not-accessible
    STATUS     current
    DESCRIPTION
            "An entry containing information applicable to a
            particular output line."
    INDEX { ioInterfaceOutputLineIndex-Second }
    ::= { ioInterfaceOutputTable-Second 1 }

IoInterfaceOutputEntry-Second ::= SEQUENCE {
    ioInterfaceOutputLineIndex-Second    PositiveInteger32,
    ioInterfaceOutputDescription-Second  DisplayString,
    ioInterfaceOutputStatus-Second       Integer32
}

ioInterfaceOutputLineIndex-Second OBJECT-TYPE
    SYNTAX     PositiveInteger32
    MAX-ACCESS not-accessible
    STATUS     current
    DESCRIPTION
            "The output line identifier."
    ::= { ioInterfaceOutputEntry-Second 1 }

ioInterfaceOutputDescription-Second OBJECT-TYPE
    SYNTAX     DisplayString (SIZE(0..63))
    MAX-ACCESS read-write
    STATUS     current
    DESCRIPTION
            "A description of the alarm monitored by this output line."
    ::= { ioInterfaceOutputEntry-Second 2 }

ioInterfaceOutputStatus-Second OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Second 3 }

--
-- Analogue lines group
--

ioInterfaceNumAnalogue-Second OBJECT-TYPE
    SYNTAX     NonNegativeInteger32
    MAX-ACCESS read-only
    STATUS     current
    DESCRIPTION
            "The number of analogue lines utilized by this device.
            This entry indicates the number of rows in the analogue
            line table."
    ::= { ioInterfaceAnalogueLine-Second 1 }

ioInterfaceAnalogueTable-Second OBJECT-TYPE
    SYNTAX     SEQUENCE OF IoInterfaceAnalogueEntry-Second
    MAX-ACCESS not-accessible
    STATUS     current
    DESCRIPTION
            "A list of analogue line table entries.  The number of
            entries is given by the value of ioInterfaceNumAnalogue."
    ::= { ioInterfaceAnalogueLine-Second 2 }

ioInterfaceAnalogueEntry-Second OBJECT-TYPE
    SYNTAX     IoInterfaceAnalogueEntry-Second
    MAX-ACCESS not-accessible
    STATUS     current
    DESCRIPTION
            "An entry containing information applicable to a
            particular analogue line."
    INDEX { ioInterfaceAnalogueLineInde-Second }
    ::= { ioInterfaceAnalogueTable-Second 1 }

IoInterfaceAnalogueEntry-Second::= SEQUENCE {
    ioInterfaceAnalogueLineIndex-Second     PositiveInteger32,
    ioInterfaceAnalogueDescription-Second   DisplayString,
    ioInterfaceAnalogueStatus-Second        Integer32,
    ioInterfaceAnalogueLowThreshold-Second  Integer32,
    ioInterfaceAnalogueHighThreshold-Second Integer32,
    ioInterfaceAnalogueResetLowThreshold-Second Integer32,
    ioInterfaceAnalogueResetHighThreshold-Second Integer32
}

ioInterfaceAnalogueLineIndex-Second OBJECT-TYPE
    SYNTAX     PositiveInteger32
    MAX-ACCESS not-accessible
    STATUS     current
    DESCRIPTION
            "The analogue line identifier."
    ::= { ioInterfaceAnalogueEntry-Second 1 }

ioInterfaceAnalogueDescription-Second OBJECT-TYPE
    SYNTAX     DisplayString (SIZE(0..63))
    MAX-ACCESS read-write
    STATUS     current
    DESCRIPTION
            "A description of the alarm monitored by this analogue line."
    ::= { ioInterfaceAnalogueEntry-Second 2 }

ioInterfaceAnalogueStatus-Second OBJECT-TYPE
    SYNTAX     Integer32
    MAX-ACCESS read-only
    STATUS     current
    DESCRIPTION
            "Read analogue value 1, when the board support such functionality"
    ::= { ioInterfaceAnalogueEntry-Second 3 }

 ioInterfaceAnalogueLowThreshold-Second OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Second 4 }

 ioInterfaceAnalogueHighThreshold-Second OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Second 5 }
    
 ioInterfaceAnalogueResetLowThreshold-Second OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Second 6 }

 ioInterfaceAnalogueResetHighThreshold-Second OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Second 7 }

--
-- ioInterface trap group
--

ioAlarmGenericChange-Second TRAP-TYPE
    ENTERPRISE ioInterfaceTraps-Second
    VARIABLES  { trapArg  }
    DESCRIPTION
            "An generic change of a digital input/digital output/analog input has become active."
    ::= 1

--
-- Third Environmental cards/boxes handing dry contact and/or analogue signals
--


--
-- Input lines group
--

ioInterfaceNumInputs-Third OBJECT-TYPE
    SYNTAX     NonNegativeInteger32
    MAX-ACCESS read-only
    STATUS     current
    DESCRIPTION
            "The number of input lines utilized in this device.
            This entry indicates the number of rows in the input
            table."
    ::= { ioInterfaceInputLine-Third 1 }

ioInterfaceInputTable-Third OBJECT-TYPE
    SYNTAX     SEQUENCE OF IoInterfaceInputEntry-Third
    MAX-ACCESS not-accessible
    STATUS     current
    DESCRIPTION
            "A list of input line table entries.  The number of
            entries is given by the value of ioInterfaceNumInputs."
    ::= { ioInterfaceInputLine-Third 2 }

ioInterfaceInputEntry-Third OBJECT-TYPE
    SYNTAX     IoInterfaceInputEntry-Third
    MAX-ACCESS not-accessible
    STATUS     current
    DESCRIPTION
            "An entry containing information applicable to a
            particular input line."
    INDEX { ioInterfaceInputLineIndex-Third }
    ::= { ioInterfaceInputTable-Third 1 }

IoInterfaceInputEntry-Third ::= SEQUENCE {
    ioInterfaceInputLineIndex-Third    PositiveInteger32,
    ioInterfaceInputDescription-Third  DisplayString,
    ioInterfaceInputStatus-Third       Integer32,
    ioInterfaceEdgeMode-Third          Integer32,
    ioInterfaceAlarmMask-Third         Integer32,
    ioInterfaceAlarmDelay-Third        NonNegativeInteger32
}

ioInterfaceInputLineIndex-Third OBJECT-TYPE
    SYNTAX     PositiveInteger32
    MAX-ACCESS not-accessible
    STATUS     current
    DESCRIPTION
            "The input line identifier."
    ::= { ioInterfaceInputEntry-Third 1 }

ioInterfaceInputDescription-Third OBJECT-TYPE
    SYNTAX     DisplayString (SIZE(0..63))
    MAX-ACCESS read-write
    STATUS     current
    DESCRIPTION
            "A description of the alarm monitored by this input line."
    ::= { ioInterfaceInputEntry-Third 2 }

ioInterfaceInputStatus-Third OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Third 3 }

ioInterfaceEdgeMode-Third OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Third 4 }

 ioInterfaceAlarmMask-Third OBJECT-TYPE
    SYNTAX     Integer32 {
        inactive(0),
        active(1) 
    }
    MAX-ACCESS read-write
    STATUS     current
    DESCRIPTION
            "Alarm functionality for the input line can be set active or
             inactive."
    ::= { ioInterfaceInputEntry-Third 5 }

 ioInterfaceAlarmDelay-Third OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Third 6 }

--
-- Output lines group
--

ioInterfaceNumOutput-Third OBJECT-TYPE
    SYNTAX     NonNegativeInteger32
    MAX-ACCESS read-only
    STATUS     current
    DESCRIPTION
            "The number of output lines utilized by this device.
            This entry indicates the number of rows in the output
            line table."
    ::= { ioInterfaceOutputLine-Third 1 }

ioInterfaceOutputTable-Third OBJECT-TYPE
    SYNTAX     SEQUENCE OF IoInterfaceOutputEntry-Third
    MAX-ACCESS not-accessible
    STATUS     current
    DESCRIPTION
            "A list of output line table entries.  The number of
            entries is given by the value of ioInterfaceNumOutputs."
    ::= { ioInterfaceOutputLine-Third 2 }

ioInterfaceOutputEntry-Third OBJECT-TYPE
    SYNTAX     IoInterfaceOutputEntry-Third
    MAX-ACCESS not-accessible
    STATUS     current
    DESCRIPTION
            "An entry containing information applicable to a
            particular output line."
    INDEX { ioInterfaceOutputLineIndex-Third }
    ::= { ioInterfaceOutputTable-Third 1 }

IoInterfaceOutputEntry-Third ::= SEQUENCE {
    ioInterfaceOutputLineIndex-Third    PositiveInteger32,
    ioInterfaceOutputDescription-Third  DisplayString,
    ioInterfaceOutputStatus-Third       Integer32
}

ioInterfaceOutputLineIndex-Third OBJECT-TYPE
    SYNTAX     PositiveInteger32
    MAX-ACCESS not-accessible
    STATUS     current
    DESCRIPTION
            "The output line identifier."
    ::= { ioInterfaceOutputEntry-Third 1 }

ioInterfaceOutputDescription-Third OBJECT-TYPE
    SYNTAX     DisplayString (SIZE(0..63))
    MAX-ACCESS read-write
    STATUS     current
    DESCRIPTION
            "A description of the alarm monitored by this output line."
    ::= { ioInterfaceOutputEntry-Third 2 }

ioInterfaceOutputStatus-Third OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Third 3 }

--
-- Analogue lines group
--

ioInterfaceNumAnalogue-Third OBJECT-TYPE
    SYNTAX     NonNegativeInteger32
    MAX-ACCESS read-only
    STATUS     current
    DESCRIPTION
            "The number of analogue lines utilized by this device.
            This entry indicates the number of rows in the analogue
            line table."
    ::= { ioInterfaceAnalogueLine-Third 1 }

ioInterfaceAnalogueTable-Third OBJECT-TYPE
    SYNTAX     SEQUENCE OF IoInterfaceAnalogueEntry-Third
    MAX-ACCESS not-accessible
    STATUS     current
    DESCRIPTION
            "A list of analogue line table entries.  The number of
            entries is given by the value of ioInterfaceNumAnalogue."
    ::= { ioInterfaceAnalogueLine-Third 2 }

ioInterfaceAnalogueEntry-Third OBJECT-TYPE
    SYNTAX     IoInterfaceAnalogueEntry-Third
    MAX-ACCESS not-accessible
    STATUS     current
    DESCRIPTION
            "An entry containing information applicable to a
            particular analogue line."
    INDEX { ioInterfaceAnalogueLineInde-Third }
    ::= { ioInterfaceAnalogueTable-Third 1 }

IoInterfaceAnalogueEntry-Third::= SEQUENCE {
    ioInterfaceAnalogueLineIndex-Third     PositiveInteger32,
    ioInterfaceAnalogueDescription-Third   DisplayString,
    ioInterfaceAnalogueStatus-Third        Integer32,
    ioInterfaceAnalogueLowThreshold-Third  Integer32,
    ioInterfaceAnalogueHighThreshold-Third Integer32,
    ioInterfaceAnalogueResetLowThreshold-Third Integer32,
    ioInterfaceAnalogueResetHighThreshold-Third Integer32
}

ioInterfaceAnalogueLineIndex-Third OBJECT-TYPE
    SYNTAX     PositiveInteger32
    MAX-ACCESS not-accessible
    STATUS     current
    DESCRIPTION
            "The analogue line identifier."
    ::= { ioInterfaceAnalogueEntry-Third 1 }

ioInterfaceAnalogueDescription-Third OBJECT-TYPE
    SYNTAX     DisplayString (SIZE(0..63))
    MAX-ACCESS read-write
    STATUS     current
    DESCRIPTION
            "A description of the alarm monitored by this analogue line."
    ::= { ioInterfaceAnalogueEntry-Third 2 }

ioInterfaceAnalogueStatus-Third OBJECT-TYPE
    SYNTAX     Integer32
    MAX-ACCESS read-only
    STATUS     current
    DESCRIPTION
            "Read analogue value 1, when the board support such functionality"
    ::= { ioInterfaceAnalogueEntry-Third 3 }

 ioInterfaceAnalogueLowThreshold-Third OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Third 4 }

 ioInterfaceAnalogueHighThreshold-Third OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Third 5 }
 
 ioInterfaceAnalogueResetLowThreshold-Third OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Third 6 }

 ioInterfaceAnalogueResetHighThreshold-Third OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Third 7 }
--
-- ioInterface trap group
--

ioAlarmGenericChange-Third TRAP-TYPE
    ENTERPRISE ioInterfaceTraps-Third
    VARIABLES  { trapArg  }
    DESCRIPTION
            "An generic change of a digital input/digital output/analog input has become active."
    ::= 1
    
--
-- Fourth Environmental cards/boxes handing dry contact and/or analogue signals
--


--
-- Input lines group
--

ioInterfaceNumInputs-Fourth OBJECT-TYPE
    SYNTAX     NonNegativeInteger32
    MAX-ACCESS read-only
    STATUS     current
    DESCRIPTION
            "The number of input lines utilized in this device.
            This entry indicates the number of rows in the input
            table."
    ::= { ioInterfaceInputLine-Fourth 1 }

ioInterfaceInputTable-Fourth OBJECT-TYPE
    SYNTAX     SEQUENCE OF IoInterfaceInputEntry-Fourth
    MAX-ACCESS not-accessible
    STATUS     current
    DESCRIPTION
            "A list of input line table entries.  The number of
            entries is given by the value of ioInterfaceNumInputs."
    ::= { ioInterfaceInputLine-Fourth 2 }

ioInterfaceInputEntry-Fourth OBJECT-TYPE
    SYNTAX     IoInterfaceInputEntry-Fourth
    MAX-ACCESS not-accessible
    STATUS     current
    DESCRIPTION
            "An entry containing information applicable to a
            particular input line."
    INDEX { ioInterfaceInputLineIndex-Fourth }
    ::= { ioInterfaceInputTable-Fourth 1 }

IoInterfaceInputEntry-Fourth ::= SEQUENCE {
    ioInterfaceInputLineIndex-Fourth    PositiveInteger32,
    ioInterfaceInputDescription-Fourth  DisplayString,
    ioInterfaceInputStatus-Fourth       Integer32,
    ioInterfaceEdgeMode-Fourth          Integer32,
    ioInterfaceAlarmMask-Fourth         Integer32,
    ioInterfaceAlarmDelay-Fourth        NonNegativeInteger32
}

ioInterfaceInputLineIndex-Fourth OBJECT-TYPE
    SYNTAX     PositiveInteger32
    MAX-ACCESS not-accessible
    STATUS     current
    DESCRIPTION
            "The input line identifier."
    ::= { ioInterfaceInputEntry-Fourth 1 }

ioInterfaceInputDescription-Fourth OBJECT-TYPE
    SYNTAX     DisplayString (SIZE(0..63))
    MAX-ACCESS read-write
    STATUS     current
    DESCRIPTION
            "A description of the alarm monitored by this input line."
    ::= { ioInterfaceInputEntry-Fourth 2 }

ioInterfaceInputStatus-Fourth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Fourth 3 }

ioInterfaceEdgeMode-Fourth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Fourth 4 }

 ioInterfaceAlarmMask-Fourth OBJECT-TYPE
    SYNTAX     Integer32 {
        inactive(0),
        active(1) 
    }
    MAX-ACCESS read-write
    STATUS     current
    DESCRIPTION
            "Alarm functionality for the input line can be set active or
             inactive."
    ::= { ioInterfaceInputEntry-Fourth 5 }

 ioInterfaceAlarmDelay-Fourth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Fourth 6 }

--
-- Output lines group
--

ioInterfaceNumOutput-Fourth OBJECT-TYPE
    SYNTAX     NonNegativeInteger32
    MAX-ACCESS read-only
    STATUS     current
    DESCRIPTION
            "The number of output lines utilized by this device.
            This entry indicates the number of rows in the output
            line table."
    ::= { ioInterfaceOutputLine-Fourth 1 }

ioInterfaceOutputTable-Fourth OBJECT-TYPE
    SYNTAX     SEQUENCE OF IoInterfaceOutputEntry-Fourth
    MAX-ACCESS not-accessible
    STATUS     current
    DESCRIPTION
            "A list of output line table entries.  The number of
            entries is given by the value of ioInterfaceNumOutputs."
    ::= { ioInterfaceOutputLine-Fourth 2 }

ioInterfaceOutputEntry-Fourth OBJECT-TYPE
    SYNTAX     IoInterfaceOutputEntry-Fourth
    MAX-ACCESS not-accessible
    STATUS     current
    DESCRIPTION
            "An entry containing information applicable to a
            particular output line."
    INDEX { ioInterfaceOutputLineIndex-Fourth }
    ::= { ioInterfaceOutputTable-Fourth 1 }

IoInterfaceOutputEntry-Fourth ::= SEQUENCE {
    ioInterfaceOutputLineIndex-Fourth    PositiveInteger32,
    ioInterfaceOutputDescription-Fourth  DisplayString,
    ioInterfaceOutputStatus-Fourth       Integer32
}

ioInterfaceOutputLineIndex-Fourth OBJECT-TYPE
    SYNTAX     PositiveInteger32
    MAX-ACCESS not-accessible
    STATUS     current
    DESCRIPTION
            "The output line identifier."
    ::= { ioInterfaceOutputEntry-Fourth 1 }

ioInterfaceOutputDescription-Fourth OBJECT-TYPE
    SYNTAX     DisplayString (SIZE(0..63))
    MAX-ACCESS read-write
    STATUS     current
    DESCRIPTION
            "A description of the alarm monitored by this output line."
    ::= { ioInterfaceOutputEntry-Fourth 2 }

ioInterfaceOutputStatus-Fourth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Fourth 3 }

--
-- Analogue lines group
--

ioInterfaceNumAnalogue-Fourth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Fourth 1 }

ioInterfaceAnalogueTable-Fourth OBJECT-TYPE
    SYNTAX     SEQUENCE OF IoInterfaceAnalogueEntry-Fourth
    MAX-ACCESS not-accessible
    STATUS     current
    DESCRIPTION
            "A list of analogue line table entries.  The number of
            entries is given by the value of ioInterfaceNumAnalogue."
    ::= { ioInterfaceAnalogueLine-Fourth 2 }

ioInterfaceAnalogueEntry-Fourth OBJECT-TYPE
    SYNTAX     IoInterfaceAnalogueEntry-Fourth
    MAX-ACCESS not-accessible
    STATUS     current
    DESCRIPTION
            "An entry containing information applicable to a
            particular analogue line."
    INDEX { ioInterfaceAnalogueLineInde-Fourth }
    ::= { ioInterfaceAnalogueTable-Fourth 1 }

IoInterfaceAnalogueEntry-Fourth::= SEQUENCE {
    ioInterfaceAnalogueLineIndex-Fourth     PositiveInteger32,
    ioInterfaceAnalogueDescription-Fourth   DisplayString,
    ioInterfaceAnalogueStatus-Fourth        Integer32,
    ioInterfaceAnalogueLowThreshold-Fourth  Integer32,
    ioInterfaceAnalogueHighThreshold-Fourth Integer32,
    ioInterfaceAnalogueResetLowThreshold-Fourth Integer32,
    ioInterfaceAnalogueResetHighThreshold-Fourth Integer32
}

ioInterfaceAnalogueLineIndex-Fourth OBJECT-TYPE
    SYNTAX     PositiveInteger32
    MAX-ACCESS not-accessible
    STATUS     current
    DESCRIPTION
            "The analogue line identifier."
    ::= { ioInterfaceAnalogueEntry-Fourth 1 }

ioInterfaceAnalogueDescription-Fourth OBJECT-TYPE
    SYNTAX     DisplayString (SIZE(0..63))
    MAX-ACCESS read-write
    STATUS     current
    DESCRIPTION
            "A description of the alarm monitored by this analogue line."
    ::= { ioInterfaceAnalogueEntry-Fourth 2 }

ioInterfaceAnalogueStatus-Fourth OBJECT-TYPE
    SYNTAX     Integer32
    MAX-ACCESS read-only
    STATUS     current
    DESCRIPTION
            "Read analogue value 1, when the board support such functionality"
    ::= { ioInterfaceAnalogueEntry-Fourth 3 }

 ioInterfaceAnalogueLowThreshold-Fourth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Fourth 4 }

 ioInterfaceAnalogueHighThreshold-Fourth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Fourth 5 }
    
 ioInterfaceAnalogueResetLowThreshold-Fourth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Fourth 6 }

 ioInterfaceAnalogueResetHighThreshold-Fourth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Fourth 7 }

--
-- ioInterface trap group
--

ioAlarmGenericChange-Fourth TRAP-TYPE
    ENTERPRISE ioInterfaceTraps-Fourth
    VARIABLES  { trapArg  }
    DESCRIPTION
            "An generic change of a digital input/digital output/analog input has become active."
    ::= 1

--
-- Fifth Environmental cards/boxes handing dry contact and/or analogue signals
--


--
-- Input lines group
--

ioInterfaceNumInputs-Fifth OBJECT-TYPE
    SYNTAX     NonNegativeInteger32
    MAX-ACCESS read-only
    STATUS     current
    DESCRIPTION
            "The number of input lines utilized in this device.
            This entry indicates the number of rows in the input
            table."
    ::= { ioInterfaceInputLine-Fifth 1 }

ioInterfaceInputTable-Fifth OBJECT-TYPE
    SYNTAX     SEQUENCE OF IoInterfaceInputEntry-Fifth
    MAX-ACCESS not-accessible
    STATUS     current
    DESCRIPTION
            "A list of input line table entries.  The number of
            entries is given by the value of ioInterfaceNumInputs."
    ::= { ioInterfaceInputLine-Fifth 2 }

ioInterfaceInputEntry-Fifth OBJECT-TYPE
    SYNTAX     IoInterfaceInputEntry-Fifth
    MAX-ACCESS not-accessible
    STATUS     current
    DESCRIPTION
            "An entry containing information applicable to a
            particular input line."
    INDEX { ioInterfaceInputLineIndex-Fifth }
    ::= { ioInterfaceInputTable-Fifth 1 }

IoInterfaceInputEntry-Fifth ::= SEQUENCE {
    ioInterfaceInputLineIndex-Fifth    PositiveInteger32,
    ioInterfaceInputDescription-Fifth  DisplayString,
    ioInterfaceInputStatus-Fifth       Integer32,
    ioInterfaceEdgeMode-Fifth          Integer32,
    ioInterfaceAlarmMask-Fifth         Integer32,
    ioInterfaceAlarmDelay-Fifth        NonNegativeInteger32
}

ioInterfaceInputLineIndex-Fifth OBJECT-TYPE
    SYNTAX     PositiveInteger32
    MAX-ACCESS not-accessible
    STATUS     current
    DESCRIPTION
            "The input line identifier."
    ::= { ioInterfaceInputEntry-Fifth 1 }

ioInterfaceInputDescription-Fifth OBJECT-TYPE
    SYNTAX     DisplayString (SIZE(0..63))
    MAX-ACCESS read-write
    STATUS     current
    DESCRIPTION
            "A description of the alarm monitored by this input line."
    ::= { ioInterfaceInputEntry-Fifth 2 }

ioInterfaceInputStatus-Fifth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Fifth 3 }

ioInterfaceEdgeMode-Fifth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Fifth 4 }

 ioInterfaceAlarmMask-Fifth OBJECT-TYPE
    SYNTAX     Integer32 {
        inactive(0),
        active(1) 
    }
    MAX-ACCESS read-write
    STATUS     current
    DESCRIPTION
            "Alarm functionality for the input line can be set active or
             inactive."
    ::= { ioInterfaceInputEntry-Fifth 5 }

 ioInterfaceAlarmDelay-Fifth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Fifth 6 }

--
-- Output lines group
--

ioInterfaceNumOutput-Fifth OBJECT-TYPE
    SYNTAX     NonNegativeInteger32
    MAX-ACCESS read-only
    STATUS     current
    DESCRIPTION
            "The number of output lines utilized by this device.
            This entry indicates the number of rows in the output
            line table."
    ::= { ioInterfaceOutputLine-Fifth 1 }

ioInterfaceOutputTable-Fifth OBJECT-TYPE
    SYNTAX     SEQUENCE OF IoInterfaceOutputEntry-Fifth
    MAX-ACCESS not-accessible
    STATUS     current
    DESCRIPTION
            "A list of output line table entries.  The number of
            entries is given by the value of ioInterfaceNumOutputs."
    ::= { ioInterfaceOutputLine-Fifth 2 }

ioInterfaceOutputEntry-Fifth OBJECT-TYPE
    SYNTAX     IoInterfaceOutputEntry-Fifth
    MAX-ACCESS not-accessible
    STATUS     current
    DESCRIPTION
            "An entry containing information applicable to a
            particular output line."
    INDEX { ioInterfaceOutputLineIndex-Fifth }
    ::= { ioInterfaceOutputTable-Fifth 1 }

IoInterfaceOutputEntry-Fifth ::= SEQUENCE {
    ioInterfaceOutputLineIndex-Fifth    PositiveInteger32,
    ioInterfaceOutputDescription-Fifth  DisplayString,
    ioInterfaceOutputStatus-Fifth       Integer32
}

ioInterfaceOutputLineIndex-Fifth OBJECT-TYPE
    SYNTAX     PositiveInteger32
    MAX-ACCESS not-accessible
    STATUS     current
    DESCRIPTION
            "The output line identifier."
    ::= { ioInterfaceOutputEntry-Fifth 1 }

ioInterfaceOutputDescription-Fifth OBJECT-TYPE
    SYNTAX     DisplayString (SIZE(0..63))
    MAX-ACCESS read-write
    STATUS     current
    DESCRIPTION
            "A description of the alarm monitored by this output line."
    ::= { ioInterfaceOutputEntry-Fifth 2 }

ioInterfaceOutputStatus-Fifth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Fifth 3 }

--
-- Analogue lines group
--

ioInterfaceNumAnalogue-Fifth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Fifth 1 }

ioInterfaceAnalogueTable-Fifth OBJECT-TYPE
    SYNTAX     SEQUENCE OF IoInterfaceAnalogueEntry-Fifth
    MAX-ACCESS not-accessible
    STATUS     current
    DESCRIPTION
            "A list of analogue line table entries.  The number of
            entries is given by the value of ioInterfaceNumAnalogue."
    ::= { ioInterfaceAnalogueLine-Fifth 2 }

ioInterfaceAnalogueEntry-Fifth OBJECT-TYPE
    SYNTAX     IoInterfaceAnalogueEntry-Fifth
    MAX-ACCESS not-accessible
    STATUS     current
    DESCRIPTION
            "An entry containing information applicable to a
            particular analogue line."
    INDEX { ioInterfaceAnalogueLineInde-Fifth }
    ::= { ioInterfaceAnalogueTable-Fifth 1 }

IoInterfaceAnalogueEntry-Fifth::= SEQUENCE {
    ioInterfaceAnalogueLineIndex-Fifth     PositiveInteger32,
    ioInterfaceAnalogueDescription-Fifth   DisplayString,
    ioInterfaceAnalogueStatus-Fifth        Integer32,
    ioInterfaceAnalogueLowThreshold-Fifth  Integer32,
    ioInterfaceAnalogueHighThreshold-Fifth Integer32,
    ioInterfaceAnalogueResetLowThreshold-Fifth Integer32,
    ioInterfaceAnalogueResetHighThreshold-Fifth Integer32
}

ioInterfaceAnalogueLineIndex-Fifth OBJECT-TYPE
    SYNTAX     PositiveInteger32
    MAX-ACCESS not-accessible
    STATUS     current
    DESCRIPTION
            "The analogue line identifier."
    ::= { ioInterfaceAnalogueEntry-Fifth 1 }

ioInterfaceAnalogueDescription-Fifth OBJECT-TYPE
    SYNTAX     DisplayString (SIZE(0..63))
    MAX-ACCESS read-write
    STATUS     current
    DESCRIPTION
            "A description of the alarm monitored by this analogue line."
    ::= { ioInterfaceAnalogueEntry-Fifth 2 }

ioInterfaceAnalogueStatus-Fifth OBJECT-TYPE
    SYNTAX     Integer32
    MAX-ACCESS read-only
    STATUS     current
    DESCRIPTION
            "Read analogue value 1, when the board support such functionality"
    ::= { ioInterfaceAnalogueEntry-Fifth 3 }

 ioInterfaceAnalogueLowThreshold-Fifth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Fifth 4 }

 ioInterfaceAnalogueHighThreshold-Fifth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Fifth 5 }
    
 ioInterfaceAnalogueResetLowThreshold-Fifth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Fifth 6 }

 ioInterfaceAnalogueResetHighThreshold-Fifth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Fifth 7 }

--
-- ioInterface trap group
--

ioAlarmGenericChange-Fifth TRAP-TYPE
    ENTERPRISE ioInterfaceTraps-Fifth
    VARIABLES  { trapArg  }
    DESCRIPTION
            "An generic change of a digital input/digital output/analog input has become active."
    ::= 1
--
-- Sixth Environmental cards/boxes handing dry contact and/or analogue signals
--


--
-- Input lines group
--

ioInterfaceNumInputs-Sixth OBJECT-TYPE
    SYNTAX     NonNegativeInteger32
    MAX-ACCESS read-only
    STATUS     current
    DESCRIPTION
            "The number of input lines utilized in this device.
            This entry indicates the number of rows in the input
            table."
    ::= { ioInterfaceInputLine-Sixth 1 }

ioInterfaceInputTable-Sixth OBJECT-TYPE
    SYNTAX     SEQUENCE OF IoInterfaceInputEntry-Sixth
    MAX-ACCESS not-accessible
    STATUS     current
    DESCRIPTION
            "A list of input line table entries.  The number of
            entries is given by the value of ioInterfaceNumInputs."
    ::= { ioInterfaceInputLine-Sixth 2 }

ioInterfaceInputEntry-Sixth OBJECT-TYPE
    SYNTAX     IoInterfaceInputEntry-Sixth
    MAX-ACCESS not-accessible
    STATUS     current
    DESCRIPTION
            "An entry containing information applicable to a
            particular input line."
    INDEX { ioInterfaceInputLineIndex-Sixth }
    ::= { ioInterfaceInputTable-Sixth 1 }

IoInterfaceInputEntry-Sixth ::= SEQUENCE {
    ioInterfaceInputLineIndex-Sixth    PositiveInteger32,
    ioInterfaceInputDescription-Sixth  DisplayString,
    ioInterfaceInputStatus-Sixth       Integer32,
    ioInterfaceEdgeMode-Sixth          Integer32,
    ioInterfaceAlarmMask-Sixth         Integer32,
    ioInterfaceAlarmDelay-Sixth        NonNegativeInteger32
}

ioInterfaceInputLineIndex-Sixth OBJECT-TYPE
    SYNTAX     PositiveInteger32
    MAX-ACCESS not-accessible
    STATUS     current
    DESCRIPTION
            "The input line identifier."
    ::= { ioInterfaceInputEntry-Sixth 1 }

ioInterfaceInputDescription-Sixth OBJECT-TYPE
    SYNTAX     DisplayString (SIZE(0..63))
    MAX-ACCESS read-write
    STATUS     current
    DESCRIPTION
            "A description of the alarm monitored by this input line."
    ::= { ioInterfaceInputEntry-Sixth 2 }

ioInterfaceInputStatus-Sixth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Sixth 3 }

ioInterfaceEdgeMode-Sixth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Sixth 4 }

 ioInterfaceAlarmMask-Sixth OBJECT-TYPE
    SYNTAX     Integer32 {
        inactive(0),
        active(1) 
    }
    MAX-ACCESS read-write
    STATUS     current
    DESCRIPTION
            "Alarm functionality for the input line can be set active or
             inactive."
    ::= { ioInterfaceInputEntry-Sixth 5 }

 ioInterfaceAlarmDelay-Sixth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Sixth 6 }

--
-- Output lines group
--

ioInterfaceNumOutput-Sixth OBJECT-TYPE
    SYNTAX     NonNegativeInteger32
    MAX-ACCESS read-only
    STATUS     current
    DESCRIPTION
            "The number of output lines utilized by this device.
            This entry indicates the number of rows in the output
            line table."
    ::= { ioInterfaceOutputLine-Sixth 1 }

ioInterfaceOutputTable-Sixth OBJECT-TYPE
    SYNTAX     SEQUENCE OF IoInterfaceOutputEntry-Sixth
    MAX-ACCESS not-accessible
    STATUS     current
    DESCRIPTION
            "A list of output line table entries.  The number of
            entries is given by the value of ioInterfaceNumOutputs."
    ::= { ioInterfaceOutputLine-Sixth 2 }

ioInterfaceOutputEntry-Sixth OBJECT-TYPE
    SYNTAX     IoInterfaceOutputEntry-Sixth
    MAX-ACCESS not-accessible
    STATUS     current
    DESCRIPTION
            "An entry containing information applicable to a
            particular output line."
    INDEX { ioInterfaceOutputLineIndex-Sixth }
    ::= { ioInterfaceOutputTable-Sixth 1 }

IoInterfaceOutputEntry-Sixth ::= SEQUENCE {
    ioInterfaceOutputLineIndex-Sixth    PositiveInteger32,
    ioInterfaceOutputDescription-Sixth  DisplayString,
    ioInterfaceOutputStatus-Sixth       Integer32
}

ioInterfaceOutputLineIndex-Sixth OBJECT-TYPE
    SYNTAX     PositiveInteger32
    MAX-ACCESS not-accessible
    STATUS     current
    DESCRIPTION
            "The output line identifier."
    ::= { ioInterfaceOutputEntry-Sixth 1 }

ioInterfaceOutputDescription-Sixth OBJECT-TYPE
    SYNTAX     DisplayString (SIZE(0..63))
    MAX-ACCESS read-write
    STATUS     current
    DESCRIPTION
            "A description of the alarm monitored by this output line."
    ::= { ioInterfaceOutputEntry-Sixth 2 }

ioInterfaceOutputStatus-Sixth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Sixth 3 }

--
-- Analogue lines group
--

ioInterfaceNumAnalogue-Sixth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Sixth 1 }

ioInterfaceAnalogueTable-Sixth OBJECT-TYPE
    SYNTAX     SEQUENCE OF IoInterfaceAnalogueEntry-Sixth
    MAX-ACCESS not-accessible
    STATUS     current
    DESCRIPTION
            "A list of analogue line table entries.  The number of
            entries is given by the value of ioInterfaceNumAnalogue."
    ::= { ioInterfaceAnalogueLine-Sixth 2 }

ioInterfaceAnalogueEntry-Sixth OBJECT-TYPE
    SYNTAX     IoInterfaceAnalogueEntry-Sixth
    MAX-ACCESS not-accessible
    STATUS     current
    DESCRIPTION
            "An entry containing information applicable to a
            particular analogue line."
    INDEX { ioInterfaceAnalogueLineInde-Sixth }
    ::= { ioInterfaceAnalogueTable-Sixth 1 }

IoInterfaceAnalogueEntry-Sixth::= SEQUENCE {
    ioInterfaceAnalogueLineIndex-Sixth     PositiveInteger32,
    ioInterfaceAnalogueDescription-Sixth   DisplayString,
    ioInterfaceAnalogueStatus-Sixth        Integer32,
    ioInterfaceAnalogueLowThreshold-Sixth  Integer32,
    ioInterfaceAnalogueHighThreshold-Sixth Integer32,
    ioInterfaceAnalogueResetLowThreshold-Sixth Integer32,
    ioInterfaceAnalogueResetHighThreshold-Sixth Integer32
}

ioInterfaceAnalogueLineIndex-Sixth OBJECT-TYPE
    SYNTAX     PositiveInteger32
    MAX-ACCESS not-accessible
    STATUS     current
    DESCRIPTION
            "The analogue line identifier."
    ::= { ioInterfaceAnalogueEntry-Sixth 1 }

ioInterfaceAnalogueDescription-Sixth OBJECT-TYPE
    SYNTAX     DisplayString (SIZE(0..63))
    MAX-ACCESS read-write
    STATUS     current
    DESCRIPTION
            "A description of the alarm monitored by this analogue line."
    ::= { ioInterfaceAnalogueEntry-Sixth 2 }

ioInterfaceAnalogueStatus-Sixth OBJECT-TYPE
    SYNTAX     Integer32
    MAX-ACCESS read-only
    STATUS     current
    DESCRIPTION
            "Read analogue value 1, when the board support such functionality"
    ::= { ioInterfaceAnalogueEntry-Sixth 3 }

 ioInterfaceAnalogueLowThreshold-Sixth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Sixth 4 }

 ioInterfaceAnalogueHighThreshold-Sixth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Sixth 5 }
    
 ioInterfaceAnalogueResetLowThreshold-Sixth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Sixth 6 }

 ioInterfaceAnalogueResetHighThreshold-Sixth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Sixth 7 }

--
-- ioInterface trap group
--

ioAlarmGenericChange-Sixth TRAP-TYPE
    ENTERPRISE ioInterfaceTraps-Sixth
    VARIABLES  { trapArg  }
    DESCRIPTION
            "An generic change of a digital input/digital output/analog input has become active."
    ::= 1
--
-- Seventh Environmental cards/boxes handing dry contact and/or analogue signals
--


--
-- Input lines group
--

ioInterfaceNumInputs-Seventh OBJECT-TYPE
    SYNTAX     NonNegativeInteger32
    MAX-ACCESS read-only
    STATUS     current
    DESCRIPTION
            "The number of input lines utilized in this device.
            This entry indicates the number of rows in the input
            table."
    ::= { ioInterfaceInputLine-Seventh 1 }

ioInterfaceInputTable-Seventh OBJECT-TYPE
    SYNTAX     SEQUENCE OF IoInterfaceInputEntry-Seventh
    MAX-ACCESS not-accessible
    STATUS     current
    DESCRIPTION
            "A list of input line table entries.  The number of
            entries is given by the value of ioInterfaceNumInputs."
    ::= { ioInterfaceInputLine-Seventh 2 }

ioInterfaceInputEntry-Seventh OBJECT-TYPE
    SYNTAX     IoInterfaceInputEntry-Seventh
    MAX-ACCESS not-accessible
    STATUS     current
    DESCRIPTION
            "An entry containing information applicable to a
            particular input line."
    INDEX { ioInterfaceInputLineIndex-Seventh }
    ::= { ioInterfaceInputTable-Seventh 1 }

IoInterfaceInputEntry-Seventh ::= SEQUENCE {
    ioInterfaceInputLineIndex-Seventh    PositiveInteger32,
    ioInterfaceInputDescription-Seventh  DisplayString,
    ioInterfaceInputStatus-Seventh       Integer32,
    ioInterfaceEdgeMode-Seventh          Integer32,
    ioInterfaceAlarmMask-Seventh         Integer32,
    ioInterfaceAlarmDelay-Seventh        NonNegativeInteger32
}

ioInterfaceInputLineIndex-Seventh OBJECT-TYPE
    SYNTAX     PositiveInteger32
    MAX-ACCESS not-accessible
    STATUS     current
    DESCRIPTION
            "The input line identifier."
    ::= { ioInterfaceInputEntry-Seventh 1 }

ioInterfaceInputDescription-Seventh OBJECT-TYPE
    SYNTAX     DisplayString (SIZE(0..63))
    MAX-ACCESS read-write
    STATUS     current
    DESCRIPTION
            "A description of the alarm monitored by this input line."
    ::= { ioInterfaceInputEntry-Seventh 2 }

ioInterfaceInputStatus-Seventh OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Seventh 3 }

ioInterfaceEdgeMode-Seventh OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Seventh 4 }

 ioInterfaceAlarmMask-Seventh OBJECT-TYPE
    SYNTAX     Integer32 {
        inactive(0),
        active(1) 
    }
    MAX-ACCESS read-write
    STATUS     current
    DESCRIPTION
            "Alarm functionality for the input line can be set active or
             inactive."
    ::= { ioInterfaceInputEntry-Seventh 5 }

 ioInterfaceAlarmDelay-Seventh OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Seventh 6 }

--
-- Output lines group
--

ioInterfaceNumOutput-Seventh OBJECT-TYPE
    SYNTAX     NonNegativeInteger32
    MAX-ACCESS read-only
    STATUS     current
    DESCRIPTION
            "The number of output lines utilized by this device.
            This entry indicates the number of rows in the output
            line table."
    ::= { ioInterfaceOutputLine-Seventh 1 }

ioInterfaceOutputTable-Seventh OBJECT-TYPE
    SYNTAX     SEQUENCE OF IoInterfaceOutputEntry-Seventh
    MAX-ACCESS not-accessible
    STATUS     current
    DESCRIPTION
            "A list of output line table entries.  The number of
            entries is given by the value of ioInterfaceNumOutputs."
    ::= { ioInterfaceOutputLine-Seventh 2 }

ioInterfaceOutputEntry-Seventh OBJECT-TYPE
    SYNTAX     IoInterfaceOutputEntry-Seventh
    MAX-ACCESS not-accessible
    STATUS     current
    DESCRIPTION
            "An entry containing information applicable to a
            particular output line."
    INDEX { ioInterfaceOutputLineIndex-Seventh }
    ::= { ioInterfaceOutputTable-Seventh 1 }

IoInterfaceOutputEntry-Seventh ::= SEQUENCE {
    ioInterfaceOutputLineIndex-Seventh    PositiveInteger32,
    ioInterfaceOutputDescription-Seventh  DisplayString,
    ioInterfaceOutputStatus-Seventh       Integer32
}

ioInterfaceOutputLineIndex-Seventh OBJECT-TYPE
    SYNTAX     PositiveInteger32
    MAX-ACCESS not-accessible
    STATUS     current
    DESCRIPTION
            "The output line identifier."
    ::= { ioInterfaceOutputEntry-Seventh 1 }

ioInterfaceOutputDescription-Seventh OBJECT-TYPE
    SYNTAX     DisplayString (SIZE(0..63))
    MAX-ACCESS read-write
    STATUS     current
    DESCRIPTION
            "A description of the alarm monitored by this output line."
    ::= { ioInterfaceOutputEntry-Seventh 2 }

ioInterfaceOutputStatus-Seventh OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Seventh 3 }

--
-- Analogue lines group
--

ioInterfaceNumAnalogue-Seventh OBJECT-TYPE
    SYNTAX     NonNegativeInteger32
    MAX-ACCESS read-only
    STATUS     current
    DESCRIPTION
            "The number of analogue lines utilized by this device.
            This entry indicates the number of rows in the analogue
            line table."
    ::= { ioInterfaceAnalogueLine-Seventh 1 }

ioInterfaceAnalogueTable-Seventh OBJECT-TYPE
    SYNTAX     SEQUENCE OF IoInterfaceAnalogueEntry-Seventh
    MAX-ACCESS not-accessible
    STATUS     current
    DESCRIPTION
            "A list of analogue line table entries.  The number of
            entries is given by the value of ioInterfaceNumAnalogue."
    ::= { ioInterfaceAnalogueLine-Seventh 2 }

ioInterfaceAnalogueEntry-Seventh OBJECT-TYPE
    SYNTAX     IoInterfaceAnalogueEntry-Seventh
    MAX-ACCESS not-accessible
    STATUS     current
    DESCRIPTION
            "An entry containing information applicable to a
            particular analogue line."
    INDEX { ioInterfaceAnalogueLineInde-Seventh }
    ::= { ioInterfaceAnalogueTable-Seventh 1 }

IoInterfaceAnalogueEntry-Seventh::= SEQUENCE {
    ioInterfaceAnalogueLineIndex-Seventh     PositiveInteger32,
    ioInterfaceAnalogueDescription-Seventh   DisplayString,
    ioInterfaceAnalogueStatus-Seventh        Integer32,
    ioInterfaceAnalogueLowThreshold-Seventh  Integer32,
    ioInterfaceAnalogueHighThreshold-Seventh Integer32,
    ioInterfaceAnalogueResetLowThreshold-Seventh Integer32,
    ioInterfaceAnalogueResetHighThreshold-Seventh Integer32
}

ioInterfaceAnalogueLineIndex-Seventh OBJECT-TYPE
    SYNTAX     PositiveInteger32
    MAX-ACCESS not-accessible
    STATUS     current
    DESCRIPTION
            "The analogue line identifier."
    ::= { ioInterfaceAnalogueEntry-Seventh 1 }

ioInterfaceAnalogueDescription-Seventh OBJECT-TYPE
    SYNTAX     DisplayString (SIZE(0..63))
    MAX-ACCESS read-write
    STATUS     current
    DESCRIPTION
            "A description of the alarm monitored by this analogue line."
    ::= { ioInterfaceAnalogueEntry-Seventh 2 }

ioInterfaceAnalogueStatus-Seventh OBJECT-TYPE
    SYNTAX     Integer32
    MAX-ACCESS read-only
    STATUS     current
    DESCRIPTION
            "Read analogue value 1, when the board support such functionality"
    ::= { ioInterfaceAnalogueEntry-Seventh 3 }

 ioInterfaceAnalogueLowThreshold-Seventh OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Seventh 4 }

 ioInterfaceAnalogueHighThreshold-Seventh OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Seventh 5 }
    
 ioInterfaceAnalogueResetLowThreshold-Seventh OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Seventh 6 }

 ioInterfaceAnalogueResetHighThreshold-Seventh OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Seventh 7 }

--
-- ioInterface trap group
--

ioAlarmGenericChange-Seventh TRAP-TYPE
    ENTERPRISE ioInterfaceTraps-Seventh
    VARIABLES  { trapArg  }
    DESCRIPTION
            "An generic change of a digital input/digital output/analog input has become active."
    ::= 1
--
-- Eighth Environmental cards/boxes handing dry contact and/or analogue signals
--


--
-- Input lines group
--

ioInterfaceNumInputs-Eighth OBJECT-TYPE
    SYNTAX     NonNegativeInteger32
    MAX-ACCESS read-only
    STATUS     current
    DESCRIPTION
            "The number of input lines utilized in this device.
            This entry indicates the number of rows in the input
            table."
    ::= { ioInterfaceInputLine-Eighth 1 }

ioInterfaceInputTable-Eighth OBJECT-TYPE
    SYNTAX     SEQUENCE OF IoInterfaceInputEntry-Eighth
    MAX-ACCESS not-accessible
    STATUS     current
    DESCRIPTION
            "A list of input line table entries.  The number of
            entries is given by the value of ioInterfaceNumInputs."
    ::= { ioInterfaceInputLine-Eighth 2 }

ioInterfaceInputEntry-Eighth OBJECT-TYPE
    SYNTAX     IoInterfaceInputEntry-Eighth
    MAX-ACCESS not-accessible
    STATUS     current
    DESCRIPTION
            "An entry containing information applicable to a
            particular input line."
    INDEX { ioInterfaceInputLineIndex-Eighth }
    ::= { ioInterfaceInputTable-Eighth 1 }

IoInterfaceInputEntry-Eighth ::= SEQUENCE {
    ioInterfaceInputLineIndex-Eighth    PositiveInteger32,
    ioInterfaceInputDescription-Eighth  DisplayString,
    ioInterfaceInputStatus-Eighth       Integer32,
    ioInterfaceEdgeMode-Eighth          Integer32,
    ioInterfaceAlarmMask-Eighth         Integer32,
    ioInterfaceAlarmDelay-Eighth        NonNegativeInteger32
}

ioInterfaceInputLineIndex-Eighth OBJECT-TYPE
    SYNTAX     PositiveInteger32
    MAX-ACCESS not-accessible
    STATUS     current
    DESCRIPTION
            "The input line identifier."
    ::= { ioInterfaceInputEntry-Eighth 1 }

ioInterfaceInputDescription-Eighth OBJECT-TYPE
    SYNTAX     DisplayString (SIZE(0..63))
    MAX-ACCESS read-write
    STATUS     current
    DESCRIPTION
            "A description of the alarm monitored by this input line."
    ::= { ioInterfaceInputEntry-Eighth 2 }

ioInterfaceInputStatus-Eighth OBJECT-TYPE
    SYNTAX     Integer32 {
        inactive(0),
        active(1) 
    }
    MAX-ACCESS read-only
    STATUS     current
    DESCRIPTION
            "The status of the input lines controlled by the device.
             When a bit is high (1), the associated line is 'active'"
    ::= { ioInterfaceInputEntry-Eighth 3 }

ioInterfaceEdgeMode-Eighth OBJECT-TYPE
    SYNTAX     Integer32 {
        off(0),
        on(1) 
    }
    MAX-ACCESS read-write
    STATUS     current
    DESCRIPTION
            "Edge mode for input lines. 
             This object specifies if the corresponding input line should be 
             recognised immediately as active (edge mode on), or only when the 
             state remains stable for at least the time specified by 
             ioInterfaceAlarmDelay (edge mode off). EdgeMode is only meaningful
             when the object ioInterfaceAlarmMask is active."
    ::= { ioInterfaceInputEntry-Eighth 4 }

 ioInterfaceAlarmMask-Eighth OBJECT-TYPE
    SYNTAX     Integer32 {
        inactive(0),
        active(1) 
    }
    MAX-ACCESS read-write
    STATUS     current
    DESCRIPTION
            "Alarm functionality for the input line can be set active or
             inactive."
    ::= { ioInterfaceInputEntry-Eighth 5 }

 ioInterfaceAlarmDelay-Eighth OBJECT-TYPE
    SYNTAX     NonNegativeInteger32
    MAX-ACCESS read-write
    STATUS     current
    DESCRIPTION
            "Time delay during which an active input line has to be stable, prior 
             to issue an alarm. Effective only when EdgeMode=off for the              corresponding line."
    ::= { ioInterfaceInputEntry-Eighth 6 }

--
-- Output lines group
--

ioInterfaceNumOutput-Eighth OBJECT-TYPE
    SYNTAX     NonNegativeInteger32
    MAX-ACCESS read-only
    STATUS     current
    DESCRIPTION
            "The number of output lines utilized by this device.
            This entry indicates the number of rows in the output
            line table."
    ::= { ioInterfaceOutputLine-Eighth 1 }

ioInterfaceOutputTable-Eighth OBJECT-TYPE
    SYNTAX     SEQUENCE OF IoInterfaceOutputEntry-Eighth
    MAX-ACCESS not-accessible
    STATUS     current
    DESCRIPTION
            "A list of output line table entries.  The number of
            entries is given by the value of ioInterfaceNumOutputs."
    ::= { ioInterfaceOutputLine-Eighth 2 }

ioInterfaceOutputEntry-Eighth OBJECT-TYPE
    SYNTAX     IoInterfaceOutputEntry-Eighth
    MAX-ACCESS not-accessible
    STATUS     current
    DESCRIPTION
            "An entry containing information applicable to a
            particular output line."
    INDEX { ioInterfaceOutputLineIndex-Eighth }
    ::= { ioInterfaceOutputTable-Eighth 1 }

IoInterfaceOutputEntry-Eighth ::= SEQUENCE {
    ioInterfaceOutputLineIndex-Eighth    PositiveInteger32,
    ioInterfaceOutputDescription-Eighth  DisplayString,
    ioInterfaceOutputStatus-Eighth       Integer32
}

ioInterfaceOutputLineIndex-Eighth OBJECT-TYPE
    SYNTAX     PositiveInteger32
    MAX-ACCESS not-accessible
    STATUS     current
    DESCRIPTION
            "The output line identifier."
    ::= { ioInterfaceOutputEntry-Eighth 1 }

ioInterfaceOutputDescription-Eighth OBJECT-TYPE
    SYNTAX     DisplayString (SIZE(0..63))
    MAX-ACCESS read-write
    STATUS     current
    DESCRIPTION
            "A description of the alarm monitored by this output line."
    ::= { ioInterfaceOutputEntry-Eighth 2 }

ioInterfaceOutputStatus-Eighth OBJECT-TYPE
    SYNTAX     Integer32 {
        inactive(0),
        active(1) 
    }
    MAX-ACCESS read-write
    STATUS     current
    DESCRIPTION
            "The status of the output lines controlled by the device.
             When a bit is high (1), the associated line is 'active'"
    ::= { ioInterfaceOutputEntry-Eighth 3 }

--
-- Analogue lines group
--

ioInterfaceNumAnalogue-Eighth OBJECT-TYPE
    SYNTAX     NonNegativeInteger32
    MAX-ACCESS read-only
    STATUS     current
    DESCRIPTION
            "The number of analogue lines utilized by this device.
            This entry indicates the number of rows in the analogue
            line table."
    ::= { ioInterfaceAnalogueLine-Eighth 1 }

ioInterfaceAnalogueTable-Eighth OBJECT-TYPE
    SYNTAX     SEQUENCE OF IoInterfaceAnalogueEntry-Eighth
    MAX-ACCESS not-accessible
    STATUS     current
    DESCRIPTION
            "A list of analogue line table entries.  The number of
            entries is given by the value of ioInterfaceNumAnalogue."
    ::= { ioInterfaceAnalogueLine-Eighth 2 }

ioInterfaceAnalogueEntry-Eighth OBJECT-TYPE
    SYNTAX     IoInterfaceAnalogueEntry-Eighth
    MAX-ACCESS not-accessible
    STATUS     current
    DESCRIPTION
            "An entry containing information applicable to a
            particular analogue line."
    INDEX { ioInterfaceAnalogueLineInde-Eighth }
    ::= { ioInterfaceAnalogueTable-Eighth 1 }

IoInterfaceAnalogueEntry-Eighth::= SEQUENCE {
    ioInterfaceAnalogueLineIndex-Eighth     PositiveInteger32,
    ioInterfaceAnalogueDescription-Eighth   DisplayString,
    ioInterfaceAnalogueStatus-Eighth        Integer32,
    ioInterfaceAnalogueLowThreshold-Eighth  Integer32,
    ioInterfaceAnalogueHighThreshold-Eighth Integer32,
    ioInterfaceAnalogueResetLowThreshold-Eighth Integer32,
    ioInterfaceAnalogueResetHighThreshold-Eighth Integer32
}

ioInterfaceAnalogueLineIndex-Eighth OBJECT-TYPE
    SYNTAX     PositiveInteger32
    MAX-ACCESS not-accessible
    STATUS     current
    DESCRIPTION
            "The analogue line identifier."
    ::= { ioInterfaceAnalogueEntry-Eighth 1 }

ioInterfaceAnalogueDescription-Eighth OBJECT-TYPE
    SYNTAX     DisplayString (SIZE(0..63))
    MAX-ACCESS read-write
    STATUS     current
    DESCRIPTION
            "A description of the alarm monitored by this analogue line."
    ::= { ioInterfaceAnalogueEntry-Eighth 2 }

ioInterfaceAnalogueStatus-Eighth OBJECT-TYPE
    SYNTAX     Integer32
    MAX-ACCESS read-only
    STATUS     current
    DESCRIPTION
            "Read analogue value 1, when the board support such functionality"
    ::= { ioInterfaceAnalogueEntry-Eighth 3 }

 ioInterfaceAnalogueLowThreshold-Eighth OBJECT-TYPE
    SYNTAX     Integer32
    MAX-ACCESS read-write
    STATUS     current
    DESCRIPTION
            "Low limit for the analogical value. When the analogical 
             measurement comes under this limit, an alarm is issued. The limit 
             can be disabled specifying the special floating point value which 
             means 'not available'."
    ::= { ioInterfaceAnalogueEntry-Eighth 4 }

 ioInterfaceAnalogueHighThreshold-Eighth OBJECT-TYPE
    SYNTAX     Integer32
    MAX-ACCESS read-write
    STATUS     current
    DESCRIPTION
            "High limit for the analogical value. When the analogical 
             measurement comes higher than this limit, an alarm is issued. The limit 
             can be disabled specifying the special floating point value which 
             means 'not available'."
    ::= { ioInterfaceAnalogueEntry-Eighth 5 }
    
 ioInterfaceAnalogueResetLowThreshold-Eighth OBJECT-TYPE
    SYNTAX     Integer32
    MAX-ACCESS read-write
    STATUS     current
    DESCRIPTION
            "After an alarm, value which has to be crossed by the 
            analogue input, in order to remove the low alarm condition 
            (hysteresis)"
    ::= { ioInterfaceAnalogueEntry-Eighth 6 }

 ioInterfaceAnalogueResetHighThreshold-Eighth OBJECT-TYPE
    SYNTAX     Integer32
    MAX-ACCESS read-write
    STATUS     current
    DESCRIPTION
            "After an alarm, value which has to be crossed by the 
            analogue input, in order to remove the high alarm condition 
            (hysteresis)"
    ::= { ioInterfaceAnalogueEntry-Eighth 7 }

--
-- ioInterface trap group
--

ioAlarmGenericChange-Eighth TRAP-TYPE
    ENTERPRISE ioInterfaceTraps-Eighth
    VARIABLES  { trapArg  }
    DESCRIPTION
            "An generic change of a digital input/digital output/analog input has become active."
    ::= 1
 
--
-- The Modem group
--

geModemStatus OBJECT-TYPE
    SYNTAX     NonNegativeInteger32
    MAX-ACCESS read-only
    STATUS     current
    DESCRIPTION
            " The status of the modem, controlled by the addressed device.
              The status word is a collection of bits, as specified below.               The SNMP value NOSUCHNAME means 'status not (yet) available'. 
		1	modemStatOnline. There is a valid online connection. 
		2	modemStatError. The last operation has failed. The device 
			will clear this bit when a new modem command is received. 
		4	unused (should be defined = 0).
		8	unused (should be defined = 0).
		16	modemStatDialling. The dialling procedure is pending.
		32	modemStatBusy. The device is performing some operation, 
			and can not be accessed, temporarily.
		64	unused (should be defined = 0).
		128	modemStatNoModem. The modem is not connected or not responding.
		256	modemStatDCD. The DCD line status signal is on.
		512	modemStatRing. The RING line status signal is on.
		1024	modemStatCTS. The CTS line status signal is on.
		2048	modemStatDSR. The DSR line status signal is on.
		4096	unused (should be defined = 0).
		8192	unused (should be defined = 0).
		16384	unused (should be defined = 0).
		32768	unused (should be defined = 0)."
    ::= { geModem 1 }

geModemNumInitString OBJECT-TYPE
    SYNTAX     NonNegativeInteger32
    MAX-ACCESS read-only
    STATUS     current
    DESCRIPTION
            "The number of modem init strings utilized by this ups.
            This entry indicates the number of rows in the init 
            string table."
    ::= { geModem 2 }

geModemInitStringTable OBJECT-TYPE
    SYNTAX     SEQUENCE OF GeModemInitStringEntry
    MAX-ACCESS not-accessible
    STATUS     current
    DESCRIPTION
            "A list of init string table entries.  The number of
            entries is given by the value of geModemNumInitString."
    ::= { geModem 3 }

geModemInitStringEntry OBJECT-TYPE
    SYNTAX     GeModemInitStringEntry
    MAX-ACCESS not-accessible
    STATUS     current
    DESCRIPTION
            "An entry containing information applicable to a
            particular Init string."
    INDEX { geModemInitStringLineIndex }
    ::= { geModemInitStringTable 1 }

GeModemInitStringEntry ::= SEQUENCE {
    geModemInitStringLineIndex     PositiveInteger32,
    geModemInitstring              DisplayString
}

geModemInitStringLineIndex OBJECT-TYPE
    SYNTAX     PositiveInteger32
    MAX-ACCESS not-accessible
    STATUS     current
    DESCRIPTION
            "The Init string line identifier."
    ::= { geModemInitStringEntry 1 }

geModemInitstring OBJECT-TYPE
    SYNTAX     DisplayString (SIZE(0..63))
    MAX-ACCESS read-write
    STATUS     current
    DESCRIPTION
            "A modem Init string."
    ::= { geModemInitStringEntry 2 }

geModemNumPhoneNumber OBJECT-TYPE
    SYNTAX     NonNegativeInteger32
    MAX-ACCESS read-only
    STATUS     current
    DESCRIPTION
            "The number of modem phone numbers utilized by this ups.
            This entry indicates the number of rows in the table."
    ::= { geModem 4 }

geModemPhoneNumberTable OBJECT-TYPE
    SYNTAX     SEQUENCE OF GeModemPhoneNumberEntry
    MAX-ACCESS not-accessible
    STATUS     current
    DESCRIPTION
            "A list of phone number table entries.  The number of
            entries is given by the value of geModemNumPhoneNumber."
    ::= { geModem 5 }

geModemPhoneNumberEntry OBJECT-TYPE
    SYNTAX     GeModemPhoneNumberEntry
    MAX-ACCESS not-accessible
    STATUS     current
    DESCRIPTION
            "An entry containing information applicable to a
            particular phone number."
    INDEX { geModemPhoneNumberLineIndex }
    ::= { geModemPhoneNumberTable 1 }

GeModemPhoneNumberEntry ::= SEQUENCE {
    geModemPhoneNumberLineIndex     PositiveInteger32,
    geModemPhoneNumber              DisplayString
}

geModemPhoneNumberLineIndex OBJECT-TYPE
    SYNTAX     PositiveInteger32
    MAX-ACCESS not-accessible
    STATUS     current
    DESCRIPTION
            "The phone number line identifier."
    ::= { geModemPhoneNumberEntry 1 }

geModemPhoneNumber OBJECT-TYPE
    SYNTAX     DisplayString (SIZE(0..63))
    MAX-ACCESS read-write
    STATUS     current
    DESCRIPTION
            "A phone number."
    ::= { geModemPhoneNumberEntry 2 }

--
-- The [partner] group
--
--
-- ge[partner]       OBJECT IDENTIFIER ::=  { geHardware [Partner-ID] }


--
-- The ProtectionClient group
--

--
-- Environment
--

geClientProcessor OBJECT-TYPE
    SYNTAX     DisplayString (SIZE(0..63))
    MAX-ACCESS read-only
    STATUS     current
    DESCRIPTION
            "The processor used by the clients machine."
    ::= { geClient 1 }

geClientOperatingSystem OBJECT-TYPE
    SYNTAX     DisplayString (SIZE(0..63))
    MAX-ACCESS read-only
    STATUS     current
    DESCRIPTION
            "Operating system on which the client runs."
    ::= { geClient 2 }

geClientJavaRuntimeVersion OBJECT-TYPE
    SYNTAX     DisplayString (SIZE(0..63))
    MAX-ACCESS read-only
    STATUS     current
    DESCRIPTION
            "JavaRuntimeVersion of the client machine."
    ::= { geClient 3 }

--
-- Config 
--

geClientMaxSizeOfLogfiles OBJECT-TYPE
    SYNTAX     NonNegativeInteger32
    MAX-ACCESS read-write
    STATUS     current
    DESCRIPTION
            "The max. size of the logfiles in Kb."
    ::= { geClient 4 }

geClientLanguageSelection OBJECT-TYPE
    SYNTAX     DisplayString (SIZE(0..32))
    MAX-ACCESS read-only
    STATUS     current
    DESCRIPTION
            "Shows the currently activated language of the client."
    ::= { geClient 5 }

geClientInternalCommunicationPort OBJECT-TYPE
    SYNTAX     NonNegativeInteger32
    MAX-ACCESS read-write
    STATUS     current
    DESCRIPTION
            "UDP port used between server and client part."
    ::= { geClient 6 }

geClientReboot OBJECT-TYPE
    SYNTAX     Integer32 {
        reboot(1)
    }
    MAX-ACCESS write-only
    STATUS     current
    DESCRIPTION
            "setting this object causes the protection client to reboot 
             and activate new settings."
    ::= { geClient 7 }

geClientNumUPS OBJECT-TYPE
    SYNTAX     NonNegativeInteger32
    MAX-ACCESS read-only
    STATUS     current
    DESCRIPTION
            "The number of UPSs utilized by this client.
            This entry indicates the number of rows in the table."
    ::= { geClient 8 }

geClientUPSTable OBJECT-TYPE
    SYNTAX     SEQUENCE OF GeClientUPSEntry
    MAX-ACCESS not-accessible
    STATUS     current
    DESCRIPTION
            "A list of UPS table entries.  The number of
            entries is given by the value of geClientNumUPS."
    ::= { geClient 9 }

geClientUPSEntry OBJECT-TYPE
    SYNTAX     GeClientUPSEntry
    MAX-ACCESS not-accessible
    STATUS     current
    DESCRIPTION
            "An entry containing information applicable to a
            particular UPS."
    INDEX { geClientUPSLineIndex }
    ::= { geClientUPSTable 1 }

GeClientUPSEntry ::= SEQUENCE {
    geClientUPSLineIndex           PositiveInteger32,
    geClientUPSName                DisplayString,
    geClientUPSCommunicationType   Integer32,
    geClientUPSCommunicationPort   DisplayString,
    geClientUPSReadCommName        DisplayString,
    geClientUPSWriteCommName       DisplayString,
    geClientUPSCommRetries         NonNegativeInteger32,
    geClientAlarmManagement        Integer32,
    geClientPreDelay               NonNegativeInteger32,
    geClientSystemShutdown         Integer32,
    geClientRuntime                NonNegativeInteger32,
    geClientUPSShutdown            Integer32,
    geClientMaxScriptExecutionTime NonNegativeInteger32,
    geClientGraceperiod            NonNegativeInteger32
}

geClientUPSLineIndex OBJECT-TYPE
    SYNTAX     PositiveInteger32
    MAX-ACCESS not-accessible
    STATUS     current
    DESCRIPTION
            "The UPS line identifier."
    ::= { geClientUPSEntry 1 }

geClientUPSName OBJECT-TYPE
    SYNTAX     DisplayString (SIZE(0..32))
    MAX-ACCESS read-write
    STATUS     current
    DESCRIPTION
            "The administrative name of the UPS."
    ::= { geClientUPSEntry 2 }

geClientUPSCommunicationType OBJECT-TYPE
    SYNTAX     Integer32 {
        serial(0),
        snmp(1)
    }
    MAX-ACCESS read-write
    STATUS     current
    DESCRIPTION
            "The method of communication."
    ::= { geClientUPSEntry 3 }

geClientUPSCommunicationPort OBJECT-TYPE
    SYNTAX     DisplayString (SIZE(0..32))
    MAX-ACCESS read-write
    STATUS     current
    DESCRIPTION
            "The communication port."
    ::= { geClientUPSEntry 4 }

geClientUPSReadCommName OBJECT-TYPE
    SYNTAX     DisplayString (SIZE(0..32))
    MAX-ACCESS read-write
    STATUS     current
    DESCRIPTION
            "The Read community string. Used when communication
             method is SNMP."
    ::= { geClientUPSEntry 5 }

geClientUPSWriteCommName OBJECT-TYPE
    SYNTAX     DisplayString (SIZE(0..32))
    MAX-ACCESS read-write
    STATUS     current
    DESCRIPTION
            "The Write community string. Used when communication
             method is SNMP."
    ::= { geClientUPSEntry 6 }

geClientUPSCommRetries OBJECT-TYPE
    SYNTAX     NonNegativeInteger32
    MAX-ACCESS read-write
    STATUS     current
    DESCRIPTION
            "Number of retries in case an answer times out.
             When the max. number of retries is reached a
             lost communication alarm will be raised."
    ::= { geClientUPSEntry 7 }

geClientAlarmManagement OBJECT-TYPE
    SYNTAX     Integer32 {
        off(0),
        on(1)
    }
    MAX-ACCESS read-write
    STATUS     current
    DESCRIPTION
            "Alarm Management enabled or disabled."
    ::= { geClientUPSEntry 8 }

geClientPreDelay OBJECT-TYPE
    SYNTAX     NonNegativeInteger32
    MAX-ACCESS read-only
    STATUS     current
    DESCRIPTION
            "The number of second an alarm needs to be active
             before action is taken."
    ::= { geClientUPSEntry 9 }

geClientSystemShutdown OBJECT-TYPE
    SYNTAX     Integer32 {
        off(0),
        on(1)
    }
    MAX-ACCESS read-only
    STATUS     current
    DESCRIPTION
            "Specifies whether the client should shutdown the machine 
             when an alarm situation occurs."
    ::= { geClientUPSEntry 10 }

geClientRuntime OBJECT-TYPE
    SYNTAX     NonNegativeInteger32
    MAX-ACCESS read-only
    STATUS     current
    DESCRIPTION
            "The user defined preferable runtime."
    ::= { geClientUPSEntry 11 }

geClientUPSShutdown OBJECT-TYPE
    SYNTAX     Integer32 {
        off(0),
        on(1)
    }
    MAX-ACCESS read-only
    STATUS     current
    DESCRIPTION
            "Defines whether the UPS will be shut down after an 
             Operating System shutdown."
    ::= { geClientUPSEntry 12 }

geClientMaxScriptExecutionTime OBJECT-TYPE
    SYNTAX     NonNegativeInteger32
    MAX-ACCESS read-only
    STATUS     current
    DESCRIPTION
            "The max. number of seconds the script file is allowed to run."
    ::= { geClientUPSEntry 13 }
						
geClientGraceperiod OBJECT-TYPE
    SYNTAX     NonNegativeInteger32
    MAX-ACCESS read-only
    STATUS     current
    DESCRIPTION
            "The time between start of the Operating System shutdown 
             and the UPS shutdown."
    ::= { geClientUPSEntry 14 }

-- Scheduled Tests

geClientNumTests OBJECT-TYPE
    SYNTAX     NonNegativeInteger32
    MAX-ACCESS read-only
    STATUS     current
    DESCRIPTION
            "The number of scheduled tests.
            This entry indicates the number of rows in the table."
    ::= { geClient 20 }

geClientTestTable OBJECT-TYPE
    SYNTAX     SEQUENCE OF GeClientTestEntry
    MAX-ACCESS not-accessible
    STATUS     current
    DESCRIPTION
            "A list of test table entries.  The number of
            entries is given by the value of geClientNumTests."
    ::= { geClient 21 }

geClientTestEntry OBJECT-TYPE
    SYNTAX     GeClientTestEntry
    MAX-ACCESS not-accessible
    STATUS     current
    DESCRIPTION
            "An entry containing information applicable to a
            particular Test."
    INDEX { geClientTestLineIndex }
    ::= { geClientTestTable 1 }

GeClientTestEntry ::= SEQUENCE {
    geClientTestLineIndex    PositiveInteger32,
    geClientTestId           Integer32,
    geClientTestDayTime      Integer32,
    geClientTestWeekDay	Integer32,
    geClientTestMonthDay	Integer32
}

geClientTestLineIndex OBJECT-TYPE
    SYNTAX     PositiveInteger32
    MAX-ACCESS not-accessible
    STATUS     current
    DESCRIPTION
            "The test line identifier."
    ::= { geClientTestEntry 1 }

geClientTestId OBJECT-TYPE
    SYNTAX     Integer32
    MAX-ACCESS read-write
    STATUS     current
    DESCRIPTION
            "The test Id."
    ::= { geClientTestEntry 2 }
		
geClientTestDayTime OBJECT-TYPE
    SYNTAX     Integer32
    MAX-ACCESS read-write
    STATUS     current
    DESCRIPTION
            "The time on which the test is due to be performed."
    ::= { geClientTestEntry 3 }

geClientTestWeekDay OBJECT-TYPE
    SYNTAX     Integer32
    MAX-ACCESS read-write
    STATUS     current
    DESCRIPTION
            "The day in the week on which the test will be performed."
    ::= { geClientTestEntry 4 }

geClientTestMonthDay OBJECT-TYPE
    SYNTAX     Integer32
    MAX-ACCESS read-write
    STATUS     current
    DESCRIPTION
            "The month day on which the test will be performed."
    ::= { geClientTestEntry 5 }

-- ScheduledShutdown

geClientNumShutdowns OBJECT-TYPE
    SYNTAX     NonNegativeInteger32
    MAX-ACCESS read-only
    STATUS     current
    DESCRIPTION
            "The number of scheduled Shutdowns.
            This entry indicates the number of rows in the table."
    ::= { geClient 30 }

geClientShutdownTable OBJECT-TYPE
    SYNTAX     SEQUENCE OF GeClientShutdownEntry
    MAX-ACCESS not-accessible
    STATUS     current
    DESCRIPTION
            "A list of Shutdown table entries.  The number of
            entries is given by the value of geClientNumShutdowns."
    ::= { geClient 31 }

geClientShutdownEntry OBJECT-TYPE
    SYNTAX     GeClientShutdownEntry
    MAX-ACCESS not-accessible
    STATUS     current
    DESCRIPTION
            "An entry containing information applicable to a
            particular Shutdown."
    INDEX { geClientShutdownLineIndex }
    ::= { geClientShutdownTable 1 }

GeClientShutdownEntry ::= SEQUENCE {
    geClientShutdownLineIndex    PositiveInteger32,
    geClientShutdownDelay        Integer32,
    geClientShutdownDuration     Integer32,
    geClientShutdownDayTime      Integer32,
    geClientShutdownWeekDay      Integer32,
    geClientShutdownMonthDay	    Integer32,
    geClientShutdownPreWarnTime  Integer32
}

geClientShutdownLineIndex OBJECT-TYPE
    SYNTAX     PositiveInteger32
    MAX-ACCESS not-accessible
    STATUS     current
    DESCRIPTION
            "The Shutdown line identifier."
    ::= { geClientShutdownEntry 1 }

geClientShutdownDelay OBJECT-TYPE
    SYNTAX     Integer32
    MAX-ACCESS read-write
    STATUS     current
    DESCRIPTION
            "The delay before start of the Shutdown."
    ::= { geClientShutdownEntry 2 }

geClientShutdownDuration OBJECT-TYPE
    SYNTAX     Integer32
    MAX-ACCESS read-write
    STATUS     current
    DESCRIPTION
            "The duration of the Shutdown."
    ::= { geClientShutdownEntry 3 }
	
geClientShutdownDayTime OBJECT-TYPE
    SYNTAX     Integer32
    MAX-ACCESS read-write
    STATUS     current
    DESCRIPTION
            "The time on which the Shutdown is due to be performed."
    ::= { geClientShutdownEntry 4 }

geClientShutdownWeekDay OBJECT-TYPE
    SYNTAX     Integer32
    MAX-ACCESS read-write
    STATUS     current
    DESCRIPTION
            "The day in the week on which the Shutdown will be performed."
    ::= { geClientShutdownEntry 5 }

geClientShutdownMonthDay OBJECT-TYPE
    SYNTAX     Integer32
    MAX-ACCESS read-write
    STATUS     current
    DESCRIPTION
            "The month day on which the Shutdown will be performed."
    ::= { geClientShutdownEntry 6 }

geClientShutdownPreWarnTime OBJECT-TYPE
    SYNTAX     Integer32
    MAX-ACCESS read-write
    STATUS     current
    DESCRIPTION
            "The number of seconds before start of the shutdown a pre 
             warning will be raised."
    ::= { geClientShutdownEntry 7 }

--
-- The AgentConfig group
--

geAgentUDPPort OBJECT-TYPE
    SYNTAX     NonNegativeInteger32
    MAX-ACCESS read-write
    STATUS     current
    DESCRIPTION
            "The UDP port number used by agent."
    ::= { geAgentConfig 1 }

geAgentWebServerPort OBJECT-TYPE
    SYNTAX     NonNegativeInteger32
    MAX-ACCESS read-write
    STATUS     current
    DESCRIPTION
            "The UDP port number used by the HTTP server."
    ::= { geAgentConfig 2 }

geAgentComPort OBJECT-TYPE
    SYNTAX     DisplayString(SIZE(0..32))
    MAX-ACCESS read-write
    STATUS     current
    DESCRIPTION
            "The COM port used by the agent."
    ::= { geAgentConfig 3 }

geAgentComTimeout OBJECT-TYPE
    SYNTAX     NonNegativeInteger32
    MAX-ACCESS read-write
    STATUS     current
    DESCRIPTION
            "The Timeout delay in seconds of the serial communication."
    ::= { geAgentConfig 4 }

geAgentComRetries OBJECT-TYPE
    SYNTAX     NonNegativeInteger32
    MAX-ACCESS read-write
    STATUS     current
    DESCRIPTION
            "The number of retries when serial communication fails."
    ::= { geAgentConfig 5 }

geAgentReadCommunity OBJECT-TYPE
    SYNTAX     DisplayString(SIZE(0..63))
    MAX-ACCESS read-write
    STATUS     current
    DESCRIPTION
            "The read community string of the agent."
    ::= { geAgentConfig 6 }

geAgentWriteCommunity OBJECT-TYPE
    SYNTAX     DisplayString(SIZE(0..63))
    MAX-ACCESS read-write
    STATUS     current
    DESCRIPTION
            "The write community string of the agent."
    ::= { geAgentConfig 7 }

geAgentResponsibleEmailAddress OBJECT-TYPE
    SYNTAX     DisplayString(SIZE(0..63))
    MAX-ACCESS read-write
    STATUS     current
    DESCRIPTION
            "The email address of the responsible person for this agent."
    ::= { geAgentConfig 8 }

geRFCTrapsToSend OBJECT-TYPE
    SYNTAX     Integer32 {
        off(0),
        on(1)
    }
    MAX-ACCESS read-write
    STATUS     current
    DESCRIPTION
            "This object defines whether RFC traps need to be send.
             The bit value 1 indicates that the traps needs to be send, while 
             value 0 does not result in a trap to send."
    ::= { geAgentConfig 9 }

geIMVTrapsToSend OBJECT-TYPE
    SYNTAX     NonNegativeInteger32
    MAX-ACCESS read-write
    STATUS     current
    DESCRIPTION
            "This object defines for which device(s) IMV traps need to be send.
             The bit value 1 indicates that the trap needs to be send, while 
             value 0 does not result in a trap to send.
             The value presents the devices as a mask:
		   1  GenericUPS
               2  FirstUPS
               4  SecondUPS
	         8  ThirdUPS
	        16  FourthUPS
	        32  FifthUPS
              64  SixthUPS
             128  SeventhUPS
             256  EigthUPS
             512  IOInterface
            "
    ::= { geAgentConfig 10 }

--
-- The AgentTrap group
--

geAgentNumTraps OBJECT-TYPE
    SYNTAX     NonNegativeInteger32
    MAX-ACCESS read-only
    STATUS     current
    DESCRIPTION
            "The number of configured traps.
            This entry indicates the number of rows in the table."
    ::= { geAgentTraps 1 }

geAgentTrapTable OBJECT-TYPE
    SYNTAX     SEQUENCE OF GeAgentTrapEntry
    MAX-ACCESS not-accessible
    STATUS     current
    DESCRIPTION
            "A list of trap table entries.  The number of
            entries is given by the value of geAgentNumTraps."
    ::= { geAgentTraps 2 }

geAgentTrapEntry OBJECT-TYPE
    SYNTAX     GeAgentTrapEntry
    MAX-ACCESS not-accessible
    STATUS     current
    DESCRIPTION
            "An entry containing information applicable to a
            particular trap target."
    INDEX { geAgentTrapLineIndex }
    ::= { geAgentTrapTable 1 }

GeAgentTrapEntry ::= SEQUENCE {
    geAgentTrapLineIndex    PositiveInteger32,
    geAgentTrapAddress      DisplayString,
    geAgentTrapCommunity    DisplayString,
    geAgentTrapPort         Integer32
}

geAgentTrapLineIndex OBJECT-TYPE
    SYNTAX     PositiveInteger32
    MAX-ACCESS not-accessible
    STATUS     current
    DESCRIPTION
            "The Trap line identifier."
    ::= { geAgentTrapEntry 1 }

geAgentTrapAddress OBJECT-TYPE
    SYNTAX     DisplayString(SIZE(0..63))
    MAX-ACCESS read-write
    STATUS     current
    DESCRIPTION
            "The destination IP-address of the trap."
    ::= { geAgentTrapEntry 2 }

geAgentTrapCommunity OBJECT-TYPE
    SYNTAX     DisplayString(SIZE(0..63))
    MAX-ACCESS read-write
    STATUS     current
    DESCRIPTION
            "The communication string used by the trap."
    ::= { geAgentTrapEntry 3 }
	
geAgentTrapPort OBJECT-TYPE
    SYNTAX     Integer32
    MAX-ACCESS read-write
    STATUS     current
    DESCRIPTION
            "The UDP port on the receiving side."
    ::= { geAgentTrapEntry 4 }

END
