G9982-MIB DEFINITIONS ::= BEGIN

  IMPORTS
    MODULE-IDENTITY,
    OBJECT-TYPE,
    Counter32,
    mib-2,
    Unsigned32
      FROM SNMPv2-SMI           -- RFC 2578
    TEXTUAL-CONVENTION,
    TruthValue,
    PhysAddress
      FROM SNMPv2-TC            -- RFC 2579
    MODULE-COMPLIANCE,
    OBJECT-GROUP
      FROM SNMPv2-CONF          -- RFC 2580
    ifIndex
      FROM IF-MIB               -- RFC 2863
    HCPerfCurrentCount,
    HCPerfValidIntervals,
    HCPerfInvalidIntervals,
    HCPerfTimeElapsed
      FROM  HC-PerfHist-TC-MIB  -- RFC 3705
    ;
------------------------------------------------------------------------
  g9982MIB MODULE-IDENTITY
    LAST-UPDATED "201302200000Z"  -- 20 February 2013
    ORGANIZATION "IETF ADSL MIB Working Group"
    CONTACT-INFO
      "WG charter:
        http://datatracker.ietf.org/wg/adslmib/charter/

      Mailing Lists:
        General Discussion: adslmib@ietf.org
        To Subscribe: adslmib-request@ietf.org
        In Body: subscribe your_email_address

       Chair: Menachem Dodge
      Postal: ECI Telecom, Ltd.
              30 Hasivim St.
              Petach-Tikva  4951169
              Israel
       Phone: +972-3-926-8421
       EMail: menachemdodge1@gmail.com

      Editor: Edward Beili
      Postal: Actelis Networks, Inc.
              25 Bazel St., P.O.B. 10173
              Petach-Tikva  49103
              Israel
       Phone: +972-3-924-3491
       EMail: edward.beili@actelis.com

      Editor: Moti Morgenstern
      Postal: ECI Telecom
              30 Hasivim St.
              Petach-Tikva  4951169
              Israel
       Phone: +972-3-926-6258
       EMail: moti.morgenstern@ecitele.com"
    DESCRIPTION
      "The objects in this MIB module are used to manage the
      Ethernet-based multi-pair bonded xDSL interfaces, as defined in
      ITU-T Recommendation G.998.2 (G.Bond/Ethernet).

      This MIB module MUST be used in conjunction with the GBOND-MIB
      module, common to all G.Bond technologies.

      The following references are used throughout this MIB module:

      [G.998.2] refers to:
        ITU-T Recommendation G.998.2: 'Ethernet-based multi-pair
        bonding', January 2005.

      [G.998.2-Amd2] refers to:
        ITU-T Recommendation G.998.2 Amendment 2, December 2007.

      [802.3] refers to:
        IEEE Std 802.3-2005: 'IEEE Standard for Information
        technology - Telecommunications and information exchange
        between systems - Local and metropolitan area networks -
        Specific requirements -

        Part 3: Carrier Sense Multiple Access with Collision
        Detection (CSMA/CD) Access Method and Physical Layer
        Specifications', December 2005.

      [TR-159] refers to:
        Broadband Forum Technical Report: 'Management Framework for
        xDSL Bonding', December 2008.

      Naming Conventions:
        BACP   - Bonding Aggregation Control Protocol
        BCE    - Bonding Channel Entity
        BTU    - Bonding Terminating Unit
        BTU-C  - Bonding Terminating Unit, CO side
        BTU-R  - Bonding Terminating Unit, Remote Terminal (CPE) side
        CO     - Central Office
        CPE    - Customer Premises Equipment
        GBS    - Generic Bonding Sub-layer
        HDLC   - High-level Data Link Control
        PTM-TC - Packet Transfer Mode Transmission Convergence
                 (sub-layer)
        SNR    - Signal to Noise Ratio
        TC     - Transmission Convergence (sub-layer)
        UAS    - Unavailable Seconds

     Copyright (c) 2013 IETF Trust and the persons identified as
     authors of the code.  All rights reserved.

     Redistribution and use in source and binary forms, with or without
     modification, is permitted pursuant to, and subject to the license
     terms contained in, the Simplified BSD License set forth in Section
     4.c of the IETF Trust's Legal Provisions Relating to IETF Documents
     (http://trustee.ietf.org/license-info)."

    REVISION    "201302200000Z"  -- 20 February 2013
    DESCRIPTION "Initial version, published as RFC 6767."
    ::= { mib-2 264 }

   -- Sections of the module
   -- Structured as recommended by RFC 4181, Appendix D

   g9982Objects     OBJECT IDENTIFIER ::= { g9982MIB 1 }

   g9982Conformance OBJECT IDENTIFIER ::= { g9982MIB 2 }

   -- Groups in the module

   g9982Port        OBJECT IDENTIFIER ::= { g9982Objects 1 }

   g9982Bce         OBJECT IDENTIFIER ::= { g9982Objects 2 }

   -------------------------------
   -- Textual Conventions
   -------------------------------

   G9982PtmTcType ::= TEXTUAL-CONVENTION
     STATUS       current
     DESCRIPTION
       "This textual convention represents possible PTM-TC types in
       G.Bond/Eth ports.  The following values are defined:
         tc6465         - 64/65-octet encapsulation, as defined in
                          [802.3] Clause 61.3.3.
         tcHDLC         - HDLC encapsulation, as defined in [G.998.2]
                          Annex B."
     SYNTAX      INTEGER {
       tc6465(1),
       tcHDLC(2)
     }

   G9982CpType ::= TEXTUAL-CONVENTION
     STATUS       current
     DESCRIPTION
       "This textual convention represents possible control protocol
       types in G.Bond/Eth ports.  The following values are defined:
         unknown      - the control protocol cannot be determined.
         cpHS         - G.hs-based discovery and aggregation,
                        as specified in [G.998.2].
         cpBACP       - Bonding Aggregation Control Protocol (BACP) --
                        a frame-based discovery, aggregation, and link
                        management protocol, as specified in
                        [G.998.2-Amd2] Annex C."
     SYNTAX      INTEGER {
       unknown(0),
       cpHS(1),
       cpBACP(2)
     }

   -------------------------------
   -- GBS Notifications group
   -------------------------------

     -- empty --

   -------------------------------
   -- GBS group
   -------------------------------

   g9982PortConfTable OBJECT-TYPE
     SYNTAX      SEQUENCE OF G9982PortConfEntry
     MAX-ACCESS  not-accessible
     STATUS      current
     DESCRIPTION
       "Table for configuration of G.Bond/Eth GBS ports.  Entries in
       this table MUST be maintained in a persistent manner."
     ::= { g9982Port 1 }

   g9982PortConfEntry OBJECT-TYPE
     SYNTAX      G9982PortConfEntry
     MAX-ACCESS  not-accessible
     STATUS      current
     DESCRIPTION
       "An entry in the G.Bond/Eth Port Configuration table.
       Each entry represents a G.Bond Ethernet port indexed by the
       ifIndex.
       Note that a G.Bond/Eth GBS port runs on top of a single or
       multiple BCE port(s), which are also indexed by the ifIndex."
     INDEX  { ifIndex }
     ::= { g9982PortConfTable 1 }

   G9982PortConfEntry ::=
     SEQUENCE {
       g9982PortConfTcAdminType         G9982PtmTcType,
       g9982PortConfAdminCp             G9982CpType
     }

   g9982PortConfTcAdminType  OBJECT-TYPE
     SYNTAX      G9982PtmTcType
     MAX-ACCESS  read-write
     STATUS      current
     DESCRIPTION
       "Administrative (desired) PTM-TC encapsulation type of a
       G.Bond/Eth port (GBS).
       Possible values are:
         tc6465(1)  - 64/65-octet encapsulation
         tcHDLC(2)  - HDLC encapsulation

       Attempts to set a port to a non-supported PTM-TC encapsulation
       type (see g9982PortCapTcTypesSupported) SHALL be rejected
       (with the error inconsistentValue).

       Changing g9982PortConfTcAdminType is a traffic-disruptive
       operation and as such SHALL be done when the link (GBS) is
       administratively 'down', as indicated by the ifAdminStatus object
       in the IF-MIB.
       Attempts to change this object SHALL be rejected (with the error
       inconsistentValue) if the link is 'up' or initializing.

       This object maps to the TR-159 attribute aEthTcAdminType."
     REFERENCE
       "[TR-159], Section 5.5.3.4; RFC 2863, IF-MIB, ifAdminStatus"
     ::= { g9982PortConfEntry 1 }

   g9982PortConfAdminCp  OBJECT-TYPE
     SYNTAX      G9982CpType
     MAX-ACCESS  read-write
     STATUS      current
     DESCRIPTION
       "Administrative (desired) bonding control protocol of a
       G.Bond/Eth port (GBS).  Possible values are:
         cpHS(1)    - use G.hs-based protocol (default)
         cpBACP(2)  - use frame-based BACP

       Note that G.hs-based protocol support is mandatory, according to
       [G.998.2].  Attempts to set a port to a non-supported bonding
       control protocol (e.g., BACP if the value of
       g9982PortCapBacpSupported is false) SHALL be rejected
       (with the error inconsistentValue).

       Changing g9982PortConfAdminCp is a traffic-disruptive
       operation and as such SHALL be done when the link (GBS) is
       administratively 'down', as indicated by the ifAdminStatus
       object in the IF-MIB.
       Attempts to change this object SHALL be rejected (with the error
       inconsistentValue) if the link is 'up' or initializing.

       This object maps to the TR-159 attribute aEthAdminCP."
     REFERENCE
       "[TR-159], Section 5.5.3.2; RFC 2863, IF-MIB, ifAdminStatus"
     DEFVAL { cpHS }
     ::= { g9982PortConfEntry 2 }

   g9982PortCapTable OBJECT-TYPE
     SYNTAX      SEQUENCE OF G9982PortCapEntry
     MAX-ACCESS  not-accessible
     STATUS      current
     DESCRIPTION
       "Table for capabilities of G.Bond/Eth ports.  Entries in this
       table MUST be maintained in a persistent manner."
     ::= { g9982Port 2 }

   g9982PortCapEntry OBJECT-TYPE
     SYNTAX      G9982PortCapEntry
     MAX-ACCESS  not-accessible
     STATUS      current
     DESCRIPTION
       "An entry in the G.Bond/Eth Port Capability table.
       Each entry represents a G.Bond port indexed by the ifIndex.
       Note that a G.Bond GBS port runs on top of a single or
       multiple BCE port(s), which are also indexed by the ifIndex."
     INDEX  { ifIndex }
     ::= { g9982PortCapTable 1 }

   G9982PortCapEntry ::=
     SEQUENCE {
       g9982PortCapTcTypesSupported         BITS,
       g9982PortCapBacpSupported            TruthValue
     }

   g9982PortCapTcTypesSupported  OBJECT-TYPE
     SYNTAX      BITS {
       tc6465(0),
       tcHDLC(1)
     }
     MAX-ACCESS  read-only
     STATUS      current
     DESCRIPTION
       "PTM-TC encapsulation types supported by the G.Bond/Eth port.
       This is a bitmap of possible encapsulation types.  The various
       bit positions are:
         tc6465   - GBS is capable of 64/65-octet encapsulation
         tcHDLC   - GBS is capable of HDLC encapsulation

       A desired encapsulation is determined by
       g9982PortConfTcAdminType, while g9982PortStatTcOperType
       reflects the current operating mode.

       This object maps to the TR-159 attribute aEthTcTypesSupported."
     REFERENCE
       "[TR-159], Section 5.5.3.6"
     ::= { g9982PortCapEntry 1 }

   g9982PortCapBacpSupported  OBJECT-TYPE
     SYNTAX      TruthValue
     MAX-ACCESS  read-only
     STATUS      current
     DESCRIPTION
       "Indicates whether the Bonding Aggregation Control Protocol
       (BACP) -- the frame-based discovery, aggregation, and link
       management protocol specified in [G.998.2-Amd2]) is supported
       by the G.Bond/Ethernet port.
       A value of true(1) indicates that BACP is supported.
       A value of false(2) indicates that BACP is unsupported.

       The BACP functionality, if supported, can be enabled or
       disabled via g9982AdminCP, while g9982OperCP
       reflects the current BACP operating mode.

       This object maps to the TR-159 attribute aEthBACPSupported."
     REFERENCE
       "[TR-159], Section 5.5.3.1; [G.998.2-Amd2], Annex C"
     ::= { g9982PortCapEntry 2 }

   g9982PortStatTable OBJECT-TYPE
     SYNTAX      SEQUENCE OF G9982PortStatEntry
     MAX-ACCESS  not-accessible
     STATUS      current
     DESCRIPTION
       "This table provides overall status information of G.Bond
       ports, complementing the generic status information from the
       ifTable of the IF-MIB.  Additional status information about
       connected BCEs is available from the relevant line MIBs.

       This table contains live data from the equipment.  As such,
       it is NOT persistent."
     ::= { g9982Port 3 }

   g9982PortStatEntry OBJECT-TYPE
     SYNTAX      G9982PortStatEntry
     MAX-ACCESS  not-accessible
     STATUS      current
     DESCRIPTION
       "An entry in the G.Bond/Eth Port Status table.
       Each entry represents a G.Bond/Eth port indexed by the
       ifIndex.
       Note that a G.Bond GBS port runs on top of a single or
       multiple BCE port(s), which are also indexed by the ifIndex."
     INDEX  { ifIndex }
     ::= { g9982PortStatTable 1 }

   G9982PortStatEntry ::=
     SEQUENCE {
       g9982PortStatTcOperType            G9982PtmTcType,
       g9982PortStatOperCp                G9982CpType,
       g9982PortStatRxErrors              Counter32,
       g9982PortStatRxSmallFragments      Counter32,
       g9982PortStatRxLargeFragments      Counter32,
       g9982PortStatRxBadFragments        Counter32,
       g9982PortStatRxLostFragments       Counter32,
       g9982PortStatRxLostStarts          Counter32,
       g9982PortStatRxLostEnds            Counter32,
       g9982PortStatRxOverflows           Counter32
     }

   g9982PortStatTcOperType  OBJECT-TYPE
     SYNTAX      G9982PtmTcType
     MAX-ACCESS  read-only
     STATUS      current
     DESCRIPTION
       "Current operational encapsulation type of the G.Bond/Eth
       port.
       Possible values are:
         tc6465(1)   - GBS uses 64/65-octet encapsulation
         tcHDLC(2)   - GBS uses HDLC encapsulation

       The operational PTM-TC encapsulation type can be configured
       via g9982PortConfTcAdminType.

       This object maps to the TR-159 attribute aEthTcOperType."
     REFERENCE
       "[TR-159], Section 5.5.3.5"
     ::= { g9982PortStatEntry 1 }

   g9982PortStatOperCp  OBJECT-TYPE
     SYNTAX      G9982CpType
     MAX-ACCESS  read-only
     STATUS      current
     DESCRIPTION
       "Current operational bonding discovery and aggregation control
       protocol of the G.Bond/Eth port.
       Possible values are:
         unknown(0)  - the protocol cannot be determined, e.g., when
                       the GBS is 'down'
         cpHS(1)     - GBS uses G.hs-based protocol
         cpBACP(2)   - GBS uses frame-based BACP

       The operational discovery and aggregation control protocol can
       be configured via the g9982PortConfAdminCp variable.

       This object maps to the TR-159 attribute aEthOperCP."
     REFERENCE
       "[TR-159], Section 5.5.3.3"
     ::= { g9982PortStatEntry 2 }

   g9982PortStatRxErrors OBJECT-TYPE
     SYNTAX      Counter32
     UNITS       "fragments"
     MAX-ACCESS  read-only
     STATUS      current
     DESCRIPTION
       "A number of Ethernet frame fragments that have been received
       by the bonding function and discarded due to various errors.

       Discontinuities in the value of this counter can occur at
       re-initialization of the management system, and at other times
       as indicated by the value of ifCounterDiscontinuityTime, as
       defined in the IF-MIB.

       This object maps to the TR-159 attribute aEthRxErrors."
     REFERENCE
       "[TR-159], Section 5.5.3.7"
     ::= { g9982PortStatEntry 3 }

   g9982PortStatRxSmallFragments OBJECT-TYPE
     SYNTAX      Counter32
     UNITS       "fragments"
     MAX-ACCESS  read-only
     STATUS      current
     DESCRIPTION
       "A number of fragments smaller than minFragmentSize (64 bytes)
       that have been received by the bonding function and discarded.

       Discontinuities in the value of this counter can occur at
       re-initialization of the management system, and at other times
       as indicated by the value of ifCounterDiscontinuityTime, as
       defined in the IF-MIB.

       This object maps to the TR-159 attribute aEthRxSmallFragments."
     REFERENCE
       "[TR-159], Section 5.5.3.8"
     ::= { g9982PortStatEntry 4 }

   g9982PortStatRxLargeFragments OBJECT-TYPE
     SYNTAX      Counter32
     UNITS       "fragments"
     MAX-ACCESS  read-only
     STATUS      current
     DESCRIPTION
       "A number of fragments larger than maxFragmentSize (512 bytes)
       that have been received by the bonding function and discarded.

       Discontinuities in the value of this counter can occur at
       re-initialization of the management system, and at other times
       as indicated by the value of ifCounterDiscontinuityTime, as
       defined in the IF-MIB.

       This object maps to the TR-159 attribute aEthRxLargeFragments."
     REFERENCE
       "[TR-159], Section 5.5.3.9"
     ::= { g9982PortStatEntry 5 }

   g9982PortStatRxBadFragments OBJECT-TYPE
     SYNTAX      Counter32
     UNITS       "fragments"
     MAX-ACCESS  read-only
     STATUS      current
     DESCRIPTION
       "A number of fragments that do not fit into the sequence
       expected by the frame assembly function and that have been
       received and discarded by the bonding function (the frame buffer
       is flushed to the next valid frame start).

       Discontinuities in the value of this counter can occur at
       re-initialization of the management system, and at other times
       as indicated by the value of ifCounterDiscontinuityTime, as
       defined in the IF-MIB.

       This object maps to the TR-159 attribute aEthRxBadFragments."
     REFERENCE
       "[TR-159], Section 5.5.3.10"
     ::= { g9982PortStatEntry 6 }

   g9982PortStatRxLostFragments OBJECT-TYPE
     SYNTAX      Counter32
     UNITS       "fragments"
     MAX-ACCESS  read-only
     STATUS      current
     DESCRIPTION
       "A number of gaps in the sequence of fragments that have
       been received by the bonding function (the frame buffer is
       flushed to the next valid frame start, when a fragment or
       fragments expected by the frame assembly function are not
       received).

       Discontinuities in the value of this counter can occur at
       re-initialization of the management system, and at other times
       as indicated by the value of ifCounterDiscontinuityTime, as
       defined in the IF-MIB.

       This object maps to the TR-159 attribute aEthRxLostFragments."
     REFERENCE
       "[TR-159], Section 5.5.3.11"
     ::= { g9982PortStatEntry 7 }

   g9982PortStatRxLostStarts OBJECT-TYPE
     SYNTAX      Counter32
     MAX-ACCESS  read-only
     STATUS      current
     DESCRIPTION
       "A number of missing StartOfPacket indicators expected by the
       frame assembly function.

       Discontinuities in the value of this counter can occur at
       re-initialization of the management system, and at other times
       as indicated by the value of ifCounterDiscontinuityTime, as
       defined in the IF-MIB.

       This object maps to the TR-159 attribute aEthRxLostStarts."
     REFERENCE
       "[TR-159], Section 5.5.3.12"
     ::= { g9982PortStatEntry 8 }

   g9982PortStatRxLostEnds OBJECT-TYPE
     SYNTAX      Counter32
     MAX-ACCESS  read-only
     STATUS      current
     DESCRIPTION
       "A number of missing EndOfPacket indicators expected by the
       frame assembly function.

       Discontinuities in the value of this counter can occur at
       re-initialization of the management system, and at other times
       as indicated by the value of ifCounterDiscontinuityTime, as
       defined in the IF-MIB.

       This object maps to the TR-159 attribute aEthRxLostEnds."
     REFERENCE
       "[TR-159], Section 5.5.3.13"
     ::= { g9982PortStatEntry 9 }

   g9982PortStatRxOverflows OBJECT-TYPE
     SYNTAX      Counter32
     UNITS       "fragments"
     MAX-ACCESS  read-only
     STATUS      current
     DESCRIPTION
       "A number of fragments, received and discarded by the bonding
       function, that would have caused the frame assembly buffer to
       overflow.

       Discontinuities in the value of this counter can occur at
       re-initialization of the management system, and at other times
       as indicated by the value of ifCounterDiscontinuityTime, as
       defined in the IF-MIB.

       This object maps to the TR-159 attribute aEthRxOverflows."
     REFERENCE
       "[TR-159], Section 5.5.3.14"
     ::= { g9982PortStatEntry 10 }

   -------------------------------
   -- GBS Performance Monitoring group
   -------------------------------

   g9982PM   OBJECT IDENTIFIER ::= { g9982Port 4 }

   g9982PortPmCurTable OBJECT-TYPE
     SYNTAX      SEQUENCE OF G9982PortPmCurEntry
     MAX-ACCESS  not-accessible
     STATUS      current
     DESCRIPTION
       "This table contains current Performance Monitoring information
       for a G.Bond/Eth port.  This table contains live data from the
       equipment and as such is NOT persistent."
     ::= { g9982PM 1 }

   g9982PortPmCurEntry OBJECT-TYPE
     SYNTAX      G9982PortPmCurEntry
     MAX-ACCESS  not-accessible
     STATUS      current
     DESCRIPTION
       "An entry in the G.Bond/Eth Port PM table.
       Each entry represents a G.Bond/Eth port indexed by the
       ifIndex."
     INDEX  { ifIndex }
     ::= { g9982PortPmCurTable 1 }

   G9982PortPmCurEntry ::=
     SEQUENCE {
       g9982PortPm15MinValidIntervals      HCPerfValidIntervals,
       g9982PortPm15MinInvalidIntervals    HCPerfInvalidIntervals,
       g9982PortPmCur15MinTimeElapsed      HCPerfTimeElapsed,
       g9982PortPmCur15MinRxErrors         HCPerfCurrentCount,
       g9982PortPmCur15MinRxSmallFragments HCPerfCurrentCount,
       g9982PortPmCur15MinRxLargeFragments HCPerfCurrentCount,
       g9982PortPmCur15MinRxBadFragments   HCPerfCurrentCount,
       g9982PortPmCur15MinRxLostFragments  HCPerfCurrentCount,
       g9982PortPmCur15MinRxLostStarts     HCPerfCurrentCount,
       g9982PortPmCur15MinRxLostEnds       HCPerfCurrentCount,
       g9982PortPmCur15MinRxOverflows      HCPerfCurrentCount,
       g9982PortPm1DayValidIntervals       Unsigned32,
       g9982PortPm1DayInvalidIntervals     Unsigned32,
       g9982PortPmCur1DayTimeElapsed       HCPerfTimeElapsed,
       g9982PortPmCur1DayRxErrors          HCPerfCurrentCount,
       g9982PortPmCur1DayRxSmallFragments  HCPerfCurrentCount,
       g9982PortPmCur1DayRxLargeFragments  HCPerfCurrentCount,
       g9982PortPmCur1DayRxBadFragments    HCPerfCurrentCount,
       g9982PortPmCur1DayRxLostFragments   HCPerfCurrentCount,
       g9982PortPmCur1DayRxLostStarts      HCPerfCurrentCount,
       g9982PortPmCur1DayRxLostEnds        HCPerfCurrentCount,
       g9982PortPmCur1DayRxOverflows       HCPerfCurrentCount
     }

   g9982PortPm15MinValidIntervals  OBJECT-TYPE
     SYNTAX      HCPerfValidIntervals
     MAX-ACCESS  read-only
     STATUS      current
     DESCRIPTION
       "A read-only number of 15-minute intervals for which the
       performance data was collected.  The value of this object will
       be 96 or the maximum number of 15-minute history intervals
       collected by the implementation, unless the measurement was
       (re)started recently, in which case the value will be the
       number of complete 15-minute intervals for which there are at
       least some data.
       In certain cases, it is possible that some intervals are
       unavailable.  In this case, this object reports the maximum
       interval number for which data is available.

       This object partially maps to the TR-159 attribute
       aGroupPerf15MinValidIntervals."
     REFERENCE
       "[TR-159], Section 5.5.1.32"
     ::= { g9982PortPmCurEntry 1 }

   g9982PortPm15MinInvalidIntervals  OBJECT-TYPE
     SYNTAX      HCPerfInvalidIntervals
     MAX-ACCESS  read-only
     STATUS      current
     DESCRIPTION
       "A read-only number of 15-minute intervals for which the
       performance data was not always available.  The value will
       typically be zero, except in cases where the data for some
       intervals are not available.

       This object partially maps to the TR-159 attribute
       aGroupPerf15MinInvalidIntervals."
     REFERENCE
       "[TR-159], Section 5.5.1.33"
     ::= { g9982PortPmCurEntry 2 }

   g9982PortPmCur15MinTimeElapsed  OBJECT-TYPE
     SYNTAX      HCPerfTimeElapsed
     UNITS       "seconds"
     MAX-ACCESS  read-only
     STATUS      current
     DESCRIPTION
       "A read-only count of seconds that have elapsed since the
       beginning of the current 15-minute performance interval.

       This object partially maps to the TR-159 attribute
       aGroupPerfCurr15MinTimeElapsed."
     REFERENCE
       "[TR-159], Section 5.5.1.34"
     ::= { g9982PortPmCurEntry 3 }

   g9982PortPmCur15MinRxErrors  OBJECT-TYPE
     SYNTAX      HCPerfCurrentCount
     UNITS       "fragments"
     MAX-ACCESS  read-only
     STATUS      current
     DESCRIPTION
       "A read-only count of errored fragments received and discarded
       by a G.Bond/Eth port during the current 15-minute performance
       interval.

       Note that the total number of errored fragments is indicated by
       the g9982PortStatRxErrors object.

       This object is inhibited during Unavailable Seconds (UAS)."
     REFERENCE
       "[TR-159], Section 5.5.3.7"
     ::= { g9982PortPmCurEntry 4}

   g9982PortPmCur15MinRxSmallFragments  OBJECT-TYPE
     SYNTAX      HCPerfCurrentCount
     UNITS       "fragments"
     MAX-ACCESS  read-only
     STATUS      current
     DESCRIPTION
       "A read-only count of fragments smaller than minFragmentSize
       (64 bytes) that have been received and discarded by a
       G.Bond/Eth port during the current 15-minute performance
       interval.

       Note that the total number of small fragments is indicated by
       the g9982PortStatRxSmallFragments object.

       This object is inhibited during Unavailable Seconds (UAS)."
     REFERENCE
       "[TR-159], Section 5.5.3.8"
     ::= { g9982PortPmCurEntry 5}

   g9982PortPmCur15MinRxLargeFragments  OBJECT-TYPE
     SYNTAX      HCPerfCurrentCount
     UNITS       "fragments"
     MAX-ACCESS  read-only
     STATUS      current
     DESCRIPTION
       "A read-only count of fragments larger than maxFragmentSize
       (512 bytes) that have been received and discarded by a
       G.Bond/Eth port during the current 15-minute performance
       interval.

       Note that the total number of large fragments is indicated by
       the g9982PortStatRxLargeFragments object.

       This object is inhibited during Unavailable Seconds (UAS)."
     REFERENCE
       "[TR-159], Section 5.5.3.9"
     ::= { g9982PortPmCurEntry 6}

   g9982PortPmCur15MinRxBadFragments  OBJECT-TYPE
     SYNTAX      HCPerfCurrentCount
     UNITS       "fragments"
     MAX-ACCESS  read-only
     STATUS      current
     DESCRIPTION
       "A read-only count of fragments that do not fit into the
       sequence expected by the frame assembly function and that have
       been received and discarded by a G.Bond/Eth port during the
       current 15-minute performance interval.

       Note that the total number of bad fragments is indicated by
       the g9982PortStatRxBadFragments object.

       This object is inhibited during Unavailable Seconds (UAS)."
     REFERENCE
       "[TR-159], Section 5.5.3.10"
     ::= { g9982PortPmCurEntry 7}

   g9982PortPmCur15MinRxLostFragments  OBJECT-TYPE
     SYNTAX      HCPerfCurrentCount
     UNITS       "fragments"
     MAX-ACCESS  read-only
     STATUS      current
     DESCRIPTION
       "A read-only count of gaps in the sequence of fragments
       expected by the frame assembly function of a G.Bond/Eth port
       during the current 15-minute performance interval.

       Note that the total number of these lost fragments is indicated
       by the g9982PortStatRxLostFragments object.

       This object is inhibited during Unavailable Seconds (UAS)."
     REFERENCE
       "[TR-159], Section 5.5.3.11"
     ::= { g9982PortPmCurEntry 8}

   g9982PortPmCur15MinRxLostStarts  OBJECT-TYPE
     SYNTAX      HCPerfCurrentCount
     MAX-ACCESS  read-only
     STATUS      current
     DESCRIPTION
       "A read-only count of missing StartOfPacket indicators expected
       by the frame assembly function of a G.Bond/Eth port during the
       current 15-minute performance interval.

       Note that the total number of missing StartOfPacket indicators
       is indicated by the g9982PortStatRxLostStarts object.

       This object is inhibited during Unavailable Seconds (UAS)."
     REFERENCE
       "[TR-159], Section 5.5.3.12"
     ::= { g9982PortPmCurEntry 9}

   g9982PortPmCur15MinRxLostEnds  OBJECT-TYPE
     SYNTAX      HCPerfCurrentCount
     MAX-ACCESS  read-only
     STATUS      current
     DESCRIPTION
       "A read-only count of missing EndOfPacket indicators expected
       by the frame assembly function of a G.Bond/Eth port during the
       current 15-minute performance interval.

       Note that the total number of missing EndOfPacket indicators
       is indicated by the g9982PortStatRxLostEnds object.

       This object is inhibited during Unavailable Seconds (UAS)."
     REFERENCE
       "[TR-159], Section 5.5.3.13"
     ::= { g9982PortPmCurEntry 10}

   g9982PortPmCur15MinRxOverflows  OBJECT-TYPE
     SYNTAX      HCPerfCurrentCount
     UNITS       "fragments"
     MAX-ACCESS  read-only
     STATUS      current
     DESCRIPTION
       "A read-only count of fragments that have been received and
       discarded by a G.Bond/Eth port, which would have caused the
       frame assembly buffer to overflow, during the current 15-minute
       performance interval.

       Note that the total number of fragments that would have caused
       the frame assembly buffer to overflow is indicated by the
       g9982PortStatRxOverflows object.

       This object is inhibited during Unavailable Seconds (UAS)."
     REFERENCE
       "[TR-159], Section 5.5.3.14"
     ::= { g9982PortPmCurEntry 11}

   g9982PortPm1DayValidIntervals  OBJECT-TYPE
     SYNTAX      Unsigned32 (0..7)
     UNITS       "days"
     MAX-ACCESS  read-only
     STATUS      current
     DESCRIPTION
       "A read-only number of 1-day intervals for which data was
       collected.  The value of this object will be 7 or the maximum
       number of 1-day history intervals collected by the
       implementation, unless the measurement was (re)started recently,
       in which case the value will be the number of complete 1-day
       intervals for which there are at least some data.
       In certain cases, it is possible that some intervals are
       unavailable.  In this case, this object reports the maximum
       interval number for which data is available."
     REFERENCE
       "[TR-159], Section 5.5.1.45"
     ::= { g9982PortPmCurEntry 12 }

   g9982PortPm1DayInvalidIntervals  OBJECT-TYPE
     SYNTAX      Unsigned32 (0..7)
     UNITS       "days"
     MAX-ACCESS  read-only
     STATUS      current
     DESCRIPTION
       "A read-only number of 1-day intervals for which data was not
       always available.  The value will typically be zero, except in
       cases where the data for some intervals are not available."
     REFERENCE
       "[TR-159], Section 5.5.1.46"
     ::= { g9982PortPmCurEntry 13 }

   g9982PortPmCur1DayTimeElapsed  OBJECT-TYPE
     SYNTAX      HCPerfTimeElapsed
     UNITS       "seconds"
     MAX-ACCESS  read-only
     STATUS      current
     DESCRIPTION
       "A read-only count of seconds that have elapsed since the
       beginning of the current 1-day performance interval."
     REFERENCE
       "[TR-159], Section 5.5.1.47"
     ::= { g9982PortPmCurEntry 14 }

   g9982PortPmCur1DayRxErrors  OBJECT-TYPE
     SYNTAX      HCPerfCurrentCount
     UNITS       "fragments"
     MAX-ACCESS  read-only
     STATUS      current
     DESCRIPTION
       "A read-only count of errored fragments received and discarded
       by a G.Bond/Eth port during the current 1-day performance
       interval.

       Note that the total number of errored fragments is indicated by
       the g9982PortStatRxErrors object.

       This object is inhibited during Unavailable Seconds (UAS)."
     REFERENCE
       "[TR-159], Section 5.5.3.7"
     ::= { g9982PortPmCurEntry 15 }

   g9982PortPmCur1DayRxSmallFragments  OBJECT-TYPE
     SYNTAX      HCPerfCurrentCount
     UNITS       "fragments"
     MAX-ACCESS  read-only
     STATUS      current
     DESCRIPTION
       "A read-only count of fragments smaller than minFragmentSize
       (64 bytes) that have been received and discarded by a
       G.Bond/Eth port during the current 1-day performance interval.

       Note that the total number of small fragments is indicated by
       the g9982PortStatRxSmallFragments object.

       This object is inhibited during Unavailable Seconds (UAS)."
     REFERENCE
       "[TR-159], Section 5.5.3.8"
     ::= { g9982PortPmCurEntry 16}

   g9982PortPmCur1DayRxLargeFragments  OBJECT-TYPE
     SYNTAX      HCPerfCurrentCount
     UNITS       "fragments"
     MAX-ACCESS  read-only
     STATUS      current
     DESCRIPTION
       "A read-only count of fragments larger than maxFragmentSize
       (512 bytes) that have been received and discarded by a
       G.Bond/Eth port during the current 1-day performance interval.

       Note that the total number of large fragments is indicated by
       the g9982PortStatRxLargeFragments object.

       This object is inhibited during Unavailable Seconds (UAS)."
     REFERENCE
       "[TR-159], Section 5.5.3.9"
     ::= { g9982PortPmCurEntry 17}

   g9982PortPmCur1DayRxBadFragments  OBJECT-TYPE
     SYNTAX      HCPerfCurrentCount
     UNITS       "fragments"
     MAX-ACCESS  read-only
     STATUS      current
     DESCRIPTION
       "A read-only count of fragments that do not fit into the
       sequence expected by the frame assembly function and that have
       been received and discarded by a G.Bond/Eth port during the
       current 1-day performance interval.

       Note that the total number of bad fragments is indicated by
       the g9982PortStatRxBadFragments object.

       This object is inhibited during Unavailable Seconds (UAS)."
     REFERENCE
       "[TR-159], Section 5.5.3.10"
     ::= { g9982PortPmCurEntry 18}

   g9982PortPmCur1DayRxLostFragments  OBJECT-TYPE
     SYNTAX      HCPerfCurrentCount
     UNITS       "fragments"
     MAX-ACCESS  read-only
     STATUS      current
     DESCRIPTION
       "A read-only count of gaps in the sequence of fragments
       expected by the frame assembly function of a G.Bond/Eth port
       during the current 1-day performance interval.

       Note that the total number of these lost fragments is indicated
       by the g9982PortStatRxLostFragments object.

       This object is inhibited during Unavailable Seconds (UAS)."
     REFERENCE
       "[TR-159], Section 5.5.3.11"
     ::= { g9982PortPmCurEntry 19}

   g9982PortPmCur1DayRxLostStarts  OBJECT-TYPE
     SYNTAX      HCPerfCurrentCount
     MAX-ACCESS  read-only
     STATUS      current
     DESCRIPTION
       "A read-only count of missing StartOfPacket indicators expected
       by the frame assembly function of a G.Bond/Eth port during the
       current 1-day performance interval.

       Note that the total number of missing StartOfPacket indicators
       is indicated by the g9982PortStatRxLostStarts object.

       This object is inhibited during Unavailable Seconds (UAS)."
     REFERENCE
       "[TR-159], Section 5.5.3.12"
     ::= { g9982PortPmCurEntry 20}

   g9982PortPmCur1DayRxLostEnds  OBJECT-TYPE
     SYNTAX      HCPerfCurrentCount
     MAX-ACCESS  read-only
     STATUS      current
     DESCRIPTION
       "A read-only count of missing EndOfPacket indicators expected
       by the frame assembly function of a G.Bond/Eth port during the
       current 1-day performance interval.

       Note that the total number of missing EndOfPacket indicators
       is indicated by the g9982PortStatRxLostEnds object.

       This object is inhibited during Unavailable Seconds (UAS)."
     REFERENCE
       "[TR-159], Section 5.5.3.13"
     ::= { g9982PortPmCurEntry 21}

   g9982PortPmCur1DayRxOverflows  OBJECT-TYPE
     SYNTAX      HCPerfCurrentCount
     UNITS       "fragments"
     MAX-ACCESS  read-only
     STATUS      current
     DESCRIPTION
       "A read-only count of fragments that have been received and
       discarded by a G.Bond/Eth port, which would have caused the
       frame assembly buffer to overflow, during the current 1-day
       performance interval.

       Note that the total number of fragments that would have caused
       the frame assembly buffer to overflow is indicated by the
       g9982PortStatRxOverflows object.

       This object is inhibited during Unavailable Seconds (UAS)."
     REFERENCE
       "[TR-159], Section 5.5.3.14"
     ::= { g9982PortPmCurEntry 22}

   -- Port PM history: 15-min buckets

   g9982PortPm15MinTable OBJECT-TYPE
     SYNTAX      SEQUENCE OF G9982PortPm15MinEntry
     MAX-ACCESS  not-accessible
     STATUS      current
     DESCRIPTION
       "This table contains historical 15-minute buckets of Performance
       Monitoring information for a G.Bond/Eth port (a row for each
       15-minute interval, up to 96 intervals).
       Entries in this table MUST be maintained in a persistent manner."
     ::= { g9982PM 2 }

   g9982PortPm15MinEntry OBJECT-TYPE
     SYNTAX      G9982PortPm15MinEntry
     MAX-ACCESS  not-accessible
     STATUS      current
     DESCRIPTION
       "An entry in the G.Bond/Eth Port historical 15-minute PM table.
       Each entry represents Performance Monitoring data for a
       G.Bond/Eth port, indexed by the ifIndex, collected during a
       particular 15-minute interval, indexed by the
       g9982PortPm15MinIntervalIndex."
     INDEX  { ifIndex, g9982PortPm15MinIntervalIndex }
     ::= { g9982PortPm15MinTable 1 }

   G9982PortPm15MinEntry ::=
     SEQUENCE {
       g9982PortPm15MinIntervalIndex            Unsigned32,
       g9982PortPm15MinIntervalMoniTime         HCPerfTimeElapsed,
       g9982PortPm15MinIntervalRxErrors         HCPerfCurrentCount,
       g9982PortPm15MinIntervalRxSmallFragments HCPerfCurrentCount,
       g9982PortPm15MinIntervalRxLargeFragments HCPerfCurrentCount,
       g9982PortPm15MinIntervalRxBadFragments   HCPerfCurrentCount,
       g9982PortPm15MinIntervalRxLostFragments  HCPerfCurrentCount,
       g9982PortPm15MinIntervalRxLostStarts     HCPerfCurrentCount,
       g9982PortPm15MinIntervalRxLostEnds       HCPerfCurrentCount,
       g9982PortPm15MinIntervalRxOverflows      HCPerfCurrentCount,
       g9982PortPm15MinIntervalValid            TruthValue
     }

   g9982PortPm15MinIntervalIndex  OBJECT-TYPE
     SYNTAX      Unsigned32 (1..96)
     MAX-ACCESS  not-accessible
     STATUS      current
     DESCRIPTION
       "Performance Data Interval number.  1 is the most recent
       previous interval; interval 96 is 24 hours ago.
       Intervals 2..96 are OPTIONAL.

       This object partially maps to the TR-159 attribute
       aGroupPerf15MinIntervalNumber."
     REFERENCE
       "[TR-159], Section 5.5.1.57"
     ::= { g9982PortPm15MinEntry 1 }

   g9982PortPm15MinIntervalMoniTime  OBJECT-TYPE
     SYNTAX      HCPerfTimeElapsed
     UNITS       "seconds"
     MAX-ACCESS  read-only
     STATUS      current
     DESCRIPTION
       "A read-only count of seconds over which the performance data
       was actually monitored.  This value will be the same as the
       interval duration (900 seconds), except in a situation where
       performance data could not be collected for any reason."
     ::= { g9982PortPm15MinEntry 2 }

   g9982PortPm15MinIntervalRxErrors  OBJECT-TYPE
     SYNTAX      HCPerfCurrentCount
     UNITS       "fragments"
     MAX-ACCESS  read-only
     STATUS      current
     DESCRIPTION
       "A read-only count of errored fragments received and discarded
       by a G.Bond/Eth port during the 15-minute performance history
       interval.

       Note that the total number of errored fragments is indicated by
       the g9982PortStatRxErrors object.

       This object is inhibited during Unavailable Seconds (UAS)."
     REFERENCE
       "[TR-159], Section 5.5.3.7"
     ::= { g9982PortPm15MinEntry 3}

   g9982PortPm15MinIntervalRxSmallFragments  OBJECT-TYPE
     SYNTAX      HCPerfCurrentCount
     UNITS       "fragments"
     MAX-ACCESS  read-only
     STATUS      current
     DESCRIPTION
       "A read-only count of fragments smaller than minFragmentSize
       (64 bytes) that have been received and discarded by a
        G.Bond/Eth port during the 15-minute performance history
        interval.

       Note that the total number of small fragments is indicated by
       the g9982PortStatRxSmallFragments object.

       This object is inhibited during Unavailable Seconds (UAS)."
     REFERENCE
       "[TR-159], Section 5.5.3.8"
     ::= { g9982PortPm15MinEntry 4}

   g9982PortPm15MinIntervalRxLargeFragments  OBJECT-TYPE
     SYNTAX      HCPerfCurrentCount
     UNITS       "fragments"
     MAX-ACCESS  read-only
     STATUS      current
     DESCRIPTION
       "A read-only count of fragments larger than maxFragmentSize
       (512 bytes) that have been received and discarded by a
       G.Bond/Eth port during the 15-minute performance history
       interval.

       Note that the total number of large fragments is indicated by
       the g9982PortStatRxLargeFragments object.

       This object is inhibited during Unavailable Seconds (UAS)."
     REFERENCE
       "[TR-159], Section 5.5.3.9"
     ::= { g9982PortPm15MinEntry 5}

   g9982PortPm15MinIntervalRxBadFragments  OBJECT-TYPE
     SYNTAX      HCPerfCurrentCount
     UNITS       "fragments"
     MAX-ACCESS  read-only
     STATUS      current
     DESCRIPTION
       "A read-only count of fragments that do not fit into the
       sequence expected by the frame assembly function and that have
       been received and discarded by a G.Bond/Eth port during the
       15-minute performance history interval.

       Note that the total number of bad fragments is indicated by
       the g9982PortStatRxBadFragments object.

       This object is inhibited during Unavailable Seconds (UAS)."
     REFERENCE
       "[TR-159], Section 5.5.3.10"
     ::= { g9982PortPm15MinEntry 6}

   g9982PortPm15MinIntervalRxLostFragments  OBJECT-TYPE
     SYNTAX      HCPerfCurrentCount
     UNITS       "fragments"
     MAX-ACCESS  read-only
     STATUS      current
     DESCRIPTION
       "A read-only count of gaps in the sequence of fragments
       expected by the frame assembly function of a G.Bond/Eth port
       during the 15-minute performance history interval.

       Note that the total number of these lost fragments is indicated
       by the g9982PortStatRxLostFragments object.

       This object is inhibited during Unavailable Seconds (UAS)."
     REFERENCE
       "[TR-159], Section 5.5.3.11"
     ::= { g9982PortPm15MinEntry 7}

   g9982PortPm15MinIntervalRxLostStarts  OBJECT-TYPE
     SYNTAX      HCPerfCurrentCount
     MAX-ACCESS  read-only
     STATUS      current
     DESCRIPTION
       "A read-only count of missing StartOfPacket indicators expected
       by the frame assembly function of a G.Bond/Eth port during the
       15-minute performance history interval.

       Note that the total number of missing StartOfPacket indicators
       is indicated by the g9982PortStatRxLostStarts object.

       This object is inhibited during Unavailable Seconds (UAS)."
     REFERENCE
       "[TR-159], Section 5.5.3.12"
     ::= { g9982PortPm15MinEntry 8}

   g9982PortPm15MinIntervalRxLostEnds  OBJECT-TYPE
     SYNTAX      HCPerfCurrentCount
     MAX-ACCESS  read-only
     STATUS      current
     DESCRIPTION
       "A read-only count of missing EndOfPacket indicators expected
       by the frame assembly function of a G.Bond/Eth port during the
       15-minute performance history interval.

       Note that the total number of missing EndOfPacket indicators
       is indicated by the g9982PortStatRxLostEnds object.

       This object is inhibited during Unavailable Seconds (UAS)."
     REFERENCE
       "[TR-159], Section 5.5.3.13"
     ::= { g9982PortPm15MinEntry 9}

   g9982PortPm15MinIntervalRxOverflows  OBJECT-TYPE
     SYNTAX      HCPerfCurrentCount
     UNITS       "fragments"
     MAX-ACCESS  read-only
     STATUS      current
     DESCRIPTION
       "A read-only count of fragments that have been received and
       discarded by a G.Bond/Eth port, which would have caused the
       frame assembly buffer to overflow, during the 15-minute
       performance history interval.

       Note that the total number of fragments that would have caused
       the frame assembly buffer to overflow is indicated by the
       g9982PortStatRxOverflows object.

       This object is inhibited during Unavailable Seconds (UAS)."
     REFERENCE
       "[TR-159], Section 5.5.3.14"
     ::= { g9982PortPm15MinEntry 10}

   g9982PortPm15MinIntervalValid  OBJECT-TYPE
     SYNTAX      TruthValue
     MAX-ACCESS  read-only
     STATUS      current
     DESCRIPTION
       "A read-only object indicating whether or not this history
       bucket contains valid data.  A valid bucket is reported as
       true(1) and an invalid bucket as false(2).
       If this history bucket is invalid, the BTU MUST NOT produce
       notifications based upon the value of the counters in this
       bucket.
       Note that an implementation may decide not to store invalid
       history buckets in its database.  In such a case, this object
       is not required, as only valid history buckets are available
       while invalid history buckets are simply not in the database.

       This object partially maps to the TR-159 attribute
       aGroupPerf15MinIntervalValid."
     REFERENCE
       "[TR-159], Section 5.5.1.58"
     ::= { g9982PortPm15MinEntry 11 }

   -- Port PM history: 1-day buckets

   g9982PortPm1DayTable OBJECT-TYPE
     SYNTAX      SEQUENCE OF G9982PortPm1DayEntry
     MAX-ACCESS  not-accessible
     STATUS      current
     DESCRIPTION
       "This table contains historical 1-day buckets of Performance
       Monitoring information for a G.Bond/Eth port (a row for each
       1-day interval, up to 7 intervals).
       Entries in this table MUST be maintained in a persistent manner."
     ::= { g9982PM 3 }

   g9982PortPm1DayEntry OBJECT-TYPE
     SYNTAX      G9982PortPm1DayEntry
     MAX-ACCESS  not-accessible
     STATUS      current
     DESCRIPTION
       "An entry in the G.Bond/Eth port historical 1-day PM table.
       Each entry represents Performance Monitoring data for such a
       port, indexed by the ifIndex, collected during a particular
       1-day interval, indexed by the g9982PortPm1DayIntervalIndex."
     INDEX  { ifIndex, g9982PortPm1DayIntervalIndex }
     ::= { g9982PortPm1DayTable 1 }

   G9982PortPm1DayEntry ::=
     SEQUENCE {
       g9982PortPm1DayIntervalIndex             Unsigned32,
       g9982PortPm1DayIntervalMoniTime          HCPerfTimeElapsed,
       g9982PortPm1DayIntervalRxErrors          HCPerfCurrentCount,
       g9982PortPm1DayIntervalRxSmallFragments  HCPerfCurrentCount,
       g9982PortPm1DayIntervalRxLargeFragments  HCPerfCurrentCount,
       g9982PortPm1DayIntervalRxBadFragments    HCPerfCurrentCount,
       g9982PortPm1DayIntervalRxLostFragments   HCPerfCurrentCount,
       g9982PortPm1DayIntervalRxLostStarts      HCPerfCurrentCount,
       g9982PortPm1DayIntervalRxLostEnds        HCPerfCurrentCount,
       g9982PortPm1DayIntervalRxOverflows       HCPerfCurrentCount,
       g9982PortPm1DayIntervalValid             TruthValue
     }

   g9982PortPm1DayIntervalIndex  OBJECT-TYPE
     SYNTAX      Unsigned32 (1..7)
     MAX-ACCESS  not-accessible
     STATUS      current
     DESCRIPTION
       "Performance Data Interval number.  1 is the most recent
       previous interval; interval 7 is 7 days ago.
       Intervals 2..7 are OPTIONAL.

       This object partially maps to the TR-159 attribute
       aGroupPerf1DayIntervalNumber."
     REFERENCE
       "[TR-159], Section 5.5.1.62"
     ::= { g9982PortPm1DayEntry 1 }

   g9982PortPm1DayIntervalMoniTime  OBJECT-TYPE
     SYNTAX      HCPerfTimeElapsed
     UNITS       "seconds"
     MAX-ACCESS  read-only
     STATUS      current
     DESCRIPTION
       "A read-only count of seconds over which the performance data
       was actually monitored.  This value will be the same as the
       interval duration (86400 seconds), except in a situation where
       performance data could not be collected for any reason.

       This object partially maps to the TR-159 attribute
       aGroupPerf1DayIntervalMoniSecs."
     REFERENCE
       "[TR-159], Section 5.5.1.64"
     ::= { g9982PortPm1DayEntry 2 }

   g9982PortPm1DayIntervalRxErrors  OBJECT-TYPE
     SYNTAX      HCPerfCurrentCount
     UNITS       "fragments"
     MAX-ACCESS  read-only
     STATUS      current
     DESCRIPTION
       "A read-only count of errored fragments received and discarded
       by a G.Bond/Eth port during the 1-day performance history
       interval.

       Note that the total number of errored fragments is indicated by
       the g9982PortStatRxErrors object.

       This object is inhibited during Unavailable Seconds (UAS)."
     REFERENCE
       "[TR-159], Section 5.5.3.7"
     ::= { g9982PortPm1DayEntry 3 }

   g9982PortPm1DayIntervalRxSmallFragments  OBJECT-TYPE
     SYNTAX      HCPerfCurrentCount
     UNITS       "fragments"
     MAX-ACCESS  read-only
     STATUS      current
     DESCRIPTION
       "A read-only count of fragments smaller than minFragmentSize
       (64 bytes) that have been received and discarded by a
       G.Bond/Eth port during the 1-day performance history interval.

       Note that the total number of small fragments is indicated by
       the g9982PortStatRxSmallFragments object.

       This object is inhibited during Unavailable Seconds (UAS)."
     REFERENCE
       "[TR-159], Section 5.5.3.8"
     ::= { g9982PortPm1DayEntry 4}

   g9982PortPm1DayIntervalRxLargeFragments  OBJECT-TYPE
     SYNTAX      HCPerfCurrentCount
     UNITS       "fragments"
     MAX-ACCESS  read-only
     STATUS      current
     DESCRIPTION
       "A read-only count of fragments larger than maxFragmentSize
       (512 bytes) that have been received and discarded by a
       G.Bond/Eth port during the 1-day performance history interval.

       Note that the total number of large fragments is indicated by
       the g9982PortStatRxLargeFragments object.

       This object is inhibited during Unavailable Seconds (UAS)."
     REFERENCE
       "[TR-159], Section 5.5.3.9"
     ::= { g9982PortPm1DayEntry 5}

   g9982PortPm1DayIntervalRxBadFragments  OBJECT-TYPE
     SYNTAX      HCPerfCurrentCount
     UNITS       "fragments"
     MAX-ACCESS  read-only
     STATUS      current
     DESCRIPTION
       "A read-only count of fragments that do not fit into the
       sequence expected by the frame assembly function and that have
       been received and discarded by a G.Bond/Eth port during the
       1-day performance history interval.

       Note that the total number of bad fragments is indicated by
       the g9982PortStatRxBadFragments object.

       This object is inhibited during Unavailable Seconds (UAS)."
     REFERENCE
       "[TR-159], Section 5.5.3.10"
     ::= { g9982PortPm1DayEntry 6}

   g9982PortPm1DayIntervalRxLostFragments  OBJECT-TYPE
     SYNTAX      HCPerfCurrentCount
     UNITS       "fragments"
     MAX-ACCESS  read-only
     STATUS      current
     DESCRIPTION
       "A read-only count of gaps in the sequence of fragments
       expected by the frame assembly function of a G.Bond/Eth port
       during the 1-day performance history interval.

       Note that the total number of these lost fragments is indicated
       by the g9982PortStatRxLostFragments object.

       This object is inhibited during Unavailable Seconds (UAS)."
     REFERENCE
       "[TR-159], Section 5.5.3.11"
     ::= { g9982PortPm1DayEntry 7}

   g9982PortPm1DayIntervalRxLostStarts  OBJECT-TYPE
     SYNTAX      HCPerfCurrentCount
     MAX-ACCESS  read-only
     STATUS      current
     DESCRIPTION
       "A read-only count of missing StartOfPacket indicators expected
       by the frame assembly function of a G.Bond/Eth port during the
       1-day performance history interval.

       Note that the total number of missing StartOfPacket indicators
       is indicated by the g9982PortStatRxLostStarts object.

       This object is inhibited during Unavailable Seconds (UAS)."
     REFERENCE
       "[TR-159], Section 5.5.3.12"
     ::= { g9982PortPm1DayEntry 8}

   g9982PortPm1DayIntervalRxLostEnds  OBJECT-TYPE
     SYNTAX      HCPerfCurrentCount
     MAX-ACCESS  read-only
     STATUS      current
     DESCRIPTION
       "A read-only count of missing EndOfPacket indicators expected
       by the frame assembly function of a G.Bond/Eth port during the
       1-day performance history interval.

       Note that the total number of missing EndOfPacket indicators
       is indicated by the g9982PortStatRxLostEnds object.

       This object is inhibited during Unavailable Seconds (UAS)."
     REFERENCE
       "[TR-159], Section 5.5.3.13"
     ::= { g9982PortPm1DayEntry 9}

   g9982PortPm1DayIntervalRxOverflows  OBJECT-TYPE
     SYNTAX      HCPerfCurrentCount
     UNITS       "fragments"
     MAX-ACCESS  read-only
     STATUS      current
     DESCRIPTION
       "A read-only count of fragments that have been received and
       discarded by a G.Bond/Eth port, which would have caused the
       frame assembly buffer to overflow, during the 1-day performance
       history interval.

       Note that the total number of fragments that would have caused
       the frame assembly buffer to overflow is indicated by the
       g9982PortStatRxOverflows object.

       This object is inhibited during Unavailable Seconds (UAS)."
     REFERENCE
       "[TR-159], Section 5.5.3.14"
     ::= { g9982PortPm1DayEntry 10}

   g9982PortPm1DayIntervalValid  OBJECT-TYPE
     SYNTAX      TruthValue
     MAX-ACCESS  read-only
     STATUS      current
     DESCRIPTION
       "A read-only object indicating whether or not this history
       bucket contains valid data.  A valid bucket is reported as
       true(1) and an invalid bucket as false(2).
       If this history bucket is invalid, the BTU MUST NOT produce
       notifications based upon the value of the counters in this
       bucket.
       Note that an implementation may decide not to store invalid
       history buckets in its database.  In such a case, this object
       is not required, as only valid history buckets are available
       while invalid history buckets are simply not in the database.

       This object partially maps to the TR-159 attribute
       aGroupPerf1DayIntervalValid."
     REFERENCE
       "[TR-159], Section 5.5.1.63"
     ::= { g9982PortPm1DayEntry 11 }

   -------------------------------
   -- BCE group
   -------------------------------

   g9982BceConfTable OBJECT-TYPE
     SYNTAX      SEQUENCE OF G9982BceConfEntry
     MAX-ACCESS  not-accessible
     STATUS      current
     DESCRIPTION
       "Table for configuration of G.Bond/Eth-specific aspects for the
       Bonding Channel Entity (BCE) ports (modems/channels).

       Entries in this table MUST be maintained in a persistent
       manner."
     ::= { g9982Bce 1 }

   g9982BceConfEntry OBJECT-TYPE
     SYNTAX      G9982BceConfEntry
     MAX-ACCESS  not-accessible
     STATUS      current
     DESCRIPTION
       "An entry in the G.Bond/Eth BCE Configuration table.
       Each entry represents G.998.2-specific aspects of a BCE port
       indexed by the ifIndex.  Note that a G.Bond/Eth BCE port can be
       stacked below a single GBS port, also indexed by the ifIndex."
     INDEX  { ifIndex }
     ::= { g9982BceConfTable 1 }

   G9982BceConfEntry ::=
     SEQUENCE {
       g9982BceConfEligibleGroupID      PhysAddress,
       g9982BceConfPeerEligibleGroupID  PhysAddress
     }

   g9982BceConfEligibleGroupID  OBJECT-TYPE
     SYNTAX      PhysAddress (SIZE(0|6))
     MAX-ACCESS  read-write
     STATUS      current
     DESCRIPTION
       "BACP Eligible Group ID of a G.Bond/ETH BCE port.
       A universally unique 6-octet-long identifier, used by the
       OPTIONAL BACP, to determine bonding eligibility.  When two BCEs
       have the same g9982BceConfEligibleGroupID on a system, they
       are eligible to be aggregated on that system.  Typically, all
       BCEs on a BTU-R device would be assigned the same
       g9982BceConfEligibleGroupID, to assert that all of the BCEs
       should be in the same bonded group.  BCEs with different
       g9982BceConfEligibleGroupID values MUST NOT be connected to
       the same GBS.
       BCEs with the same g9982BceConfEligibleGroupID MAY be
       connected to different GBS ports.
       This object MUST be instantiated during BACP initialization,
       when every BCE belongs to its own GBS.  Attempts to change this
       object MUST be rejected (with the error inconsistentValue), if
       the BCE is aggregated with other BCEs, i.e., more than one BCE
       is connected to the same GBS, or if the BCE in question is not
       eligible to be bonded with other BCEs having the same value
       (e.g., the bonding is limited to a single line card and BCEs are
       located on different line cards, or BCEs are the channels of
       the same line).

       Note that bonding eligibility is reflected in the
       ifCapStackTable and its inverse, the ifInvCapStackTable;
       as such, any modification of g9982BceConfEligibleGroupID MUST
       be reflected in these tables.

       A zero-length octet string SHALL be returned on an attempt to
       read this object on systems not supporting BACP (the value of
       g9982PortCapBacpSupported for the connected GBS is false).

       This object maps to the TR-159 attribute
       aChannelEligibleGroupID."
     REFERENCE
       "[TR-159], Section 5.5.7.3"
     ::= { g9982BceConfEntry 1 }

   g9982BceConfPeerEligibleGroupID  OBJECT-TYPE
     SYNTAX      PhysAddress (SIZE(0|6))
     MAX-ACCESS  read-only
     STATUS      current
     DESCRIPTION
       "BACP Eligible Group ID of a peer G.Bond/ETH BCE port, most
       recently received by the local BCE via a Local info TLV BACPDU
       message from the peer BCE.
       A universally unique 6-octet-long identifier, used by the
       OPTIONAL BACP, to determine bonding eligibility.
       BCEs with different g9982BceConfPeerEligibleGroupID values
       MUST NOT be connected to the same GBS.
       BCEs with the same g9982BceConfPeerEligibleGroupID MAY be
       connected to different GBS ports.

       A zero-length octet string SHALL be returned on an attempt to
       read this object on systems not supporting BACP (the value of
       g9982PortCapBacpSupported for the connected GBS is false)
       or when no BACPDUs have been received from the peer BCE.

       This object maps to the G.998.2-Amd2 attribute
       Remote Group ID."
     REFERENCE
       "[G.998.2-Amd2], Appendix C.3.1.6"
     ::= { g9982BceConfEntry 2 }

   g9982BceStatTable OBJECT-TYPE
     SYNTAX      SEQUENCE OF G9982BceStatEntry
     MAX-ACCESS  not-accessible
     STATUS      current
     DESCRIPTION
       "This table provides common status information of G.Bond/Eth
       BCE ports.

       This table contains live data from the equipment.  As such,
       it is NOT persistent."
     ::= { g9982Bce 2 }

   g9982BceStatEntry OBJECT-TYPE
     SYNTAX      G9982BceStatEntry
     MAX-ACCESS  not-accessible
     STATUS      current
     DESCRIPTION
       "An entry in the G.Bond/Eth BCE Status table.
       Each entry represents common aspects of a G.Bond/Eth BCE port
       indexed by the ifIndex.  Note that a BCE port can be stacked
       below a single GBS port, also indexed by the ifIndex,
       possibly together with other BCE ports."
     INDEX  { ifIndex }
     ::= { g9982BceStatTable 1 }

   G9982BceStatEntry ::=
     SEQUENCE {
       g9982BceStatTcInCodingErrors        Counter32,
       g9982BceStatTcInCrcErrors           Counter32
     }

   g9982BceStatTcInCodingErrors OBJECT-TYPE
     SYNTAX      Counter32
     MAX-ACCESS  read-only
     STATUS      current
     DESCRIPTION
       "A number of PTM-TC encapsulation errors.  This counter is
       incremented for each encapsulation error detected by the
       PTM-TC receive function.

       Discontinuities in the value of this counter can occur at
       re-initialization of the management system, and at other times
       as indicated by the value of ifCounterDiscontinuityTime, as
       defined in the IF-MIB.

       This object maps to the TR-159 attribute
       aChannelPtmTcRxCodingViolations."
     REFERENCE
       "[TR-159], Section 5.5.7.8"
     ::= { g9982BceStatEntry 1 }

   g9982BceStatTcInCrcErrors OBJECT-TYPE
     SYNTAX      Counter32
     MAX-ACCESS  read-only
     STATUS      current
     DESCRIPTION
       "A number of PTM-TC CRC errors.  This counter is incremented
       for each CRC error detected by the PTM-TC receive function.

       Discontinuities in the value of this counter can occur at
       re-initialization of the management system, and at other times
       as indicated by the value of ifCounterDiscontinuityTime, as
       defined in the IF-MIB.

       This object maps to the TR-159 attribute
       aChannelPtmTcRxCrcErrors."
     REFERENCE
       "[TR-159], Section 5.5.7.9"
     ::= { g9982BceStatEntry 2 }

  -------------------------------
  -- Conformance Statements
  -------------------------------

   g9982Groups      OBJECT IDENTIFIER
     ::= { g9982Conformance 1 }

   g9982Compliances OBJECT IDENTIFIER
     ::= { g9982Conformance 2 }

   -- Object groups

   g9982BasicGroup OBJECT-GROUP
     OBJECTS {
       g9982PortCapTcTypesSupported,
       g9982PortCapBacpSupported,
       g9982PortConfTcAdminType,
       g9982PortStatTcOperType,
       g9982PortStatRxErrors,
       g9982PortStatRxSmallFragments,
       g9982PortStatRxLargeFragments,
       g9982PortStatRxBadFragments,
       g9982PortStatRxLostFragments,
       g9982PortStatRxLostStarts,
       g9982PortStatRxLostEnds,
       g9982PortStatRxOverflows,
       g9982BceStatTcInCodingErrors,
       g9982BceStatTcInCrcErrors
     }
     STATUS      current
     DESCRIPTION
       "A collection of objects representing management information
       for G.Bond/Eth GBS ports."
     ::= { g9982Groups 1 }

   g9982BacpGroup OBJECT-GROUP
     OBJECTS {
       g9982PortConfAdminCp,
       g9982PortStatOperCp,
       g9982BceConfEligibleGroupID,
       g9982BceConfPeerEligibleGroupID

     }
     STATUS      current
     DESCRIPTION
       "A collection of objects representing management information
       for the OPTIONAL frame-based Bonding Aggregation Control
       Protocol (BACP) used by G.Bond/Eth GBS ports instead of the
       mandatory G.hs-based discovery and aggregation protocol."
     ::= { g9982Groups 2 }

   g9982BceGroup OBJECT-GROUP
     OBJECTS {
       g9982BceStatTcInCodingErrors,
       g9982BceStatTcInCrcErrors
     }
     STATUS      current
     DESCRIPTION
       "A collection of objects representing OPTIONAL management
       information for G.Bond/Eth BCE ports."
     ::= { g9982Groups 3 }

   g9982PerfCurrGroup OBJECT-GROUP
     OBJECTS {
       g9982PortPm15MinValidIntervals,
       g9982PortPm15MinInvalidIntervals,
       g9982PortPmCur15MinTimeElapsed,
       g9982PortPmCur15MinRxErrors,
       g9982PortPmCur15MinRxSmallFragments,
       g9982PortPmCur15MinRxLargeFragments,
       g9982PortPmCur15MinRxBadFragments,
       g9982PortPmCur15MinRxLostFragments,
       g9982PortPmCur15MinRxLostStarts,
       g9982PortPmCur15MinRxLostEnds,
       g9982PortPmCur15MinRxOverflows,
       g9982PortPm1DayValidIntervals,
       g9982PortPm1DayInvalidIntervals,
       g9982PortPmCur1DayTimeElapsed,
       g9982PortPmCur1DayRxErrors,
       g9982PortPmCur1DayRxSmallFragments,
       g9982PortPmCur1DayRxLargeFragments,
       g9982PortPmCur1DayRxBadFragments,
       g9982PortPmCur1DayRxLostFragments,
       g9982PortPmCur1DayRxLostStarts,
       g9982PortPmCur1DayRxLostEnds,
       g9982PortPmCur1DayRxOverflows
     }
     STATUS      current
     DESCRIPTION
       "A collection of objects supporting OPTIONAL current Performance
       Monitoring information for G.Bond/Eth ports."
     ::= { g9982Groups 4 }

   g9982Perf15MinGroup OBJECT-GROUP
     OBJECTS {
       g9982PortPm15MinIntervalMoniTime,
       g9982PortPm15MinIntervalRxErrors,
       g9982PortPm15MinIntervalRxSmallFragments,
       g9982PortPm15MinIntervalRxLargeFragments,
       g9982PortPm15MinIntervalRxBadFragments,
       g9982PortPm15MinIntervalRxLostFragments,
       g9982PortPm15MinIntervalRxLostStarts,
       g9982PortPm15MinIntervalRxLostEnds,
       g9982PortPm15MinIntervalRxOverflows,
       g9982PortPm15MinIntervalValid
     }
     STATUS      current
     DESCRIPTION
       "A collection of objects supporting OPTIONAL historical
       Performance Monitoring information for G.Bond/Eth ports, during
       previous 15-minute intervals."
     ::= { g9982Groups 5 }

   g9982Perf1DayGroup OBJECT-GROUP
     OBJECTS {
       g9982PortPm1DayIntervalMoniTime,
       g9982PortPm1DayIntervalRxErrors,
       g9982PortPm1DayIntervalRxSmallFragments,
       g9982PortPm1DayIntervalRxLargeFragments,
       g9982PortPm1DayIntervalRxBadFragments,
       g9982PortPm1DayIntervalRxLostFragments,
       g9982PortPm1DayIntervalRxLostStarts,
       g9982PortPm1DayIntervalRxLostEnds,
       g9982PortPm1DayIntervalRxOverflows,
       g9982PortPm1DayIntervalValid
     }
     STATUS      current
     DESCRIPTION
       "A collection of objects supporting OPTIONAL historical
       Performance Monitoring information for G.Bond/Eth ports, during
       previous 1-day intervals."
     ::= { g9982Groups 6 }

  -------------------------------
  -- Compliance Statements
  -------------------------------

   g9982Compliance MODULE-COMPLIANCE
     STATUS      current
     DESCRIPTION
       "The compliance statement for G.Bond Ethernet interfaces.
       Compliance with the following external compliance statements
       is REQUIRED:

       MIB Module             Compliance Statement
       ----------             --------------------
       IF-MIB                 ifCompliance3
       GBOND-MIB              gBondCompliance"

     MODULE  -- this module
       MANDATORY-GROUPS {
         g9982BasicGroup
       }

       GROUP       g9982BceGroup
       DESCRIPTION
         "Support for this group is OPTIONAL."

       GROUP       g9982BacpGroup
       DESCRIPTION
         "Support for this group is OPTIONAL and only required for
         implementations supporting BACP."

       GROUP       g9982PerfCurrGroup
       DESCRIPTION
         "Support for this group is only required for implementations
         supporting Performance Monitoring."

       GROUP       g9982Perf15MinGroup
       DESCRIPTION
         "Support for this group is only required for implementations
         supporting 15-minute historical Performance Monitoring."

       GROUP       g9982Perf1DayGroup
       DESCRIPTION
         "Support for this group is only required for implementations
         supporting 1-day historical Performance Monitoring."

       OBJECT      g9982PortCapTcTypesSupported
       SYNTAX      BITS {
         tc6465(0),
         tcHDLC(1)
       }
       DESCRIPTION
         "Support for all TC types is not required.  However, at least
         one value SHALL be supported."

       OBJECT      g9982PortCapBacpSupported
       SYNTAX      TruthValue
       DESCRIPTION
         "Support for BACP is OPTIONAL; therefore, a value of false(2)
         SHALL be supported."

       OBJECT      g9982PortConfTcAdminType
       MIN-ACCESS  read-only
       DESCRIPTION
         "Write access is not required (needed only for GBS
         supporting more than a single TC encapsulation type, i.e.,
         tc6465 and tcHDLC)."

       OBJECT      g9982PortConfAdminCp
       MIN-ACCESS  read-only
       DESCRIPTION
         "Write access is not required (needed only for GBS
         supporting BACP in addition to mandatory G.hs-based bonding
         discovery and aggregation protocol)."
     ::= { g9982Compliances 1 }
END
