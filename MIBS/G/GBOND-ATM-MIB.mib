-- extracted from draft-ietf-adslmib-gbond-atm-mib-00.txt
-- at Tue May 15 06:08:08 2007

   GBOND-ATM-MIB DEFINITIONS ::= BEGIN

     IMPORTS
       MODULE-IDENTITY, OBJECT-TYPE, NOTIFICATION-TYPE,
       Unsigned32, Counter32, TimeTicks
         FROM SNMPv2-SMI         -- RFC 2578
       TEXTUAL-CONVENTION, TruthValue
         FROM SNMPv2-TC          -- RFC 2579
       MODULE-COMPLIANCE, OBJECT-GROUP, NOTIFICATION-GROUP
         FROM SNMPv2-CONF        -- RFC 2580
       ifIndex, InterfaceIndex
         FROM IF-MIB             -- RFC 2863
       gBondMIB
         FROM GBOND-MIB          -- RFC YYYY
         -- EdNote: Replace YYYY with the actual RFC number and
         -- remove this note
       ;

     gBondAtmMIB MODULE-IDENTITY
       LAST-UPDATED "200705140000Z"  -- May 14, 2007
       ORGANIZATION "IETF ADSL MIB Working Group"
       CONTACT-INFO
         "WG charter:
           http://www.ietf.org/html.charters/adslmib-charter.html

         Mailing Lists:
           General Discussion: adslmib@ietf.org
           To Subscribe: adslmib-request@ietf.org
           In Body: subscribe your_email_address

          Chair: Menachem Dodge
         Postal: ECI Telecom, Ltd.
                 30 Hasivim St.,
                 Petach-Tikva 49517
                 Israel
          Phone: +972-3-926-8421
          EMail: menachem.dodge@ecitele.com

         Editor: Edward Beili
         Postal: Actelis Networks, Inc.
                 25 Bazel St., P.O.B. 10173
                 Petach-Tikva 10173
                 Israel
          Phone: +972-3-924-3491
          EMail: edward.beili@actelis.com

         Editor: Narendranath Nair
         Postal: Wipro Technologies
                 Keonics Electronics City
                 Bangalore 560 100
                 India
          Phone: +91-99-00-12-96-29
          EMail: narendranath.nair@wipro.com"

       DESCRIPTION
         "The objects in this MIB module are used to manage the
         multi-pair bonded xDSL Interfaces using ATM inverse
         multiplexing, defined in ITU-T recommendation G.998.1
         (G.Bond/ATM).

         This MIB module MUST be used in conjunction with GBOND-MIB
         module, common to all G.Bond technologies.

         The following references are used throughout this MIB module:

         [WT-159] refers to:
           DSL Forum Technical Report: 'Management Framework for xDSL
           Bonding', January 2007.

         Naming Conventions:
           BCE   - Bonding Channel Entity
           CO    - Central Office
           CPE   - Customer Premises Equipment
           GBS   - Generic Bonding Sublayer
           SNR   - Signal to Noise Ratio

         Copyright (C) The Internet Society (2007). This version of this
         MIB module is part of RFC XXXX; see the RFC itself for full
         legal notices."

       REVISION    "200705140000Z"  -- May 14, 2007
       DESCRIPTION "Initial version, published as RFC XXXX."

         -- EdNote: Replace XXXX with the actual RFC number and
         -- remove this note

       ::= { gBondMIB 1 }

      -- Sections of the module
      -- Structured as recommended by RFC 4181, Appendix D

      gBondAtmObjects     OBJECT IDENTIFIER ::= { gBondAtmMIB 1 }

      gBondAtmConformance OBJECT IDENTIFIER ::= { gBondAtmMIB 2 }
      -- Groups in the module

      gBondAtmPort        OBJECT IDENTIFIER ::= { gBondAtmObjects 1 }

     -- Textual Conventions

     -- Port Notifications Group

     -- gBondAtmPortNotifications OBJECT IDENTIFIER
     --  ::= { gBondAtmPort 0 }

      -- G.Bond ATM Port group

      gBondAtmPortConfTable OBJECT-TYPE
        SYNTAX      SEQUENCE OF GBondAtmPortConfEntry
        MAX-ACCESS  not-accessible
        STATUS      current
        DESCRIPTION
          "Table for Configuration of G.Bond ATM ports. Entries in
          this table MUST be maintained in a persistent manner"
        ::= { gBondAtmPort 1 }

      gBondAtmPortConfEntry OBJECT-TYPE
        SYNTAX      GBondAtmPortConfEntry
        MAX-ACCESS  not-accessible
        STATUS      current
        DESCRIPTION
          "An entry in the G.Bond ATM Port Configuration table.
          Each entry represents an G.Bond ATM port indexed by the
          ifIndex. Additional configuration parameters are available
          via the gBondPortConfEntry of GBOND-MIB.
          Note that an G.Bond ATM port runs on top of a single or
          multiple BCE port(s), which are also indexed by ifIndex."
        INDEX  { ifIndex }
        ::= { gBondAtmPortConfTable 1 }

      GBondAtmPortConfEntry ::=
        SEQUENCE {
                -- ATM Port conf Entry
                gBondAtmUpMaxDataRate           Unsigned32,
                gBondAtmDownMaxDataRate         Unsigned32,
                gBondAtmUpDiffDelayTolerence    Unsigned32,
                gBondAtmDownDiffDelayTolerence  Unsigned32
                }

      gBondAtmUpMaxDataRate  OBJECT-TYPE
        SYNTAX      Unsigned32(1..1000000|9999999)
        UNITS       "Kbps"
        MAX-ACCESS  read-write
        STATUS      current
        DESCRIPTION
          "The maximum net upstream data rate a bonding group
                  is allowed to achieve to carry an ATM stream.If set
                  to '9999999', this parameter is ignored."
        REFERENCE
          "[G.998.1] Sec. 11.4.1 - (4)"
        ::= { gBondAtmPortConfEntry 1 }

      gBondAtmDownMaxDataRate  OBJECT-TYPE
        SYNTAX      Unsigned32(1..1000000|9999999)
        UNITS       "Kbps"
        MAX-ACCESS  read-write
        STATUS      current
        DESCRIPTION
          "The maximum net downstream data rate a bonding group
                  is allowed to achieve to carry an ATM stream.If set
                  to '9999999', this parameter is ignored."
        REFERENCE
          "[G.998.1] Sec. 11.4.1 - (4)"
        ::= { gBondAtmPortConfEntry 2 }

      gBondAtmUpDiffDelayTolerence  OBJECT-TYPE
        SYNTAX      Unsigned32(0..8176)
        UNITS       "milliseconds"
        MAX-ACCESS  read-write
        STATUS      current
        DESCRIPTION
          "The maximum upstream differential delay among member
                  links in a bonding group."
        REFERENCE
          "[G.998.1] Sec. 11.4.1 - (6)"
        ::= { gBondAtmPortConfEntry 3 }

      gBondAtmDownDiffDelayTolerence  OBJECT-TYPE
        SYNTAX      Unsigned32(0..8176)
        UNITS       "milliseconds"
        MAX-ACCESS  read-write
        STATUS      current
        DESCRIPTION
          "The maximum downstream differential delay among member
                  links in a bonding group."
        REFERENCE
          "[G.998.1] Sec. 11.4.1 - (6)"
        ::= { gBondAtmPortConfEntry 4 }

      gBondAtmPortStatusTable OBJECT-TYPE
        SYNTAX      SEQUENCE OF GBondAtmPortStatusEntry
        MAX-ACCESS  not-accessible
        STATUS      current
        DESCRIPTION
          "This table provides overall status information of G.Bond
          ATM ports, complementing the generic status information from
          the ifTable of IF-MIB and gBondFltStatus of GBOND-MIB.
          Additional status information about connected BCEs is
          available from the relevant line MIBs
          This table contains live data from the equipment. As such,
          it is NOT persistent."
        ::= { gBondAtmPort 2 }

      gBondAtmPortStatusEntry OBJECT-TYPE
        SYNTAX      GBondAtmPortStatusEntry
        MAX-ACCESS  not-accessible
        STATUS      current
        DESCRIPTION
          "An entry in the G.Bond ATM port Status table.
          Each entry represents a G.Bond ATM port indexed by the
          ifIndex.
          Note that an G.Bond GBS port runs on top of a single
          or multiple BCE port(s), which are also indexed by ifIndex."
        INDEX  { ifIndex }
        ::= { gBondAtmPortStatusTable 1 }

      GBondAtmPortStatusEntry ::=
        SEQUENCE {
                -- ATM Port status entries
                gBondAtmShowTime        TimeTicks,
                gBondAtmUpRxCellLossCount Counter32,
                gBondAtmDownRxCellLossCount Counter32
        }

      gBondAtmShowTime  OBJECT-TYPE
        SYNTAX      TimeTicks
        UNITS       "seconds"
        MAX-ACCESS  read-only
        STATUS      current
        DESCRIPTION
          "The accumulated time when a bonding group is in normal
                  operation."
        REFERENCE
          "[G.998.1] Sec. 11.4.2 - (3)"
        ::= { gBondAtmPortStatusEntry 1 }

      gBondAtmUpRxCellLossCount  OBJECT-TYPE
        SYNTAX      Counter32
        MAX-ACCESS  read-only
        STATUS      current
        DESCRIPTION
          "The total number of cells that are lost at aggregation
                  output in the upstream direction from a bonding group
                  for the accumulation interval."
        REFERENCE
          "[G.998.1] Sec. 11.4.2 - (4)"
        ::= { gBondAtmPortStatusEntry 2 }

      gBondAtmDownRxCellLossCount  OBJECT-TYPE
        SYNTAX      Counter32
        MAX-ACCESS  read-only
        STATUS      current
        DESCRIPTION
          "The total number of cells that are lost at aggregation
                  output in the downstream direction from a bonding
                  group for the accumulation interval."
        REFERENCE
          "[G.998.1] Sec. 11.4.2 - (4)"
        ::= { gBondAtmPortStatusEntry 3 }


     --
     -- Conformance Statements
     --

      gBondAtmGroups      OBJECT IDENTIFIER
        ::= { gBondAtmConformance 1 }

      gBondAtmCompliances OBJECT IDENTIFIER
        ::= { gBondAtmConformance 2 }

      -- Object Groups

      gBondAtmBasicGroup OBJECT-GROUP
        OBJECTS {
                gBondAtmUpMaxDataRate,
                gBondAtmDownMaxDataRate,
                gBondAtmUpDiffDelayTolerence,
                gBondAtmDownDiffDelayTolerence,
                gBondAtmShowTime,
                gBondAtmUpRxCellLossCount,
                gBondAtmDownRxCellLossCount
        }
        STATUS      current
        DESCRIPTION
          "A collection of objects representing management
                  information for G.Bond ATM ports."
        ::= { gBondAtmGroups 1 }

     -- Compliance Statements

      gBondAtmCompliance MODULE-COMPLIANCE
        STATUS      current
        DESCRIPTION
          "The compliance statement for G.Bond ATM interfaces.
          Compliance with the following external compliance
                  statements
          is REQUIRED:

          MIB Module             Compliance Statement
          ----------             --------------------
          IF-MIB                 ifCompliance3
          GBOND-MIB              gBondCompliance"

        MODULE  -- this module
          MANDATORY-GROUPS {
            gBondAtmBasicGroup
          }

        ::= { gBondAtmCompliances 1 }
END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- 
-- Acknowledgment
-- 
--    Funding for the RFC Editor function is provided by the IETF
--    Administrative Support Activity (IASA).
