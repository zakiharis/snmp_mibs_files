-- Copyright 1996 General DataComm Inc., Inc. All Rights Reserved.
--
-- Reproduction of this document is authorized on condition that the
-- foregoing copyright notice is included. This General DataComm, GDC,
-- SNMP Management Information Base Specification embodies GDCs'
-- confidential and proprietary intellectual property. GDC retains all
-- title and ownership in the Specification, including any revisions.
--
-- It is GDCs intent to encourage the widespread use of this Specification
-- in connection with the management of GDC's products. GDC grants vendors,
-- end-users, and other interested parties a non-exclusive license to use
-- this Specification in connection with the management of GDC's products.
--
-- This Specification is supplied "AS IS," and GDC makes no warranty,
-- either expressed or implied, as to the use operation, condition, or
-- performance of the Specification.
--
-- GDC MP7001 MIB
--
-- ****************************************************************************
--                        Revision History
-- ****************************************************************************
-- Version		Date		Name		Description
-- 1.00A		1-Jul-96	W. Richards     Initial Revision based on gdc7002_100F.mib
--							Changed 7002->7001, E1->T1, 31 time slots
--							to 24
-- 1.00B		16-Jul-96	W. Meltzer     	Move page feeds inside comments 
--							(it confuses some compilers)
-- 1.00C		29-Jul-96       C. Amorossi    	Changed alarm OID, changed
--						     	description of mp7001AlarmStatus,
--							removed performance tables,
--							modified diagnostics table
-- 1.00D		30-Jul-96	C. Amorossi     Added mp7001StatLastInitialized, 
--							mp7001ValidIntervals, changed
--						     	description of mp7001AlarmStatus,
--							removed mp7001OnesDensity
-- 1.00E		05-Aug-96	C. Amorossi	Added performance tables
-- 1.00F		16-Sep-96	C. Amorossi	Added mp7001LineBuildoutCtrl.
--							Swapped enums for 
--							mp7001FramingMode.
--							Added mp7001ControlSlips &
--							mp7001UnsolicitedTest to
--							alarms.  Modified description
--							of mp7001AlarmStatus.
--							Add enum (4) to 
--							mp7001LineBuildout.
-- ****************************************************************************




--
-- ****************************************************************************
--                          mib definitions begin
-- ****************************************************************************

GDCMP7001-MIB DEFINITIONS ::= BEGIN

IMPORTS
	 enterprises	FROM RFC1155-SMI
	 OBJECT-TYPE    FROM RFC-1212
	 DisplayString  FROM RFC1213-MIB
	 SCinstance     FROM GDCMACRO-MIB;

gdc           	 	OBJECT IDENTIFIER ::= { enterprises 498 }
dsx1           		OBJECT IDENTIFIER ::= { gdc 6 }
mp7001System   		OBJECT IDENTIFIER ::= { dsx1 10 }

mp7001Version          	OBJECT IDENTIFIER ::= { mp7001System 1 }
mp7001Maintenance     	OBJECT IDENTIFIER ::= { mp7001System 2 }
mp7001Configuration	OBJECT IDENTIFIER ::= { mp7001System 3 }
mp7001Diagnostics	OBJECT IDENTIFIER ::= { mp7001System 4 }
mp7001Performance	OBJECT IDENTIFIER ::= { mp7001System 5 }
mp7001AlarmConfig      	OBJECT IDENTIFIER ::= { mp7001System 6 }
mp7001SysConfig		OBJECT IDENTIFIER ::= { mp7001System 7 } 
 
-- This MIB module uses the extended OBJECT-TYPE macro as
-- defined in RFC 1212.

-- The implementation of all groups is mandatory for all products that
-- support a T1 interface.

-- Note:  All rows in all tables defined within this MIB module are
-- virtual.  They can neither be created or deleted by management
-- operations.

-- ****************************************************************************


mp7001MIBversion OBJECT-TYPE
	SYNTAX DisplayString (SIZE (5))
     	ACCESS read-only
     	STATUS mandatory
     	DESCRIPTION
	"Identifies the version of the MIB. The format of the version
	is x.yzT, where 'x' identifies the major revision number, 'y'
	identifies the minor revision number, 'z' identifies the
	typographical revision, and T identifies the test revision.
	Acceptable values for the individual revision components are
	as follows:

		 x: 1 - 9
		 y: 0 - 9
		 z: 0 - 9
		 T: A - Z

	Upon formal release, no designation for the test revision will
	be present."
     	::= { mp7001Version 1 }


--
-- ****************************************************************************
--                                Version Table
-- ****************************************************************************

mp7001VersionTable OBJECT-TYPE
	SYNTAX SEQUENCE OF Mp7001VersionEntry
	ACCESS not-accessible
	STATUS mandatory
	DESCRIPTION " "
	::= { mp7001Version 2  }

mp7001VersionEntry OBJECT-TYPE
	SYNTAX Mp7001VersionEntry
	ACCESS not-accessible
	STATUS mandatory
	DESCRIPTION
	"An entry in the GDC Mp7001System Version Table."
	INDEX  { mp7001VersionIndex }
	::= { mp7001VersionTable 1 }

Mp7001VersionEntry ::=
	SEQUENCE {
		  mp7001VersionIndex
			 SCinstance,
		  mp7001FirmwareRev
			 DisplayString,
		  mp7001CardType
			 DisplayString,
		  mp7001BootRev
			 DisplayString
	}

mp7001VersionIndex OBJECT-TYPE
	SYNTAX SCinstance
	ACCESS read-only
	STATUS mandatory
	DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
	::= { mp7001VersionEntry 1 }

mp7001FirmwareRev 	OBJECT-TYPE
	SYNTAX DisplayString (SIZE(2))
	ACCESS read-only
	STATUS mandatory
	DESCRIPTION
	"The version number of the firmware, to allow products
  	to know which revision is installed.  The released
	version number is sequenced from --, A-, ... AA, ... ZZ."
	::= { mp7001VersionEntry 2 }

mp7001CardType	OBJECT-TYPE
	SYNTAX DisplayString (SIZE(0..16))
	ACCESS read-only
	STATUS mandatory
	DESCRIPTION
	"This variable is used to determine the type
	of card family installed ex. MP7001."
	::= { mp7001VersionEntry 3 }

mp7001BootRev 	OBJECT-TYPE
	SYNTAX DisplayString (SIZE(2))
	ACCESS read-only
	STATUS mandatory
	DESCRIPTION
	"The version number of the boot firmware, to allow products
	to know which revision is installed.  The released version
	number is sequenced from --, A-, ... AA, ... ZZ.  "
	::= { mp7001VersionEntry 4 }


-- 
-- ********************************************************************
-- GDC 7001 Maintenance Table
-- ********************************************************************

mp7001MaintenanceTable OBJECT-TYPE
	SYNTAX SEQUENCE OF Mp7001MaintenanceEntry
	ACCESS not-accessible
	STATUS mandatory
	DESCRIPTION
	"The table describes the maintenance objects for MP 7001." 
	::= { mp7001Maintenance 1  }

mp7001MaintenanceEntry OBJECT-TYPE
	SYNTAX Mp7001MaintenanceEntry
	ACCESS not-accessible
	STATUS mandatory
	DESCRIPTION
	"An entry in the GDC 701 Maintenance Table."
	INDEX  { mp7001MaintenanceLineIndex }
	::= { mp7001MaintenanceTable 1 }

Mp7001MaintenanceEntry ::=
	SEQUENCE {
		  mp7001MaintenanceLineIndex
			 SCinstance,
		  mp7001SoftReset
			 INTEGER,
		  mp7001SysUpTime
			 INTEGER,
		  mp7001DefaultInit
			 INTEGER,
		  mp7001ResetStats
			 INTEGER,
		  mp7001LedStatus
			 OCTET STRING,
		  mp7001T1CircuitName
			 DisplayString,
		  mp7001SetRealTime
			 INTEGER,
		  mp7001AlarmStatus
			 OCTET STRING,
		  mp7001SystemTimingGenStatus
			 INTEGER,
		  mp7001StatLastInitialized
			 INTEGER,
		  mp7001ValidIntervals
			 INTEGER
	}

mp7001MaintenanceLineIndex OBJECT-TYPE
	SYNTAX SCinstance
	ACCESS read-only
	STATUS mandatory
	DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
	::= { mp7001MaintenanceEntry 1 }

mp7001SoftReset		OBJECT-TYPE
	SYNTAX INTEGER {
			 norm(1),
			 reset(2)
	   	       }
	ACCESS read-write
	STATUS mandatory
	DESCRIPTION
	"Supports the action of soft resetting the unit.  When this
	object is set to reset(2), then the unit performs a soft
	reset, whose meaning is specific to the type of unit being
	managed. The value of norm(1) will be returned when 
	the reset is complete.
	The value of norm(1) can not be set by management."
	::= { mp7001MaintenanceEntry 2 }

mp7001SysUpTime       	OBJECT-TYPE
	SYNTAX INTEGER (1..2147483647)
	ACCESS read-only
	STATUS mandatory
	DESCRIPTION
	"This variable is used to report the elapsed system tick
	time for conversion to real time at the controller and is
	not related to the sysUpTime referenced in MIB-II.
	Upon power-up of the unit, the elapsed time is cleared.
	The elapsed time counter rolls over upon reaching the
	maximum count."
	::= { mp7001MaintenanceEntry 3 }

mp7001DefaultInit     	OBJECT-TYPE
	SYNTAX INTEGER  {
			 normal(1),
			 factoryDefault(2)
			 }
	ACCESS read-write
	STATUS mandatory
	DESCRIPTION
	"This is used to allow the NonVolatile Configuration to 
	be set to a factory default state.  When this value is set to
	factoryDefault(2) the unit will perform  a reset to make 
	the default configuration take affect. 
	The value of normal(1) will be returned when the initialization
	is complete.
	The value of normal(1) can not be set by management."
	::= { mp7001MaintenanceEntry 4 }

mp7001ResetStats      	OBJECT-TYPE
	SYNTAX  INTEGER        {
			 norm(1),
			 reset(2)
		 }
	ACCESS  read-write
	STATUS  mandatory
	DESCRIPTION
	"Supports the action of soft resetting the mp7001ValidIntervals
	object.  When this object is set to reset(2), then the unit
	will reset the mp7001ValidIntervals object to zero.
	The value of norm(1) can not be set by management."
	::= { mp7001MaintenanceEntry 5 }

mp7001LedStatus 	OBJECT-TYPE
	SYNTAX  OCTET STRING (SIZE(2))
	ACCESS  read-only
	STATUS  mandatory
	DESCRIPTION
	"Returns a bitwise snapshot of the front panel LED state.
		 Octet 1 bit 7 - not used
			 bit 6 - ON
			 bit 5 - INSV
			 bit 4 - RSP
			 bit 3 - TMG
			 bit 2 - future use
			 bit 1 - future use
			 bit 0 - future use

		 Octet 2 bit 7 - not used
			 bit 6 - future use
			 bit 5 - NTWK AIS
			 bit 4 - NTWK LCV
			 bit 3 - NTWK LOS
			 bit 2 - NTWK OOF
			 bit 1 - ALM
			 bit 0 - TM "
	::= { mp7001MaintenanceEntry 6 }

mp7001T1CircuitName	OBJECT-TYPE
	SYNTAX  DisplayString (SIZE(16))
	ACCESS  read-write
	STATUS  mandatory
	DESCRIPTION
	"Circuit name T1 is connected to."
	::= { mp7001MaintenanceEntry 7 }

mp7001SetRealTime      	OBJECT-TYPE
	SYNTAX  INTEGER (1..2147483647)
	ACCESS  read-write
	STATUS  mandatory
	DESCRIPTION
	"Number of seconds from midnight Dec 31, 1969."
	::= {mp7001MaintenanceEntry 8}

mp7001AlarmStatus	OBJECT-TYPE
	SYNTAX OCTET STRING (SIZE(4))
	ACCESS read-only
	STATUS mandatory
	DESCRIPTION
	"Returns a bit-wise Status of alarms
		 Octet 1 bit 7 - not used
			 bit 6 - NTWK LOS
			 bit 5 - NTWK LOF
			 bit 4 - NWTK_AIS
			 bit 3 - future use
			 bit 2 - NTWK Received YELLOW
			 bit 1 - NTWK Excessive Zeros - not supported
			 bit 0 - NTWK Low Average Density - not supported

		 Octet 2 bit 7 - not used
			 bit 6 - NTWK BiPolar Violations
			 bit 5 - NTWK CRC Errors
			 bit 4 - NTWK Controlled Slips
			 bit 3 - Unavailable Signal State
			 bit 2 - Status Change
			 bit 1 - Timing Loss
			 bit 0 - Unit Failure

		 Octet 3 bit 7 - not used
			 bit 6 - future use
			 bit 5 - future use
			 bit 4 - future use
			 bit 3 - future use
			 bit 2 - future use
			 bit 1 - future use
			 bit 0 - future use
		
		 Octet 4 bit 7 - not used
			 bit 6 - ES
			 bit 5 - BES
			 bit 4 - SES
			 bit 3 - UAS
			 bit 2 - Unsolicited Test
			 bit 1 - NVRAM checksum corrupted
			 bit 0 - Power-up Alarm "
	::= {mp7001MaintenanceEntry 9}

mp7001SystemTimingGenStatus	OBJECT-TYPE
	SYNTAX INTEGER {
			none(1),
			clk8khz(2),
			clk4mhz(3),
			clk8khzand4mhz(4)
	}
	ACCESS read-only
	STATUS mandatory
	DESCRIPTION
	"Indicates if the units configured for primary or secondary system clock are
	actually supplying clock and if it is the 8hkz, 4mhz, or both."
	::= {mp7001MaintenanceEntry 10}

mp7001StatLastInitialized      	OBJECT-TYPE
	SYNTAX  INTEGER (1..2147483647)
	ACCESS  read-only
	STATUS  mandatory
	DESCRIPTION
	"Number of seconds from midnight Dec 31, 1969 up until
        mp7001ValidIntervals was last initialized to zero"
	::= {mp7001MaintenanceEntry 11}

mp7001ValidIntervals OBJECT-TYPE
	SYNTAX  INTEGER (1..96)
	ACCESS  read-only
	STATUS  mandatory
	DESCRIPTION
	"The number of  previous  intervals  for  which
	valid data was collected.  The value will be 96
	unless the interface was brought on-line within
	the last 24 hours, in which case the value will
	be the number of complete 15  minute  intervals
	the since interface has been online."
	::= {mp7001MaintenanceEntry 12}

--
-- ********************************************************************
-- The GDC 7001 Configuration Table
-- ********************************************************************

mp7001ConfigTable OBJECT-TYPE
     SYNTAX SEQUENCE OF Mp7001ConfigEntry
     ACCESS not-accessible
     STATUS mandatory
     DESCRIPTION
	 "The GDC Configuration table."
     ::= { mp7001Configuration 1 }

mp7001ConfigEntry OBJECT-TYPE
     SYNTAX Mp7001ConfigEntry
     ACCESS not-accessible
     STATUS mandatory
     DESCRIPTION
	 "The GDC Configuration table entry."
     INDEX { mp7001ConfigIndex }
     ::= { mp7001ConfigTable 1 }

Mp7001ConfigEntry ::= 
     SEQUENCE {
	 mp7001ConfigIndex SCinstance,
	 mp7001NetworkInterfaceType INTEGER,
	 mp7001TransmitClockSource INTEGER,
	 mp7001FallbackClockSource INTEGER,
	 mp7001PreEqualization INTEGER,
	 mp7001Framing INTEGER,
	 mp7001LineCoding INTEGER,
         mp7001LineBuildout INTEGER,
         mp7001FDLMode INTEGER,
         mp7001FramingMode INTEGER,
         mp7001Loopback INTEGER,
         mp7001AISLoopdown INTEGER,
         mp7001SignalMode INTEGER,
	 mp7001LineBuildoutCtrl INTEGER
     	 }

mp7001ConfigIndex 	OBJECT-TYPE
     	 SYNTAX SCinstance
     	 ACCESS read-only
     	 STATUS mandatory
     	 DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
         ::= { mp7001ConfigEntry 1 }

mp7001NetworkInterfaceType   	OBJECT-TYPE
	 SYNTAX INTEGER {
			ds1(1),
			dsx1(2)
		        }
	 ACCESS read-write
	 STATUS mandatory
	 DESCRIPTION
		"Sets the transmit range to DSX-1 short or DS-1 long "
	 ::= { mp7001ConfigEntry 2 }

mp7001TransmitClockSource OBJECT-TYPE
     	 SYNTAX INTEGER {
			system(1),
			recovered(2),
			internal(3)
     	 		}
     	 ACCESS read-write
     	 STATUS mandatory
     	 DESCRIPTION
		"Sets the transmit clock source."
     	 ::= { mp7001ConfigEntry 3 }

mp7001FallbackClockSource OBJECT-TYPE
     	 SYNTAX INTEGER {
			system(1),
			recovered(2),
			internal(3)
			}
     	 ACCESS read-write
     	 STATUS mandatory
    	 DESCRIPTION
	 "Identifies the fallback transmit clock source."

    	 ::= { mp7001ConfigEntry 4 }

mp7001PreEqualization OBJECT-TYPE
     	 SYNTAX INTEGER {
			none(1),
	 		feet130(2),                    
	 		feet260(3),
	 		feet390(4),
         		feet530(5),
         		feet655(6)
     			}
     	 ACCESS read-write
    	 STATUS mandatory
     	 DESCRIPTION
		"Pre-Equalization distance"
     	 ::= { mp7001ConfigEntry 5 }

mp7001Framing OBJECT-TYPE
	 SYNTAX INTEGER {
			eSF(1),
			d4(2)
			}
	 ACCESS read-write
	 STATUS mandatory
	 DESCRIPTION
		"Set the framing for the interface.
		 Abbreviations are as follows:
		 eSF - Extended Super Frame
		 d4  -  Super Frame"
	 ::= {mp7001ConfigEntry 6 }

mp7001LineCoding OBJECT-TYPE
	 SYNTAX INTEGER {
			b8zs(1),
			ami(2)
			}
	 ACCESS read-write
	 STATUS mandatory
	 DESCRIPTION
		"Sets the line coding for the interface."
	 ::= {mp7001ConfigEntry 7 }
 
mp7001LineBuildout OBJECT-TYPE
	SYNTAX INTEGER  {
			dB0(1),
			dB75(2),
                        dB15(3),
			dB22(4)
			}
	 ACCESS read-write
	 STATUS mandatory
	 DESCRIPTION
		"Sets the line build out for the interface
                         0, -7.5, -15 or -22.5dB"
	 ::= {mp7001ConfigEntry 8 }
 
mp7001FDLMode OBJECT-TYPE
	 SYNTAX INTEGER {
			none(1),
			aNSIT1403(2),
                        tR54016(3)
			}
	 ACCESS read-write
	 STATUS mandatory
	 DESCRIPTION
		"Sets the Facility Data Link Mode."
	 ::= {mp7001ConfigEntry 9 }
 
mp7001FramingMode OBJECT-TYPE
	 SYNTAX INTEGER {
			auto(1),
			manual(2)
			}
	 ACCESS read-write
	 STATUS mandatory
	 DESCRIPTION
		"Sets the framing mode"
	 ::= {mp7001ConfigEntry 10 }

mp7001Loopback OBJECT-TYPE
	 SYNTAX INTEGER {
			inhibitloop(1),
			payloadloop(2),
			lineloop(3)
			}
	 ACCESS read-write
	 STATUS mandatory
	 DESCRIPTION
		"Sets the loopback type"
	 ::= {mp7001ConfigEntry 11 }

mp7001AISLoopdown OBJECT-TYPE
	 SYNTAX INTEGER (4..60)
	 ACCESS read-write
	 STATUS mandatory
	 DESCRIPTION
		"Sets AIS unloop time where 4 = inhibit,
                         5 thru 60 = number of seconds"
 	 ::= {mp7001ConfigEntry 12 }

mp7001SignalMode OBJECT-TYPE
	 SYNTAX INTEGER {
			none(1),
			robbedbit(2)
			}
	 ACCESS read-write
	 STATUS mandatory
	 DESCRIPTION
		"Sets signalling mode"
	 ::= {mp7001ConfigEntry 13 }

mp7001LineBuildoutCtrl OBJECT-TYPE
	 SYNTAX INTEGER {
			auto(1),
			manual(2)
			}
	 ACCESS read-write
	 STATUS mandatory
	 DESCRIPTION
		"Sets the line buildout control"
	 ::= {mp7001ConfigEntry 14 }
 
--
-- ********************************************************************
-- The GDC 7001 System Configuration Table
-- ********************************************************************

mp7001SysTimingTable OBJECT-TYPE
     SYNTAX SEQUENCE OF Mp7001SysTimingEntry
     ACCESS not-accessible
     STATUS mandatory
     DESCRIPTION
	 "The GDC System Timing table."
     ::= { mp7001SysConfig 1 }

mp7001SysTimingEntry OBJECT-TYPE
     SYNTAX Mp7001SysTimingEntry
     ACCESS not-accessible
     STATUS mandatory
     DESCRIPTION
	 "The GDC Configuration table entry."
     INDEX { mp7001SysTimingIndex }
     ::= { mp7001SysTimingTable 1 }

Mp7001SysTimingEntry ::= 
     SEQUENCE 	{
		mp7001SysTimingIndex SCinstance,
		mp7001SysTimingGen INTEGER
		}

mp7001SysTimingIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001SysTimingEntry 1 }

mp7001SysTimingGen     OBJECT-TYPE 
	SYNTAX INTEGER {
			none(1),
			primary(2),
			secondary(3)
			}
	ACCESS read-write
	STATUS mandatory
	DESCRIPTION
		"Selects if the unit provides system timing.
		none(1) - does not provide Timing Generator
		primary(2) - unit is primary Timing Generator for the shelf.
		secondary(3) - unit is secondary Timing Generator for the 
			shelf.

		Only 1 unit in the shelf can the primary or secondary 
		timing generator. All other must be none."

	::= {mp7001SysTimingEntry 2}

--
-- *********************************************************************
-- The GDC 7001 DCC Configuration Table
-- *********************************************************************

mp7001DCCConfigurationTable OBJECT-TYPE
     SYNTAX SEQUENCE OF Mp7001DCCConfigurationEntry
     ACCESS not-accessible
     STATUS mandatory
     DESCRIPTION
	 "The GDC DCC Configuration table. These are Diagnostic Channel 
	  configuration options."
     ::= { mp7001Configuration 2}

mp7001DCCConfigurationEntry OBJECT-TYPE
     SYNTAX Mp7001DCCConfigurationEntry
     ACCESS not-accessible
     STATUS mandatory
     DESCRIPTION
	 "The GDC Diagnostic Configuration table entry."
     INDEX { mp7001DCCConfigurationIndex }
     ::= { mp7001DCCConfigurationTable 1 }

Mp7001DCCConfigurationEntry ::= 
     SEQUENCE {
	mp7001DCCConfigurationIndex SCinstance,
	mp7001TimeSlot INTEGER,
	mp7001Bandwidth INTEGER
	}

mp7001DCCConfigurationIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001DCCConfigurationEntry 1 }

mp7001TimeSlot OBJECT-TYPE
	SYNTAX INTEGER(1..24)
	ACCESS read-write
	STATUS mandatory
	DESCRIPTION
		"Time Slot DCC goes in"
	::={ mp7001DCCConfigurationEntry 2}

mp7001Bandwidth OBJECT-TYPE
	SYNTAX INTEGER {
		kbps8(1),
		kbps56(2),
		kbps64(3),
		notAssigned(4)
		}
	ACCESS read-write
	STATUS mandatory
	DESCRIPTION
		"Bandwidth to use:
			8 kbps - bit 7 only
			56 kbps - bits 0 - 6
			64 kbps - all 8 bits"
	::={ mp7001DCCConfigurationEntry 3}

--
-- ********************************************************************
-- The GDC 7001 T1 Highway Assignment Table
-- ********************************************************************

mp7001HighwayAssignTable OBJECT-TYPE
     SYNTAX SEQUENCE OF Mp7001HighwayAssignEntry
     ACCESS not-accessible
     STATUS mandatory
     DESCRIPTION
	 "The GDC Highway/Timeslot Assignment Table."
     ::= { mp7001SysConfig 2}

mp7001HighwayAssignEntry OBJECT-TYPE
     SYNTAX Mp7001HighwayAssignEntry
     ACCESS not-accessible
     STATUS mandatory
     DESCRIPTION
	 "The GDC T1 Highway Assign table entry."
     INDEX { mp7001HighwayAssignIndex }
     ::= { mp7001HighwayAssignTable 1 }

Mp7001HighwayAssignEntry ::= 
     SEQUENCE {
	 mp7001HighwayAssignIndex SCinstance,
	 mp7001StartTimeSlot INTEGER,
	 mp7001NumberOfTimeSlots INTEGER,
	 mp7001BundleDestination INTEGER,
	 mp7001ExecuteAssign INTEGER
	}
 
mp7001HighwayAssignIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001HighwayAssignEntry 1 }

mp7001StartTimeSlot    OBJECT-TYPE
	SYNTAX  INTEGER (1..24)
	ACCESS  read-write
	STATUS  mandatory
	DESCRIPTION
		"Starting time slot of the bundle. If only 1 bundle is
		being assigned, or the first of 2 is being assigned, 
		it must start at 1. The second of 2 must start at the next
		available time slot after the first bundle."
	::= {mp7001HighwayAssignEntry 2 }

mp7001NumberOfTimeSlots        OBJECT-TYPE
	SYNTAX  INTEGER (1..24)
	ACCESS  read-write
	STATUS  mandatory
	DESCRIPTION
		"Number of time slots assigned to the bundle."
	::= {mp7001HighwayAssignEntry 3 }

mp7001BundleDestination      OBJECT-TYPE
	SYNTAX  INTEGER {
			notAssigned(1),
			highway1(2),
			highway2(3),
			highway3(4),
			highway4(5)
			}
	ACCESS read-write
	STATUS mandatory
	DESCRIPTION
		"Defines the destination of the bundle."
	::= {mp7001HighwayAssignEntry 4 }

mp7001ExecuteAssign OBJECT-TYPE
	SYNTAX  INTEGER {
			normal(1),
			execute(2)
			}
	ACCESS read-write
	STATUS mandatory
	DESCRIPTION
		"Causes the MP7001 to execute configuration of the assigned 
		 highway configuration. This object should be sent in a separate 
		 PDU after acknowlegement of the assign PDU(s) has been received."
	::= {mp7001HighwayAssignEntry 5 }


--
-- ********************************************************************
-- GDC 7001 Diagnostics
-- ********************************************************************

mp7001DiagTable OBJECT-TYPE
     SYNTAX SEQUENCE OF Mp7001DiagEntry
     ACCESS not-accessible
     STATUS mandatory
     DESCRIPTION
	 "The GDC T1 Diagnostics table.  Information in the entries of
	 this table support diagnostics testing, both active testing
	 via patterns, and passive testing via loopbacks."
     ::= { mp7001Diagnostics 1 }

mp7001DiagEntry OBJECT-TYPE
     SYNTAX Mp7001DiagEntry
     ACCESS not-accessible
     STATUS mandatory
     DESCRIPTION
	 "The GDC T1 Diagnostics table entry."
     INDEX { mp7001DiagIndex }
     ::= { mp7001DiagTable 1 }

Mp7001DiagEntry ::= 
     SEQUENCE {
	 mp7001DiagIndex SCinstance,
	 mp7001TestPattern INTEGER,
	 mp7001DiagConfig INTEGER,
	 mp7001TestLimit INTEGER,
	 mp7001TestExecutionStatus INTEGER,
	 mp7001TestExceptions INTEGER,
	 mp7001TestResults INTEGER,
	 mp7001ResetTestResults INTEGER,
	 mp7001DS0Diag INTEGER
     }

mp7001DiagIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001DiagEntry 1 }

mp7001TestPattern OBJECT-TYPE
     SYNTAX INTEGER {
		noCode(1),
		pat511(2),
		pat2047(3),
		patQRSS(4),
		pat3in24(5),
		inbandCode(6),
		resetInband(7),
		ntwkInterfaceCode(8),
		resetNtwkInterface(9),
		ds0Delay(10)
		}
     ACCESS read-write
     STATUS mandatory
     DESCRIPTION
		"Test pattern for tests that use the pattern generator."
     ::= { mp7001DiagEntry 2 }

mp7001DiagConfig OBJECT-TYPE
     SYNTAX INTEGER {
		noLoop(1),
		lineLoopback(2),
		payloadLoopback(3),
		dsoLoopback(4),
		cascadeLoopback(5),
		localTest(6)
     }
     ACCESS read-write
     STATUS mandatory
     DESCRIPTION
		"Selects the test to run. noLoop(1) ends the test."
     ::= { mp7001DiagEntry 3 }

mp7001TestLimit OBJECT-TYPE
     SYNTAX INTEGER     {
				 noLimit(1),
				 testTime1Min(2),
				 testTime2Mins(3),
				 testTime3Mins(4),
				 testTime4Mins(5),
				 testTime5Mins(6),
				 testTime6Mins(7),
				 testTime7Mins(8),
				 testTime8Mins(9),
				 testTime9Mins(10),
				 testTime10Mins(11),
				 testTime15Mins(12),
				 testTime20Mins(13),
				 testTime25Mins(14),
				 testTime30Mins(15),
				 testTime30Secs(16)
	     		}                  
     ACCESS read-write
     STATUS mandatory
     DESCRIPTION
	 "Selects the duration to run a diagnostic test.  The value(1)
	 noLimit signifies that the test should run indefinitely until
	 explicitly terminated." 
     	::= { mp7001DiagEntry 4 }

mp7001TestExecutionStatus OBJECT-TYPE
     SYNTAX INTEGER {
	 notInTest(1),                  -- a test is not running
	 testInProgress(2),             -- the test is running
	 testCompleted(4),              -- the test is complete
	 testCompletedNotInTest(5)      -- a test has completed,nolonger in test
     }
     ACCESS read-only
     STATUS mandatory
     DESCRIPTION
     "This variable reports the status of a test.  notInTest(1) indicates
      a test is not running.  testInProgress(2) indicates that a test is
      currently running.  testCompleted(4) indicates that a test has run
      and is completed. testCompletedNotInTest(5) indicates that a test has
      completed and it is no longer in test."
	::= { mp7001DiagEntry 5 }

mp7001TestExceptions OBJECT-TYPE
     SYNTAX INTEGER (0..7)
     ACCESS read-only
     STATUS mandatory
     DESCRIPTION
	 "Indicates exceptions that have occurred that may affect
	 interpretation of the test results.

	 The value of this object is a sum.  This sum initially take
	 the value zero.  Then, for each exception, the value
	 associated with the exception is added to the sum.

	 The exception values are:

		 value  exception
		     1   a timed test was preempted so the result
			 cannot be viewed in relation to the test
			 duration
		     2   the results overflowed so the result cannot be
			 viewed as an absolute value
		     4   the test was performed while synchronization
			 could not be performed so the result may not
			 be accurate."
	::= { mp7001DiagEntry 6 }

mp7001TestResults OBJECT-TYPE
     SYNTAX INTEGER(0..1048576)
     ACCESS read-only
     STATUS mandatory
     DESCRIPTION
	 "The results of the last diagnostic test.  This can be the
	 current test running or the last completed test.

	 Note that the interpretation of these results may be affected
	 by the value of the mp7001TestExceptions object."
     ::= { mp7001DiagEntry 7 }

mp7001ResetTestResults	OBJECT-TYPE
	SYNTAX INTEGER {
				norm(1),
				reset(2)
			}
	ACCESS read-only
	STATUS mandatory
	DESCRIPTION
	"Resets the diagnostic error count."
    ::= { mp7001DiagEntry 8 }

mp7001DS0Diag OBJECT-TYPE
     SYNTAX INTEGER (0..32)            -- 0, 1-32		
     ACCESS read-write
     STATUS mandatory
     DESCRIPTION
	"Defines a DS0 level diagnostic.  Setting this object value to 0
	 disables a DS0 level diagnostic.  Setting this object to a value
	 from 1 to 32 enables a DS0 level diagnostic on the DS0 indicated.
	 Enabling a DS0 level diagnostic bysetting this object to a value
	 from 1 to 32 alters the meaning of the diagnostic test to be 
	 specific to the DS0 specified instead of the whole DS1.
	 Note that a DS0 level diagnostic and a DS1 level diagnostic
	 cannot be performed simultaneously."
    ::= { mp7001DiagEntry 9 }
 
--
-- ********************************************************************
-- GDC Dsx-1 Alarm Object Identifier Definitions
-- ********************************************************************

mp7001Alarms       	OBJECT IDENTIFIER ::= { mp7001System 8  }

mp7001NoResponseAlm	OBJECT IDENTIFIER ::= { mp7001Alarms 1  }
mp7001DiagRxErrAlm	OBJECT IDENTIFIER ::= { mp7001Alarms 2  }
mp7001PowerUpAlm	OBJECT IDENTIFIER ::= { mp7001Alarms 3  }
mp7001NvRamCorrupt	OBJECT IDENTIFIER ::= { mp7001Alarms 4  }
mp7001UnitFailure   	OBJECT IDENTIFIER ::= { mp7001Alarms 5  }
mp7001LossOfSignal     	OBJECT IDENTIFIER ::= { mp7001Alarms 6  }
mp7001LossOfFrame     	OBJECT IDENTIFIER ::= { mp7001Alarms 7  }
mp7001Ais		OBJECT IDENTIFIER ::= { mp7001Alarms 8  }
mp7001YELLOW		OBJECT IDENTIFIER ::= { mp7001Alarms 9  }
mp7001BipolarViolation 	OBJECT IDENTIFIER ::= { mp7001Alarms 10 }
mp7001CRC		OBJECT IDENTIFIER ::= { mp7001Alarms 11 }
mp7001UnSigState	OBJECT IDENTIFIER ::= { mp7001Alarms 12 }
mp7001TimingLoss       	OBJECT IDENTIFIER ::= { mp7001Alarms 13 }
mp7001ES		OBJECT IDENTIFIER ::= { mp7001Alarms 14 }
mp7001BES		OBJECT IDENTIFIER ::= { mp7001Alarms 15 }
mp7001SES		OBJECT IDENTIFIER ::= { mp7001Alarms 16 }
mp7001UAS		OBJECT IDENTIFIER ::= { mp7001Alarms 17 }
mp7001ControlSlips      OBJECT IDENTIFIER ::= { mp7001Alarms 18 }
mp7001UnsolicitedTest   OBJECT IDENTIFIER ::= { mp7001Alarms 19 }
-- ALARM                     Maskable               window/thres
-- ===================================================================
-- mp7001NoResponseAlm		no			no
-- mp7001DiagRxErrAlm		no			no
-- mp7001PowerUpAlm		no			no
-- mp7001NvRamCorrupt		no			no
-- mp7001UnitFailure		no			no
-- mp7001LossofSignal		yes			no
-- mp7001LossOfFrame		yes			no
-- mp7001Ais			yes			no
-- mp7001YELLOW			yes			no
-- mp7001BiPolarViolation	yes			yes
-- mp7001CRC		        yes			yes
-- mp7001UnSigState	        yes			no
-- mp7001TimingLoss		yes			no
-- mp7001ES			yes			yes
-- mp7001BES			yes			yes
-- mp7001SES			yes			yes
-- mp7001UAS			yes			yes
-- mp7001ControlSlips           yes			no
-- mp7001UnsolicitedTest	yes			no 
--
-- ********************************************************************
-- GDC MP7001 Alarm Configuration
-- ********************************************************************

mp7001NearEndAlarmConfigTable OBJECT-TYPE
     SYNTAX SEQUENCE OF Mp7001NearEndAlarmConfigEntry
     ACCESS not-accessible
     STATUS mandatory
     DESCRIPTION
    	"This table contains entries that configure Near End Alarm reporting."
     ::= { mp7001AlarmConfig 1 }

mp7001NearEndAlarmConfigEntry OBJECT-TYPE
     SYNTAX Mp7001NearEndAlarmConfigEntry
     ACCESS not-accessible
     STATUS mandatory
     DESCRIPTION
	 "An entry in the MP7001 Alarm Configuration table."
     INDEX { mp7001NearEndAlarmConfigIndex, mp7001NearEndAlarmConfigIdentifier }
     ::= { mp7001NearEndAlarmConfigTable 1 }

Mp7001NearEndAlarmConfigEntry ::=
     SEQUENCE {
	 mp7001NearEndAlarmConfigIndex
	     SCinstance,
	 mp7001NearEndAlarmConfigIdentifier
	     OBJECT IDENTIFIER,
	 mp7001NearEndAlarmCountWindow
	     INTEGER,
	 mp7001NearEndAlarmCountThreshold
	     INTEGER
     }

mp7001NearEndAlarmConfigIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001NearEndAlarmConfigEntry 1 }

mp7001NearEndAlarmConfigIdentifier OBJECT-TYPE
     SYNTAX OBJECT IDENTIFIER
     ACCESS read-only
     STATUS mandatory
     DESCRIPTION
	 "The unique alarm identifier assigned to this alarm type.
	 The format of this identifier is an OBJECT IDENTIFIER that has
	 the following format: {iso(1) org(3) dod(6) internet(1)
	 private(4) enterprises(1) gdc(498) xxx(x) alarm(z) yyy(y) 
	 where xxx(x) is the administratively assigned family object 
	 identifier (z) is the object identifier for alarms in the family
	 defined MIB and yyy(y) is the administratively assigned alarm 
	 type identifier for this alarm."
     ::= { mp7001NearEndAlarmConfigEntry 2 }

mp7001NearEndAlarmCountWindow OBJECT-TYPE
     SYNTAX INTEGER{
			disabled(1),
			last1sec(2),
			last10sec(3),
			last30sec(4),
			last1min(5),
			last15min(6),
			last1hr(7),
			last24hr(8),
			infinite(9)
		}
	ACCESS  read-write
	STATUS  mandatory
	DESCRIPTION
		"This variable sets/reads the alarm window.

		This window is used with the alarm threshold to determine
		how long the alarm should be active before reporting.

		Default: disabled(1)"
    ::= { mp7001NearEndAlarmConfigEntry 3 }

mp7001NearEndAlarmCountThreshold OBJECT-TYPE
    SYNTAX INTEGER {
			thresGT1(1),
			thresGT3(2),
			thresGT10(3),
			thresGT100(4),
			thresGT1000(5),
			thresGT10000(6)
		}
	ACCESS  read-write
	STATUS  mandatory
	DESCRIPTION
		"This function sets/reads the alarm threshold criteria.

		This threshold is used along with the the alarm window to 
		determine the number of instances in a given time frame for
		an alarm to occur before the alarm is considered active.

		Default: thresGT1(1)"
    ::= { mp7001NearEndAlarmConfigEntry 4 }

--
-- ********************************************************************
-- GDC LOCAL MP7001 Alarm Configuration
-- ********************************************************************

mp7001LocalAlarmConfigTable OBJECT-TYPE
     SYNTAX SEQUENCE OF Mp7001LocalAlarmConfigEntry
     ACCESS not-accessible
     STATUS mandatory
     DESCRIPTION
	 "The mp7001LocalAlarmConfigTable contains entries that configure 
	 alarm reporting to the alarm card."
     ::= { mp7001AlarmConfig 2 }

mp7001LocalAlarmConfigEntry OBJECT-TYPE
     SYNTAX Mp7001LocalAlarmConfigEntry
     ACCESS not-accessible
     STATUS mandatory
     DESCRIPTION
	 "An entry in the GDC Local Alarm Configuration table."
     INDEX { mp7001LocalAlarmConfigIndex }
     ::= { mp7001LocalAlarmConfigTable 1 }

Mp7001LocalAlarmConfigEntry ::=
     SEQUENCE {
	 mp7001LocalAlarmConfigIndex
	     SCinstance,
	 mp7001LOSLocal
	     INTEGER,
	 mp7001LOFLocal
	     INTEGER,
	 mp7001AISLocal
	     INTEGER,
	 mp7001RxYELLOWLocal
	     INTEGER,
	 mp7001BPVLocal
	     INTEGER,
	 mp7001CRCLocal
	     INTEGER,
	 mp7001UnSigStateLocal
	     INTEGER,
	 mp7001TiminglossLocal
	     INTEGER,
	 mp7001ESLocal
	     INTEGER,
	 mp7001BESLocal
	     INTEGER,
	 mp7001SESLocal
	     INTEGER,
	 mp7001UASLocal
	     INTEGER
	 }

mp7001LocalAlarmConfigIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001LocalAlarmConfigEntry 1 }

mp7001LOSLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 2 }

mp7001LOFLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 3 }

mp7001AISLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 4 }

mp7001RxYELLOWLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 5 }

mp7001BPVLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 6 }

mp7001CRCLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 7 }

mp7001UnSigStateLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 8 }

mp7001TiminglossLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 9 }

mp7001ESLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 10 }

mp7001BESLocal      OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 11 }

mp7001SESLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 12 }

mp7001UASLocal       OBJECT-TYPE
	SYNTAX  INTEGER {
			disabled(1),
			enabledMajor(2),
			enabledMinor(3)
			}
	ACCESS  read-write
	STATUS  mandatory
	DESCRIPTION
		"Disables or enables the alarm on the Major buss or Minor
		buss."
     ::= { mp7001LocalAlarmConfigEntry 13 }

--
-- ********************************************************************
-- ANSI Performance 
-- ********************************************************************

-- ********************************************************************
-- Inbound Direction
-- ********************************************************************

mp7001InboundANSIperfTable OBJECT-TYPE
     SYNTAX SEQUENCE OF Mp7001InboundANSIperfEntry
     ACCESS not-accessible
     STATUS mandatory
     DESCRIPTION
	 "The GDC ANSI Performance table.  Information in the entries
	 of this table support the ANSI Scheduled Performance Reports.
	 Entries supply information for inbound 
	 reports for the last 4 seconds."
     ::= { mp7001Performance 1 }

mp7001InboundANSIperfEntry OBJECT-TYPE
     SYNTAX Mp7001InboundANSIperfEntry
     ACCESS not-accessible
     STATUS mandatory
     DESCRIPTION
	 "The GDC ANSI Performance table entry.  The information in
	 this entry presents one of the 4 second periods performance
	 data in the inbound direction."
     INDEX { mp7001InboundANSIperfIndex, mp7001InboundANSIseconds }
     ::= { mp7001InboundANSIperfTable 1 }

Mp7001InboundANSIperfEntry ::= 
     SEQUENCE {
	 mp7001InboundANSIperfIndex SCinstance,
	 mp7001InboundANSIseconds INTEGER,
	 mp7001InboundANSICRCerrorEvents INTEGER,
	 mp7001InboundANSIsevereErrors INTEGER,
	 mp7001InboundANSIframeErrors INTEGER,
	 mp7001InboundANSIcodeViolations INTEGER,
	 mp7001InboundANSIcontrolledSlips INTEGER,
	 mp7001InboundANSIactivePayloadLoops INTEGER
     }

mp7001InboundANSIperfIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001InboundANSIperfEntry 1 }    

mp7001InboundANSIseconds OBJECT-TYPE
     SYNTAX INTEGER (1..4)		-- 1 to 4 seconds of statistics
     ACCESS read-only
     STATUS mandatory
     DESCRIPTION
	 "Identifies the reporting interval.  This has the value 1 to 4
	 supporting up to the last 4 seconds of performance data."
     ::= { mp7001InboundANSIperfEntry 2 }

mp7001InboundANSICRCerrorEvents OBJECT-TYPE
     SYNTAX INTEGER {
	 noErrors(1),			-- no errors in the interval
	 errors1(2),			-- 1 error in the interval
	 errors2to5(4),			-- 2 to 5 errors in the interval
	 errors6to10(8),		-- 6 to 10 errors in the interval
	 errors11to100(16),		-- 11 to 100 errors in the interval
	 errors101to320(32),		-- 101 to 320 errors in the interval
	 errors321orMore(64)		-- 321 or more errors in the interval
     }
     ACCESS read-only
     STATUS mandatory
     DESCRIPTION
	 "Identifies the magnitude of the error events in the interval
	 which this entry represents."
     ::= { mp7001InboundANSIperfEntry 3 }

mp7001InboundANSIsevereErrors OBJECT-TYPE
     SYNTAX INTEGER {
	 noEventsDetected(1),		-- no events detected in the interval
	 eventsDetected(2)		-- events detected in the interval
     }
     ACCESS read-only
     STATUS mandatory
     DESCRIPTION
	 "Identifies whether or not any severe errors were detected in
	 the interval which this entry represents."
     ::= { mp7001InboundANSIperfEntry 4 }

mp7001InboundANSIframeErrors OBJECT-TYPE
     SYNTAX INTEGER {
	 noEventsDetected(1),		-- no events detected in the interval
	 eventsDetected(2)		-- events detected in the interval
     }
     ACCESS read-only
     STATUS mandatory
     DESCRIPTION
	 "Identifies whether or not any framing errors were detected in
	 the interval which this entry represents."
     ::= { mp7001InboundANSIperfEntry 5 }

mp7001InboundANSIcodeViolations OBJECT-TYPE
     SYNTAX INTEGER {
	 noEventsDetected(1),		-- no events detected in the interval
	 eventsDetected(2)		-- events detected in the interval
     }
     ACCESS read-only
     STATUS mandatory
     DESCRIPTION
	 "Identifies whether or not any code violations were detected in
	 the interval which this entry represents."
     ::= { mp7001InboundANSIperfEntry 6 }

mp7001InboundANSIcontrolledSlips OBJECT-TYPE
     SYNTAX INTEGER {
	 noEventsDetected(1),		-- no events detected in the interval
	 eventsDetected(2)		-- events detected in the interval
     }
     ACCESS read-only
     STATUS mandatory
     DESCRIPTION
	 "Identifies whether or not any controlled slips were detected in
	 the interval which this entry represents."
     ::= { mp7001InboundANSIperfEntry 7 }

mp7001InboundANSIactivePayloadLoops OBJECT-TYPE
     SYNTAX INTEGER {
	 noEventsDetected(1),		-- no events detected in the interval
	 eventsDetected(2)		-- events detected in the interval
     }
     ACCESS read-only
     STATUS mandatory
     DESCRIPTION
	 "Identifies whether or not any active payload loops were detected in
	 the interval which this entry represents."
     ::= { mp7001InboundANSIperfEntry 8 }

--
-- ********************************************************************
-- Outbound Direction
-- ********************************************************************

mp7001OutboundANSIperfTable OBJECT-TYPE
     SYNTAX SEQUENCE OF Mp7001OutboundANSIperfEntry
     ACCESS not-accessible
     STATUS mandatory
     DESCRIPTION
	 "The GDC ANSI Performance table.  Information in the entries
	 of this table support the ANSI Scheduled Performance Reports.
	 Entries supply information for outbound 
	 reports for the last 4 seconds."
     ::= { mp7001Performance 2 }

mp7001OutboundANSIperfEntry OBJECT-TYPE
     SYNTAX Mp7001OutboundANSIperfEntry
     ACCESS not-accessible
     STATUS mandatory
     DESCRIPTION
	 "The GDC ANSI Performance table entry.  The information in
	 this entry presents one of the 4 second periods performance
	 data in the outbound direction."
     INDEX { mp7001OutboundANSIperfIndex, mp7001OutboundANSIseconds }
     ::= { mp7001OutboundANSIperfTable 1 }

Mp7001OutboundANSIperfEntry ::= 
     SEQUENCE {
	 mp7001OutboundANSIperfIndex SCinstance,
	 mp7001OutboundANSIseconds INTEGER,
	 mp7001OutboundANSICRCerrorEvents INTEGER,
	 mp7001OutboundANSIsevereErrors INTEGER,
	 mp7001OutboundANSIframeErrors INTEGER,
	 mp7001OutboundANSIcodeViolations INTEGER,
	 mp7001OutboundANSIcontrolledSlips INTEGER,
	 mp7001OutboundANSIactivePayloadLoops INTEGER
     }

mp7001OutboundANSIperfIndex OBJECT-TYPE
     SYNTAX SCinstance
     ACCESS read-only
     STATUS mandatory
     DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
     ::= { mp7001OutboundANSIperfEntry 1 }    

mp7001OutboundANSIseconds OBJECT-TYPE
     SYNTAX INTEGER (1..4)		-- 1 to 4 seconds of statistics
     ACCESS read-only
     STATUS mandatory
     DESCRIPTION
	 "Identifies the reporting interval.  This has the value 1 to 4
	 supporting up to the last 4 seconds of performance data."
     ::= { mp7001OutboundANSIperfEntry 2 }

mp7001OutboundANSICRCerrorEvents OBJECT-TYPE
     SYNTAX INTEGER {
	 noErrors(1),			-- no errors in the interval
	 errors1(2),			-- 1 error in the interval
	 errors2to5(4),			-- 2 to 5 errors in the interval
	 errors6to10(8),		-- 6 to 10 errors in the interval
	 errors11to100(16),		-- 11 to 100 errors in the interval
	 errors101to320(32),		-- 101 to 320 errors in the interval
	 errors321orMore(64)		-- 321 or more errors in the interval
     }
     ACCESS read-only
     STATUS mandatory
     DESCRIPTION
	 "Identifies the magnitude of the error events in the interval
	 which this entry represents."
     ::= { mp7001OutboundANSIperfEntry 3 }

mp7001OutboundANSIsevereErrors OBJECT-TYPE
     SYNTAX INTEGER {
	 noEventsDetected(1),		-- no events detected in the interval
	 eventsDetected(2)		-- events detected in the interval
     }
     ACCESS read-only
     STATUS mandatory
     DESCRIPTION
	 "Identifies whether or not any severe errors were detected in
	 the interval which this entry represents."
     ::= { mp7001OutboundANSIperfEntry 4 }

mp7001OutboundANSIframeErrors OBJECT-TYPE
     SYNTAX INTEGER {
	 noEventsDetected(1),		-- no events detected in the interval
	 eventsDetected(2)		-- events detected in the interval
     }
     ACCESS read-only
     STATUS mandatory
     DESCRIPTION
	 "Identifies whether or not any framing errors were detected in
	 the interval which this entry represents."
     ::= { mp7001OutboundANSIperfEntry 5 }

mp7001OutboundANSIcodeViolations OBJECT-TYPE
     SYNTAX INTEGER {
	 noEventsDetected(1),		-- no events detected in the interval
	 eventsDetected(2)		-- events detected in the interval
     }
     ACCESS read-only
     STATUS mandatory
     DESCRIPTION
	 "Identifies whether or not any code violations were detected in
	 the interval which this entry represents."
     ::= { mp7001OutboundANSIperfEntry 6 }

mp7001OutboundANSIcontrolledSlips OBJECT-TYPE
     SYNTAX INTEGER {
	 noEventsDetected(1),		-- no events detected in the interval
	 eventsDetected(2)		-- events detected in the interval
     }
     ACCESS read-only
     STATUS mandatory
     DESCRIPTION
	 "Identifies whether or not any controlled slips were detected in
	 the interval which this entry represents."
     ::= { mp7001OutboundANSIperfEntry 7 }

mp7001OutboundANSIactivePayloadLoops OBJECT-TYPE
     SYNTAX INTEGER {
	 noEventsDetected(1),		-- no events detected in the interval
	 eventsDetected(2)		-- events detected in the interval
     }
     ACCESS read-only
     STATUS mandatory
     DESCRIPTION
	 "Identifies whether or not any active payload loops were detected in
	 the interval which this entry represents."
     ::= { mp7001OutboundANSIperfEntry 8 }


--
-- ********************************************************************
-- ATT Current Performance Table
-- ********************************************************************

mp7001CurrentTable 	OBJECT-TYPE
	 SYNTAX  SEQUENCE OF Mp7001CurrentEntry
	 ACCESS  not-accessible
	 STATUS  mandatory
	 DESCRIPTION
		 "The mp7001 Current table.  This table supplements the
		 entries in the DS1 AT&T performance table of the DS1
		 MIB defined in RFC1406."
	 ::= { mp7001Performance 3 }


mp7001CurrentEntry 	OBJECT-TYPE
	 SYNTAX  Mp7001CurrentEntry
	 ACCESS  not-accessible
	 STATUS  mandatory
	 DESCRIPTION
		 "An entry in the mp7001 Current table."
	 INDEX   { mp7001CurrentIndex }
	 ::= { mp7001CurrentTable 1 }

Mp7001CurrentEntry ::=
	 SEQUENCE {
		  mp7001CurrentIndex
			 SCinstance,
		  mp7001CurrentStat
			 OCTET STRING
	  }

mp7001CurrentIndex 	OBJECT-TYPE
	 SYNTAX  SCinstance
	 ACCESS  read-only
	 STATUS  mandatory
	 DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
	    ::= { mp7001CurrentEntry 1 }

mp7001CurrentStat 	OBJECT-TYPE
	SYNTAX OCTET STRING (SIZE(17))
	ACCESS read-only
	STATUS mandatory
	DESCRIPTION
		"Returns a bitwise snapshot of the current statistics.
		 Octet 1 bit 7 - not used
			 bit 6 - future use
			 bit 5 - future use
			 bit 4 - future use
			 bit 3 - future use
			 bit 2 - future use
			 bit 1 - future use
			 bit 0 - 1: New Interval
		 Octet 2 bit 7 - not used
			 bit 6 - future use
			 bit 5 - future use
			 bit 4 - future use
			 bit 3 - future use
			 bit 2 - future use
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored Seconds
		 Octet 5 bit 7 - not used
			 bit 6 - future use
			 bit 5 - future use
			 bit 4 - future use
			 bit 3 - future use
			 bit 2 - future use
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds
		 Octet 8 bit 7 - not used
			 bit 6 - future use
			 bit 5 - future use
			 bit 4 - future use
			 bit 3 - future use
			 bit 2 - future use
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
		Octet 10 bit 7 - not used
			 bit 6 - 2^6 
			 bit 5 - 2^5 
			 bit 4 - 2^4 
			 bit 3 - 2^3 
			 bit 2 - 2^2 
			 bit 1 - 2^1 
			 bit 0 - 2^0    Bursty Errored Seconds
		Octet 11 bit 7 - not used
			 bit 6 - future use
			 bit 5 - future use
			 bit 4 - future use
			 bit 3 - future use
			 bit 2 - future use
			 bit 1 - 2^15
			 bit 0 - 2^14
		Octet 12 bit 7 - not used
			 bit 6 - 2^13
			 bit 5 - 2^12
			 bit 4 - 2^11
			 bit 3 - 2^10
			 bit 2 - 2^9
			 bit 1 - 2^8
			 bit 0 - 2^7
		Octet 13 bit 7 - not used
			 bit 6 - 2^6 
			 bit 5 - 2^5 
			 bit 4 - 2^4 
			 bit 3 - 2^3 
			 bit 2 - 2^2 
			 bit 1 - 2^1 
			 bit 0 - 2^0    Unavailable Seconds
		Octet 14 bit 7 - not used
			 bit 6 - future use
			 bit 5 - future use
			 bit 4 - future use
			 bit 3 - future use
			 bit 2 - future use
			 bit 1 - future use
			 bit 0 - 2^7 
		Octet 15 bit 7 - not used
			 bit 6 - 2^6 
			 bit 5 - 2^5 
			 bit 4 - 2^4 
			 bit 3 - 2^3 
			 bit 2 - 2^2 
			 bit 1 - 2^1 
			 bit 0 - 2^0    Controlled Slip Seconds
		Octet 16 bit 7 - not used
			 bit 6 - future use
			 bit 5 - future use
			 bit 4 - future use
			 bit 3 - future use
			 bit 2 - future use
			 bit 1 - future use
			 bit 0 - 2^7 
		Octet 17 bit 7 - not used
			 bit 6 - 2^6 
			 bit 5 - 2^5 
			 bit 4 - 2^4 
			 bit 3 - 2^3 
			 bit 2 - 2^2 
			 bit 1 - 2^1 
			 bit 0 - 2^0    Loss of Frame Count"
	::= {mp7001CurrentEntry 2 }


--
-- ********************************************************************
-- ATT Interval Performance Table
-- ********************************************************************

mp7001IntervalTable 	OBJECT-TYPE
	 SYNTAX  SEQUENCE OF Mp7001IntervalEntry
	 ACCESS  not-accessible
	 STATUS  mandatory
	 DESCRIPTION
		 "The mp7001 Interval table.  This table supplements the
		 entries in the DS1 AT&T performance table of the DS1
		 MIB defined in RFC1406."
	 ::= { mp7001Performance 4 }


mp7001IntervalEntry 	OBJECT-TYPE
	 SYNTAX  Mp7001IntervalEntry
	 ACCESS  not-accessible
	 STATUS  mandatory
	 DESCRIPTION
		 "An entry in the DS1 Interval table."
	 INDEX   { mp7001IntervalIndex, mp7001IntervalNumber }
	 ::= { mp7001IntervalTable 1 }

Mp7001IntervalEntry ::=
	 SEQUENCE {
		  mp7001IntervalIndex
			 SCinstance,
		  mp7001IntervalNumber
			 INTEGER,
		  mp7001IntervalStat
			 OCTET STRING
	  }

mp7001IntervalIndex 	OBJECT-TYPE
	 SYNTAX  SCinstance
	 ACCESS  read-only
	 STATUS  mandatory
	 DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
	 ::= { mp7001IntervalEntry 1 }

mp7001IntervalNumber 	OBJECT-TYPE
	 SYNTAX  INTEGER (1..96)
	 ACCESS  read-only
	 STATUS  mandatory
	 DESCRIPTION
		 "A number between 1 and 96, where 1 is the most recently completed 
		 15 minute interval and 96 is the least recently completed 15 minutes  
		 interval   (assuming   that  all  96  intervals  are valid)."
	 ::= { mp7001IntervalEntry 2 }

mp7001IntervalStat 	OBJECT-TYPE
	SYNTAX OCTET STRING (SIZE(16))
	ACCESS read-only
	STATUS mandatory
	DESCRIPTION
		"Returns a bitwise snapshot of the interval statistics.
		 Octet 1 bit 7 - not used
			 bit 6 - future use
			 bit 5 - future use
			 bit 4 - future use
			 bit 3 - future use
			 bit 2 - future use
			 bit 1 - 2^15
			 bit 0 - 2^14
		 Octet 2 bit 7 - not used
			 bit 6 - 2^13
			 bit 5 - 2^12
			 bit 4 - 2^11
			 bit 3 - 2^10
			 bit 2 - 2^9
			 bit 1 - 2^8
			 bit 0 - 2^7
		 Octet 3 bit 7 - not used
			 bit 6 - 2^6 
			 bit 5 - 2^5 
			 bit 4 - 2^4 
			 bit 3 - 2^3 
			 bit 2 - 2^2 
			 bit 1 - 2^1 
			 bit 0 - 2^0    Errored Seconds
		 Octet 4 bit 7 - not used
			 bit 6 - future use
			 bit 5 - future use
			 bit 4 - future use
			 bit 3 - future use
			 bit 2 - future use
			 bit 1 - 2^15
			 bit 0 - 2^14
		 Octet 5 bit 7 - not used
			 bit 6 - 2^13
			 bit 5 - 2^12
			 bit 4 - 2^11
			 bit 3 - 2^10
			 bit 2 - 2^9
			 bit 1 - 2^8
			 bit 0 - 2^7
		 Octet 6 bit 7 - not used
			 bit 6 - 2^6 
			 bit 5 - 2^5 
			 bit 4 - 2^4 
			 bit 3 - 2^3 
			 bit 2 - 2^2 
			 bit 1 - 2^1 
			 bit 0 - 2^0    Severely Errored Seconds
		 Octet 7 bit 7 - not used
			 bit 6 - future use
			 bit 5 - future use
			 bit 4 - future use
			 bit 3 - future use
			 bit 2 - future use
			 bit 1 - 2^15
			 bit 0 - 2^14
		 Octet 8 bit 7 - not used
			 bit 6 - 2^13
			 bit 5 - 2^12
			 bit 4 - 2^11
			 bit 3 - 2^10
			 bit 2 - 2^9
			 bit 1 - 2^8
			 bit 0 - 2^7
		 Octet 9 bit 7 - not used
			 bit 6 - 2^6 
			 bit 5 - 2^5 
			 bit 4 - 2^4 
			 bit 3 - 2^3 
			 bit 2 - 2^2 
			 bit 1 - 2^1 
			 bit 0 - 2^0    Bursty Errored Seconds
		Octet 10 bit 7 - not used
			 bit 6 - future use
			 bit 5 - future use
			 bit 4 - future use
			 bit 3 - future use
			 bit 2 - future use
			 bit 1 - 2^15
			 bit 0 - 2^14
		Octet 11 bit 7 - not used
			 bit 6 - 2^13
			 bit 5 - 2^12
			 bit 4 - 2^11
			 bit 3 - 2^10
			 bit 2 - 2^9
			 bit 1 - 2^8
			 bit 0 - 2^7
		Octet 12 bit 7 - not used
			 bit 6 - 2^6 
			 bit 5 - 2^5 
			 bit 4 - 2^4 
			 bit 3 - 2^3 
			 bit 2 - 2^2 
			 bit 1 - 2^1 
			 bit 0 - 2^0    Unavailable Seconds
		Octet 13 bit 7 - not used
			 bit 6 - future use
			 bit 5 - future use
			 bit 4 - future use
			 bit 3 - future use
			 bit 2 - future use
			 bit 1 - future use
			 bit 0 - 2^7 
		Octet 14 bit 7 - not used
			 bit 6 - 2^6 
			 bit 5 - 2^5 
			 bit 4 - 2^4 
			 bit 3 - 2^3 
			 bit 2 - 2^2 
			 bit 1 - 2^1 
			 bit 0 - 2^0    Controlled Slip Seconds
		Octet 15 bit 7 - not used
			 bit 6 - future use
			 bit 5 - future use
			 bit 4 - future use
			 bit 3 - future use
			 bit 2 - future use
			 bit 1 - future use
			 bit 0 - 2^7 
		Octet 16 bit 7 - not used
			 bit 6 - 2^6 
			 bit 5 - 2^5 
			 bit 4 - 2^4 
			 bit 3 - 2^3 
			 bit 2 - 2^2 
			 bit 1 - 2^1 
			 bit 0 - 2^0    Loss of Frame Count"
	 ::= {mp7001IntervalEntry 3 }

--
-- ********************************************************************
-- ATT Total Performance Table
-- ********************************************************************

mp7001TotalTable 		OBJECT-TYPE
	 SYNTAX  SEQUENCE OF Mp7001TotalEntry
	 ACCESS  not-accessible
	 STATUS  mandatory
	 DESCRIPTION
		 "The DS1 Total table.  24 hour interval.
		 This table supplements the entries in the DS1 
		 AT&T performance table of the DS1
		 MIB defined in RFC1406."
	 ::= { mp7001Performance 5 }

mp7001TotalEntry 		OBJECT-TYPE
	 SYNTAX  Mp7001TotalEntry
	 ACCESS  not-accessible
	 STATUS  mandatory
	 DESCRIPTION
		 "An entry in the DS1 Total table."
	 INDEX   { mp7001TotalIndex }
	 ::= { mp7001TotalTable 1 }

Mp7001TotalEntry ::=
	 SEQUENCE {
		  mp7001TotalIndex
			 SCinstance,
		  mp7001TotalStat
			 OCTET STRING
	  }

mp7001TotalIndex 		OBJECT-TYPE
	 SYNTAX  SCinstance
	 ACCESS  read-only
	 STATUS  mandatory
	 DESCRIPTION
    	"Integer value which uniquely identifies the MP7001 to which this
    	entry is applicable. SCinstance is defined to be ssllddcc where:
    	ss (byte value) - physical shelf slot location (01-32)
    	ll (byte value) - line number (01-128)
    	dd (byte value) - drop number (00-31)
    	cc (byte value) - channel or interface number (always 00)"
	 ::= { mp7001TotalEntry 1 }

mp7001TotalStat 		OBJECT-TYPE
	SYNTAX OCTET STRING (SIZE(17))
	ACCESS read-only
	STATUS mandatory
	DESCRIPTION
		"Returns a bitwise snapshot of the total statistics.
		 Octet 1 bit 7 - not used
			 bit 6 - future use
			 bit 5 - future use
			 bit 4 - future use
			 bit 3 - future use
			 bit 2 - future use
			 bit 1 - future use
			 bit 0 - 1: New Interval
		 Octet 2 bit 7 - not used
			 bit 6 - future use
			 bit 5 - future use
			 bit 4 - future use
			 bit 3 - future use
			 bit 2 - future use
			 bit 1 - 2^15
			 bit 0 - 2^14
		 Octet 3 bit 7 - not used
			 bit 6 - 2^13
			 bit 5 - 2^12
			 bit 4 - 2^11
			 bit 3 - 2^10
			 bit 2 - 2^9
			 bit 1 - 2^8
			 bit 0 - 2^7
		 Octet 4 bit 7 - not used
			 bit 6 - 2^6 
			 bit 5 - 2^5 
			 bit 4 - 2^4 
			 bit 3 - 2^3 
			 bit 2 - 2^2 
			 bit 1 - 2^1 
			 bit 0 - 2^0    Errored Seconds
		 Octet 5 bit 7 - not used
			 bit 6 - future use
			 bit 5 - future use
			 bit 4 - future use
			 bit 3 - future use
			 bit 2 - future use
			 bit 1 - 2^15
			 bit 0 - 2^14
		 Octet 6 bit 7 - not used
			 bit 6 - 2^13
			 bit 5 - 2^12
			 bit 4 - 2^11
			 bit 3 - 2^10
			 bit 2 - 2^9
			 bit 1 - 2^8
			 bit 0 - 2^7
		 Octet 7 bit 7 - not used
			 bit 6 - 2^6 
			 bit 5 - 2^5 
			 bit 4 - 2^4 
			 bit 3 - 2^3 
			 bit 2 - 2^2 
			 bit 1 - 2^1 
			 bit 0 - 2^0    Severely Errored Seconds
		 Octet 8 bit 7 - not used
			 bit 6 - future use
			 bit 5 - future use
			 bit 4 - future use
			 bit 3 - future use
			 bit 2 - future use
			 bit 1 - 2^15
			 bit 0 - 2^14
		 Octet 9 bit 7 - not used
			 bit 6 - 2^13
			 bit 5 - 2^12
			 bit 4 - 2^11
			 bit 3 - 2^10
			 bit 2 - 2^9
			 bit 1 - 2^8
			 bit 0 - 2^7
		Octet 10 bit 7 - not used
			 bit 6 - 2^6 
			 bit 5 - 2^5 
			 bit 4 - 2^4 
			 bit 3 - 2^3 
			 bit 2 - 2^2 
			 bit 1 - 2^1 
			 bit 0 - 2^0    Bursty Errored Seconds
		Octet 11 bit 7 - not used
			 bit 6 - future use
			 bit 5 - future use
			 bit 4 - future use
			 bit 3 - future use
			 bit 2 - future use
			 bit 1 - 2^15
			 bit 0 - 2^14
		Octet 12 bit 7 - not used
			 bit 6 - 2^13
			 bit 5 - 2^12
			 bit 4 - 2^11
			 bit 3 - 2^10
			 bit 2 - 2^9
			 bit 1 - 2^8
			 bit 0 - 2^7
		Octet 13 bit 7 - not used
			 bit 6 - 2^6 
			 bit 5 - 2^5 
			 bit 4 - 2^4 
			 bit 3 - 2^3 
			 bit 2 - 2^2 
			 bit 1 - 2^1 
			 bit 0 - 2^0    Unavailable Seconds
		Octet 14 bit 7 - not used
			 bit 6 - future use
			 bit 5 - future use
			 bit 4 - future use
			 bit 3 - future use
			 bit 2 - future use
			 bit 1 - future use
			 bit 0 - 2^7 
		Octet 15 bit 7 - not used
			 bit 6 - 2^6 
			 bit 5 - 2^5 
			 bit 4 - 2^4 
			 bit 3 - 2^3 
			 bit 2 - 2^2 
			 bit 1 - 2^1 
			 bit 0 - 2^0    Controlled Slip Seconds
		Octet 16 bit 7 - not used
			 bit 6 - future use
			 bit 5 - future use
			 bit 4 - future use
			 bit 3 - future use
			 bit 2 - future use
			 bit 1 - future use
			 bit 0 - 2^7 
		Octet 17 bit 7 - not used
			 bit 6 - 2^6 
			 bit 5 - 2^5 
			 bit 4 - 2^4 
			 bit 3 - 2^3 
			 bit 2 - 2^2 
			 bit 1 - 2^1 
			 bit 0 - 2^0    Loss of Frame Count"
	 ::= {mp7001TotalEntry 2 }

-- ****************************************************************************
--                       mib definitions end
-- ****************************************************************************

END
