-- *****************************************************************************
-- Unisphere-Data-QoS-MIB
--
-- Unisphere Networks Enterprise MIB
--     Quality of Service (QoS) MIB
--
-- Copyright (c) 2002 Unisphere Networks, Inc.  All Rights Reserved.
-- *****************************************************************************

Unisphere-Data-QoS-MIB DEFINITIONS ::= BEGIN

IMPORTS
    MODULE-IDENTITY, OBJECT-TYPE, Gauge32, Counter64, Unsigned32
        FROM SNMPv2-SMI
    RowStatus, TruthValue, DisplayString
        FROM SNMPv2-TC
    ifIndex
        FROM IF-MIB
    MODULE-COMPLIANCE, OBJECT-GROUP
        FROM SNMPv2-CONF
    usDataMibs
        FROM Unisphere-Data-MIBs;

usdQosMIB  MODULE-IDENTITY
    LAST-UPDATED "200205101725Z"  -- 10-May-02 01:25 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Quality of Service (QoS) MIB for the Unisphere Networks
        enterprise."
    -- Revision History
    REVISION    "200205101725Z"  -- 10-May-02 01:25 PM EDT  - RX 4.0
    DESCRIPTION
        "Initial version of this MIB module."
    ::= { usDataMibs 57 }


-- +++++++++++++++++++++++++++++++++++++++++++++++++++++++++++++++++++++++++++++
-- Textual conventions
-- +++++++++++++++++++++++++++++++++++++++++++++++++++++++++++++++++++++++++++++


-- +++++++++++++++++++++++++++++++++++++++++++++++++++++++++++++++++++++++++++++
-- Managed objects
-- +++++++++++++++++++++++++++++++++++++++++++++++++++++++++++++++++++++++++++++
usdQosObjects                      OBJECT IDENTIFIER ::= { usdQosMIB 1 }
usdQosCapability                   OBJECT IDENTIFIER ::= { usdQosObjects 1 }
usdQos                             OBJECT IDENTIFIER ::= { usdQosObjects 2 }
usdQosTrafficClassList             OBJECT IDENTIFIER ::= { usdQosObjects 3 }
usdQosTrafficClassGroupList        OBJECT IDENTIFIER ::= { usdQosObjects 4 }
usdQosTrafficClassGroupEntryList   OBJECT IDENTIFIER ::= { usdQosObjects 5 }
usdQosSchedulerProfileList         OBJECT IDENTIFIER ::= { usdQosObjects 6 }
usdQosQueueProfileList             OBJECT IDENTIFIER ::= { usdQosObjects 7 }
usdQosProfile                      OBJECT IDENTIFIER ::= { usdQosObjects 8 }
usdQosProfileElement               OBJECT IDENTIFIER ::= { usdQosObjects 9 }
usdQosIfAttach                     OBJECT IDENTIFIER ::= { usdQosObjects 10 }
usdQosQosPortTypeProfile           OBJECT IDENTIFIER ::= { usdQosObjects 11 }
usdQosQueueStatistics              OBJECT IDENTIFIER ::= { usdQosObjects 12 }


-- +++++++++++++++++++++++++++++++++++++++++++++++++++++++++++++++++++++++++++++
-- QoS Capability Attributes
-- +++++++++++++++++++++++++++++++++++++++++++++++++++++++++++++++++++++++++++++
usdQosMaxTrafficClass OBJECT-TYPE
    SYNTAX      Unsigned32
    MAX-ACCESS  read-only
    STATUS      current
    DESCRIPTION
        "This object reflects the maximum number of traffic classes supported."
    ::= { usdQosCapability 1 }

usdQosMaxQueueLength OBJECT-TYPE
    SYNTAX      Unsigned32
    UNITS       "bytes"
    MAX-ACCESS  read-only
    STATUS      current
    DESCRIPTION
        "This object reflects the maximum supported queue length in bytes."
    ::= { usdQosCapability 2 }

usdQosMinSchedulerBurst OBJECT-TYPE
    SYNTAX      Unsigned32
    UNITS       "bytes"
    MAX-ACCESS  read-only
    STATUS      current
    DESCRIPTION
        "This object reflects the minimum supported scheduler burst size in
        bytes."
    ::= { usdQosCapability 3 }

usdQosMaxSchedulerBurst OBJECT-TYPE
    SYNTAX      Unsigned32
    UNITS       "bytes"
    MAX-ACCESS  read-only
    STATUS      current
    DESCRIPTION
        "This object reflects the maximum supported scheduler burst size in
        bytes."
    ::= { usdQosCapability 4 }


-- +++++++++++++++++++++++++++++++++++++++++++++++++++++++++++++++++++++++++++++
-- QoS Scalar Attributes
-- +++++++++++++++++++++++++++++++++++++++++++++++++++++++++++++++++++++++++++++

usdQosTrafficClassCount OBJECT-TYPE
    SYNTAX      Gauge32
    MAX-ACCESS  read-only
    STATUS      current
    DESCRIPTION
        "This object reflects the number of configured traffic classes."
    ::= { usdQos 1 }

usdQosQueueProfileCount OBJECT-TYPE
    SYNTAX      Gauge32
    MAX-ACCESS  read-only
    STATUS      current
    DESCRIPTION
        "This object reflects the number of configured queue profiles."
    ::= { usdQos 2 }

usdQosSchedulerProfileCount OBJECT-TYPE
    SYNTAX      Gauge32
    MAX-ACCESS  read-only
    STATUS      current
    DESCRIPTION
        "This object reflects the number of configured scheduler profiles."
    ::= { usdQos 3 }

usdQosProfileCount OBJECT-TYPE
    SYNTAX      Gauge32
    MAX-ACCESS  read-only
    STATUS      current
    DESCRIPTION
        "This object reflects the number of configured QoS profiles."
    ::= { usdQos 4 }

usdQosInterfaceCount OBJECT-TYPE
    SYNTAX      Gauge32
    MAX-ACCESS  read-only
    STATUS      current
    DESCRIPTION
        "This object reflects the number of configured interface QoS
        attachments."
    ::= { usdQos 5 }

usdQosQosPortTypeProfileCount OBJECT-TYPE
    SYNTAX      Gauge32
    MAX-ACCESS  read-only
    STATUS      current
    DESCRIPTION
        "This object reflects the number of configured default port profiles."
    ::= { usdQos 6 }


-- +++++++++++++++++++++++++++++++++++++++++++++++++++++++++++++++++++++++++++++
-- Traffic Class List
-- +++++++++++++++++++++++++++++++++++++++++++++++++++++++++++++++++++++++++++++
usdQosTrafficClassNextIndex OBJECT-TYPE
    SYNTAX      Unsigned32
    MAX-ACCESS  read-only
    STATUS      current
    DESCRIPTION
        "This scalar object returns the index of the next available row in the
        usdQosTrafficClassTable."
    ::= { usdQosTrafficClassList 1 }

usdQosTrafficClassTable OBJECT-TYPE
    SYNTAX      SEQUENCE OF UsdQosTrafficClassEntry
    MAX-ACCESS  not-accessible
    STATUS      current
    DESCRIPTION
        "This table contains entries for elements of Traffic Class definitions."
    ::= { usdQosTrafficClassList 2 }

usdQosTrafficClassEntry OBJECT-TYPE
    SYNTAX      UsdQosTrafficClassEntry
    MAX-ACCESS  not-accessible
    STATUS      current
    DESCRIPTION
        "Each entry describes the characteristics of a traffic class element."
    INDEX     { usdQosTrafficClassIndex }
    ::= { usdQosTrafficClassTable 1 }

UsdQosTrafficClassEntry ::= SEQUENCE {
    usdQosTrafficClassIndex                     Unsigned32,
    usdQosTrafficClassRowStatus                 RowStatus,
    usdQosTrafficClassName                      DisplayString,
    usdQosTrafficClassWeight                    Unsigned32,
    usdQosTrafficClassStrictPriority            TruthValue,
    usdQosTrafficClassUpdatePending             TruthValue,
    usdQosTrafficClassUpdateNow                 TruthValue,
    usdQosTrafficClassIsReferencedByGroup       TruthValue,
    usdQosTrafficClassIsReferencedByQosProfile  TruthValue }

usdQosTrafficClassIndex OBJECT-TYPE
    SYNTAX      Unsigned32
    MAX-ACCESS  not-accessible
    STATUS      current
    DESCRIPTION
        "The number of the traffic class entry which is defined by this row."
    ::= { usdQosTrafficClassEntry 1 }

usdQosTrafficClassRowStatus OBJECT-TYPE
    SYNTAX      RowStatus
    MAX-ACCESS  read-create
    STATUS      current
    DESCRIPTION
        "Controls creation/deletion of conceptual rows within this table.

        All rowStatus modes are supported.

        To create an entry in this table, the following entry objects MUST be
        explicitly configured:
             usdQosTrafficClassRowStatus
             usdQosTrafficClassName "
    ::= { usdQosTrafficClassEntry 2 }

usdQosTrafficClassName OBJECT-TYPE
    SYNTAX      DisplayString (SIZE(1..32))
    MAX-ACCESS  read-create
    STATUS      current
    DESCRIPTION
        "Specifies the name of the traffic class defined by this row."
    ::= { usdQosTrafficClassEntry 3 }

usdQosTrafficClassWeight OBJECT-TYPE
    SYNTAX      Unsigned32 (1..63)
    MAX-ACCESS  read-create
    STATUS      current
    DESCRIPTION
        "The relative weight for queues in this traffic class."
    DEFVAL    { 8 }
    ::= { usdQosTrafficClassEntry 4 }

usdQosTrafficClassStrictPriority OBJECT-TYPE
    SYNTAX      TruthValue
    MAX-ACCESS  read-create
    STATUS      current
    DESCRIPTION
        "The traffic to be dequeued before all other classes."
    DEFVAL    { false }
    ::= { usdQosTrafficClassEntry 5 }

usdQosTrafficClassUpdatePending OBJECT-TYPE
    SYNTAX      TruthValue
    MAX-ACCESS  read-only
    STATUS      current
    DESCRIPTION
        "True if modifications have been made to the traffic class object which
        have not been committed to the line cards."
    ::= { usdQosTrafficClassEntry 6  }

usdQosTrafficClassUpdateNow OBJECT-TYPE
    SYNTAX      TruthValue
    MAX-ACCESS  read-create
    STATUS      current
    DESCRIPTION
        "When set to true, modifications made to the traffic class object will
        be committed to the line cards."
    ::= { usdQosTrafficClassEntry 7 }

usdQosTrafficClassIsReferencedByGroup OBJECT-TYPE
    SYNTAX      TruthValue
    MAX-ACCESS  read-only
    STATUS      current
    DESCRIPTION
        "When true, the traffic class is referenced by a traffic class group."
    ::= { usdQosTrafficClassEntry 8 }

usdQosTrafficClassIsReferencedByQosProfile OBJECT-TYPE
    SYNTAX      TruthValue
    MAX-ACCESS  read-only
    STATUS      current
    DESCRIPTION
        "When true, the traffic class is referenced by a QoS profile."
    ::= { usdQosTrafficClassEntry 9 }


-- +++++++++++++++++++++++++++++++++++++++++++++++++++++++++++++++++++++++++++++
-- Traffic Class Group List
-- +++++++++++++++++++++++++++++++++++++++++++++++++++++++++++++++++++++++++++++
usdQosTrafficClassGroupNextIndex OBJECT-TYPE
    SYNTAX      Unsigned32
    MAX-ACCESS  read-only
    STATUS      current
    DESCRIPTION
        "This scalar object returns the index of the next available row in the
        usdQosTrafficClassGroupTable."
    ::= { usdQosTrafficClassGroupList 1 }

usdQosTrafficClassGroupTable OBJECT-TYPE
    SYNTAX      SEQUENCE OF UsdQosTrafficClassGroupEntry
    MAX-ACCESS  not-accessible
    STATUS      current
    DESCRIPTION
        "This table contains entries for elements of Traffic Class group
        definitions."
    ::= { usdQosTrafficClassGroupList 2 }

usdQosTrafficClassGroupEntry OBJECT-TYPE
    SYNTAX      UsdQosTrafficClassGroupEntry
    MAX-ACCESS  not-accessible
    STATUS      current
    DESCRIPTION
        "Each entry describes the characteristics of a traffic class group
        element."
    INDEX     { usdQosTrafficClassGroupIndex }
    ::= { usdQosTrafficClassGroupTable 1 }

UsdQosTrafficClassGroupEntry ::= SEQUENCE {
    usdQosTrafficClassGroupIndex                    Unsigned32,
    usdQosTrafficClassGroupRowStatus                RowStatus,
    usdQosTrafficClassGroupName                     DisplayString,
    usdQosTrafficClassGroupUpdatePending            TruthValue,
    usdQosTrafficClassGroupUpdateNow                TruthValue,
    usdQosTrafficClassGroupIsReferencedByQosProfile TruthValue }

usdQosTrafficClassGroupIndex OBJECT-TYPE
    SYNTAX      Unsigned32
    MAX-ACCESS  not-accessible
    STATUS      current
    DESCRIPTION
        "The number of the traffic class entry which is defined by this row."
    ::= { usdQosTrafficClassGroupEntry 1 }

usdQosTrafficClassGroupRowStatus OBJECT-TYPE
    SYNTAX      RowStatus
    MAX-ACCESS  read-create
    STATUS      current
    DESCRIPTION
        "Controls creation/deletion of conceptual rows within this table.

        All rowStatus modes are supported.

        To create an entry in this table, the following entry objects MUST be
        explicitly configured:
             usdQosTrafficClassGroupRowStatus
             usdQosTrafficClassGroupName "
    ::= { usdQosTrafficClassGroupEntry 2 }

usdQosTrafficClassGroupName OBJECT-TYPE
    SYNTAX      DisplayString (SIZE(1..32))
    MAX-ACCESS  read-create
    STATUS      current
    DESCRIPTION
        "Specifies the name of the traffic class group defined by this row."
    ::= { usdQosTrafficClassGroupEntry 3 }

usdQosTrafficClassGroupUpdatePending OBJECT-TYPE
    SYNTAX      TruthValue
    MAX-ACCESS  read-only
    STATUS      current
    DESCRIPTION
        "True if modifications have been made to the traffic class group object
        which have not been committed to the line cards."
    ::= { usdQosTrafficClassGroupEntry 4  }

usdQosTrafficClassGroupUpdateNow OBJECT-TYPE
    SYNTAX      TruthValue
    MAX-ACCESS  read-create
    STATUS      current
    DESCRIPTION
        "When set to true, modifications made to the traffic class group object
        will be committed to the line cards."
    ::= { usdQosTrafficClassGroupEntry 5 }

usdQosTrafficClassGroupIsReferencedByQosProfile OBJECT-TYPE
    SYNTAX      TruthValue
    MAX-ACCESS  read-only
    STATUS      current
    DESCRIPTION
        "When true, the traffic class group is referenced by a QoS profile."
    ::= { usdQosTrafficClassGroupEntry 6 }


-- +++++++++++++++++++++++++++++++++++++++++++++++++++++++++++++++++++++++++++++
-- Traffic Class Group Entry List
-- +++++++++++++++++++++++++++++++++++++++++++++++++++++++++++++++++++++++++++++
usdQosTrafficClassGroupEntryTable OBJECT-TYPE
    SYNTAX      SEQUENCE OF UsdQosTrafficClassGroupEntryEntry
    MAX-ACCESS  not-accessible
    STATUS      current
    DESCRIPTION
        "This table identifies which traffic classes are in each traffic class
        group."
    ::= { usdQosTrafficClassGroupEntryList 1 }

usdQosTrafficClassGroupEntryEntry OBJECT-TYPE
    SYNTAX      UsdQosTrafficClassGroupEntryEntry
    MAX-ACCESS  not-accessible
    STATUS      current
    DESCRIPTION
        "Each entry ties a traffic class table entry to a traffic class group."
    INDEX     { usdQosTrafficClassGroupIndex,
                usdQosTrafficClassIndex }
    ::= { usdQosTrafficClassGroupEntryTable 1 }

UsdQosTrafficClassGroupEntryEntry ::= SEQUENCE {
    usdQosTrafficClassGroupEntryRowStatus   RowStatus }

usdQosTrafficClassGroupEntryRowStatus OBJECT-TYPE
    SYNTAX      RowStatus
    MAX-ACCESS  read-create
    STATUS      current
    DESCRIPTION
        "Controls creation/deletion of conceptual rows within this table.

        All rowStatus modes are supported.

        To create an entry in this table, the following entry object MUST be
        explicitly configured:
             usdQosTrafficClassGroupEntryRowStatus "
    ::= { usdQosTrafficClassGroupEntryEntry 1 }


-- +++++++++++++++++++++++++++++++++++++++++++++++++++++++++++++++++++++++++++++
-- Queue Profile List
-- +++++++++++++++++++++++++++++++++++++++++++++++++++++++++++++++++++++++++++++
usdQosQueueProfileNextIndex OBJECT-TYPE
    SYNTAX      Unsigned32
    MAX-ACCESS  read-only
    STATUS      current
    DESCRIPTION
        "This scalar object returns the index of the next available row in the
        usdQosQueueProfileTable."
    ::= { usdQosQueueProfileList 1 }

usdQosQueueProfileTable OBJECT-TYPE
    SYNTAX      SEQUENCE OF UsdQosQueueProfileEntry
    MAX-ACCESS  not-accessible
    STATUS      current
    DESCRIPTION
        "This table contains entries for elements of queue profile definitions."
    ::= { usdQosQueueProfileList 2 }

usdQosQueueProfileEntry OBJECT-TYPE
    SYNTAX      UsdQosQueueProfileEntry
    MAX-ACCESS  not-accessible
    STATUS      current
    DESCRIPTION
        "Each entry describes the characteristics of a queue profile element."
    INDEX     { usdQosQueueProfileIndex }
    ::= { usdQosQueueProfileTable 1 }

UsdQosQueueProfileEntry ::= SEQUENCE {
    usdQosQueueProfileIndex                     Unsigned32,
    usdQosQueueProfileRowStatus                 RowStatus,
    usdQosQueueProfileName                      DisplayString,
    usdQosQueueProfileCommittedMinLength        Unsigned32,
    usdQosQueueProfileCommittedMaxLength        Unsigned32,
    usdQosQueueProfileConformedMinLength        Unsigned32,
    usdQosQueueProfileConformedMaxLength        Unsigned32,
    usdQosQueueProfileExceededMinLength         Unsigned32,
    usdQosQueueProfileExceededMaxLength         Unsigned32,
    usdQosQueueProfileConformedFraction         Unsigned32,
    usdQosQueueProfileExceededFraction          Unsigned32,
    usdQosQueueProfileCommittedDropThreshold    Unsigned32,
    usdQosQueueProfileCommittedDropRate         Unsigned32,
    usdQosQueueProfileConformedDropThreshold    Unsigned32,
    usdQosQueueProfileConformedDropRate         Unsigned32,
    usdQosQueueProfileExceededDropThreshold     Unsigned32,
    usdQosQueueProfileExceededDropRate          Unsigned32,
    usdQosQueueProfileBufferWeight              Unsigned32,
    usdQosQueueProfileUpdatePending             TruthValue,
    usdQosQueueProfileUpdateNow                 TruthValue,
    usdQosQueueProfileIsReferencedByQosProfile  TruthValue }

usdQosQueueProfileIndex OBJECT-TYPE
    SYNTAX      Unsigned32
    MAX-ACCESS  not-accessible
    STATUS      current
    DESCRIPTION
        "The number of the queue profile entry which is defined by this row."
    ::= { usdQosQueueProfileEntry 1 }

usdQosQueueProfileRowStatus OBJECT-TYPE
    SYNTAX      RowStatus
    MAX-ACCESS  read-create
    STATUS      current
    DESCRIPTION
        "Controls creation/deletion of conceptual rows within this table.

        All rowStatus modes are supported.

        To create an entry in this table, the following entry objects MUST be
        explicitly configured:
             usdQosQueueProfileRowStatus
             usdQosQueueProfileName "
    ::= { usdQosQueueProfileEntry 2 }

usdQosQueueProfileName OBJECT-TYPE
    SYNTAX      DisplayString (SIZE(1..32))
    MAX-ACCESS  read-create
    STATUS      current
    DESCRIPTION
        "Specifies the name of the queue profile defined by this row."
    ::= { usdQosQueueProfileEntry 3 }

usdQosQueueProfileCommittedMinLength OBJECT-TYPE
    SYNTAX      Unsigned32
    UNITS       "bytes"
    MAX-ACCESS  read-create
    STATUS      current
    DESCRIPTION
        "Specifies the minimum queue length in bytes for committed traffic."
    DEFVAL    { 0 }
    ::= { usdQosQueueProfileEntry 4 }

usdQosQueueProfileCommittedMaxLength OBJECT-TYPE
    SYNTAX      Unsigned32
    UNITS       "bytes"
    MAX-ACCESS  read-create
    STATUS      current
    DESCRIPTION
        "Specifies the maximum queue length in bytes for committed traffic."
    DEFVAL    { 1073741824 }
    ::= { usdQosQueueProfileEntry 5 }

usdQosQueueProfileConformedMinLength OBJECT-TYPE
    SYNTAX      Unsigned32
    UNITS       "bytes"
    MAX-ACCESS  read-create
    STATUS      current
    DESCRIPTION
        "Specifies the minimum queue length in bytes for conformed traffic."
    DEFVAL    { 0 }
    ::= { usdQosQueueProfileEntry 6 }

usdQosQueueProfileConformedMaxLength OBJECT-TYPE
    SYNTAX      Unsigned32
    UNITS       "bytes"
    MAX-ACCESS  read-create
    STATUS      current
    DESCRIPTION
        "Specifies the maximum queue length in bytes for conformed traffic."
    DEFVAL    { 1073741824 }
    ::= { usdQosQueueProfileEntry 7 }

usdQosQueueProfileExceededMinLength OBJECT-TYPE
    SYNTAX      Unsigned32
    UNITS       "bytes"
    MAX-ACCESS  read-create
    STATUS      current
    DESCRIPTION
        "Specifies the minimum queue length in bytes for exceeded traffic."
    DEFVAL    { 0 }
    ::= { usdQosQueueProfileEntry 8 }

usdQosQueueProfileExceededMaxLength OBJECT-TYPE
    SYNTAX      Unsigned32
    UNITS       "bytes"
    MAX-ACCESS  read-create
    STATUS      current
    DESCRIPTION
        "Specifies the maximum queue length in bytes for exceeded traffic."
    DEFVAL    { 1073741824 }
    ::= { usdQosQueueProfileEntry 9 }

usdQosQueueProfileConformedFraction OBJECT-TYPE
    SYNTAX      Unsigned32 (0..100)
    UNITS       "percent"
    MAX-ACCESS  read-create
    STATUS      current
    DESCRIPTION
        "Specifies the maximum percentage of queue occupied by conformed
        traffic."
    DEFVAL    { 50 }
    ::= { usdQosQueueProfileEntry 10 }

usdQosQueueProfileExceededFraction OBJECT-TYPE
    SYNTAX      Unsigned32 (0..100)
    UNITS       "percent"
    MAX-ACCESS  read-create
    STATUS      current
    DESCRIPTION
        "Specifies the maximum percentage of queue occupied by exceeded
        traffic."
    DEFVAL    { 25 }
    ::= { usdQosQueueProfileEntry 11 }

usdQosQueueProfileCommittedDropThreshold OBJECT-TYPE
    SYNTAX      Unsigned32 (0..100)
    UNITS       "percent"
    MAX-ACCESS  read-create
    STATUS      current
    DESCRIPTION
        "Specifies the drop threshold (percent of queue) for committed traffic."
    DEFVAL    { 100 }
    ::= { usdQosQueueProfileEntry 12 }

usdQosQueueProfileCommittedDropRate OBJECT-TYPE
    SYNTAX      Unsigned32 (0..100)
    UNITS       "percent"
    MAX-ACCESS  read-create
    STATUS      current
    DESCRIPTION
        "Specifies the drop rate (percent of traffic) for committed traffic."
    DEFVAL    { 0 }
    ::= { usdQosQueueProfileEntry 13 }

usdQosQueueProfileConformedDropThreshold OBJECT-TYPE
    SYNTAX      Unsigned32 (0..100)
    UNITS       "percent"
    MAX-ACCESS  read-create
    STATUS      current
    DESCRIPTION
        "Specifies the drop threshold (percent of queue) for comformed traffic."
    DEFVAL    { 0 }
    ::= { usdQosQueueProfileEntry 14 }

usdQosQueueProfileConformedDropRate OBJECT-TYPE
    SYNTAX      Unsigned32 (0..100)
    UNITS       "percent"
    MAX-ACCESS  read-create
    STATUS      current
    DESCRIPTION
        "Specifies the drop rate (percent of traffic) for comformed traffic."
    DEFVAL    { 0 }
    ::= { usdQosQueueProfileEntry 15 }

usdQosQueueProfileExceededDropThreshold OBJECT-TYPE
    SYNTAX      Unsigned32 (0..100)
    UNITS       "percent"
    MAX-ACCESS  read-create
    STATUS      current
    DESCRIPTION
        "Specifies the drop threshold (percent of queue) for exceeded traffic."
    DEFVAL    { 0 }
    ::= { usdQosQueueProfileEntry 16 }

usdQosQueueProfileExceededDropRate OBJECT-TYPE
    SYNTAX      Unsigned32 (0..100)
    UNITS       "percent"
    MAX-ACCESS  read-create
    STATUS      current
    DESCRIPTION
        "Specifies the drop rate (percent of traffic) for exceeded traffic."
    DEFVAL    { 0 }
    ::= { usdQosQueueProfileEntry 17 }

usdQosQueueProfileBufferWeight OBJECT-TYPE
    SYNTAX      Unsigned32 (1..63)
    MAX-ACCESS  read-create
    STATUS      current
    DESCRIPTION
        "The relative weight for queues in this traffic class."
    DEFVAL    { 8 }
    ::= { usdQosQueueProfileEntry 18 }

usdQosQueueProfileUpdatePending OBJECT-TYPE
    SYNTAX      TruthValue
    MAX-ACCESS  read-only
    STATUS      current
    DESCRIPTION
        "True if modifications have been made to the queue profile object which
        have not been committed to the line cards."
    ::= { usdQosQueueProfileEntry 19  }

usdQosQueueProfileUpdateNow OBJECT-TYPE
    SYNTAX      TruthValue
    MAX-ACCESS  read-create
    STATUS      current
    DESCRIPTION
        "When set to true, modifications made to the queue profile object will
        be committed to the line cards."
    ::= { usdQosQueueProfileEntry 20 }

usdQosQueueProfileIsReferencedByQosProfile OBJECT-TYPE
    SYNTAX      TruthValue
    MAX-ACCESS  read-only
    STATUS      current
    DESCRIPTION
        "When true, the queue profile is referenced by a QoS profile."
    ::= { usdQosQueueProfileEntry 21 }


-- +++++++++++++++++++++++++++++++++++++++++++++++++++++++++++++++++++++++++++++
-- Scheduler Profile List
-- +++++++++++++++++++++++++++++++++++++++++++++++++++++++++++++++++++++++++++++
usdQosSchedulerProfileNextIndex OBJECT-TYPE
    SYNTAX      Unsigned32
    MAX-ACCESS  read-only
    STATUS      current
    DESCRIPTION
        "This scalar object returns the index of the next available row in the
        usdQosSchedulerProfileTable."
    ::= { usdQosSchedulerProfileList 1 }

usdQosSchedulerProfileTable OBJECT-TYPE
    SYNTAX      SEQUENCE OF UsdQosSchedulerProfileEntry
    MAX-ACCESS  not-accessible
    STATUS      current
    DESCRIPTION
        "This table contains entries for elements of Scheduler Profile
        definitions."
    ::= { usdQosSchedulerProfileList 2 }

usdQosSchedulerProfileEntry OBJECT-TYPE
    SYNTAX      UsdQosSchedulerProfileEntry
    MAX-ACCESS  not-accessible
    STATUS      current
    DESCRIPTION
        "Each entry describes the characteristics of a scheduler profile
        element."
    INDEX     { usdQosSchedulerProfileIndex }
    ::= { usdQosSchedulerProfileTable 1 }

UsdQosSchedulerProfileEntry ::= SEQUENCE {
    usdQosSchedulerProfileIndex                     Unsigned32,
    usdQosSchedulerProfileRowStatus                 RowStatus,
    usdQosSchedulerProfileName                      DisplayString,
    usdQosSchedulerProfileShapingRate               Unsigned32,
    usdQosSchedulerProfileBurst                     Unsigned32,
    usdQosSchedulerProfileWeight                    Unsigned32,
    usdQosSchedulerProfileStrictPriority            TruthValue,
    usdQosSchedulerProfileUpdatePending             TruthValue,
    usdQosSchedulerProfileUpdateNow                 TruthValue,
    usdQosSchedulerProfileIsReferencedByQosProfile  TruthValue }

usdQosSchedulerProfileIndex OBJECT-TYPE
    SYNTAX      Unsigned32
    MAX-ACCESS  not-accessible
    STATUS      current
    DESCRIPTION
        "The number of the scheduler profile entry which is defined by this
        row."
    ::= { usdQosSchedulerProfileEntry 1 }

usdQosSchedulerProfileRowStatus OBJECT-TYPE
    SYNTAX      RowStatus
    MAX-ACCESS  read-create
    STATUS      current
    DESCRIPTION
        "Controls creation/deletion of conceptual rows within this table.

        All rowStatus modes are supported.

        To create an entry in this table, the following entry objects MUST be
        explicitly configured:
             usdQosSchedulerProfileRowStatus
             usdQosSchedulerProfileName "
    ::= { usdQosSchedulerProfileEntry 2 }

usdQosSchedulerProfileName OBJECT-TYPE
    SYNTAX      DisplayString (SIZE(1..32))
    MAX-ACCESS  read-create
    STATUS      current
    DESCRIPTION
        "Specifies the name of the scheduler profile defined by this row."
    ::= { usdQosSchedulerProfileEntry 3 }

usdQosSchedulerProfileShapingRate OBJECT-TYPE
    SYNTAX      Unsigned32
    UNITS       "kbps"
    MAX-ACCESS  read-create
    STATUS      current
    DESCRIPTION
        "Specifies the shaping rate in kilobits/second (kbps)."
    DEFVAL    { 0 }
    ::= { usdQosSchedulerProfileEntry 4 }

usdQosSchedulerProfileBurst OBJECT-TYPE
    SYNTAX      Unsigned32
    UNITS       "bytes"
    MAX-ACCESS  read-create
    STATUS      current
    DESCRIPTION
        "Specifies the catch-up burst size in bytes."
    DEFVAL    { 32768 }
    ::= { usdQosSchedulerProfileEntry 5 }

usdQosSchedulerProfileWeight OBJECT-TYPE
    SYNTAX      Unsigned32 (1..127)
    MAX-ACCESS  read-create
    STATUS      current
    DESCRIPTION
        "The relative weight of the scheduler."
    DEFVAL    { 8 }
    ::= { usdQosSchedulerProfileEntry 6 }

usdQosSchedulerProfileStrictPriority OBJECT-TYPE
    SYNTAX      TruthValue
    MAX-ACCESS  read-create
    STATUS      current
    DESCRIPTION
        "Specifies the traffic to be dequeued before all other scheduler nodes."
    DEFVAL    { false }
    ::= { usdQosSchedulerProfileEntry 7 }

usdQosSchedulerProfileUpdatePending OBJECT-TYPE
    SYNTAX      TruthValue
    MAX-ACCESS  read-only
    STATUS      current
    DESCRIPTION
        "True if modifications have been made to the scheduler profile object
        which have not been committed to the line cards."
    ::= { usdQosSchedulerProfileEntry 8  }

usdQosSchedulerProfileUpdateNow OBJECT-TYPE
    SYNTAX      TruthValue
    MAX-ACCESS  read-create
    STATUS      current
    DESCRIPTION
        "When set to true, modifications made to the scheduler profile object
        will be committed to the line cards."
    ::= { usdQosSchedulerProfileEntry 9 }

usdQosSchedulerProfileIsReferencedByQosProfile OBJECT-TYPE
    SYNTAX      TruthValue
    MAX-ACCESS  read-only
    STATUS      current
    DESCRIPTION
        "When true, the scheduler profile is referenced by a QoS profile."
    ::= { usdQosSchedulerProfileEntry 10 }


-- +++++++++++++++++++++++++++++++++++++++++++++++++++++++++++++++++++++++++++++
-- QoS Profile Table
-- +++++++++++++++++++++++++++++++++++++++++++++++++++++++++++++++++++++++++++++
usdQosProfileNextIndex OBJECT-TYPE
    SYNTAX      Unsigned32
    MAX-ACCESS  read-only
    STATUS      current
    DESCRIPTION
        "This scalar object returns the index of the next available row in the
        usdQosProfileTable."
    ::= { usdQosProfile 1 }

usdQosProfileTable OBJECT-TYPE
    SYNTAX      SEQUENCE OF UsdQosProfileEntry
    MAX-ACCESS  not-accessible
    STATUS      current
    DESCRIPTION
        "This table contains entries for elements of QoS Profile definitions."
    ::= { usdQosProfile 2 }

usdQosProfileEntry OBJECT-TYPE
    SYNTAX      UsdQosProfileEntry
    MAX-ACCESS  not-accessible
    STATUS      current
    DESCRIPTION
        "Each entry describes the characteristics of a QoS profile element."
    INDEX     { usdQosProfileIndex }
    ::= { usdQosProfileTable 1 }

UsdQosProfileEntry ::= SEQUENCE {
    usdQosProfileIndex                                  Unsigned32,
    usdQosProfileRowStatus                              RowStatus,
    usdQosProfileName                                   DisplayString,
    usdQosProfileUpdatePending                          TruthValue,
    usdQosProfileUpdateNow                              TruthValue,
    usdQosProfileIsReferencedByInterfaceQosAttachment   TruthValue,
    usdQosProfileIsReferencedByQosPortTypeProfile       TruthValue }

usdQosProfileIndex OBJECT-TYPE
    SYNTAX      Unsigned32
    MAX-ACCESS  not-accessible
    STATUS      current
    DESCRIPTION
        "The number identifies this QoS profile."
    ::= { usdQosProfileEntry 1 }

usdQosProfileRowStatus OBJECT-TYPE
    SYNTAX      RowStatus
    MAX-ACCESS  read-create
    STATUS      current
    DESCRIPTION
        "Controls creation/deletion of conceptual rows within this table.

        All rowStatus modes are supported.

        To create a QoS profile in this table, the following entry objects MUST
        be explicitly configured:
             usdQosProfileRowStatus
             usdQosProfileName "
    ::= { usdQosProfileEntry 2 }

usdQosProfileName OBJECT-TYPE
    SYNTAX      DisplayString (SIZE(1..32))
    MAX-ACCESS  read-create
    STATUS      current
    DESCRIPTION
        "Specifies the name of the QoS profile defined by this row."
    ::= { usdQosProfileEntry 3 }

usdQosProfileUpdatePending OBJECT-TYPE
    SYNTAX      TruthValue
    MAX-ACCESS  read-only
    STATUS      current
    DESCRIPTION
        "True if modifications have been made to the qos profile object which
        have not been committed to the line cards."
    ::= { usdQosProfileEntry 4  }

usdQosProfileUpdateNow OBJECT-TYPE
    SYNTAX      TruthValue
    MAX-ACCESS  read-create
    STATUS      current
    DESCRIPTION
        "When set to true, modifications made to the qos profile object will be
        committed to the line cards."
    ::= { usdQosProfileEntry 5 }

usdQosProfileIsReferencedByInterfaceQosAttachment OBJECT-TYPE
    SYNTAX      TruthValue
    MAX-ACCESS  read-only
    STATUS      current
    DESCRIPTION
        "When true, the QoS profile is referenced by an interface QoS
        attachment."
    ::= { usdQosProfileEntry 6 }

usdQosProfileIsReferencedByQosPortTypeProfile OBJECT-TYPE
    SYNTAX      TruthValue
    MAX-ACCESS  read-only
    STATUS      current
    DESCRIPTION
        "When true, the QoS profile is referenced by a QoS port type profile."
    ::= { usdQosProfileEntry 7 }


-- +++++++++++++++++++++++++++++++++++++++++++++++++++++++++++++++++++++++++++++
-- QoS Profile Element Table
-- +++++++++++++++++++++++++++++++++++++++++++++++++++++++++++++++++++++++++++++
usdQosProfileElementTable OBJECT-TYPE
    SYNTAX      SEQUENCE OF UsdQosProfileElementEntry
    MAX-ACCESS  not-accessible
    STATUS      current
    DESCRIPTION
        "This table contains entries for elements of QoS profile definitions."
    ::= { usdQosProfileElement 1 }

usdQosProfileElementEntry OBJECT-TYPE
    SYNTAX      UsdQosProfileElementEntry
    MAX-ACCESS  not-accessible
    STATUS      current
    DESCRIPTION
        "Each entry describes the characteristics of a QoS profile element."
    INDEX     { usdQosProfileIndex,
                usdQosInterfaceType,
                usdQosProfileEntryType,
                usdQosTrafficClassIndex,
                usdQosTrafficClassGroupIndex }
    ::= { usdQosProfileElementTable 1 }

UsdQosProfileElementEntry ::= SEQUENCE {
    usdQosProfileElementEntryRowStatus          RowStatus,
    usdQosProfileElementEntryQueueProfile       Unsigned32,
    usdQosProfileElementEntrySchedulerProfile   Unsigned32,
    usdQosInterfaceType                         INTEGER,
    usdQosProfileEntryType                      INTEGER }

usdQosProfileElementEntryRowStatus OBJECT-TYPE
    SYNTAX      RowStatus
    MAX-ACCESS  read-create
    STATUS      current
    DESCRIPTION
        "Controls creation/deletion of conceptual rows within this table.

        All rowStatus modes are supported.

        To create an entry in this table, the following entry object MUST be
        explicitly configured:
             usdQosProfileRowStatus "
    ::= { usdQosProfileElementEntry 1 }

usdQosProfileElementEntryQueueProfile OBJECT-TYPE
    SYNTAX      Unsigned32
    MAX-ACCESS  read-create
    STATUS      current
    DESCRIPTION
        "Specifies the queue profile assigned to the QoS entry."
    ::= { usdQosProfileElementEntry 2 }

usdQosProfileElementEntrySchedulerProfile OBJECT-TYPE
    SYNTAX      Unsigned32
    MAX-ACCESS  read-create
    STATUS      current
    DESCRIPTION
        "Specifies the scheduler profile assigned to the QoS entry."
    ::= { usdQosProfileElementEntry 3 }

usdQosInterfaceType OBJECT-TYPE
    SYNTAX      INTEGER {
                    ip(0),
                    ethernet(6),
                    atm(9),
                    atmVc(11),
                    serial(13),
                    frVc(16),
                    serverPort(31),
                    vlan(35),
                    cbf(36),
                    l2tpTunnel(150),
                    ipTunnel(151) }
    MAX-ACCESS  not-accessible
    STATUS      current
    DESCRIPTION
        "The QoS interface type ID, part of the index for
        usdQosProfileElementTable."
    ::= { usdQosProfileElementEntry 4 }

usdQosProfileEntryType OBJECT-TYPE
    SYNTAX      INTEGER {
                    trafficClass(1),
                    schedulerProfile(2),
                    trafficClassGroup(3) }
    MAX-ACCESS  not-accessible
    STATUS      current
    DESCRIPTION
        "The QoS profile type, part of the index for usdQosProfileElementTable."
    ::= { usdQosProfileElementEntry 5 }


-- +++++++++++++++++++++++++++++++++++++++++++++++++++++++++++++++++++++++++++++
-- QoS Interface Attached Table
-- +++++++++++++++++++++++++++++++++++++++++++++++++++++++++++++++++++++++++++++
usdQosIfAttachTable OBJECT-TYPE
    SYNTAX      SEQUENCE OF UsdQosIfAttachEntry
    MAX-ACCESS  not-accessible
    STATUS      current
    DESCRIPTION
        "This table contains entries which represent attachment of QoS to
        interfaces."
    ::= { usdQosIfAttach 1 }

usdQosIfAttachEntry OBJECT-TYPE
    SYNTAX      UsdQosIfAttachEntry
    MAX-ACCESS  not-accessible
    STATUS      current
    DESCRIPTION
        "Each entry contains the attachment of QoS to an interface."
    INDEX     { usdQosIfAttachIndex }
    ::= { usdQosIfAttachTable 1 }

UsdQosIfAttachEntry ::= SEQUENCE {
    usdQosIfAttachIndex             Unsigned32,
    usdQosIfAttachRowStatus         RowStatus,
    usdQosIfAttachQosProfileIndex   Unsigned32 }

usdQosIfAttachIndex OBJECT-TYPE
    SYNTAX      Unsigned32
    MAX-ACCESS  not-accessible
    STATUS      current
    DESCRIPTION
        "The interface number representing the interface to which QoS has been
        attached."
    ::= { usdQosIfAttachEntry 1 }

usdQosIfAttachRowStatus OBJECT-TYPE
    SYNTAX      RowStatus
    MAX-ACCESS  read-create
    STATUS      current
    DESCRIPTION
        "Controls creation/deletion of entries in this table according to the
        RowStatus textual convention, constrained to support the following
        values only:
            createAndGo
            destroy

        *** LIMITED ACCESS LIST CONFIGURATION LEVEL ***
        RowStatus createAndGo/destroy operations have the following
        special-purpose semantics:
            createAndGo     Create an entry having the specified configuration
                            and append it to the target list.
            destroy         Destroy the specified list and all of its
                            constituent elements. "
    ::= { usdQosIfAttachEntry 2 }

usdQosIfAttachQosProfileIndex OBJECT-TYPE
    SYNTAX      Unsigned32
    MAX-ACCESS  read-create
    STATUS      current
    DESCRIPTION
        "The QoS profile attached to this interface."
    ::= { usdQosIfAttachEntry 3 }


-- +++++++++++++++++++++++++++++++++++++++++++++++++++++++++++++++++++++++++++++
-- QoS Port Type Profile Table
-- +++++++++++++++++++++++++++++++++++++++++++++++++++++++++++++++++++++++++++++
usdQosQosPortTypeProfileTable OBJECT-TYPE
    SYNTAX      SEQUENCE OF UsdQosQosPortTypeProfileEntry
    MAX-ACCESS  not-accessible
    STATUS      current
    DESCRIPTION
        "This table contains entries which represent attachment of QoS to
        interface types with which they are associated."
    ::= { usdQosQosPortTypeProfile 1 }

usdQosQosPortTypeProfileEntry OBJECT-TYPE
    SYNTAX      UsdQosQosPortTypeProfileEntry
    MAX-ACCESS  not-accessible
    STATUS      current
    DESCRIPTION
        "Each entry contains the attachment of QoS to an interface."
    INDEX     { usdQosQosPortTypeProfileIndex }
    ::= { usdQosQosPortTypeProfileTable 1 }

UsdQosQosPortTypeProfileEntry ::= SEQUENCE {
    usdQosQosPortTypeProfileIndex           INTEGER,
    usdQosQosPortTypeProfileRowStatus       RowStatus,
    usdQosQosPortTypeProfileQosProfileIndex Unsigned32 }

usdQosQosPortTypeProfileIndex OBJECT-TYPE
    SYNTAX      INTEGER {
                    ethernet(6),
                    atm(9),
                    serial(13),
                    serverPort(31) }
    MAX-ACCESS  not-accessible
    STATUS      current
    DESCRIPTION
        "The interface number representing the types of interface to which QoS
        has been attached."
    ::= { usdQosQosPortTypeProfileEntry 1 }

usdQosQosPortTypeProfileRowStatus OBJECT-TYPE
    SYNTAX      RowStatus
    MAX-ACCESS  read-create
    STATUS      current
    DESCRIPTION
        "Controls creation/deletion of entries in this table according to the
        RowStatus textual convention, constrained to support the following
        values only:
            createAndGo
            destroy

        *** LIMITED ACCESS LIST CONFIGURATION LEVEL ***
        RowStatus createAndGo/destroy operations have the following
        special-purpose semantics:
            createAndGo     Create an entry having the specified configuration
                            and append it to the target list.

            destroy         Destroy the specified list and all of its
                            constituent elements. "
     ::= { usdQosQosPortTypeProfileEntry 2 }

usdQosQosPortTypeProfileQosProfileIndex OBJECT-TYPE
    SYNTAX      Unsigned32
    MAX-ACCESS  read-create
    STATUS      current
    DESCRIPTION
        "The QoS profile assigned to this port type."
    ::= { usdQosQosPortTypeProfileEntry 3 }


-- +++++++++++++++++++++++++++++++++++++++++++++++++++++++++++++++++++++++++++++
-- QoS Queue Statistics
-- +++++++++++++++++++++++++++++++++++++++++++++++++++++++++++++++++++++++++++++
usdQosQueueStatisticsTable OBJECT-TYPE
    SYNTAX      SEQUENCE OF UsdQosQueueStatisticsEntry
    MAX-ACCESS  not-accessible
    STATUS      current
    DESCRIPTION
        "Each entry within this table contains queue statistics for an
        interface/traffic class combination."
    ::= { usdQosQueueStatistics 1 }

usdQosQueueStatisticsEntry OBJECT-TYPE
    SYNTAX      UsdQosQueueStatisticsEntry
    MAX-ACCESS  not-accessible
    STATUS      current
    DESCRIPTION
        "Each entry defines a single queue statistics entry."
    INDEX     { ifIndex,
                usdQosTrafficClassIndex }
    ::= { usdQosQueueStatisticsTable 1 }

UsdQosQueueStatisticsEntry ::= SEQUENCE {
    usdQosOutPacketForwarded                Counter64,
    usdQosOutBytesForwarded                 Counter64,
    usdQosOutGreenPacketsSchedulerDrops     Counter64,
    usdQosOutYellowPacketsSchedulerDrops    Counter64,
    usdQosOutRedPacketsSchedulerDrops       Counter64,
    usdQosOutGreenBytesSchedulerDrops       Counter64,
    usdQosOutYellowBytesSchedulerDrops      Counter64,
    usdQosOutRedBytesSchedulerDrops         Counter64 }

usdQosOutPacketForwarded OBJECT-TYPE
    SYNTAX      Counter64
    UNITS       "packets"
    MAX-ACCESS  read-only
    STATUS      current
    DESCRIPTION
        "The number of packets queued on this interface."
    ::= { usdQosQueueStatisticsEntry 1 }

usdQosOutBytesForwarded OBJECT-TYPE
    SYNTAX      Counter64
    UNITS       "bytes"
    MAX-ACCESS  read-only
    STATUS      current
    DESCRIPTION
        "The number of bytes queued on this interface."
    ::= { usdQosQueueStatisticsEntry 2 }

usdQosOutGreenPacketsSchedulerDrops OBJECT-TYPE
    SYNTAX      Counter64
    UNITS       "packets"
    MAX-ACCESS  read-only
    STATUS      current
    DESCRIPTION
        "The number of green packets dropped on this interface."
    ::= { usdQosQueueStatisticsEntry 3 }

usdQosOutYellowPacketsSchedulerDrops OBJECT-TYPE
    SYNTAX      Counter64
    UNITS       "packets"
    MAX-ACCESS  read-only
    STATUS      current
    DESCRIPTION
        "The number of yellow packets dropped on this interface."
    ::= { usdQosQueueStatisticsEntry 4 }

usdQosOutRedPacketsSchedulerDrops OBJECT-TYPE
    SYNTAX      Counter64
    UNITS       "packets"
    MAX-ACCESS  read-only
    STATUS      current
    DESCRIPTION
        "The number of red packets dropped on this interface."
    ::= { usdQosQueueStatisticsEntry 5 }

usdQosOutGreenBytesSchedulerDrops OBJECT-TYPE
    SYNTAX      Counter64
    UNITS       "bytes"
    MAX-ACCESS  read-only
    STATUS      current
    DESCRIPTION
        "The number of green bytes dropped on this interface."
    ::= { usdQosQueueStatisticsEntry 6 }

usdQosOutYellowBytesSchedulerDrops OBJECT-TYPE
    SYNTAX      Counter64
    UNITS       "bytes"
    MAX-ACCESS  read-only
    STATUS      current
    DESCRIPTION
        "The number of yellow bytes dropped on this interface."
    ::= { usdQosQueueStatisticsEntry 7 }

usdQosOutRedBytesSchedulerDrops OBJECT-TYPE
    SYNTAX      Counter64
    UNITS       "bytes"
    MAX-ACCESS  read-only
    STATUS      current
    DESCRIPTION
        "The number of red bytes dropped on this interface."
    ::= { usdQosQueueStatisticsEntry 8 }


-- +++++++++++++++++++++++++++++++++++++++++++++++++++++++++++++++++++++++++++++
-- Conformance information
-- +++++++++++++++++++++++++++++++++++++++++++++++++++++++++++++++++++++++++++++
usdQosConformance OBJECT IDENTIFIER ::= { usdQosMIB 2 }
usdQosCompliances OBJECT IDENTIFIER ::= { usdQosConformance 1 }
usdQosGroups      OBJECT IDENTIFIER ::= { usdQosConformance 2 }

--
-- compliance statements
--
usdQosCompliance MODULE-COMPLIANCE
    STATUS      current
    DESCRIPTION
        "The compliance statement for entities which implement the Unisphere
        QoS management MIB."
    MODULE  -- this module
        MANDATORY-GROUPS {
            usdQosCapabilityGroup,
            usdQosScalarGroup,
            usdQosTrafficClassListGroup,
            usdQosTrafficClassGroupListGroup,
            usdQosQueueProfileListGroup,
            usdQosSchedulerProfileListGroup,
            usdQosProfileListGroup,
            usdQosProfileElementGroup,
            usdQosIfAttachGroup,
            usdQosQosPortTypeProfileGroup,
            usdQosQueueStatisticsGroup }
    ::= { usdQosCompliances 1 }                                        -- RX 4.0

--
-- units of conformance
--
usdQosCapabilityGroup OBJECT-GROUP
    OBJECTS {
        usdQosMaxTrafficClass,
        usdQosMaxQueueLength,
        usdQosMinSchedulerBurst,
        usdQosMaxSchedulerBurst }
    STATUS      current
    DESCRIPTION
        "This group defines QoS application-wide saclar management."
    ::= { usdQosGroups 1 }

usdQosScalarGroup OBJECT-GROUP
    OBJECTS {
        usdQosTrafficClassCount,
        usdQosQueueProfileCount,
        usdQosSchedulerProfileCount,
        usdQosProfileCount,
        usdQosInterfaceCount,
        usdQosQosPortTypeProfileCount }
    STATUS      current
    DESCRIPTION
        "This group defines QoS application-wide saclar management."
    ::= { usdQosGroups 2 }

usdQosTrafficClassListGroup OBJECT-GROUP
    OBJECTS {
        usdQosTrafficClassNextIndex,

        usdQosTrafficClassRowStatus,
        usdQosTrafficClassName,
        usdQosTrafficClassWeight,
        usdQosTrafficClassStrictPriority,
        usdQosTrafficClassUpdatePending,
        usdQosTrafficClassUpdateNow,
        usdQosTrafficClassIsReferencedByGroup,
        usdQosTrafficClassIsReferencedByQosProfile }
    STATUS      current
    DESCRIPTION
        "This group defines QoS traffic class management."
    ::= { usdQosGroups 3 }

usdQosTrafficClassGroupListGroup OBJECT-GROUP
    OBJECTS {
        usdQosTrafficClassGroupNextIndex,

        usdQosTrafficClassGroupRowStatus,
        usdQosTrafficClassGroupName,
        usdQosTrafficClassGroupUpdatePending,
        usdQosTrafficClassGroupUpdateNow,
        usdQosTrafficClassGroupIsReferencedByQosProfile,

        usdQosTrafficClassGroupEntryRowStatus }
    STATUS      current
    DESCRIPTION
        "This group defines QoS traffic class group management."
    ::= { usdQosGroups 4 }

usdQosQueueProfileListGroup OBJECT-GROUP
    OBJECTS {
        usdQosQueueProfileNextIndex,

        usdQosQueueProfileRowStatus,
        usdQosQueueProfileName,
        usdQosQueueProfileCommittedMinLength,
        usdQosQueueProfileCommittedMaxLength,
        usdQosQueueProfileConformedMinLength,
        usdQosQueueProfileConformedMaxLength,
        usdQosQueueProfileExceededMinLength,
        usdQosQueueProfileExceededMaxLength,
        usdQosQueueProfileConformedFraction,
        usdQosQueueProfileExceededFraction,
        usdQosQueueProfileCommittedDropThreshold,
        usdQosQueueProfileCommittedDropRate,
        usdQosQueueProfileConformedDropThreshold,
        usdQosQueueProfileConformedDropRate,
        usdQosQueueProfileExceededDropThreshold,
        usdQosQueueProfileExceededDropRate,
        usdQosQueueProfileBufferWeight,
        usdQosQueueProfileUpdatePending,
        usdQosQueueProfileUpdateNow,
        usdQosQueueProfileIsReferencedByQosProfile }
    STATUS      current
    DESCRIPTION
        "This group defines QoS queue profile management."
    ::= { usdQosGroups 5 }

usdQosSchedulerProfileListGroup OBJECT-GROUP
    OBJECTS {
        usdQosSchedulerProfileNextIndex,

        usdQosSchedulerProfileRowStatus,
        usdQosSchedulerProfileName,
        usdQosSchedulerProfileShapingRate,
        usdQosSchedulerProfileBurst,
        usdQosSchedulerProfileWeight,
        usdQosSchedulerProfileStrictPriority,
        usdQosSchedulerProfileUpdatePending,
        usdQosSchedulerProfileUpdateNow,
        usdQosSchedulerProfileIsReferencedByQosProfile }
    STATUS      current
    DESCRIPTION
        "This group defines QoS scheduler profile management."
    ::= { usdQosGroups 6 }

usdQosProfileListGroup OBJECT-GROUP
    OBJECTS {
        usdQosProfileNextIndex,

        usdQosProfileRowStatus,
        usdQosProfileName,
        usdQosProfileUpdatePending,
        usdQosProfileUpdateNow,
        usdQosProfileIsReferencedByInterfaceQosAttachment,
        usdQosProfileIsReferencedByQosPortTypeProfile }
    STATUS      current
    DESCRIPTION
        "This group defines QoS profile management."
    ::= { usdQosGroups 7 }

usdQosProfileElementGroup OBJECT-GROUP
    OBJECTS {
        usdQosProfileElementEntryRowStatus,
        usdQosProfileElementEntryQueueProfile,
        usdQosProfileElementEntrySchedulerProfile }
    STATUS      current
    DESCRIPTION
        "This group defines QoS profile elment entry management."
    ::= { usdQosGroups 8 }

usdQosIfAttachGroup OBJECT-GROUP
    OBJECTS {
        usdQosIfAttachRowStatus,
        usdQosIfAttachQosProfileIndex }
    STATUS      current
    DESCRIPTION
        "This group defines QoS interface attachment management."
    ::= { usdQosGroups 9 }

usdQosQosPortTypeProfileGroup OBJECT-GROUP
    OBJECTS {
        usdQosQosPortTypeProfileRowStatus,
        usdQosQosPortTypeProfileQosProfileIndex }
    STATUS      current
    DESCRIPTION
        "This group defines QoS default port profile management."
    ::= { usdQosGroups 10 }

usdQosQueueStatisticsGroup OBJECT-GROUP
    OBJECTS {
        usdQosOutPacketForwarded,
        usdQosOutBytesForwarded,
        usdQosOutGreenPacketsSchedulerDrops,
        usdQosOutYellowPacketsSchedulerDrops,
        usdQosOutRedPacketsSchedulerDrops,
        usdQosOutGreenBytesSchedulerDrops,
        usdQosOutYellowBytesSchedulerDrops,
        usdQosOutRedBytesSchedulerDrops }
    STATUS      current
    DESCRIPTION
        "This group defines QoS queue statistics reporting."
    ::= { usdQosGroups 11 }

END
