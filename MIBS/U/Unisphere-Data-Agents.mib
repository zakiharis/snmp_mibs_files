-- *****************************************************************************
-- Unisphere-Data-Agents
--
-- Unisphere Networks Data Products SNMP Agent Capabilities Registry.
--
-- Copyright (c) 2001, 2002 Unisphere Networks, Inc.  All rights reserved.
-- *****************************************************************************

Unisphere-Data-Agents DEFINITIONS ::= BEGIN

IMPORTS
    MODULE-IDENTITY, OBJECT-IDENTITY
        FROM SNMPv2-SMI
    usAgentCapability
        FROM Unisphere-SMI;

usDataAgents MODULE-IDENTITY
    LAST-UPDATED "200201251419Z"  -- 25-Jan-02 09:19 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definition identifiers for the Unisphere
        Networks data communications products.  This is the top-level object
        identifier registry for SNMP modules containing agent capabilities
        definitions."
    -- Revision History
    REVISION    "200201251419Z"  -- 25-Jan-02 09:19 AM EST  - RX 4.0
    DESCRIPTION
        "Added module OIDs for the QoS manager, MPLS, system clock and X.21/V.35
        MIB agent capabilities."
    REVISION    "200201241523Z"  -- 24-Jan-02 10:23 AM EST  - RX 3.4
    DESCRIPTION
        "Added module OIDs for the VRRP MIB agent capabilities."
    REVISION    "200104131716Z"  -- 13-Apr-01 01:16 PM EDT  - RX 3.2
    DESCRIPTION
        "The initial release of this management information module."
    ::= { usAgentCapability 2 }


-- *****************************************************************************
-- Unisphere Networks object identifier registry for SNMP modules containing
-- agent capabilities definitions for data communications products.
-- *****************************************************************************

usdAaaServerAgent  OBJECT IDENTIFIER
--  MODULE-IDENTITY
--      The SNMP module containing the AGENT-CAPABILITIES definitions for the
--      Authentication, Authorization and Accounting (AAA) Server component of
--      the Unisphere Routing Switch family of products.  The supported MIB is
--      the Unisphere-Data-AAA-MIB.
--
--      The actual capabilities are defined in the Unisphere-Data-AAA-CONF
--      module (in the usDataConfAaaServer.mi2 file).
    ::= { usDataAgents 1 }

usdAccountingAgent  OBJECT IDENTIFIER
--  MODULE-IDENTITY
--      The SNMP module containing the AGENT-CAPABILITIES definitions for the
--      network connection accounting information management component of the
--      Unisphere Routing Switch family of products.  The supported MIBs are the
--      ACCOUNTING-CONTROL-MIB and the Unisphere-Data-ACCOUNTING-MIB.
--
--      The actual capabilities are defined in the Unisphere-Data-Accounting-
--      CONF module (in the usDataConfAccounting.mi2 file).
    ::= { usDataAgents 2 }

usdAtmAgent  OBJECT IDENTIFIER
--  MODULE-IDENTITY
--      The SNMP module containing the AGENT-CAPABILITIES definitions for the
--      ATM component of the Unisphere Routing Switch family of products.  The
--      supported MIBs are the ATM-MIB and the Unisphere-Data-ATM-MIB.
--
--      The actual capabilities are defined in the Unisphere-Data-ATM-CONF
--      module (in the usDataConfAtm.mi2 file).
    ::= { usDataAgents 3 }

usdBgpAgent  OBJECT IDENTIFIER
--  MODULE-IDENTITY
--      The SNMP module containing the AGENT-CAPABILITIES definitions for the
--      border gateway protocol (BGP) component of the Unisphere Routing Switch
--      family of products.  The supported MIBs are the BGP4-MIB and the
--      Unisphere-Data-BGP-MIB.
--
--      The actual capabilities are defined in the Unisphere-Data-BGP-CONF
--      module (in the usDataConfBgp.mi2 file).
    ::= { usDataAgents 4 }

usdBridgedEthernetAgent  OBJECT IDENTIFIER
--  MODULE-IDENTITY
--      The SNMP module containing the AGENT-CAPABILITIES definitions for the
--      Bridged Ethernet components of the Unisphere Routing Switch family of
--      products.  The supported MIB is the Unisphere-Data-BRIDGE-ETHERNET-MIB.
--
--      The actual capabilities are defined in the Unisphere-Data-Bridged-
--      Ethernet-CONF module (in the usDataConfBridgedEthernet.mi2 file).
    ::= { usDataAgents 5 }

usdCliAgent  OBJECT IDENTIFIER
--  MODULE-IDENTITY
--      The SNMP module containing the AGENT-CAPABILITIES definitions for the
--      command line interface (CLI) component of the Unisphere Routing Switch
--      family of products.  The supported MIB is the Unisphere-Data-CLI-MIB.
--
--      The actual capabilities are defined in the Unisphere-Data-CLI-CONF
--      module (in the usDataConfCli.mi2 file).
    ::= { usDataAgents 6 }

usdCopsAgent  OBJECT IDENTIFIER
--  MODULE-IDENTITY
--      The SNMP module containing the AGENT-CAPABILITIES definitions for the
--      COPS component of the Unisphere Routing Switch family of products.  The
--      supported MIB is the Unisphere-Data-COPS-MIB.
--
--      The actual capabilities are defined in the Unisphere-Data-COPS-CONF
--      module (in the usDataConfCops.mi2 file).
    ::= { usDataAgents 7 }

usdDhcpAgent  OBJECT IDENTIFIER
--  MODULE-IDENTITY
--      The SNMP module containing the AGENT-CAPABILITIES definitions for the
--      DHCP component of the Unisphere Routing Switch family of products.  The
--      supported MIB is the Unisphere-Data-DHCP-MIB.
--
--      The actual capabilities are defined in the Unisphere-Data-DHCP-CONF
--      module (in the usDataConfDhcp.mi2 file).
    ::= { usDataAgents 8 }

usdDnsAgent  OBJECT IDENTIFIER
--  MODULE-IDENTITY
--      The SNMP module containing the AGENT-CAPABILITIES definitions for the
--      DNS component of the Unisphere Routing Switch family of products.  The
--      supported MIB is the Unisphere-Data-DNS-MIB.
--
--      The actual capabilities are defined in the Unisphere-Data-DNS-CONF
--      module (in the usDataConfDns.mi2 file).
    ::= { usDataAgents 9 }

usdDs1Agent  OBJECT IDENTIFIER
--  MODULE-IDENTITY
--      The SNMP module containing the AGENT-CAPABILITIES definitions for the
--      DS1 component of the Unisphere Routing Switch family of products.  The
--      supported MIBs are the DS1-MIB and the Unisphere-Data-DS1-MIB.
--
--      The actual capabilities are defined in the Unisphere-Data-DS1-CONF
--      module (in the usDataConfDs1.mi2 file).
    ::= { usDataAgents 10 }

usdDs3Agent  OBJECT IDENTIFIER
--  MODULE-IDENTITY
--      The SNMP module containing the AGENT-CAPABILITIES definitions for the
--      DS3 component of the Unisphere Routing Switch family of products.  The
--      supported MIBs are the DS3-MIB and the Unisphere-Data-DS3-MIB.
--
--      The actual capabilities are defined in the Unisphere-Data-DS3-CONF
--      module (in the usDataConfDs3.mi2 file).
    ::= { usDataAgents 11 }

usdDvmrpAgent  OBJECT IDENTIFIER
--  MODULE-IDENTITY
--      The SNMP module containing the AGENT-CAPABILITIES definitions for the
--      DVMRP component of the Unisphere Routing Switch family of products.  The
--      supported MIBs are the DVMRP-STD-MIB and the Unisphere-Data-DVMRP-MIB.
--
--      The actual capabilities are defined in the Unisphere-Data-DVMRP-CONF
--      module (in the usDataConfDvmrp.mi2 file).
    ::= { usDataAgents 12 }

usdEntityAgent  OBJECT IDENTIFIER
--  MODULE-IDENTITY
--      The SNMP module containing the AGENT-CAPABILITIES definitions for the
--      physical and logical entity components of the Unisphere Routing Switch
--      family of products.  The supported MIB is the ENTITY-MIB.
--
--      The actual capabilities are defined in the Unisphere-Data-Entity-CONF
--      module (in the usDataConfEntity.mi2 file).
    ::= { usDataAgents 13 }

usdEthernetAgent  OBJECT IDENTIFIER
--  MODULE-IDENTITY
--      The SNMP module containing the AGENT-CAPABILITIES definitions for the
--      Ethernet components of the Unisphere Routing Switch family of products.
--      The supported MIBs are the EtherLike-MIB and the Unisphere-Data-
--      ETHERNET-MIB.
--
--      The actual capabilities are defined in the Unisphere-Data-Ethernet-CONF
--      module (in the usDataConfEthernet.mi2 file).
    ::= { usDataAgents 14 }

usdFileTransferAgent  OBJECT IDENTIFIER
--  MODULE-IDENTITY
--      The SNMP module containing the AGENT-CAPABILITIES definitions for the
--      file transfer component of the Unisphere Routing Switch family of
--      products.  The supported MIB is the Unisphere-Data-FILE-XFER-MIB.
--
--      The actual capabilities are defined in the Unisphere-Data-File-
--      Transfer-CONF module (in the usDataConfFileTransfer.mi2 file).
    ::= { usDataAgents 15 }

usdFractionalT1Agent  OBJECT IDENTIFIER
--  MODULE-IDENTITY
--      The SNMP module containing the AGENT-CAPABILITIES definitions for the
--      Fractional T1 component of the Unisphere Routing Switch family of
--      products.  The supported MIB is the Unisphere-Data-FRACTIONAL-T1-MIB.
--
--      The actual capabilities are defined in the Unisphere-Data-Fractional-
--      T1-CONF module (in the usDataConfFractionalT1.mi2 file).
    ::= { usDataAgents 16 }

usdFrameRelayAgent  OBJECT IDENTIFIER
--  MODULE-IDENTITY
--      The SNMP module containing the AGENT-CAPABILITIES definitions for the
--      frame relay component of the Unisphere Routing Switch family of
--      products.  The supported MIBs are the FRAME-RELAY-DTE-MIB and the
--      Unisphere-Data-FRAME-RELAY-MIB.
--
--      The actual capabilities are defined in the Unisphere-Data-Frame-Relay-
--      CONF module (in the usDataConfFrameRelay.mi2 file).
    ::= { usDataAgents 17 }

usdHdlcAgent  OBJECT IDENTIFIER
--  MODULE-IDENTITY
--      The SNMP module containing the AGENT-CAPABILITIES definitions for the
--      HDLC component of the Unisphere Routing Switch family of products.  The
--      supported MIB is the Unisphere-Data-HDLC-MIB.
--
--      The actual capabilities are defined in the Unisphere-Data-HDLC-CONF
--      module (in the usDataConfHdlc.mi2 file).
    ::= { usDataAgents 18 }

usdIgmpAgent  OBJECT IDENTIFIER
--  MODULE-IDENTITY
--      The SNMP module containing the AGENT-CAPABILITIES definitions for the
--      IGMP component of the Unisphere Routing Switch family of products. The
--      supported MIB is the Unisphere-Data-HDLC-MIB.
--
--      The actual capabilities are defined in the Unisphere-Data-IGMP-CONF
--      module (in the usDataConfIgmp.mi2 file).
    ::= { usDataAgents 19 }

usdInterfacesAgent  OBJECT IDENTIFIER
--  MODULE-IDENTITY
--      The SNMP module containing the AGENT-CAPABILITIES definitions for the
--      basic interfaces (IF) component of the Unisphere Routing Switch family
--      of products.  The supported MIBs are the IF-MIB and the Unisphere-Data-
--      IF-MIB.
--
--      The actual capabilities are defined in the Unisphere-Data-Interfaces-
--      CONF module (in the usDataConfInterfaces.mi2 file).
    ::= { usDataAgents 20 }

usdInternetAgent  OBJECT IDENTIFIER
--  MODULE-IDENTITY
--      The SNMP module containing the AGENT-CAPABILITIES definitions for the
--      Internet (basic layer 3 and 4 protocols) component of the Unisphere
--      Routing Switch family of products.  The supported MIBs are the IP-MIB,
--      the IP-FORWARD-MIB, the UDP-MIB, the TCP-MIB, Unisphere-Data-IP-MIB and
--      the Unisphere-Data-HOST-MIB.
--
--      The actual capabilities are defined in the Unisphere-Data-Internet-CONF
--      module (in the usDataConfInternet.mi2 file).
    ::= { usDataAgents 21 }

usdIpPolicyAgent  OBJECT IDENTIFIER
--  MODULE-IDENTITY
--      The SNMP module containing the AGENT-CAPABILITIES definitions for the
--      IP policy component of the Unisphere Routing Switch family of products.
--      The supported MIB is the Unisphere-Data-IP-POLICY-MIB.
--
--      The actual capabilities are defined in the Unisphere-Data-IP-Policy-
--      CONF module (in the usDataConfIpPolicy.mi2 file).
    ::= { usDataAgents 22 }

usdIsisAgent  OBJECT IDENTIFIER
--  MODULE-IDENTITY
--      The SNMP module containing the AGENT-CAPABILITIES definitions for the
--      IS-IS protocol component of the Unisphere Routing Switch family of
--      products.  The supported MIB is the Unisphere-Data-ISIS-MIB.
--
--      The actual capabilities are defined in the Unisphere-Data-IS-IS-CONF
--      module (in the usDataConfIsis.mi2 file).
    ::= { usDataAgents 23 }

usdL2tpAgent  OBJECT IDENTIFIER
--  MODULE-IDENTITY
--      The SNMP module containing the AGENT-CAPABILITIES definitions for the
--      layer 2 tunneling protocol (L2TP) component of the Unisphere Routing
--      Switch family of products.  The supported MIB is the Unisphere-Data-
--      L2TP-MIB.
--
--      The actual capabilities are defined in the Unisphere-Data-L2TP-CONF
--      module (in the usDataConfL2tp.mi2 file).
    ::= { usDataAgents 24 }

usdLocalAddressServerAgent  OBJECT IDENTIFIER
--  MODULE-IDENTITY
--      The SNMP module containing the AGENT-CAPABILITIES definitions for the
--      local address server component of the Unisphere Routing Switch family of
--      products.  The supported MIB is the Unisphere-Data-ADDRESS-POOL-MIB.
--
--      The actual capabilities are defined in the Unisphere-Data-Local-
--      Address-Server-CONF module (in the usDataConfLocalAddressServer.mi2
--      file).
    ::= { usDataAgents 25 }

usdLogAgent  OBJECT IDENTIFIER
--  MODULE-IDENTITY
--      The SNMP module containing the AGENT-CAPABILITIES definitions for the
--      logging managment component of the Unisphere Routing Switch family of
--      products.  The supported MIB is the Unisphere-Data-LOG-MIB.
--
--      The actual capabilities are defined in the Unisphere-Data-Log-CONF
--      module (in the usDataConfLog.mi2 file).
    ::= { usDataAgents 26 }

usdNsLookupAgent  OBJECT IDENTIFIER
--  MODULE-IDENTITY
--      The SNMP module containing the AGENT-CAPABILITIES definitions for the
--      remote name server lookup component of the Unisphere Routing Switch
--      family of products.  The supported MIB is the DISMAN-NSLOOKUP-MIB.
--
--      The actual capabilities are defined in the Unisphere-Data-NS-Lookup-
--      CONF module (in the usDataConfNsLookup.mi2 file).
    ::= { usDataAgents 27 }

usdOspfAgent  OBJECT IDENTIFIER
--  MODULE-IDENTITY
--      The SNMP module containing the AGENT-CAPABILITIES definitions for the
--      OSPF component of the Unisphere Routing Switch family of products.  The
--      supported MIBs are the OSPF-MIB and the Unisphere-Data-OSPF-MIB.
--
--      The actual capabilities are defined in the Unisphere-Data-OSPF-CONF
--      module (in the usDataConfOspf.mi2 file).
    ::= { usDataAgents 28 }

usdPimAgent  OBJECT IDENTIFIER
--  MODULE-IDENTITY
--      The SNMP module containing the AGENT-CAPABILITIES definitions for the
--      Protocol Independent Multicast (PIM) component of the Unisphere Routing
--      Switch family of products.  The supported MIBs are the PIM-MIB and the
--      Unisphere-Data-PIM-MIB.
--
--      The actual capabilities are defined in the Unisphere-Data-PIM-CONF
--      module (in the usDataConfPim.mi2 file).
    ::= { usDataAgents 29 }

usdPingAgent  OBJECT IDENTIFIER
--  MODULE-IDENTITY
--      The SNMP module containing the AGENT-CAPABILITIES definitions for the
--      remote ping operation component of the Unisphere Routing Switch family
--      of products.  The supported MIB is the DISMAN-PING-MIB.
--
--      The actual capabilities are defined in the Unisphere-Data-Ping-CONF
--      module (in the usDataConfPing.mi2 file).
    ::= { usDataAgents 30 }

usdPolicyManagerAgent  OBJECT IDENTIFIER
--  MODULE-IDENTITY
--      The SNMP module containing the AGENT-CAPABILITIES definitions for the
--      policy manager component of the Unisphere Routing Switch family of
--      products.  The supported MIB is the Unisphere-Data-POLICY-MIB.
--
--      The actual capabilities are defined in the Unisphere-Data-Policy-
--      Manager-CONF module (in the usDataConfPolicyManager.mi2 file).
    ::= { usDataAgents 31 }

usdPppAgent  OBJECT IDENTIFIER
--  MODULE-IDENTITY
--      The SNMP module containing the AGENT-CAPABILITIES definitions for the
--      point-to-point protocol (PPP) component of the Unisphere Routing Switch
--      family of products.  The supported MIBs are the PPP-LCP-MIB, the
--      PPP-IP-NCP-MIB and the Unisphere-Data-PPP-MIB.
--
--      The actual capabilities are defined in the Unisphere-Data-PPP-CONF
--      module (in the usDataConfPpp.mi2 file).
    ::= { usDataAgents 32 }

usdPppoeAgent  OBJECT IDENTIFIER
--  MODULE-IDENTITY
--      The SNMP module containing the AGENT-CAPABILITIES definitions for the
--      point-to-point protocol over Ethernet (PPPoE) component of the Unisphere
--      Routing Switch family of products.  The supported MIB is the Unisphere-
--      Data-PPPOE-MIB.
--
--      The actual capabilities are defined in the Unisphere-Data-PPPoE-CONF
--      module (in the usDataConfPppoe.mi2 file).
    ::= { usDataAgents 33 }

usdProfileAgents  OBJECT-IDENTITY
    STATUS      current
    DESCRIPTION
        "The group of Agent Capabilities modules that are deal with profile
        management."
    ::= { usDataAgents 34 }

usdProfileManagerAgent  OBJECT IDENTIFIER
--  MODULE-IDENTITY
--      The SNMP module containing the AGENT-CAPABILITIES definitions for the
--      profile manager component of the Unisphere Routing Switch family of
--      products.  The supported MIB is the Unisphere-Data-PROFILE-MIB.
--
--      The actual capabilities are defined in the Unisphere-Data-Profile-CONF
--      module (in the usDataConfProfile.mi2 file).
    ::= { usdProfileAgents 1 }

usdIpProfileAgent  OBJECT IDENTIFIER
--  MODULE-IDENTITY
--      The SNMP module containing the AGENT-CAPABILITIES definitions for the
--      IP profile manager component of the Unisphere Routing Switch family of
--      products.  The supported MIB is the Unisphere-Data-IP-PROFILE-MIB.
--
--      The actual capabilities are defined in the Unisphere-Data-IP-Profile-
--      CONF module (in the usDataConfIpProfile.mi2 file).
    ::= { usdProfileAgents 2 }

usdPppProfileAgent  OBJECT IDENTIFIER
--  MODULE-IDENTITY
--      The SNMP module containing the AGENT-CAPABILITIES definitions for the
--      PPP profile manager component of the Unisphere Routing Switch family of
--      products.  The supported MIB is the Unisphere-Data-PPP-PROFILE-MIB.
--
--      The actual capabilities are defined in the Unisphere-Data-PPP-Profile-
--      CONF module (in the usDataConfPppProfile.mi2 file).
    ::= { usdProfileAgents 3 }

usdPppoeProfileAgent  OBJECT IDENTIFIER
--  MODULE-IDENTITY
--      The SNMP module containing the AGENT-CAPABILITIES definitions for the
--      PPPoE profile manager component of the Unisphere Routing Switch family
--      of products.  The supported MIB is the Unisphere-Data-PPPOE-PROFILE-MIB.
--
--      The actual capabilities are defined in the Unisphere-Data-PPPoE-Profile-
--      CONF module (in the usDataConfPppoeProfile.mi2 file).
    ::= { usdProfileAgents 4 }

usdRadiusClientAgent  OBJECT IDENTIFIER
--  MODULE-IDENTITY
--      The SNMP module containing the AGENT-CAPABILITIES definitions for the
--      RADIUS client component of the Unisphere Routing Switch family of
--      products.  The supported MIB is the Unisphere-Data-RADIUS-CLIENT-MIB.
--
--      The actual capabilities are defined in the Unisphere-Data-RADIUS-
--      Client-CONF module (in the usDataConfRadiusClient.mi2 file).
    ::= { usDataAgents 35 }

usdRipAgent  OBJECT IDENTIFIER
--  MODULE-IDENTITY
--      The SNMP module containing the AGENT-CAPABILITIES definitions for the
--      Routing Information Protocol (RIP) component of the Unisphere Routing
--      Switch family of products.  The supported MIB is the RIPv2-MIB.
--
--      The actual capabilities are defined in the Unisphere-Data-RIP-CONF
--      module (in the usDataConfRip.mi2 file).
    ::= { usDataAgents 36 }

usdRouterAgent  OBJECT IDENTIFIER
--  MODULE-IDENTITY
--      The SNMP module containing the AGENT-CAPABILITIES definitions for the
--      router component of the Unisphere Routing Switch family of products.
--      The supported MIB is the Unisphere-Data-ROUTER-MIB.
--
--      The actual capabilities are defined in the Unisphere-Data-Router-CONF
--      module (in the usDataConfRouter.mi2 file).
    ::= { usDataAgents 37 }

usdSlepAgent  OBJECT IDENTIFIER
--  MODULE-IDENTITY
--      The SNMP module containing the AGENT-CAPABILITIES definitions for the
--      Serial Line Encapsulation Protocol (SLEP) component of the Unisphere
--      Routing Switch family of products.  The supported MIB is the Unisphere-
--      Data-SLEP-MIB.
--
--      The actual capabilities are defined in the Unisphere-Data-SLEP-CONF
--      module (in the usDataConfSlep.mi2 file).
    ::= { usDataAgents 38 }

usdSnmpAgent  OBJECT IDENTIFIER
--  MODULE-IDENTITY
--      The SNMP module containing the AGENT-CAPABILITIES definitions for the
--      SNMP components of the Unisphere Routing Switch family of products.  The
--      supported MIBs are the SNMPv2-MIB, the SNMP-FRAMEWORK-MIB, the
--      SNMP-MPD-MIB, the SNMP-TARGET-MIB, the SNMP-NOTOFICATION-MIB, the
--      SNMP-USER-BASE-SM-MIB, the SNMP-VIEW-BASED-ACM-MIB and the
--      Unisphere-Data-SNMP-MIB.
--
--      The actual capabilities are defined in the Unisphere-Data-SNMP-CONF
--      module (in the usDataConfSnmp.mi2 file).
    ::= { usDataAgents 39 }

usdSonetAgent  OBJECT IDENTIFIER
--  MODULE-IDENTITY
--      The SNMP module containing the AGENT-CAPABILITIES definitions for the
--      SONET component of the Unisphere Routing Switch family of products.  The
--      supported MIBs are the SONET-MIB and the Unisphere-Data-SONET-MIB.
--
--      The actual capabilities are defined in the Unisphere-Data-SONET-CONF
--      module (in the usDataConfSonet.mi2 file).
    ::= { usDataAgents 40 }

usdSscClientAgent  OBJECT IDENTIFIER
--  MODULE-IDENTITY
--      The SNMP module containing the AGENT-CAPABILITIES definitions for the
--      Service Selection Center (SSC) client component of the Unisphere Routing
--      Switch family of products.  The supported MIB is the Unisphere-Data-
--      SSC-CLIENT-MIB.
--
--      The actual capabilities are defined in the Unisphere-Data-SSC-Client-
--      CONF module (in the usDataConfSscClient.mi2 file).
    ::= { usDataAgents 41 }

usdSystemAgents  OBJECT-IDENTITY
    STATUS      current
    DESCRIPTION
        "The root object identifier under which are registered the platform-
        specific SNMP modules containing the AGENT-CAPABILITIES definitions for
        the system components of the Unisphere Routing Switch family of
        products."
   ::= { usDataAgents 42 }

usdErxSystemAgent  OBJECT IDENTIFIER
--  MODULE-IDENTITY
--      The SNMP modules containing the AGENT-CAPABILITIES definitions for the
--      system components of the Unisphere Edge Routing Switch (ERX) family of
--      products.  The supported MIB is the Unisphere ERX platform-specific
--      system MIB, Unisphere-Data-ERX-System-MIB.
--
--      The actual capabilities are defined in the Unisphere-Data-ERX-System-
--      CONF module (in the usDataConfErxSystem.mi2 file).
    ::= { usdSystemAgents 1 }

usdMrxSystemAgent  OBJECT IDENTIFIER
--  MODULE-IDENTITY
--      The SNMP modules containing the AGENT-CAPABILITIES definitions for the
--      system components of the Unisphere MRX Routing Switch family of
--      products.  The supported MIB is the Unisphere MRX platform-specific
--      system MIB, Unisphere-Data-MRX-System-MIB.
--
--      The actual capabilities are defined in the Unisphere-Data-MRX-System-
--      CONF module (in the usDataConfMrxSystem.mi2 file).
    ::= { usdSystemAgents 2 }

usdTraceRouteAgent  OBJECT IDENTIFIER
--  MODULE-IDENTITY
--      The SNMP module containing the AGENT-CAPABILITIES definitions for the
--      remote trace-route component of the Unisphere Routing Switch family of
--      products.  The supported MIB is the DISMAN-TRACEROUTE-MIB.
--
--      The actual capabilities are defined in the Unisphere-Data-Trace-Route-
--      CONF module (in the usDataConfTraceRoute.mi2 file).
    ::= { usDataAgents 43 }

usdAutoConfAgent  OBJECT IDENTIFIER
--  MODULE-IDENTITY
--      The SNMP module containing the AGENT-CAPABILITIES definitions for the
--      auto-configuration component of the Unisphere Routing Switch family of
--      products.  The supported MIB is the Unisphere-Data-AUTOCONFIGURE-MIB.
--
--      The actual capabilities are defined in the Unisphere-Data-Autoconfigure-
--      CONF module (in the usDataConfAutoconf.mi2 file).
    ::= { usDataAgents 44 }

usdSubscriberAgent  OBJECT IDENTIFIER
--  MODULE-IDENTITY
--      The SNMP module containing the AGENT-CAPABILITIES definitions for the
--      subscriber component of the Unisphere Routing Switch family of
--      products.  The supported MIB is the Unisphere-Data-SUBSCRIBER-MIB.
--
--      The actual capabilities are defined in the Unisphere-Data-Subscriber-
--      CONF module (in the usDataConfSubscriber.mi2 file).
    ::= { usDataAgents 45 }

usdSmdsAgent  OBJECT IDENTIFIER
--  MODULE-IDENTITY
--      The SNMP module containing the AGENT-CAPABILITIES definitions for the
--      Switched Multimegabit Data Service (SMDS) management component of the
--      Unisphere Routing Switch family of products.  The supported MIB is the
--      Unisphere-Data-SMDS-MIB.
--
--      The actual capabilities are defined in the Unisphere-Data-SMDS-CONF
--      module (in the usDataConfSmds.mi2 file).
    ::= { usDataAgents 46 }

usdIpTunnelAgent  OBJECT IDENTIFIER
--  MODULE-IDENTITY
--      The SNMP module containing the AGENT-CAPABILITIES definitions for the
--      IP Tunnel (GRE/DVMRP) management component of the Unisphere Routing
--      Switch family of products.  The supported MIB is the Unisphere-Data-IP-
--      TUNNEL-MIB.
--
--      The actual capabilities are defined in the Unisphere-Data-IP-Tunnel-CONF
--      module (in the usDataConfIpTunnel.mi2 file).
    ::= { usDataAgents 47 }

usdCbfAgent  OBJECT IDENTIFIER
--  MODULE-IDENTITY
--      The SNMP module containing the AGENT-CAPABILITIES definitions for the
--      Connection-Based Forwarding (CBF) Protocol management component of the
--      Unisphere Routing Switch family of products.  The supported MIB is the
--      Unisphere-Data-CBF-MIB.
--
--      The actual capabilities are defined in the Unisphere-Data-CBF-CONF
--      module (in the usDataConfCbf.mi2 file).
    ::= { usDataAgents 48 }

usdL2fAgent  OBJECT IDENTIFIER
--  MODULE-IDENTITY
--      The SNMP module containing the AGENT-CAPABILITIES definitions for the
--      Layer 2 Forwarding (L2F) Protocol management component of the Unisphere
--      Data Routing Switch family of products.  The supported MIB is the
--      Unisphere-Data-L2F-MIB.
--
--      The actual capabilities are defined in the Unisphere-Data-L2F-CONF
--      module (in the usDataConfL2f.mi2 file).
    ::= { usDataAgents 49 }

usdQosManagerAgent  OBJECT IDENTIFIER
--  MODULE-IDENTITY
--      The SNMP module containing the AGENT-CAPABILITIES definitions for the
--      Quality of Service (QoS) Manager component of the Unisphere Routing
--      Switch family of products.  The supported MIB is the Unisphere-Data-QoS-
--      MIB.
--
--      The actual capabilities are defined in the Unisphere-Data-QoS-Manager-
--      CONF module (in the usDataConfQosManager.mi2 file).
    ::= { usDataAgents 50 }

usdMplsAgent  OBJECT IDENTIFIER
--  MODULE-IDENTITY
--      The SNMP module containing the AGENT-CAPABILITIES definitions for the
--      Multiprotocol Label Switching (MPLS) component of the Unisphere Routing
--      Switch family of products.  The supported MIB is the Unisphere-Data-
--      MPLS-MIB.
--
--      The actual capabilities are defined in the Unisphere-Data-MPSL-CONF
--      module (in the usDataConfMpls.mi2 file).
    ::= { usDataAgents 51 }

usdSysClockAgent  OBJECT IDENTIFIER
--  MODULE-IDENTITY
--      The SNMP module containing the AGENT-CAPABILITIES definitions for the
--      system clock component of the Unisphere Routing Switch family of
--      products.  The supported MIB is the Unisphere-Data-System-Clock-MIB.
--
--      The actual capabilities are defined in the Unisphere-Data-System-Clock-
--      CONF module (in the usDataConfSysClock.mi2 file).
    ::= { usDataAgents 52 }

usdVrrpAgent  OBJECT IDENTIFIER
--  MODULE-IDENTITY
--      The SNMP module containing the AGENT-CAPABILITIES definitions for the
--      Virtual Router Redundancy Protocol (VRRP) component of the Unisphere
--      Routing Switch family of products.  The supported MIB is the VRRP-MIB.
--
--      The actual capabilities are defined in the Unisphere-Data-VRRP-CONF
--      module (in the usDataConfVrrp.mi2 file).
    ::= { usDataAgents 53 }

usdV35Agent  OBJECT IDENTIFIER
--  MODULE-IDENTITY
--      The SNMP module containing the AGENT-CAPABILITIES definitions for the
--      X.21/V.35 component of the Unisphere Routing Switch family of products.
--      The supported MIB is the Unisphere-Data-V35-MIB.
--
--      The actual capabilities are defined in the Unisphere-Data-V35-CONF
--      module (in the usDataConfV35.mi2 file).
    ::= { usDataAgents 54 }

END
