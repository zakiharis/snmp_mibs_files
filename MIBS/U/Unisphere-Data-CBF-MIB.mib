-- *****************************************************************************
-- Unisphere-Data-CBF-MIB
--
-- Unisphere Networks Inc. Enterprise MIB
-- Extensions for Connection-Based Forwarding Protocol Management
--
-- Copyright 2001 Unisphere Networks, Incorporated.  All Rights Reserved.
-- *****************************************************************************

Unisphere-Data-CBF-MIB DEFINITIONS ::= BEGIN

IMPORTS
    MODULE-IDENTITY,
    OBJECT-TYPE
        FROM SNMPv2-SMI

    RowStatus
        FROM SNMPv2-TC

    MODULE-COMPLIANCE,
    OBJECT-GROUP
        FROM SNMPv2-CONF

    usDataMibs
        FROM Unisphere-Data-MIBs

    InterfaceIndex,
    InterfaceIndexOrZero
        FROM IF-MIB

    UsdNextIfIndex
       FROM Unisphere-Data-TC;

usdCbfMIB MODULE-IDENTITY
    LAST-UPDATED "200103301627Z"  -- 30-Mar-01 11:27 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The Connection-Based Forwarding (CBF) Protocol MIB for the Unisphere
        Networks Inc. enterprise."
    -- Revision History
    REVISION    "200103301627Z"  -- 30-Mar-01 11:27 AM EST  - RX 3.2
    DESCRIPTION
        "Initial version of this MIB module."
    ::= { usDataMibs 52 }


-- ++++++++++++++++++++++++++++++++++++++++++++++++++++++++++++++++++++++
-- Textual conventions
-- ++++++++++++++++++++++++++++++++++++++++++++++++++++++++++++++++++++++

-- No textual conventions are defined in this MIB.

-- ++++++++++++++++++++++++++++++++++++++++++++++++++++++++++++++++++++++
-- Managed objects
-- ++++++++++++++++++++++++++++++++++++++++++++++++++++++++++++++++++++++

usdCbfObjects     OBJECT IDENTIFIER ::= { usdCbfMIB 1 }

usdCbfInterface   OBJECT IDENTIFIER ::= { usdCbfObjects 1 }

-- +++++++++++++++++++++++++++++++++++++++++++++++++++++++++++++++++++++++++++++
-- CBF Global attributes
-- +++++++++++++++++++++++++++++++++++++++++++++++++++++++++++++++++++++++++++++

-- No global attributes are defined in this MIB.

-- +++++++++++++++++++++++++++++++++++++++++++++++++++++++++++++++++++++++++++++
-- CBF Interface attributes
-- +++++++++++++++++++++++++++++++++++++++++++++++++++++++++++++++++++++++++++++

--
-- IfIndex selection for creating new CBF interfaces
--

usdCbfNextIfIndex OBJECT-TYPE
    SYNTAX      UsdNextIfIndex
    MAX-ACCESS  read-only
    STATUS      current
    DESCRIPTION
        "Coordinate ifIndex value allocation for entries in usdCbfIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { usdCbfInterface 1 }

--
-- The CBF Interface Table
--

usdCbfIfTable OBJECT-TYPE
    SYNTAX      SEQUENCE OF UsdCbfIfEntry
    MAX-ACCESS  not-accessible
    STATUS      current
    DESCRIPTION
        "This table contains entries for CBF interfaces present in the system."
    ::= { usdCbfInterface 2 }

usdCbfIfEntry OBJECT-TYPE
    SYNTAX      UsdCbfIfEntry
    MAX-ACCESS  not-accessible
    STATUS      current
    DESCRIPTION
        "Each entry describes the characteristics of an CBF interface. 
        Creating/deleting entries in this table causes corresponding 
        entries for be created /deleted in ifTable/ifXTable/usdIfTable."
    INDEX   { usdCbfIfIndex }
    ::= { usdCbfIfTable 1 }

UsdCbfIfEntry ::= SEQUENCE {
    usdCbfIfIndex
        InterfaceIndex,
    usdCbfIfRowStatus
        RowStatus,
    usdCbfIfLowerIfIndex
        InterfaceIndexOrZero
    }

usdCbfIfIndex OBJECT-TYPE
    SYNTAX      InterfaceIndex
    MAX-ACCESS  not-accessible
    STATUS      current
    DESCRIPTION
        "The ifIndex of the CBF interface.  When creating entries in this table,
        suitable values for this object are determined by reading
        usdCbfNextIfIndex."
    ::= { usdCbfIfEntry 1 }

usdCbfIfRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdCbfIfRowStatus
            usdCbfIfLowerIfIndex

        In addition, when creating an entry the following conditions must hold:

            A value for usdCbfIfIndex must have been determined previously,
            typically by reading usdCbfNextIfIndex.

            The interface identified by a nonzero usdCbfIfLowerIfIndex must exist.

        Once created, the following objects may not be modified:

            usdCbfIfLowerIfIndex

        A corresponding entry in ifTable/ifXTable/usdIfTable is created/destroyed
        as a result of creating/destroying an entry in this table."
    ::= { usdCbfIfEntry 2 }

usdCbfIfLowerIfIndex OBJECT-TYPE
    SYNTAX      InterfaceIndexOrZero
    MAX-ACCESS  read-create
    STATUS      current
    DESCRIPTION
        "The ifIndex of a media interface over which this CBF interface is to be
        layered."  
    ::= { usdCbfIfEntry 3 }

-- +++++++++++++++++++++++++++++++++++++++++++++++++++++++++++++++++++++++++++++
-- CBF connection attributes
-- +++++++++++++++++++++++++++++++++++++++++++++++++++++++++++++++++++++++++++++

usdCbfIfConnTable OBJECT-TYPE
    SYNTAX      SEQUENCE OF UsdCbfIfConnEntry
    MAX-ACCESS  not-accessible
    STATUS      current
    DESCRIPTION
        "This table contains entries for CBF interface connection present in the
        system."
    ::= { usdCbfInterface 4 }

usdCbfIfConnEntry OBJECT-TYPE
    SYNTAX      UsdCbfIfConnEntry
    MAX-ACCESS  not-accessible
    STATUS      current
    DESCRIPTION
        "Each entry defines a CBF connection."
    INDEX   { usdCbfIfIngressIfIndex }
    ::= { usdCbfIfConnTable 1 }

UsdCbfIfConnEntry ::= SEQUENCE {
    usdCbfIfIngressIfIndex
        InterfaceIndex,
    usdCbfIfConnRowStatus
        RowStatus,
    usdCbfIfEgressIfIndex
        InterfaceIndex
    }

usdCbfIfIngressIfIndex OBJECT-TYPE
    SYNTAX      InterfaceIndex
    MAX-ACCESS  not-accessible
    STATUS      current
    DESCRIPTION
        "The ifIndex of the ingress interface for the CBF connection.  When
        creating entries in this table, suitable values for this object are
        walking the usdCbfIfTable and picking the appropriate usdCbfIfIndex."
    ::= { usdCbfIfConnEntry 1 }

usdCbfIfConnRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdCbfIfRowStatus
            usdCbfIfIngressIfIndex

        Once created, the following objects may not be modified:

            usdCbfIfIngressIfIndex"

    ::= { usdCbfIfConnEntry 2 }

usdCbfIfEgressIfIndex OBJECT-TYPE
    SYNTAX      InterfaceIndex
    MAX-ACCESS  read-create
    STATUS      current
    DESCRIPTION
        "The ifIndex of the egress interface for the CBF interface.  When
        creating entries in this table, suitable values for this object are
        walking the usdCbfIfTable and picking the appropriate usdCbfIfIndex."
    ::= { usdCbfIfConnEntry 3 }


-- ++++++++++++++++++++++++++++++++++++++++++++++++++++++++++++++++++++++
-- Notification control objects
-- ++++++++++++++++++++++++++++++++++++++++++++++++++++++++++++++++++++++

-- No notifications are defined in this MIB. Placeholder follows.

-- usdCbfTrapControl      OBJECT IDENTIFIER ::= { usdCbfMIB 2 }

-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdCbfTraps            OBJECT IDENTIFIER ::= { usdCbfMIB 3 }
-- usdCbfTrapPrefix       OBJECT IDENTIFIER ::= { usdCbfTraps 0 }


-- ++++++++++++++++++++++++++++++++++++++++++++++++++++++++++++++++++++++
-- Conformance information
-- ++++++++++++++++++++++++++++++++++++++++++++++++++++++++++++++++++++++

usdCbfConformance OBJECT IDENTIFIER ::= { usdCbfMIB 4 }
usdCbfCompliances OBJECT IDENTIFIER ::= { usdCbfConformance 1 }
usdCbfGroups      OBJECT IDENTIFIER ::= { usdCbfConformance 2 }

-- compliance statements

usdCbfCompliance MODULE-COMPLIANCE
    STATUS      current
    DESCRIPTION
        "The compliance statement for entities which implement the Unisphere CBF
        MIB."
    MODULE  -- this module
        MANDATORY-GROUPS { usdCbfGroup }
    ::= { usdCbfCompliances 1 }

-- units of conformance

usdCbfGroup OBJECT-GROUP
    OBJECTS {
        usdCbfNextIfIndex,

        usdCbfIfRowStatus,
        usdCbfIfLowerIfIndex,
        usdCbfIfConnRowStatus,
        usdCbfIfEgressIfIndex
    }
    STATUS      current
    DESCRIPTION
        "A collection of objects providing management of CBF interfaces in a
        Unisphere product."
    ::= { usdCbfGroups 1 }

END
