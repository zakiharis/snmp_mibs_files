-- *****************************************************************************
-- Unisphere-Data-Ping-CONF
--
-- SNMP Agent Capabilities definitions for the Ping MIB.
--
-- Copyright (c) 2001 Unisphere Networks, Inc.  All rights reserved.
-- *****************************************************************************

Unisphere-Data-Ping-CONF DEFINITIONS ::= BEGIN

IMPORTS
    MODULE-IDENTITY
        FROM SNMPv2-SMI
    AGENT-CAPABILITIES
        FROM SNMPv2-CONF
    usDataAgents
        FROM Unisphere-Data-Agents
    pingGroup,
    pingTimeStampGroup,
    pingNotificationsGroup
        FROM DISMAN-PING-MIB;

usdPingAgent MODULE-IDENTITY
    LAST-UPDATED "200103291414Z"  -- 29-Mar-01 09:14 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Ping component of the SNMP
        agent in the Unisphere Routing Switch family of products."
    -- Revision History
    REVISION    "200103291414Z"  -- 29-Mar-01 09:14 AM EST  - RX 3.2
    DESCRIPTION
        "The initial release of this management information module."
    ::= { usDataAgents 30 }

usdPingAgentV1 AGENT-CAPABILITIES
    PRODUCT-RELEASE
        "Version 1 of the Ping component of the Unisphere Routing Switch SNMP
        agent.  This version of the Ping component is supported in the
        Unisphere RX 3.0 and subsequent system releases."
    STATUS      current
    DESCRIPTION
        "The MIB supported by the SNMP agent for the Ping application in the
        Unisphere Routing Switch."

    SUPPORTS        DISMAN-PING-MIB
        INCLUDES  { pingGroup,
                    pingTimeStampGroup,
                    pingNotificationsGroup }

    ::= { usdPingAgent 1 }

END
