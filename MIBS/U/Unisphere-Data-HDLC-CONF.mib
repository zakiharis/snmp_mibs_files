-- *****************************************************************************
-- Unisphere-Data-HDLC-CONF
--
-- SNMP Agent Capabilities definitions for the HDLC MIBs.
--
-- Copyright (c) 2001 Unisphere Networks, Inc.  All rights reserved.
-- *****************************************************************************

Unisphere-Data-HDLC-CONF DEFINITIONS ::= BEGIN

IMPORTS
    MODULE-IDENTITY
        FROM SNMPv2-SMI
    AGENT-CAPABILITIES
        FROM SNMPv2-CONF
    usDataAgents
        FROM Unisphere-Data-Agents
    usdHdlcGroup,
    usdHdlcGroup2,
    usdHdlcGroup3
        FROM Unisphere-Data-HDLC-MIB;

usdHdlcAgent MODULE-IDENTITY
    LAST-UPDATED "200103281417Z"  -- 28-Mar-01 09:17 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the HDLC component of the SNMP
        agent in the Unisphere Routing Switch family of products."
    -- Revision History
    REVISION    "200103281417Z"  -- 28-Mar-01 09:17 AM EST  - RX 3.2
    DESCRIPTION
        "The initial release of this management information module."
    ::= { usDataAgents 18 }

usdHdlcAgentV1 AGENT-CAPABILITIES
    PRODUCT-RELEASE
        "Version 1 of the HDLC component of the Unisphere Routing Switch SNMP
        agent.  This version of the HDLC component was supported in the
        Unisphere RX 1.0 system release."
    STATUS      obsolete
    DESCRIPTION
        "The MIB supported by the SNMP agent for the HDLC application in the
        Unisphere Routing Switch.  These capabilities became obsolete when
        rsHdlcIfDataPolarity was added."

    SUPPORTS        Unisphere-Data-HDLC-MIB
        INCLUDES  { usdHdlcGroup }

    ::= { usdHdlcAgent 1 }

usdHdlcAgentV2 AGENT-CAPABILITIES
    PRODUCT-RELEASE
        "Version 2 of the HDLC component of the Unisphere Routing Switch SNMP
        agent.  This version of the HDLC component was supported in the
        Unisphere RX 1.1 thru 3.0 system releases."
    STATUS      current
    DESCRIPTION
        "The MIB supported by the SNMP agent for the HDLC application in the
        Unisphere Routing Switch.  These capabilities became obsolete when
        more objects were added."

    SUPPORTS        Unisphere-Data-HDLC-MIB
        INCLUDES  { usdHdlcGroup2 }

    ::= { usdHdlcAgent 2 }

usdHdlcAgentV3 AGENT-CAPABILITIES
    PRODUCT-RELEASE
        "Version 3 of the HDLC component of the Unisphere Routing Switch SNMP
        agent.  This version of the HDLC component is supported in the Unisphere
        RX 3.1 and subsequent system releases."
    STATUS      current
    DESCRIPTION
        "The MIB supported by the SNMP agent for the HDLC application in the
        Unisphere Routing Switch."

    SUPPORTS        Unisphere-Data-HDLC-MIB
        INCLUDES  { usdHdlcGroup3 }

    ::= { usdHdlcAgent 3 }

END
