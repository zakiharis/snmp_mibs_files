-- *****************************************************************************
-- Unisphere-Data-SUBSCRIBER-MIB
--
-- Unisphere Networks Enterprise MIB
--   Subscriber MIB
--
-- Copyright (c) 2000, 2002 Unisphere Networks, Inc.  All Rights Reserved.
-- *****************************************************************************

Unisphere-Data-SUBSCRIBER-MIB DEFINITIONS ::= BEGIN

IMPORTS
    MODULE-IDENTITY, OBJECT-TYPE
        FROM SNMPv2-SMI
    TEXTUAL-CONVENTION, DisplayString
        FROM SNMPv2-TC
    MODULE-COMPLIANCE, OBJECT-GROUP
        FROM SNMPv2-CONF
    InterfaceIndex
        FROM IF-MIB
    usDataMibs
        FROM Unisphere-Data-MIBs
    UsdEnable
        FROM Unisphere-Data-TC;

usdSubscriberMIB MODULE-IDENTITY
    LAST-UPDATED "200205101953Z"  -- 10-May-02 03:53 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Subscriber MIB for the Unisphere Networks enterprise."
    -- Revision History
    REVISION    "200205101953Z"  -- 10-May-02 03:53 PM EDT  - RX 4.0
    DESCRIPTION
        "Added local authentication support."
    REVISION    "200011160000Z"  -- 16-Nov-00               - RX 3.0
    DESCRIPTION
        "Initial version of this MIB module."
    ::= { usDataMibs 49 }


-- +++++++++++++++++++++++++++++++++++++++++++++++++++++++++++++++++++++++++++++
-- Textual conventions
-- +++++++++++++++++++++++++++++++++++++++++++++++++++++++++++++++++++++++++++++
UsdSubscrEncaps ::= TEXTUAL-CONVENTION
    STATUS      current
    DESCRIPTION
        "Encapsulated protocol type."
    SYNTAX      INTEGER {
                    ip(0),
                    bridgedEthernet(19) }


-- +++++++++++++++++++++++++++++++++++++++++++++++++++++++++++++++++++++++++++++
-- Managed object groups
-- +++++++++++++++++++++++++++++++++++++++++++++++++++++++++++++++++++++++++++++

usdSubscrObjects        OBJECT IDENTIFIER ::= {usdSubscriberMIB 1}

-- Functional groups

usdSubscrLocal          OBJECT IDENTIFIER ::= {usdSubscrObjects 1}

-- +++++++++++++++++++++++++++++++++++++++++++++++++++++++++++++++++++++++++++++
-- Managed objects
-- +++++++++++++++++++++++++++++++++++++++++++++++++++++++++++++++++++++++++++++
usdSubscrLocalTable OBJECT-TYPE
    SYNTAX      SEQUENCE OF UsdSubscrLocalEntry
    MAX-ACCESS  not-accessible
    STATUS      current
    DESCRIPTION
        "Permits local configuration associating a remote subscriber's identity
        with a local interface, for use in circumstances where the remote
        subscriber's identity cannot be queried directly (e.g. dynamic IPoA
        operation)."
    ::= { usdSubscrLocal 1 }

usdSubscrLocalEntry OBJECT-TYPE
    SYNTAX      UsdSubscrLocalEntry
    MAX-ACCESS  not-accessible
    STATUS      current
    DESCRIPTION
        "Local configuration associating a remote subscriber's identity with a
        local interface."
    INDEX     { usdSubscrLocalIfIndex,
                usdSubscrLocalEncaps }
    ::= { usdSubscrLocalTable 1 }

UsdSubscrLocalEntry ::= SEQUENCE {
    usdSubscrLocalIfIndex           InterfaceIndex,
    usdSubscrLocalEncaps            UsdSubscrEncaps,
    usdSubscrLocalControl           INTEGER,
    usdSubscrLocalNamePrefix        UsdEnable,
    usdSubscrLocalName              DisplayString,
    usdSubscrLocalPasswordPrefix    UsdEnable,
    usdSubscrLocalPassword          DisplayString,
    usdSubscrLocalDomain            DisplayString,
    usdSubscrLocalAuthentication    UsdEnable }

usdSubscrLocalIfIndex OBJECT-TYPE
    SYNTAX      InterfaceIndex
    MAX-ACCESS  not-accessible
    STATUS      current
    DESCRIPTION
        "The ifIndex of the interface to which this subscriber information
        applies."
    ::= { usdSubscrLocalEntry 1 }

usdSubscrLocalEncaps OBJECT-TYPE
    SYNTAX      UsdSubscrEncaps
    MAX-ACCESS  not-accessible
    STATUS      current
    DESCRIPTION
        "The incoming data encapsulation to which this subscriber information
        applies.  An interface may have a unique subscriber identity configured
        for each incoming data encapsulation it supports."
    ::= { usdSubscrLocalEntry 2 }

usdSubscrLocalControl OBJECT-TYPE
    SYNTAX      INTEGER {
                    ok(0),
                    clear(1) }
    MAX-ACCESS  read-write
    STATUS      current
    DESCRIPTION
        "When set to clear(1), causes the subscriber information in this entry
        to be cleared.  When set to ok(0), there is no effect and subscriber
        information is unchanged.

        When read, always returns a value of ok(0).

        No other object in this entry can be set simultaneously, otherwise an
        InconsistentValue error is reported."
    ::= { usdSubscrLocalEntry 3 }

usdSubscrLocalNamePrefix OBJECT-TYPE
    SYNTAX      UsdEnable
    MAX-ACCESS  read-write
    STATUS      current
    DESCRIPTION
        "If enabled, indicates whether the value of usdSubscrLocalName is a
        prefix rather than a full name."
    ::= { usdSubscrLocalEntry 4 }

usdSubscrLocalName OBJECT-TYPE
    SYNTAX      DisplayString (SIZE(0..31))
    MAX-ACCESS  read-write
    STATUS      current
    DESCRIPTION
        "The subscriber's name.

        If usdSubscrLocalNamePrefix has the value 'enabled', the value of this
        object serves as the prefix of a full subscriber name.  The full name is
        constructed by appending local geographic information (slot, port, etc.)
        that uniquely distinguishes the subscriber."
    ::= { usdSubscrLocalEntry 5 }

usdSubscrLocalPasswordPrefix OBJECT-TYPE
    SYNTAX      UsdEnable
    MAX-ACCESS  read-write
    STATUS      current
    DESCRIPTION
        "If enabled, indicates whether the value of usdSubscrLocalPassword prefix
        rather than a full password."
    ::= { usdSubscrLocalEntry 6 }

usdSubscrLocalPassword OBJECT-TYPE
    SYNTAX      DisplayString (SIZE(0..31))
    MAX-ACCESS  read-write
    STATUS      current
    DESCRIPTION
        "The subscriber's password.

        If usdSubscrLocalPasswordPrefix has the value 'enabled', the value of
        this object serves as the prefix of a full subscriber password.  The
        full password is constructed by appending local geographic information
        (slot, port, etc.) that uniquely distinguishes the subscriber."
    ::= { usdSubscrLocalEntry 7 }

usdSubscrLocalDomain OBJECT-TYPE
    SYNTAX      DisplayString (SIZE(0..31))
    MAX-ACCESS  read-write
    STATUS      current
    DESCRIPTION
        "The subscriber's domain."
    ::= { usdSubscrLocalEntry 8 }

usdSubscrLocalAuthentication OBJECT-TYPE
    SYNTAX      UsdEnable
    MAX-ACCESS  read-write
    STATUS      current
    DESCRIPTION
        "When enabled, the interface performs authentication with RADIUS server
        using the configured subscriber information and associated with the
        incoming data encapsulation (usdSubscriberLocalEncaps)."
    DEFVAL    { enable }
    ::= { usdSubscrLocalEntry 9 }


-- +++++++++++++++++++++++++++++++++++++++++++++++++++++++++++++++++++++++++++++
-- Conformance information
-- +++++++++++++++++++++++++++++++++++++++++++++++++++++++++++++++++++++++++++++
usdSubscriberMIBConformance
             OBJECT IDENTIFIER ::= { usdSubscriberMIB 4 }
usdSubscriberMIBCompliances
             OBJECT IDENTIFIER ::= { usdSubscriberMIBConformance 1 }
usdSubscriberMIBGroups
             OBJECT IDENTIFIER ::= { usdSubscriberMIBConformance 2 }

--
-- compliance statements
--
usdSubscriberCompliance MODULE-COMPLIANCE
    STATUS      obsolete
    DESCRIPTION
        "Obsolete compliance statement for systems supporting subscriber
        operation.  This statement became obsolete when local authentication
        support was added."
    MODULE   -- this module
        MANDATORY-GROUPS {
            usdSubscriberLocalGroup }
    ::= { usdSubscriberMIBCompliances 1 }

usdSubscriberCompliance2 MODULE-COMPLIANCE
    STATUS      current
    DESCRIPTION
        "The compliance statement for systems supporting subscriber operation."
    MODULE  -- this module
        MANDATORY-GROUPS { usdSubscriberLocalGroup2 }
    ::= { usdSubscriberMIBCompliances 2 }

--
-- units of conformance
--
usdSubscriberLocalGroup OBJECT-GROUP
    OBJECTS {
        usdSubscrLocalControl,
        usdSubscrLocalNamePrefix,
        usdSubscrLocalName,
        usdSubscrLocalPasswordPrefix,
        usdSubscrLocalPassword,
        usdSubscrLocalDomain }
    STATUS      obsolete
    DESCRIPTION
        "Obsolete basic collection of objects providing management of
        locally-configured subscriber identities in a Unisphere product.  This
        group became obsolete when local authentication support was added."
    ::= { usdSubscriberMIBGroups 1 }

usdSubscriberLocalGroup2 OBJECT-GROUP
    OBJECTS {
        usdSubscrLocalControl,
        usdSubscrLocalNamePrefix,
        usdSubscrLocalName,
        usdSubscrLocalPasswordPrefix,
        usdSubscrLocalPassword,
        usdSubscrLocalDomain,
        usdSubscrLocalAuthentication }
    STATUS      current
    DESCRIPTION
        "The basic collection of objects providing management of
        locally-configured subscriber identities in a Unisphere product."
    ::= { usdSubscriberMIBGroups 2 }

END
