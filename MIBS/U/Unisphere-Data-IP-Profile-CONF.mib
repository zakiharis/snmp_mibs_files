-- *****************************************************************************
-- Unisphere-Data-IP-Profile-CONF
--
-- SNMP Agent Capabilities definitions for the IP Profile MIB.
--
-- Copyright (c) 2001 Unisphere Networks, Inc.  All rights reserved.
-- *****************************************************************************

Unisphere-Data-IP-Profile-CONF DEFINITIONS ::= BEGIN

IMPORTS
    MODULE-IDENTITY
        FROM SNMPv2-SMI
    AGENT-CAPABILITIES
        FROM SNMPv2-CONF
    usdProfileAgents
        FROM Unisphere-Data-Agents
    usdIpProfileGroup, usdIpProfileGroup1, usdIpProfileGroup2,
    usdIpProfileDeprecatedGroup, usdIpProfileRowStatus, usdIpProfileRouterName,
    usdIpProfileIpAddr, usdIpProfileIpMask, usdIpProfileDirectedBcastEnable,
    usdIpProfileIcmpRedirectEnable, usdIpProfileAccessRoute, usdIpProfileMtu,
    usdIpProfileLoopback, usdIpProfileSetMap, usdIpProfileSrcAddrValidEnable
        FROM Unisphere-Data-IP-PROFILE-MIB;

usdIpProfileAgent MODULE-IDENTITY
    LAST-UPDATED "200103282143Z"  -- 28-Mar-01 04:43 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the IP Profile Manager component
        of the SNMP agent in the Unisphere Routing Switch family of products."
    -- Revision History
    REVISION    "200103282143Z"  -- 28-Mar-01 04:43 PM EST  - RX 3.2
    DESCRIPTION
        "The initial release of this management information module."
    ::= { usdProfileAgents 2 }

usdIpProfileAgentV1 AGENT-CAPABILITIES
    PRODUCT-RELEASE
        "Version 1 of the IP Profile component of the Unisphere Routing Switch
        SNMP agent.  This version of the IP Profile Manager component was
        supported in the Unisphere RX 1.x system releases."
    STATUS      obsolete
    DESCRIPTION
        "The MIB supported by the SNMP agent for the IP Profile Manager
        application in the Unisphere Routing Switch.  These capabilities became
        obsolete when the profile loopback object changed."
    SUPPORTS        Unisphere-Data-IP-PROFILE-MIB
        INCLUDES  { usdIpProfileGroup }
    ::= { usdIpProfileAgent 1 }                                        -- RX 1.1

usdIpProfileAgentV2 AGENT-CAPABILITIES
    PRODUCT-RELEASE
        "Version 2 of the IP Profile component of the Unisphere Routing Switch
        SNMP agent.  This version of the IP Profile Manager component was
        supported in the Unisphere RX 2.x system releases."
    STATUS      obsolete
    DESCRIPTION
        "The MIB supported by the SNMP agent for the IP Profile Manager
        application in the Unisphere Routing Switch.  These capabilities became
        obsolete when rsIpProfileRowStatus was deprecate and the
        rsIpProfileSetMap and rsIpProfileSrcAddrValidEnable objects were added."
    SUPPORTS        Unisphere-Data-IP-PROFILE-MIB
        INCLUDES  { usdIpProfileGroup1 }
    ::= { usdIpProfileAgent 2 }                                        -- RX 2.0

usdIpProfileAgentV3 AGENT-CAPABILITIES
    PRODUCT-RELEASE
        "Version 3 of the IP Profile component of the Unisphere Routing Switch
        SNMP agent.  This version of the IP Profile Manager component is
        supported in the Unisphere RX 3.0 and subsequent system releases."
    STATUS      current
    DESCRIPTION
        "The MIB supported by the SNMP agent for the IP Profile Manager
        application in the Unisphere Routing Switch."

    SUPPORTS        Unisphere-Data-IP-PROFILE-MIB
        INCLUDES  {
            usdIpProfileGroup2,
            usdIpProfileDeprecatedGroup }
        VARIATION   usdIpProfileRowStatus
            ACCESS      read-only
            DESCRIPTION
                "Entries in the usdIpProfileTable cannot be created via SNMP in
                this agent."
        VARIATION   usdIpProfileRouterName
            ACCESS      read-write
            DESCRIPTION
                "Entries in the usdIpProfileTable cannot be created via SNMP in
                this agent."
        VARIATION   usdIpProfileIpAddr
            ACCESS      read-write
            DESCRIPTION
                "Entries in the usdIpProfileTable cannot be created via SNMP in
                this agent."
        VARIATION   usdIpProfileIpMask
            ACCESS      read-write
            DESCRIPTION
                "Entries in the usdIpProfileTable cannot be created via SNMP in
                this agent."
        VARIATION   usdIpProfileDirectedBcastEnable
            ACCESS      read-write
            DESCRIPTION
                "Entries in the usdIpProfileTable cannot be created via SNMP in
                this agent."
        VARIATION   usdIpProfileIcmpRedirectEnable
            ACCESS      read-write
            DESCRIPTION
                "Entries in the usdIpProfileTable cannot be created via SNMP in
                this agent."
        VARIATION   usdIpProfileAccessRoute
            ACCESS      read-write
            DESCRIPTION
                "Entries in the usdIpProfileTable cannot be created via SNMP in
                this agent."
        VARIATION   usdIpProfileMtu
            ACCESS      read-write
            DESCRIPTION
                "Entries in the usdIpProfileTable cannot be created via SNMP in
                this agent."
        VARIATION   usdIpProfileLoopback
            ACCESS      read-write
            DESCRIPTION
                "Entries in the usdIpProfileTable cannot be created via SNMP in
                this agent."
        VARIATION   usdIpProfileSetMap
            ACCESS      read-write
            DESCRIPTION
                "Entries in the usdIpProfileTable cannot be created via SNMP in
                this agent."
        VARIATION   usdIpProfileSrcAddrValidEnable
            ACCESS      read-write
            DESCRIPTION
                "Entries in the usdIpProfileTable cannot be created via SNMP in
                this agent."
    ::= { usdIpProfileAgent 3 }                                        -- RX 3.0


END
