-- *****************************************************************************
-- Unisphere-Data-COPS-CONF
--
-- SNMP Agent Capabilities definitions for the COPS MIB.
--
-- Copyright (c) 2001, 2002 Unisphere Networks, Inc.  All rights reserved.
-- *****************************************************************************

Unisphere-Data-COPS-CONF DEFINITIONS ::= BEGIN

IMPORTS
    MODULE-IDENTITY
        FROM SNMPv2-SMI
    AGENT-CAPABILITIES
        FROM SNMPv2-CONF
    usDataAgents
        FROM Unisphere-Data-Agents
    usdCopsProtocolGroup, usdCopsProtocolGroup2
        FROM Unisphere-Data-COPS-MIB;

usdCopsAgent MODULE-IDENTITY
    LAST-UPDATED "200201141936Z"  -- 14-Jan-02 02:36 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Common Open Policy Service
        (COPS) Protocol management component of the SNMP agent in the Unisphere
        Routing Switch family of products."
    -- Revision History
    REVISION    "200201141936Z"  -- 14-Jan-02 02:36 PM EST  - RX 4.0
    DESCRIPTION
        "Added support for the local address and transport router name objects."
    REVISION    "200103272245Z"  -- 27-Mar-01 05:45 PM EST  - RX 3.2
    DESCRIPTION
        "The initial release of this management information module."
    ::= { usDataAgents 7 }

usdCopsAgentV1 AGENT-CAPABILITIES
    PRODUCT-RELEASE
        "Version 1 of the COPS component of the Unisphere Routing Switch SNMP
        agent.  This version of the COPS component was supported in the
        Unisphere RX 2.x and 3.x system releases."
    STATUS      current
    DESCRIPTION
        "The MIB supported by the SNMP agent for the COPS application in the
        Unisphere Routing Switch.  These capabilities became obsolete when the
        local address and transport router name objects were add."
    SUPPORTS    Unisphere-Data-COPS-MIB
        INCLUDES {
            usdCopsProtocolGroup }
    ::= { usdCopsAgent 1 }

usdCopsAgentV2 AGENT-CAPABILITIES
    PRODUCT-RELEASE
        "Version 2 of the COPS component of the Unisphere Routing Switch SNMP
        agent.  This version of the COPS component is supported in the Unisphere
        RX 4.0 and subsequent system releases."
    STATUS      current
    DESCRIPTION
        "The MIB supported by the SNMP agent for the COPS application in the
        Unisphere Routing Switch."
    SUPPORTS    Unisphere-Data-COPS-MIB
        INCLUDES {
            usdCopsProtocolGroup2 }
    ::= { usdCopsAgent 2 }

END
