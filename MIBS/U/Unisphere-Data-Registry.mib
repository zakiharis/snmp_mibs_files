-- *****************************************************************************
-- Unisphere-Data-Registry
--
-- Unisphere Networks enterprise SNMP MIB.
-- Registry for the Data communications family of products.
--
-- Copyright (c) 2001 Unisphere Networks, Inc.  All Rights Reserved.
-- *****************************************************************************

Unisphere-Data-Registry DEFINITIONS ::= BEGIN

IMPORTS
    MODULE-IDENTITY, OBJECT-IDENTITY
        FROM SNMPv2-SMI
    usAdmin
        FROM Unisphere-SMI;

usDataAdmin  MODULE-IDENTITY
    LAST-UPDATED "200109251525Z"  -- 25-Sep-01 11:25 AM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "Administratively assigned object identifiers for Unisphere Networks
        data communications products."
    -- Revision History
    REVISION    "200109251525Z"  -- 25-Sep-01 11:25 AM EDT  - RX 3.3
    DESCRIPTION
        "Change the name of the MRX."
    REVISION    "200106012118Z"  -- 01-Jun-01 05:18 PM EDT  - RX 3.0
    DESCRIPTION
        "Initial version of this SNMP management information module."
    ::= { usAdmin 2 }

-- +++++++++++++++++++++++++++++++++++++++++++++++++++++++++++++++++++++++++++++
-- Object identities for product family registries.
-- +++++++++++++++++++++++++++++++++++++++++++++++++++++++++++++++++++++++++++++

usDataRegistry OBJECT-IDENTITY
    STATUS      current
    DESCRIPTION
        "The root for administratively assigned object identifiers for Unisphere
        Networks Data cross-product objects."
    ::= { usDataAdmin 1 }

usdErxRegistry OBJECT IDENTIFIER
--  STATUS      current
--  DESCRIPTION
--      "The root for administratively assigned object identifiers for Unisphere
--      Networks Edge Routing Switch (ERX) product family."
--  REFERENCE
--      "Actual values are defined in the Unisphere-Data-ERX-Registry module (in
--      the usErxRegistry.mi2 file)."
    ::= { usDataAdmin 2 }

usdMrxRegistry OBJECT IDENTIFIER
--  STATUS      current
--  DESCRIPTION
--      "The root for administratively assigned object identifiers for Unisphere
--      Networks MRX Routing Switch product family."
--  REFERENCE
--      "Actual values are defined in the Unisphere-Data-MRX-Registry module (in
--      the usMrxRegistry.mi2 file)."
    ::= { usDataAdmin 3 }


-- +++++++++++++++++++++++++++++++++++++++++++++++++++++++++++++++++++++++++++++
--  Cross-product physical entity identifiers.
--  The OID values under usDataEntPhysicalType are used by the SNMP agent in the
--  Unisphere Networks Data products as the AutonomousType values for the
--  entPhysicalVendorType varbinds for objects in the entPhysicalTable.
-- +++++++++++++++++++++++++++++++++++++++++++++++++++++++++++++++++++++++++++++

usDataEntPhysicalType
    OBJECT IDENTIFIER ::= { usDataRegistry 1 }

--
-- PCMCIA Flash Cards
--
usdPcmciaFlashCard  OBJECT-IDENTITY
    STATUS      current
    DESCRIPTION
        "The vendor type id for a standard PCMCIA flash card."
    ::= { usDataEntPhysicalType 1 }

usd85MegT2FlashCard  OBJECT-IDENTITY
    STATUS      current
    DESCRIPTION
        "The vendor type id for an 85 Megabyte Type II ATA PCMCIA flash card
        (Product Code: PCM-85)."
    ::= { usdPcmciaFlashCard 1 }

usd220MegT2FlashCard  OBJECT-IDENTITY
    STATUS      current
    DESCRIPTION
        "The vendor type id for a 220 Megabyte Type II ATA PCMCIA flash card
        (Product Code: FLASH-220M)."
    ::= { usdPcmciaFlashCard 2 }


-- +++++++++++++++++++++++++++++++++++++++++++++++++++++++++++++++++++++++++++++
--  The registration node (point) for Unisphere Traceroute implementation types.
--  See DISMAN-TRACEROUTE-MIB.traceRouteCtlType (RFC2925) for how this object is
--  used.
-- +++++++++++++++++++++++++++++++++++++++++++++++++++++++++++++++++++++++++++++

usdTraceRouteImplementationTypes
    OBJECT IDENTIFIER ::= { usDataRegistry 2 }

usdTraceRouteUsingIcmpProbe OBJECT-IDENTITY
    STATUS      current
    DESCRIPTION
        "Indicates that an implementation is using ICMP probes to perform the
        trace-route operation."
    ::= { usdTraceRouteImplementationTypes 1 }

END
