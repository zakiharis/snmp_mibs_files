-- *****************************************************************
-- Unisphere-Data-FRACTIONAL-T1-MIB
--
-- Unisphere Networks Inc. Enterprise MIB
-- Fractional T1 MIB
--
-- Copyright (c) 1998, 1999 Redstone Communications, Incorporated.
-- Copyright (c) 1999, 2002 Unisphere Networks, Incorporated.
-- All Rights Reserved.
-- *****************************************************************

Unisphere-Data-FRACTIONAL-T1-MIB DEFINITIONS ::= BEGIN

IMPORTS
    MODULE-IDENTITY, OBJECT-TYPE
        FROM SNMPv2-SMI

    RowStatus
        FROM SNMPv2-TC

    MODULE-COMPLIANCE, OBJECT-GROUP  
        FROM SNMPv2-CONF

    InterfaceIndex, InterfaceIndexOrZero
        FROM IF-MIB

    usDataMibs
        FROM Unisphere-Data-MIBs

    UsdNextIfIndex, UsdTimeSlotMap
        FROM Unisphere-Data-TC;


usdFt1MIB  MODULE-IDENTITY
    LAST-UPDATED "200009261730Z" -- 26-Sep-00 1:50 PM EDT
    ORGANIZATION "Unisphere Networks, Inc."
    CONTACT-INFO
        "       Unisphere Networks, Inc.
        Postal: 10 Technology Park Drive
                Westford MA  01886
                USA
        Tel:    +1 978 589 5800
        Email:  mib@UnisphereNetworks.com"
    DESCRIPTION
        "The Fractional T1 MIB for the Unisphere Networks Inc. enterprise."
    -- Revision History
    REVISION      "200009261730Z" -- 26-Sep-00 1:50 PM EDT  kwc
    DESCRIPTION
        "Make it SMIv2 conformant."
    REVISION      "9907140000Z" -- 14-Jul-99
    DESCRIPTION
        "Obsoleted usdFt1IfDataPolarity and updated corresponding compliances."
    REVISION      "9811130000Z" -- 13-Nov-98
    DESCRIPTION
        "Initial version of this MIB module."
    ::= { usDataMibs 6 }

-- ++++++++++++++++++++++++++++++++++++++++++++++++++++++++++++++++++++++
-- Textual conventions
-- ++++++++++++++++++++++++++++++++++++++++++++++++++++++++++++++++++++++

-- No textual conventions are defined in this MIB



-- ++++++++++++++++++++++++++++++++++++++++++++++++++++++++++++++++++++++
-- Managed objects
-- ++++++++++++++++++++++++++++++++++++++++++++++++++++++++++++++++++++++

usdFt1Objects     OBJECT IDENTIFIER ::= { usdFt1MIB 1 }

-- 
-- This MIB contains managed objects for Fractional T1 arrangements.
-- Management objects are provided to query for an available
-- interface index, and to create/delete interfaces of this type.
-- Creating/deleting this interface type using this MIB has
-- the side effect of creating/deleting corresponding entries
-- in the Interface MIB ifTable/ifXTable, and in the Unisphere
-- Enterprise Interface MIB usdIfTable.
--



-- //////////////////////////////////////////////////////////////////////
--
-- Fractional T1 Interfaces
--
-- //////////////////////////////////////////////////////////////////////

--
-- IfIndex selection for creating new FT1 interfaces
--

usdFt1NextIfIndex OBJECT-TYPE
    SYNTAX      UsdNextIfIndex
    MAX-ACCESS  read-only
    STATUS      current
    DESCRIPTION
        "Coordinate ifIndex value allocation for entries
        in usdFt1IfTable.

        A GET of this object returns the next available ifIndex 
        value to be used to create an entry in the associated
        interface table; or zero, if no valid ifIndex value is
        available. This object also returns a value of zero when 
        it is the lexicographic successor of a varbind presented 
        in an SNMP GETNEXT or GETBULK request, for which circumstance
        it is assumed that ifIndex allocation is unintended.

        Successive GETs will typically return different
        values, thus avoiding collisions among cooperating
        management clients seeking to create table entries
        simultaneously.
        "
    ::= { usdFt1Objects 1 }

--
-- The FT1 Interface Table
--

usdFt1IfTable OBJECT-TYPE
    SYNTAX      SEQUENCE OF UsdFt1IfEntry
    MAX-ACCESS  not-accessible
    STATUS      current
    DESCRIPTION
        "This table contains entries for FT1 interfaces present in the system."
    ::= { usdFt1Objects 2 }

usdFt1IfEntry OBJECT-TYPE
    SYNTAX      UsdFt1IfEntry
    MAX-ACCESS  not-accessible
    STATUS      current
    DESCRIPTION
        "Each entry describes the characteristics of an FT1 interface. 
        Creating/deleting entries in this table causes corresponding 
        entries for be created /deleted in ifTable/ifXTable/usdIfTable."
    INDEX   { usdFt1IfIndex }
    ::= { usdFt1IfTable 1 }

UsdFt1IfEntry ::= SEQUENCE {
    usdFt1IfIndex
        InterfaceIndex,
    usdFt1IfRowStatus
        RowStatus,
    usdFt1IfLowerIfIndex
        InterfaceIndexOrZero,
    usdFt1IfTimeSlotMap
        UsdTimeSlotMap,
    usdFt1IfTimeSlotRate
        INTEGER,
    usdFt1IfDataPolarity
        INTEGER,
    usdFt1IfLoopbackConfig
        INTEGER
    }


usdFt1IfIndex OBJECT-TYPE
    SYNTAX      InterfaceIndex
    MAX-ACCESS  not-accessible
    STATUS      current
    DESCRIPTION
        "The ifIndex of the FT1 interface. When 
        creating entries in this table, suitable values
        for this object are determined by reading
        usdFt1NextIfIndex."
    ::= { usdFt1IfEntry 1 }

usdFt1IfRowStatus OBJECT-TYPE
    SYNTAX      RowStatus
    MAX-ACCESS  read-create
    STATUS      current
    DESCRIPTION
        "Controls creation/deletion of entries in this table
        according to the RowStatus textual convention, 
        constrained to support the following values only:

            createAndGo
            destroy
            
        To create an entry in this table, the following 
        entry objects MUST be explicitly configured:

            usdFt1IfRowStatus
            usdFt1IfLowerIfIndex
            usdFt1IfTimeSlotMap

        In addition, when creating an entry the following
        conditions must hold:

            A value for usdFt1IfIndex must have been determined
            previously, by reading usdFt1NextIfIndex. 

            The DS1 interface identified by usdFt1IfLowerIfIndex
            must exist.

            The DS0s specified in usdFt1IfTimeSlotMap must be 
            available (unallocated) on the DS1 interface
            identified by usdFt1IfLowerIfIndex.

        A corresponding entry in ifTable/ifXTable/usdIfTable is 
        created/destroyed as a result of creating/destroying an entry 
        in this table.
        "
    ::= { usdFt1IfEntry 2 }

usdFt1IfLowerIfIndex OBJECT-TYPE
    SYNTAX      InterfaceIndexOrZero
    MAX-ACCESS  read-create
    STATUS      current
    DESCRIPTION
        "The ifIndex of a DS1 interface over which this FT1 interface 
        is to be layered. A value of zero indicates no layering.
        An implementation may choose to require that a nonzero value
        be configured at entry creation."
    ::= { usdFt1IfEntry 3 }

usdFt1IfTimeSlotMap OBJECT-TYPE
    SYNTAX      UsdTimeSlotMap
    MAX-ACCESS  read-create
    STATUS      current
    DESCRIPTION
        "A bitmap representing the DS0s on the underlying DS1 interface
        that have been allocated to this FT1 interface."
    ::= { usdFt1IfEntry 4 }

usdFt1IfTimeSlotRate OBJECT-TYPE
    SYNTAX      INTEGER {
                    nx56kbps(0),
                    nx64kbps(1)
                }
    MAX-ACCESS  read-create
    STATUS      current
    DESCRIPTION
        "Data rate per time slot allocated to this FT1 interface."
    DEFVAL  { nx64kbps }
    ::= { usdFt1IfEntry 5 }

usdFt1IfDataPolarity OBJECT-TYPE
    SYNTAX      INTEGER {
                    normal(0),
                    inverted(1)
                }
    MAX-ACCESS  read-create
    STATUS      obsolete
    DESCRIPTION
        "Polarity of data transmitted on this FT1 interface. Inverted data is
        used for certain line coding configurations to ensure sufficient
        one's density for timing recovery by the remote end."
    DEFVAL  { normal }
    ::= { usdFt1IfEntry 6 }

usdFt1IfLoopbackConfig OBJECT-TYPE
    SYNTAX      INTEGER {
                    noLoop(0),
                    loop(1)
                }
    MAX-ACCESS  read-create
    STATUS      current
    DESCRIPTION
        "Selects loopback configuration. loop(1) causes received data to be 
        looped back out the transmitter."
    DEFVAL  { noLoop }
    ::= { usdFt1IfEntry 7 }


-- ++++++++++++++++++++++++++++++++++++++++++++++++++++++++++++++++++++++
-- Notification control objects
-- ++++++++++++++++++++++++++++++++++++++++++++++++++++++++++++++++++++++

-- No notifications are defined in this MIB. Placeholder follows.

-- usdFt1TrapControl      OBJECT IDENTIFIER ::= { usdFt1MIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdFt1Traps            OBJECT IDENTIFIER ::= { usdFt1MIB 3 }
-- usdFt1TrapPrefix       OBJECT IDENTIFIER ::= { usdFt1Traps 0 }



-- ++++++++++++++++++++++++++++++++++++++++++++++++++++++++++++++++++++++
-- Conformance information
-- ++++++++++++++++++++++++++++++++++++++++++++++++++++++++++++++++++++++

usdFt1Conformance OBJECT IDENTIFIER ::= { usdFt1MIB 4 }
usdFt1Compliances OBJECT IDENTIFIER ::= { usdFt1Conformance 1 }
usdFt1Groups      OBJECT IDENTIFIER ::= { usdFt1Conformance 2 }

-- compliance statements

usdFt1Compliance MODULE-COMPLIANCE
    STATUS  obsolete
    DESCRIPTION
        "The compliance statement for entities that implement the Unisphere FT1
        MIB."
    MODULE  -- this module
        MANDATORY-GROUPS { usdFt1Group }
    ::= { usdFt1Compliances 1 }

usdFt1Compliance2 MODULE-COMPLIANCE
    STATUS  current
    DESCRIPTION
        "The compliance statement for entities that implement the Unisphere FT1
        MIB."
    MODULE  -- this module
        MANDATORY-GROUPS { usdFt1Group2 }
    ::= { usdFt1Compliances 2 }

-- units of conformance

usdFt1Group OBJECT-GROUP
    OBJECTS {
        usdFt1NextIfIndex,

        usdFt1IfRowStatus,
        usdFt1IfLowerIfIndex,
        usdFt1IfTimeSlotMap,
        usdFt1IfTimeSlotRate,
        usdFt1IfDataPolarity,
        usdFt1IfLoopbackConfig
    }
    STATUS  obsolete
    DESCRIPTION
        "A collection of objects providing management of FT1 interfaces
        in a Unisphere product."
    ::= { usdFt1Groups 1 }

usdFt1Group2 OBJECT-GROUP
    OBJECTS {
        usdFt1NextIfIndex,

        usdFt1IfRowStatus,
        usdFt1IfLowerIfIndex,
        usdFt1IfTimeSlotMap,
        usdFt1IfTimeSlotRate,
        usdFt1IfLoopbackConfig
    }
    STATUS  current
    DESCRIPTION
        "A collection of objects providing management of FT1 interfaces
        in a Unisphere product."
    ::= { usdFt1Groups 2 }

END
