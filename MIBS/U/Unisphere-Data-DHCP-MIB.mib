-- *****************************************************************************
-- Unisphere-Data-DHCP-MIB
--
-- Unisphere Networks Enterprise MIB
--   DHCP MIB
--
-- Copyright (c) 1999 Redstone Communications, Incorporated.
-- Copyright (c) 1999, 2002 Unisphere Networks, Incorporated.
-- All Rights Reserved.
-- *****************************************************************************

Unisphere-Data-DHCP-MIB DEFINITIONS ::= BEGIN

IMPORTS
    MODULE-IDENTITY, OBJECT-TYPE, IpAddress, Counter32
        FROM SNMPv2-SMI
    TEXTUAL-CONVENTION, RowStatus, PhysAddress, TruthValue, TimeInterval
        FROM SNMPv2-TC
    MODULE-COMPLIANCE, OBJECT-GROUP
        FROM SNMPv2-CONF
    usDataMibs
        FROM Unisphere-Data-MIBs
    UsdEnable
        FROM Unisphere-Data-TC;

usdDhcpMIB MODULE-IDENTITY
    LAST-UPDATED "200205101927Z"  -- 10-May-02 03:27 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The DHCP MIB for the Unisphere Networks enterprise."
    -- Revision History
    REVISION    "200205101927Z"  -- 10-May-02 03:27 PM EDT  - RX 4.0
    DESCRIPTION
        "Added local server reservation and cable modem support.
         Refined agent info enable into agent circuit ID enable and agent remote
         ID enable."
    REVISION    "200103301809Z"  -- 30-Mar-01 01:09 PM EST  - RX 3.1
    DESCRIPTION
        "Added Local Server support."
    REVISION    "200002031950Z"  --  3-Feb-00  2:50 PM EST  - RX 1.3
    DESCRIPTION
        "Added support for DHCP Proxy Client under usdDhcpProxyClient node.
         Added additional error/discard statistics for DHCP Relay."
    REVISION      "9906010000Z"  --  1-Jun-99               - RX 1.1
    DESCRIPTION
        "Initial version of this MIB module."
    ::= { usDataMibs 22 }


-- +++++++++++++++++++++++++++++++++++++++++++++++++++++++++++++++++++++++++++++
-- Textual conventions
-- +++++++++++++++++++++++++++++++++++++++++++++++++++++++++++++++++++++++++++++
UsdDhcpLocalServerPoolName ::= TEXTUAL-CONVENTION
    DISPLAY-HINT "64a"
    STATUS      current
    DESCRIPTION
        "DHCP Local Server Pool name.  Represents textual information taken from
        the NVT ASCII character set."
    REFERENCE
        "RFC 854: NVT ASCII character set.  See SNMPv2-TC.DisplayString
        DESCRIPTION for a summary."
    SYNTAX      OCTET STRING (SIZE(0..64))

UsdDhcpLocalServerPoolDomainName ::= TEXTUAL-CONVENTION
    DISPLAY-HINT "64a"
    STATUS      current
    DESCRIPTION
        "DHCP Local Server Pool domain name.  Represents textual information
        taken from the NVT ASCII character set."
    REFERENCE
        "RFC 854: NVT ASCII character set.  See SNMPv2-TC.DisplayString
        DESCRIPTION for a summary."
    SYNTAX      OCTET STRING (SIZE(0..64))

UsdDhcpLocalServerPoolNetBiosNodeType ::= TEXTUAL-CONVENTION
    STATUS      current
    DESCRIPTION
        "The set of netbios node types that may be assigned to the DHCP local
         server pool."
    SYNTAX      INTEGER {
                    netBiosNodeTypeNone(1),
                    netBiosNodeTypeBroadcast(2),
                    netBiosNodeTypePeerToPeer(3),
                    netBiosNodeTypeMixed(4),
                    netBiosNodeTypeHybrid(5) }

UsdDhcpLocalServerModeType ::= TEXTUAL-CONVENTION
    STATUS      current
    DESCRIPTION
        "The set of DHCP Local Server operational Mode types."
    SYNTAX      INTEGER {
                    localServerModeTypeEqualAccess(1),
                    localServerModeTypeStandalone(2) }

UsdDhcpLocalServerPhysAddressString ::= TEXTUAL-CONVENTION
    DISPLAY-HINT "48a"
    STATUS      current
    DESCRIPTION
        "DHCP local server MAC address.  Represents the physical address in
        textual form, eg. 00-d0-b7-09-e0-00-00-00-00-00-00-00-00-00-00-00.  Only
        hexidecimal digits (0-9, a-f) and the dash (-) from the NVT ASCII
        character set are valid."
    REFERENCE
        "RFC 854: NVT ASCII character set.  See SNMPv2-TC.DisplayString
        DESCRIPTION for a summary."
    SYNTAX      OCTET STRING (SIZE(0..48))


-- +++++++++++++++++++++++++++++++++++++++++++++++++++++++++++++++++++++++++++++
-- Managed object groups
-- +++++++++++++++++++++++++++++++++++++++++++++++++++++++++++++++++++++++++++++
usdDhcpObjects              OBJECT IDENTIFIER ::= { usdDhcpMIB 1 }
usdDhcpRelay                OBJECT IDENTIFIER ::= { usdDhcpObjects 1 }
usdDhcpProxy                OBJECT IDENTIFIER ::= { usdDhcpObjects 2 }
usdDhcpLocalServerObjects   OBJECT IDENTIFIER ::= { usdDhcpObjects 3 }

-- +++++++++++++++++++++++++++++++++++++++++++++++++++++++++++++++++++++++++++++
-- Managed objects for DHCP Relay
-- +++++++++++++++++++++++++++++++++++++++++++++++++++++++++++++++++++++++++++++
--
-- DHCP Relay Scalars
--
usdDhcpRelayScalars  OBJECT IDENTIFIER ::= { usdDhcpRelay 1 }

usdDhcpRelayAgentInfoEnable OBJECT-TYPE
    SYNTAX      UsdEnable
    MAX-ACCESS  read-write
    STATUS      deprecated
    DESCRIPTION
        "Enable/disable use of the DHCP relay agent information option."
    ::= { usdDhcpRelayScalars 1 }

usdDhcpRelayBadMessages OBJECT-TYPE
    SYNTAX      Counter32
    MAX-ACCESS  read-only
    STATUS      current
    DESCRIPTION
        "Number of DHCP relay messages received by this agent, that were
        discarded because of apparent corruption."
    ::= { usdDhcpRelayScalars 2 }

usdDhcpRelayUnknownMessages OBJECT-TYPE
    SYNTAX      Counter32
    MAX-ACCESS  read-only
    STATUS      current
    DESCRIPTION
        "Number of DHCP relay messages received by this agent, that were
        discarded because they contained information or options not recognized
        by this agent."
    ::= { usdDhcpRelayScalars 3 }

usdDhcpRelayAgentInfoAlreadyPresents OBJECT-TYPE
    SYNTAX      Counter32
    MAX-ACCESS  read-only
    STATUS      current
    DESCRIPTION
        "Number of DHCP requests discarded because they already contained the
        Agent Info option when this agent expected to insert it."
    ::= { usdDhcpRelayScalars 4 }

usdDhcpRelayGatewayAddrSpoofs OBJECT-TYPE
    SYNTAX      Counter32
    MAX-ACCESS  read-only
    STATUS      current
    DESCRIPTION
        "Number of DHCP requests discarded because the gateway IP address field
        already contained this agent's address."
    ::= { usdDhcpRelayScalars 5 }

usdDhcpRelayAgentCircuitIdEnable OBJECT-TYPE
    SYNTAX      UsdEnable
    MAX-ACCESS  read-write
    STATUS      current
    DESCRIPTION
        "Enable/disable use of the DHCP Relay Agent Circuit Id suboption."
    ::= { usdDhcpRelayScalars 6 }

usdDhcpRelayAgentRemoteIdEnable OBJECT-TYPE
    SYNTAX      UsdEnable
    MAX-ACCESS  read-write
    STATUS      current
    DESCRIPTION
        "Enable/disable use of the DHCP Relay Agent Remote Id suboption."
    ::= { usdDhcpRelayScalars 7 }

--
-- DHCP Relay Server Table
--
usdDhcpRelayServerTable OBJECT-TYPE
    SYNTAX      SEQUENCE OF UsdDhcpRelayServerEntry
    MAX-ACCESS  not-accessible
    STATUS      current
    DESCRIPTION
        "The (conceptual) table listing the DHCP Relay servers."
    ::= { usdDhcpRelay 2 }

usdDhcpRelayServerEntry OBJECT-TYPE
    SYNTAX      UsdDhcpRelayServerEntry
    MAX-ACCESS  not-accessible
    STATUS      current
    DESCRIPTION
        "An entry (conceptual row) representing a DHCP Relay server."
    INDEX     { usdDhcpRelayServerAddress }
    ::= { usdDhcpRelayServerTable 1 }

UsdDhcpRelayServerEntry ::= SEQUENCE {
    usdDhcpRelayServerAddress       IpAddress,
    usdDhcpRelayServerRowStatus     RowStatus }

usdDhcpRelayServerAddress OBJECT-TYPE
    SYNTAX      IpAddress
    MAX-ACCESS  not-accessible
    STATUS      current
    DESCRIPTION
        "The IP address of the DHCP server to which DHCP requests received from
        attached DHCP clients are forwarded."
    ::= { usdDhcpRelayServerEntry 1 }

usdDhcpRelayServerRowStatus OBJECT-TYPE
    SYNTAX      RowStatus
    MAX-ACCESS  read-create
    STATUS      current
    DESCRIPTION
        "Supports 'createAndGo' and 'destroy' only."
    ::= { usdDhcpRelayServerEntry 2 }


-- +++++++++++++++++++++++++++++++++++++++++++++++++++++++++++++++++++++++++++++
-- Managed objects for DHCP Proxy
-- +++++++++++++++++++++++++++++++++++++++++++++++++++++++++++++++++++++++++++++
usdDhcpProxyClient   OBJECT IDENTIFIER
    ::= { usdDhcpProxy 1 }
usdDhcpProxyServer   OBJECT IDENTIFIER
    ::= { usdDhcpProxy 2 }    -- reserved for future use

--
-- DHCP Proxy Client Scalars
--
usdDhcpProxyClientScalars  OBJECT IDENTIFIER ::= { usdDhcpProxyClient 1 }

usdDhcpProxyClientUnknownServers OBJECT-TYPE
    SYNTAX      Counter32
    MAX-ACCESS  read-only
    STATUS      current
    DESCRIPTION
        "Total number of DHCP Proxy messages received from servers not listed
        in the usdDhcpProxyClientServerTable."
    ::= { usdDhcpProxyClientScalars 1 }


--
-- DHCP Proxy Client Server Table
--
usdDhcpProxyClientServerTable OBJECT-TYPE
    SYNTAX      SEQUENCE OF UsdDhcpProxyClientServerEntry
    MAX-ACCESS  not-accessible
    STATUS      current
    DESCRIPTION
        "The (conceptual) table listing the DHCP Proxy servers known to the
        client."
    ::= { usdDhcpProxyClient 2 }

usdDhcpProxyClientServerEntry OBJECT-TYPE
    SYNTAX      UsdDhcpProxyClientServerEntry
    MAX-ACCESS  not-accessible
    STATUS      current
    DESCRIPTION
        "An entry (conceptual row) representing a DHCP Proxy server known to the
        client."
    INDEX     { usdDhcpProxyClientServerAddress }
    ::= { usdDhcpProxyClientServerTable 1 }

UsdDhcpProxyClientServerEntry ::= SEQUENCE {
    usdDhcpProxyClientServerAddress         IpAddress,
    usdDhcpProxyClientServerRowStatus       RowStatus,
    usdDhcpProxyClientServerAdminStatus     INTEGER,
    usdDhcpProxyClientServerOperStatus      INTEGER,
    usdDhcpProxyClientServerLeases          Counter32,
    usdDhcpProxyClientServerDiscovers       Counter32,
    usdDhcpProxyClientServerOffers          Counter32,
    usdDhcpProxyClientServerRequests        Counter32,
    usdDhcpProxyClientServerAcks            Counter32,
    usdDhcpProxyClientServerNaks            Counter32,
    usdDhcpProxyClientServerDeclines        Counter32,
    usdDhcpProxyClientServerReleases        Counter32,
    usdDhcpProxyClientServerInforms         Counter32,
    usdDhcpProxyClientServerBadMessages     Counter32,
    usdDhcpProxyClientServerUnknownMessages Counter32 }

usdDhcpProxyClientServerAddress OBJECT-TYPE
    SYNTAX      IpAddress
    MAX-ACCESS  not-accessible
    STATUS      current
    DESCRIPTION
        "The IP address of a DHCP server with which DHCP transactions are
        conducted by this client."
    ::= { usdDhcpProxyClientServerEntry 1 }

usdDhcpProxyClientServerRowStatus OBJECT-TYPE
    SYNTAX      RowStatus
    MAX-ACCESS  read-create
    STATUS      current
    DESCRIPTION
        "Supports 'createAndGo' and 'destroy' only."
    ::= { usdDhcpProxyClientServerEntry 2 }

usdDhcpProxyClientServerAdminStatus OBJECT-TYPE
    SYNTAX      INTEGER {
                    disable(0),
                    drain(1),
                    enable(2) }
    MAX-ACCESS  read-create
    STATUS      current
    DESCRIPTION
        "Permits configuration of the client's operation status with respect
        to this server:
            disable     Bar the client from using this server to obtain new
                        address leases; and cause any leases from that server,
                        that are currently in use by the client, to be released.
            drain       Bar the client from using this server to obtain new
                        address leases; but permit any leases from that server,
                        that are currently in use by the client, to remain in
                        use until they expire naturally.
            enabled     Allow the client to use the server to obtain new address
                        leases.

        Implementations that don't support administrative control of the server
        always report the value of enable(2), and disallow setting this object
        to any other value."
    ::= { usdDhcpProxyClientServerEntry 3 }

usdDhcpProxyClientServerOperStatus OBJECT-TYPE
    SYNTAX      INTEGER {
                    disabled(0),
                    draining(1),
                    enabled(2) }
    MAX-ACCESS  read-only
    STATUS      current
    DESCRIPTION
        "Reports the client's current operation status with respect to this
        server:
            disabled    The client is barred from using this server to obtain
                        new address leases; and any leases from that server,
                        that were in use by the client, have been released.
            draining    The client is barred from using this server to obtain
                        new address leases, but one or more leases from that
                        server, that are in use by the client, will remain in
                        use until they expire naturally.
            enabled     The client may use the server to obtain new address
                        leases, and may have one or more leases currently in
                        use.

        Implementations that don't support administrative control of the server
        always report the value enabled(2)."
    ::= { usdDhcpProxyClientServerEntry 4 }

usdDhcpProxyClientServerLeases OBJECT-TYPE
    SYNTAX      Counter32
    MAX-ACCESS  read-only
    STATUS      current
    DESCRIPTION
        "Total number of address leases granted to the client by this server
        (including those that have expired).  The number of active leases from
        this server is determined by subtracting the value of
        usdDhcpProxyClientServerReleases from the value of this object."
    ::= { usdDhcpProxyClientServerEntry 5 }

usdDhcpProxyClientServerDiscovers OBJECT-TYPE
    SYNTAX      Counter32
    MAX-ACCESS  read-only
    STATUS      current
    DESCRIPTION
        "Number of DHCP Discovers directed (i.e. nonbroadcast) by the client to
        this server."
    ::= { usdDhcpProxyClientServerEntry 6 }

usdDhcpProxyClientServerOffers OBJECT-TYPE
    SYNTAX      Counter32
    MAX-ACCESS  read-only
    STATUS      current
    DESCRIPTION
        "Number of DHCP Offers received by the client from this server."
    ::= { usdDhcpProxyClientServerEntry 7 }

usdDhcpProxyClientServerRequests OBJECT-TYPE
    SYNTAX      Counter32
    MAX-ACCESS  read-only
    STATUS      current
    DESCRIPTION
        "Number of DHCP Requests sent by the client to this server."
    ::= { usdDhcpProxyClientServerEntry 8 }

usdDhcpProxyClientServerAcks OBJECT-TYPE
    SYNTAX      Counter32
    MAX-ACCESS  read-only
    STATUS      current
    DESCRIPTION
        "Number of DHCP ACKS received by the client from this server."
    ::= { usdDhcpProxyClientServerEntry 9 }

usdDhcpProxyClientServerNaks OBJECT-TYPE
    SYNTAX      Counter32
    MAX-ACCESS  read-only
    STATUS      current
    DESCRIPTION
        "Number of DHCP NAKS received by the client from this server."
    ::= { usdDhcpProxyClientServerEntry 10 }

usdDhcpProxyClientServerDeclines OBJECT-TYPE
    SYNTAX      Counter32
    MAX-ACCESS  read-only
    STATUS      current
    DESCRIPTION
        "Number of DHCP Declines sent by the client to this server."
    ::= { usdDhcpProxyClientServerEntry 11 }

usdDhcpProxyClientServerReleases OBJECT-TYPE
    SYNTAX      Counter32
    MAX-ACCESS  read-only
    STATUS      current
    DESCRIPTION
        "Number of DHCP Releases sent by the client to this server."
    ::= { usdDhcpProxyClientServerEntry 12 }

usdDhcpProxyClientServerInforms OBJECT-TYPE
    SYNTAX      Counter32
    MAX-ACCESS  read-only
    STATUS      current
    DESCRIPTION
        "Number of DHCP Informs sent by the client to this server."
    ::= { usdDhcpProxyClientServerEntry 13 }

usdDhcpProxyClientServerBadMessages OBJECT-TYPE
    SYNTAX      Counter32
    MAX-ACCESS  read-only
    STATUS      current
    DESCRIPTION
        "Number of DHCP Proxy messages received by the client from this server,
        that were discarded because of apparent corruption."
    ::= { usdDhcpProxyClientServerEntry 14 }

usdDhcpProxyClientServerUnknownMessages OBJECT-TYPE
    SYNTAX      Counter32
    MAX-ACCESS  read-only
    STATUS      current
    DESCRIPTION
        "Number of DHCP Proxy messages received by the client from this server,
        that were discarded because they contained information or options
        not recognized by the client."
    ::= { usdDhcpProxyClientServerEntry 15 }


-- +++++++++++++++++++++++++++++++++++++++++++++++++++++++++++++++++++++++++++++
-- Managed objects for DHCP Local Server
-- +++++++++++++++++++++++++++++++++++++++++++++++++++++++++++++++++++++++++++++
usdDhcpLocalServerStatistics OBJECT IDENTIFIER
    ::= { usdDhcpLocalServerObjects 1 }
usdDhcpLocalServerBindings   OBJECT IDENTIFIER
    ::= { usdDhcpLocalServerObjects 2 }
usdDhcpLocalServerPool       OBJECT IDENTIFIER
    ::= { usdDhcpLocalServerObjects 3 }
usdDhcpLocalServerAttributes OBJECT IDENTIFIER
    ::= { usdDhcpLocalServerObjects 4 }
usdDhcpLocalServerReserves   OBJECT IDENTIFIER
    ::= { usdDhcpLocalServerObjects 5 }
usdDhcpLocalServerCableModemServers OBJECT IDENTIFIER
    ::= { usdDhcpLocalServerObjects 6 }
usdDhcpLocalServerCableModemStatistics OBJECT IDENTIFIER
    ::= { usdDhcpLocalServerObjects 7 }

-- +++++++++++++++++++++++++++++++++++++++++++++++++++++++++++++++++++++++++++++
-- DHCP Local Server Statistics
-- +++++++++++++++++++++++++++++++++++++++++++++++++++++++++++++++++++++++++++++
usdDhcpLocalServerMemUsage OBJECT-TYPE
    SYNTAX      Counter32
    MAX-ACCESS  read-only
    STATUS      current
    DESCRIPTION
        "The amount (in bytes) of memory currently allocated to this local
        server."
    ::= { usdDhcpLocalServerStatistics 1 }

usdDhcpLocalServerNumBindings OBJECT-TYPE
    SYNTAX      Counter32
    MAX-ACCESS  read-only
    STATUS      current
    DESCRIPTION
        "The number of address bindings maintained by this local server."
    ::= { usdDhcpLocalServerStatistics 2 }

usdDhcpLocalServerRxDiscovers OBJECT-TYPE
    SYNTAX      Counter32
    MAX-ACCESS  read-only
    STATUS      current
    DESCRIPTION
        "The number of discover messages received by this local server."
    ::= { usdDhcpLocalServerStatistics 3 }

usdDhcpLocalServerRxAccepts OBJECT-TYPE
    SYNTAX      Counter32
    MAX-ACCESS  read-only
    STATUS      current
    DESCRIPTION
        "The number of accept messages received by this local server."
    ::= { usdDhcpLocalServerStatistics 4 }

usdDhcpLocalServerRxRenews OBJECT-TYPE
    SYNTAX      Counter32
    MAX-ACCESS  read-only
    STATUS      current
    DESCRIPTION
        "The number of renew messages received by this local server."
    ::= { usdDhcpLocalServerStatistics 5 }

usdDhcpLocalServerRxDeclines OBJECT-TYPE
    SYNTAX      Counter32
    MAX-ACCESS  read-only
    STATUS      current
    DESCRIPTION
        "The number of decline messages received by this local server."
    ::= { usdDhcpLocalServerStatistics 6 }

usdDhcpLocalServerRxReleases OBJECT-TYPE
    SYNTAX      Counter32
    MAX-ACCESS  read-only
    STATUS      current
    DESCRIPTION
        "The number of release messages received by this local server."
    ::= { usdDhcpLocalServerStatistics 7 }

usdDhcpLocalServerRxInforms OBJECT-TYPE
    SYNTAX      Counter32
    MAX-ACCESS  read-only
    STATUS      current
    DESCRIPTION
        "The number of inform messages received by this local server."
    ::= { usdDhcpLocalServerStatistics 8 }

usdDhcpLocalServerTxOffers OBJECT-TYPE
    SYNTAX      Counter32
    MAX-ACCESS  read-only
    STATUS      current
    DESCRIPTION
        "The number of offer messages sent by this local server."
    ::= { usdDhcpLocalServerStatistics 9 }

usdDhcpLocalServerTxAcks OBJECT-TYPE
    SYNTAX      Counter32
    MAX-ACCESS  read-only
    STATUS      current
    DESCRIPTION
        "The number of ack messages sent by this local server."
    ::= { usdDhcpLocalServerStatistics 10 }

usdDhcpLocalServerTxNaks OBJECT-TYPE
    SYNTAX      Counter32
    MAX-ACCESS  read-only
    STATUS      current
    DESCRIPTION
        "The number of nak messages sent by this local server."
    ::= { usdDhcpLocalServerStatistics 11 }

usdDhcpLocalServerUnknownMessages OBJECT-TYPE
    SYNTAX      Counter32
    MAX-ACCESS  read-only
    STATUS      current
    DESCRIPTION
        "The number of unknown messages processed by this local server."
    ::= { usdDhcpLocalServerStatistics 12 }

usdDhcpLocalServerBadMessages OBJECT-TYPE
    SYNTAX      Counter32
    MAX-ACCESS  read-only
    STATUS      current
    DESCRIPTION
        "The number of bad messages processed by this local server."
    ::= { usdDhcpLocalServerStatistics 13 }

usdDhcpLocalServerPacketsIn OBJECT-TYPE
    SYNTAX      Counter32
    MAX-ACCESS  read-only
    STATUS      current
    DESCRIPTION
        "The number of input packets processed by this local server."
    ::= { usdDhcpLocalServerStatistics 14 }

usdDhcpLocalServerPacketsOut OBJECT-TYPE
    SYNTAX      Counter32
    MAX-ACCESS  read-only
    STATUS      current
    DESCRIPTION
        "The number of output packets processed by this local server."
    ::= { usdDhcpLocalServerStatistics 15 }


-- +++++++++++++++++++++++++++++++++++++++++++++++++++++++++++++++++++++++++++++
-- DHCP Local Server Bindings Table
-- +++++++++++++++++++++++++++++++++++++++++++++++++++++++++++++++++++++++++++++
usdDhcpLocalServerBindingsTable OBJECT-TYPE
    SYNTAX      SEQUENCE OF UsdDhcpLocalServerBindingsEntry
    MAX-ACCESS  not-accessible
    STATUS      current
    DESCRIPTION
        "A table of address bindings maintained by this DHCP Local Server."
    ::= { usdDhcpLocalServerBindings 1 }

usdDhcpLocalServerBindingsEntry OBJECT-TYPE
    SYNTAX      UsdDhcpLocalServerBindingsEntry
    MAX-ACCESS  not-accessible
    STATUS      current
    DESCRIPTION
        "An entry (conceptual row) representing an address binding maintained
         by this DHCP Local Server."
    INDEX     { usdDhcpLocalServerBindingsIpAddress }
    ::= { usdDhcpLocalServerBindingsTable 1 }

UsdDhcpLocalServerBindingsEntry ::= SEQUENCE {
    usdDhcpLocalServerBindingsIpAddress     IpAddress,
    usdDhcpLocalServerBindingsPhysAddress   PhysAddress,
    usdDhcpLocalServerBindingsInfinite      TruthValue,
    usdDhcpLocalServerBindingsExpireTime    TimeInterval }

usdDhcpLocalServerBindingsIpAddress OBJECT-TYPE
    SYNTAX      IpAddress
    MAX-ACCESS  not-accessible
    STATUS      current
    DESCRIPTION
        "The IP Address associated with this entry in the bindings table."
    ::= { usdDhcpLocalServerBindingsEntry 1 }

usdDhcpLocalServerBindingsPhysAddress OBJECT-TYPE
    SYNTAX      PhysAddress (SIZE(6))
    MAX-ACCESS  read-only
    STATUS      current
    DESCRIPTION
        "The Physical (MAC) Address associated with this entry in the bindings
        table and corresponding to the IP Address denoted by the table index."
    ::= { usdDhcpLocalServerBindingsEntry 2 }

usdDhcpLocalServerBindingsInfinite OBJECT-TYPE
    SYNTAX      TruthValue
    MAX-ACCESS  read-only
    STATUS      current
    DESCRIPTION
        "If true, then this binding will be maintained indefinitely.
         If false, then this binding will expire in accordance with
         the value of usdDhcpLocalServerBindingsExpireTime."
    ::= { usdDhcpLocalServerBindingsEntry 3 }

usdDhcpLocalServerBindingsExpireTime OBJECT-TYPE
    SYNTAX      TimeInterval
    MAX-ACCESS  read-only
    STATUS      current
    DESCRIPTION
        "If usdDhcpLocalServerBindingsInfinite is false, then this is the time
        remaining prior to expiration of the address binding associated with
        this entry."
    ::= { usdDhcpLocalServerBindingsEntry 4 }


-- +++++++++++++++++++++++++++++++++++++++++++++++++++++++++++++++++++++++++++++
-- DHCP Local Server Pool Table
-- +++++++++++++++++++++++++++++++++++++++++++++++++++++++++++++++++++++++++++++
usdDhcpLocalServerPoolTable OBJECT-TYPE
    SYNTAX      SEQUENCE OF UsdDhcpLocalServerPoolEntry
    MAX-ACCESS  not-accessible
    STATUS      current
    DESCRIPTION
        "A table of address pools associated this DHCP Local Server.  A DHCP
        Local Server may have multiple uniquely-named pools configured; however,
        only a single pool (with the name 'default') may have a network address
        and mask assigned."
    ::= { usdDhcpLocalServerPool 1 }

usdDhcpLocalServerPoolEntry OBJECT-TYPE
    SYNTAX      UsdDhcpLocalServerPoolEntry
    MAX-ACCESS  not-accessible
    STATUS      current
    DESCRIPTION
        "An entry (conceptual row) representing an address pool associated this
        DHCP Local Server."
    INDEX     { usdDhcpLocalServerPoolName }
    ::= { usdDhcpLocalServerPoolTable 1 }

UsdDhcpLocalServerPoolEntry ::= SEQUENCE {
    usdDhcpLocalServerPoolName              UsdDhcpLocalServerPoolName,
    usdDhcpLocalServerPoolDomainName        UsdDhcpLocalServerPoolDomainName,
    usdDhcpLocalServerPoolNetworkIpAddress  IpAddress,
    usdDhcpLocalServerPoolNetworkMask       IpAddress,
    usdDhcpLocalServerPoolNetBiosNodeType   UsdDhcpLocalServerPoolNetBiosNodeType,
    usdDhcpLocalServerPoolLeaseTime         TimeInterval,
    usdDhcpLocalServerPoolPrimaryDnsServer  IpAddress,
    usdDhcpLocalServerPoolSecondaryDnsServer            IpAddress,
    usdDhcpLocalServerPoolPrimaryNetBiosNameServer      IpAddress,
    usdDhcpLocalServerPoolSecondaryNetBiosNameServer    IpAddress,
    usdDhcpLocalServerPoolPrimaryDefaultRouter          IpAddress,
    usdDhcpLocalServerPoolSecondaryDefaultRouter        IpAddress,
    usdDhcpLocalServerPoolLinkName          UsdDhcpLocalServerPoolName,
    usdDhcpLocalServerPoolRowStatus         RowStatus }

usdDhcpLocalServerPoolName OBJECT-TYPE
    SYNTAX      UsdDhcpLocalServerPoolName
    MAX-ACCESS  not-accessible
    STATUS      current
    DESCRIPTION
        "The name of the local server pool to which this entry belongs.  Only an
        entry with the name 'default' may have a network address and mask
        assigned."
    ::= { usdDhcpLocalServerPoolEntry 1 }

usdDhcpLocalServerPoolDomainName OBJECT-TYPE
    SYNTAX      UsdDhcpLocalServerPoolDomainName
    MAX-ACCESS  read-create
    STATUS      current
    DESCRIPTION
        "The domain name assigned to this local server pool.  Modification of
        extant values for this object require that it first be cleared (via set
        to null string) and then modified (via set to new string)."
    DEFVAL    { "" }
    ::= { usdDhcpLocalServerPoolEntry 2 }

usdDhcpLocalServerPoolNetworkIpAddress OBJECT-TYPE
    SYNTAX      IpAddress
    MAX-ACCESS  read-create
    STATUS      current
    DESCRIPTION
        "The IP Address assigned to this local server pool.  This object must be
        set in conjunction with usdDhcpLocalServerPoolNetworkMask.  Modification
        of extant values for this object require that it first be cleared (via
        set to null IP address) and then modified (via set to new IP address).
        Only configurable/valid for entries with the index name
        (usdDhcpLocalServerPoolName) 'default'."
    DEFVAL   { '00000000'H } -- 0.0.0.0
    ::= { usdDhcpLocalServerPoolEntry 3 }

usdDhcpLocalServerPoolNetworkMask OBJECT-TYPE
    SYNTAX      IpAddress
    MAX-ACCESS  read-create
    STATUS      current
    DESCRIPTION
        "The network mask assigned to this local server pool.  This object must
        be set in conjunction with usdDhcpLocalServerPoolNetworkIpAddress.
        Modification of extant values for this object require that it first be
        cleared (via set to null IP mask) and then modified (via set to new IP
        mask).  Only configurable/valid for entries with the index name
        (usdDhcpLocalServerPoolName) 'default'."
    DEFVAL    { '00000000'H } -- 0.0.0.0
    ::= { usdDhcpLocalServerPoolEntry 4 }

usdDhcpLocalServerPoolNetBiosNodeType OBJECT-TYPE
    SYNTAX      UsdDhcpLocalServerPoolNetBiosNodeType
    MAX-ACCESS  read-create
    STATUS      current
    DESCRIPTION
        "The NetBios node type assigned to this local server pool."
    DEFVAL    { netBiosNodeTypeHybrid }
    ::= { usdDhcpLocalServerPoolEntry 5 }

usdDhcpLocalServerPoolLeaseTime OBJECT-TYPE
    SYNTAX      TimeInterval
    MAX-ACCESS  read-create
    STATUS      current
    DESCRIPTION
        "The time interval for address renewal required of a client using the
        address associated with this local server pool entry.  Setting a zero
        value will effect an infinite lease, which in turn is indicated by the
        value -1 returned via a get."
    ::= { usdDhcpLocalServerPoolEntry 6 }

usdDhcpLocalServerPoolPrimaryDnsServer OBJECT-TYPE
    SYNTAX      IpAddress
    MAX-ACCESS  read-create
    STATUS      current
    DESCRIPTION
        "The address of the primary DNS Server associated with this local server
        pool.  This object must be set in conjunction with
        usdDhcpLocalServerPoolSecondaryDnsServer.  Modification of extant values
        for this object require that it first be cleared (via set to null IP
        address) and then modified (via set to new IP address)."
    DEFVAL    { '00000000'H } -- 0.0.0.0
    ::= { usdDhcpLocalServerPoolEntry 7 }

usdDhcpLocalServerPoolSecondaryDnsServer OBJECT-TYPE
    SYNTAX      IpAddress
    MAX-ACCESS  read-create
    STATUS      current
    DESCRIPTION
        "The address of the secondary DNS Server associated with this local
        server pool.  This object must be set in conjunction with
        usdDhcpLocalServerPoolPrimaryDnsServer.  Modification of extant values
        for this object require that it first be cleared (via set to null IP
        address) and then modified (via set to new IP address)."
    DEFVAL    { '00000000'H } -- 0.0.0.0
    ::= { usdDhcpLocalServerPoolEntry 8 }

usdDhcpLocalServerPoolPrimaryNetBiosNameServer OBJECT-TYPE
    SYNTAX      IpAddress
    MAX-ACCESS  read-create
    STATUS      current
    DESCRIPTION
        "The address of the primary NetBios Name Server associated with this
        local server pool.  This object must be set in conjunction with
        usdDhcpLocalServerPoolSecondaryNetBiosNameServer.  Modification of extant
        values for this object require that it first be cleared (via set to null
        IP address) and then modified (via set to new IP address)."
    DEFVAL    { '00000000'H } -- 0.0.0.0
    ::= { usdDhcpLocalServerPoolEntry 9 }

usdDhcpLocalServerPoolSecondaryNetBiosNameServer OBJECT-TYPE
    SYNTAX      IpAddress
    MAX-ACCESS  read-create
    STATUS      current
    DESCRIPTION
        "The address of the secondary NetBios Name Server associated with this
        local server pool.  This object must be set in conjunction with
        usdDhcpLocalServerPoolPrimaryNetBiosNameServer.  Modification of extant
        values for this object require that it first be cleared (via set to null
        IP address) and then modified (via set to new IP address)."
    DEFVAL    { '00000000'H } -- 0.0.0.0
    ::= { usdDhcpLocalServerPoolEntry 10 }

usdDhcpLocalServerPoolPrimaryDefaultRouter OBJECT-TYPE
    SYNTAX      IpAddress
    MAX-ACCESS  read-create
    STATUS      current
    DESCRIPTION
        "The address of the primary Default Router associated with this local
        server pool.  This object must be set in conjunction with
        usdDhcpLocalServerPoolSecondaryDefaultRouter.  Modification of extant
        values for this object require that it first be cleared (via set to null
        IP address) and then modified (via set to new IP address)."
    DEFVAL    { '00000000'H } -- 0.0.0.0
    ::= { usdDhcpLocalServerPoolEntry 11 }

usdDhcpLocalServerPoolSecondaryDefaultRouter OBJECT-TYPE
    SYNTAX      IpAddress
    MAX-ACCESS  read-create
    STATUS      current
    DESCRIPTION
        "The address of the secondary Default Router associated with this local
        server pool.  This object must be set in conjunction with
        usdDhcpLocalServerPoolPrimaryDefaultRouter.  Modification of extant
        values for this object require that it first be cleared (via set to null
        IP address) and then modified (via set to new IP address)."
    DEFVAL    { '00000000'H } -- 0.0.0.0
    ::= { usdDhcpLocalServerPoolEntry 12 }

usdDhcpLocalServerPoolRowStatus OBJECT-TYPE
    SYNTAX      RowStatus
    MAX-ACCESS  read-create
    STATUS      current
    DESCRIPTION
        "Supports 'createAndGo' and 'destroy' only."
    ::= { usdDhcpLocalServerPoolEntry 13 }

usdDhcpLocalServerPoolLinkName OBJECT-TYPE
    SYNTAX      UsdDhcpLocalServerPoolName
    MAX-ACCESS  read-create
    STATUS      current
    DESCRIPTION
        "The name of this local server pool's backup pool."
    DEFVAL    { "" }
    ::= { usdDhcpLocalServerPoolEntry 14 }


-- +++++++++++++++++++++++++++++++++++++++++++++++++++++++++++++++++++++++++++++
-- DHCP Local Server Attributes
-- +++++++++++++++++++++++++++++++++++++++++++++++++++++++++++++++++++++++++++++
usdDhcpLocalServerAttributesMode OBJECT-TYPE
    SYNTAX      UsdDhcpLocalServerModeType
    MAX-ACCESS  read-only
    STATUS      current
    DESCRIPTION
        "An object representing the mode in which the DHCP Local Server is
        operating."
    ::= { usdDhcpLocalServerAttributes 1 }


-- +++++++++++++++++++++++++++++++++++++++++++++++++++++++++++++++++++++++++++++
-- DHCP Local Server Reserves
-- +++++++++++++++++++++++++++++++++++++++++++++++++++++++++++++++++++++++++++++
usdDhcpLocalServerReservesTable OBJECT-TYPE
    SYNTAX      SEQUENCE OF UsdDhcpLocalServerReservesEntry
    MAX-ACCESS  not-accessible
    STATUS      current
    DESCRIPTION
        "A table of pool name, MAC address, and IP address reservation groups
        that are maintained by this DHCP Local Server."
    ::= { usdDhcpLocalServerReserves 1 }

usdDhcpLocalServerReservesEntry OBJECT-TYPE
    SYNTAX      UsdDhcpLocalServerReservesEntry
    MAX-ACCESS  not-accessible
    STATUS      current
    DESCRIPTION
        "An entry (conceptual row) representing an MAC address, IP address, pool
        name reservation maintained by this DHCP Local Server."
    INDEX     { usdDhcpLocalServerReservesEntryIpAddress }
    ::= { usdDhcpLocalServerReservesTable 1 }

UsdDhcpLocalServerReservesEntry ::= SEQUENCE {
    usdDhcpLocalServerReservesEntryIpAddress    IpAddress,
    usdDhcpLocalServerReservesEntryPoolName     UsdDhcpLocalServerPoolName,
    usdDhcpLocalServerReservesEntryPhysAddress
        UsdDhcpLocalServerPhysAddressString,
    usdDhcpLocalServerReservesEntryRowStatus    RowStatus }

usdDhcpLocalServerReservesEntryIpAddress OBJECT-TYPE
    SYNTAX      IpAddress
    MAX-ACCESS  not-accessible
    STATUS      current
    DESCRIPTION
        "The IP Address associated with this entry in reserves table."
    ::= { usdDhcpLocalServerReservesEntry 1 }

usdDhcpLocalServerReservesEntryPoolName OBJECT-TYPE
    SYNTAX      UsdDhcpLocalServerPoolName
    MAX-ACCESS  read-create
    STATUS      current
    DESCRIPTION
        "The name of the local server pool associated with this entry in the
        reserves table and corresponding to the IP Address denoted by the table
        index."
    ::= { usdDhcpLocalServerReservesEntry 2 }

usdDhcpLocalServerReservesEntryPhysAddress OBJECT-TYPE
    SYNTAX      UsdDhcpLocalServerPhysAddressString
    MAX-ACCESS  read-create
    STATUS      current
    DESCRIPTION
        "The physical (MAC) address string associated with this entry in the
        reserves table and corresponding to the IP Address denoted by the table
        index."
    ::= { usdDhcpLocalServerReservesEntry 3 }

usdDhcpLocalServerReservesEntryRowStatus OBJECT-TYPE
    SYNTAX      RowStatus
    MAX-ACCESS  read-create
    STATUS      current
    DESCRIPTION
        "Supports 'createAndGo' and 'destroy' only."
    ::= { usdDhcpLocalServerReservesEntry 4 }


-- +++++++++++++++++++++++++++++++++++++++++++++++++++++++++++++++++++++++++++++
-- DHCP Local Server Cable Modem Servers
-- +++++++++++++++++++++++++++++++++++++++++++++++++++++++++++++++++++++++++++++
usdDhcpLocalServerCableModemServerTable OBJECT-TYPE
    SYNTAX      SEQUENCE OF UsdDhcpLocalServerCableModemServerEntry
    MAX-ACCESS  not-accessible
    STATUS      current
    DESCRIPTION
        "The (conceptual) table listing the DHCP Cable Modem Relay servers."
    ::= { usdDhcpLocalServerCableModemServers 1 }

usdDhcpLocalServerCableModemServerEntry OBJECT-TYPE
    SYNTAX      UsdDhcpLocalServerCableModemServerEntry
    MAX-ACCESS  not-accessible
    STATUS      current
    DESCRIPTION
        "An entry (conceptual row) representing a DHCP Cable Modem DHCP server."
    INDEX     { usdDhcpLocalServerCableModemServerEntryAddress }
    ::= { usdDhcpLocalServerCableModemServerTable 1 }

UsdDhcpLocalServerCableModemServerEntry ::= SEQUENCE {
    usdDhcpLocalServerCableModemServerEntryAddress      IpAddress,
    usdDhcpLocalServerCableModemServerEntryRowStatus    RowStatus }

usdDhcpLocalServerCableModemServerEntryAddress OBJECT-TYPE
    SYNTAX      IpAddress
    MAX-ACCESS  not-accessible
    STATUS      current
    DESCRIPTION
        "The IP address of the DHCP server to which DHCP requests received from
        attached Cable Modem DHCP clients are forwarded."
    ::= { usdDhcpLocalServerCableModemServerEntry 1 }

usdDhcpLocalServerCableModemServerEntryRowStatus OBJECT-TYPE
    SYNTAX      RowStatus
    MAX-ACCESS  read-create
    STATUS      current
    DESCRIPTION
        "Supports 'createAndGo' and 'destroy' only."
    ::= { usdDhcpLocalServerCableModemServerEntry 2 }


-- +++++++++++++++++++++++++++++++++++++++++++++++++++++++++++++++++++++++++++++
-- DHCP Local Server Cable Modem Statistics
-- +++++++++++++++++++++++++++++++++++++++++++++++++++++++++++++++++++++++++++++
usdDhcpLocalServerCableModemRequestIn OBJECT-TYPE
    SYNTAX      Counter32
    MAX-ACCESS  read-only
    STATUS      current
    DESCRIPTION
        "The number of Cable Modem DHCP Client Requests that are received."
    ::= { usdDhcpLocalServerCableModemStatistics 1 }

usdDhcpLocalServerCableModemResponseIn OBJECT-TYPE
    SYNTAX      Counter32
    MAX-ACCESS  read-only
    STATUS      current
    DESCRIPTION
        "The number of Cable Modem DHCP Server Responses that are received."
    ::= { usdDhcpLocalServerCableModemStatistics 2 }

usdDhcpLocalServerCableModemRequestOut OBJECT-TYPE
    SYNTAX      Counter32
    MAX-ACCESS  read-only
    STATUS      current
    DESCRIPTION
        "The number of Cable Modem DHCP Client Request that are transmitted."
    ::= { usdDhcpLocalServerCableModemStatistics 3 }

usdDhcpLocalServerCableModemResponseOut OBJECT-TYPE
    SYNTAX      Counter32
    MAX-ACCESS  read-only
    STATUS      current
    DESCRIPTION
        "The number of Cable Modem DHCP Server Responses that are transmitted."
    ::= { usdDhcpLocalServerCableModemStatistics 4 }

usdDhcpLocalServerCableModemRequestDropped OBJECT-TYPE
    SYNTAX      Counter32
    MAX-ACCESS  read-only
    STATUS      current
    DESCRIPTION
        "The number of Cable Modem DHCP Client Request that are dropped."
    ::= { usdDhcpLocalServerCableModemStatistics 5 }

usdDhcpLocalServerCableModemResponseDropped OBJECT-TYPE
    SYNTAX      Counter32
    MAX-ACCESS  read-only
    STATUS      current
    DESCRIPTION
        "The number of Cable Modem DHCP Server Responses that are dropped."
    ::= { usdDhcpLocalServerCableModemStatistics 6 }

usdDhcpLocalServerCableModemRequestBad OBJECT-TYPE
    SYNTAX      Counter32
    MAX-ACCESS  read-only
    STATUS      current
    DESCRIPTION
        "The number of Cable Modem DHCP Client Request that are bad."
    ::= { usdDhcpLocalServerCableModemStatistics 7 }

usdDhcpLocalServerCableModemResponseBad OBJECT-TYPE
    SYNTAX      Counter32
    MAX-ACCESS  read-only
    STATUS      current
    DESCRIPTION
        "The number of Cable Modem DHCP Server Responses that are bad."
    ::= { usdDhcpLocalServerCableModemStatistics 8 }

usdDhcpLocalServerCableModemRequestDeleted OBJECT-TYPE
    SYNTAX      Counter32
    MAX-ACCESS  read-only
    STATUS      current
    DESCRIPTION
        "The number of Cable Modem DHCP Requests that were deleted because they
        were stale."
    ::= { usdDhcpLocalServerCableModemStatistics 9 }

usdDhcpLocalServerCableModemPacketsIn OBJECT-TYPE
    SYNTAX      Counter32
    MAX-ACCESS  read-only
    STATUS      current
    DESCRIPTION
        "The number of Cable Modem DHCP Packets received."
    ::= { usdDhcpLocalServerCableModemStatistics 10 }

usdDhcpLocalServerCableModemPacketsOut OBJECT-TYPE
    SYNTAX      Counter32
    MAX-ACCESS  read-only
    STATUS      current
    DESCRIPTION
        "The number of Cable Modem DHCP Packets transmitted."
    ::= { usdDhcpLocalServerCableModemStatistics 11 }

usdDhcpLocalServerCableModemPacketsDropped OBJECT-TYPE
    SYNTAX      Counter32
    MAX-ACCESS  read-only
    STATUS      current
    DESCRIPTION
        "The number of Cable Modem DHCP Packets dropped."
    ::= { usdDhcpLocalServerCableModemStatistics 12 }


-- +++++++++++++++++++++++++++++++++++++++++++++++++++++++++++++++++++++++++++++
-- Notification control objects
-- +++++++++++++++++++++++++++++++++++++++++++++++++++++++++++++++++++++++++++++
-- No notifications are defined in this MIB. Placeholder follows.
-- usdDhcpTrapControl      OBJECT IDENTIFIER ::= { usdDhcpMIB 2 }

-- +++++++++++++++++++++++++++++++++++++++++++++++++++++++++++++++++++++++++++++
-- Notifications
-- +++++++++++++++++++++++++++++++++++++++++++++++++++++++++++++++++++++++++++++
-- No notifications are defined in this MIB. Placeholder follows.
-- The following OBJECT IDENTIFIER is used to define SNMPv2
-- Notifications that are easily translated into SNMPv1 Traps.
-- usdDhcpTraps            OBJECT IDENTIFIER ::= { usdDhcpMIB 0 }


-- +++++++++++++++++++++++++++++++++++++++++++++++++++++++++++++++++++++++++++++
-- Conformance information
-- +++++++++++++++++++++++++++++++++++++++++++++++++++++++++++++++++++++++++++++
usdDhcpMIBConformance
             OBJECT IDENTIFIER ::= { usdDhcpMIB 4 }
usdDhcpMIBCompliances
             OBJECT IDENTIFIER ::= { usdDhcpMIBConformance 1 }
usdDhcpMIBGroups
             OBJECT IDENTIFIER ::= { usdDhcpMIBConformance 2 }

--
-- compliance statements
--
usdDhcpRelayCompliance MODULE-COMPLIANCE
    STATUS      obsolete
    DESCRIPTION
        "Obsolete compliance statement for systems supporting DHCP Relay.  This
        statement became obsolete when Local Server support objects were added."
    MODULE   -- this module
        MANDATORY-GROUPS {
            usdDhcpRelayGroup,
            usdDhcpProxyGroup }
    ::= { usdDhcpMIBCompliances 1 }                                    -- RX 1.3

usdDhcpProxyCompliance MODULE-COMPLIANCE
    STATUS      obsolete
    DESCRIPTION
        "Obsolete compliance statement for systems supporting DHCP Proxy.  This
        statement became obsolete when Local Server support objects were added."
    MODULE   -- this module
        MANDATORY-GROUPS {
            usdDhcpProxyGroup }
    ::= { usdDhcpMIBCompliances 2 }                                    -- RX 1.3

usdDhcpCompliance MODULE-COMPLIANCE
    STATUS      obsolete
    DESCRIPTION
        "Obsolete compliance statement for systems supporting DHCP.  This
        compliance statement became obsolete when support was added for
        reservations and cable modem servers."
    MODULE  -- this module
        GROUP usdDhcpRelayGroup
            DESCRIPTION
                "The DHCP Relay group is mandatory for systems supporting DHCP
                Relay."
        GROUP usdDhcpProxyGroup
            DESCRIPTION
                "The DHCP Proxy group is mandatory for systems supporting DHCP
                Proxy."
        GROUP usdDhcpLocalServerGroup
            DESCRIPTION
                "The DHCP Local Server group is mandatory for systems supporting
                DHCP Local Servers."
    ::= { usdDhcpMIBCompliances 3 }                                    -- RX 3.1

usdDhcpCompliance2 MODULE-COMPLIANCE
    STATUS      current
    DESCRIPTION
        "The compliance statement for systems supporting DHCP."
    MODULE  -- this module
        GROUP usdDhcpRelayGroup2
            DESCRIPTION
                "The DHCP Relay group is mandatory for systems supporting DHCP
                Relay."
        GROUP usdDhcpProxyGroup
            DESCRIPTION
                "The DHCP Proxy group is mandatory for systems supporting DHCP
                Proxy."
        GROUP usdDhcpLocalServerGroup2
            DESCRIPTION
                "The DHCP Local Server group is mandatory for systems supporting
                DHCP Local Servers."
    ::= { usdDhcpMIBCompliances 4 }                                    -- RX 4.0

--
-- units of conformance
--
usdDhcpRelayGroup OBJECT-GROUP
    OBJECTS {
        usdDhcpRelayAgentInfoEnable,
        usdDhcpRelayBadMessages,
        usdDhcpRelayUnknownMessages,
        usdDhcpRelayAgentInfoAlreadyPresents,
        usdDhcpRelayGatewayAddrSpoofs,
        usdDhcpRelayServerRowStatus }
    STATUS      deprecated
    DESCRIPTION
        "Deprecated basic collection of objects providing management of DHCP
        Relay functionality.  This group became deprecated when the agent info
        enable was divided into agent circuit ID enable and agent remote ID
        enable."
    ::= { usdDhcpMIBGroups 1 }

usdDhcpProxyGroup OBJECT-GROUP
    OBJECTS {
        usdDhcpProxyClientUnknownServers,
        usdDhcpProxyClientServerRowStatus,
        usdDhcpProxyClientServerAdminStatus,
        usdDhcpProxyClientServerOperStatus,
        usdDhcpProxyClientServerLeases,
        usdDhcpProxyClientServerDiscovers,
        usdDhcpProxyClientServerOffers,
        usdDhcpProxyClientServerRequests,
        usdDhcpProxyClientServerAcks,
        usdDhcpProxyClientServerNaks,
        usdDhcpProxyClientServerDeclines,
        usdDhcpProxyClientServerReleases,
        usdDhcpProxyClientServerInforms,
        usdDhcpProxyClientServerBadMessages,
        usdDhcpProxyClientServerUnknownMessages }
    STATUS      current
    DESCRIPTION
        "The basic collection of objects providing management of DHCP Proxy
        functionality."
    ::= { usdDhcpMIBGroups 2 }

usdDhcpLocalServerGroup OBJECT-GROUP
    OBJECTS {
        usdDhcpLocalServerMemUsage,
        usdDhcpLocalServerNumBindings,
        usdDhcpLocalServerRxDiscovers,
        usdDhcpLocalServerRxAccepts,
        usdDhcpLocalServerRxRenews,
        usdDhcpLocalServerRxDeclines,
        usdDhcpLocalServerRxReleases,
        usdDhcpLocalServerRxInforms,
        usdDhcpLocalServerTxOffers,
        usdDhcpLocalServerTxAcks,
        usdDhcpLocalServerTxNaks,
        usdDhcpLocalServerUnknownMessages,
        usdDhcpLocalServerBadMessages,
        usdDhcpLocalServerPacketsIn,
        usdDhcpLocalServerPacketsOut,
        usdDhcpLocalServerBindingsPhysAddress,
        usdDhcpLocalServerBindingsInfinite,
        usdDhcpLocalServerBindingsExpireTime,
        usdDhcpLocalServerPoolDomainName,
        usdDhcpLocalServerPoolNetworkIpAddress,
        usdDhcpLocalServerPoolNetworkMask,
        usdDhcpLocalServerPoolNetBiosNodeType,
        usdDhcpLocalServerPoolLeaseTime,
        usdDhcpLocalServerPoolPrimaryDnsServer,
        usdDhcpLocalServerPoolSecondaryDnsServer,
        usdDhcpLocalServerPoolPrimaryNetBiosNameServer,
        usdDhcpLocalServerPoolSecondaryNetBiosNameServer,
        usdDhcpLocalServerPoolPrimaryDefaultRouter,
        usdDhcpLocalServerPoolSecondaryDefaultRouter,
        usdDhcpLocalServerPoolRowStatus }
    STATUS      obsolete
    DESCRIPTION
        "Obsolete basic collection of objects providing management of DHCP Local
        Server functionality.  This group became obsolete when support was added
        for reservations and cable modem servers."
    ::= { usdDhcpMIBGroups 3 }

usdDhcpLocalServerGroup2 OBJECT-GROUP
    OBJECTS {
        usdDhcpLocalServerMemUsage,
        usdDhcpLocalServerNumBindings,
        usdDhcpLocalServerRxDiscovers,
        usdDhcpLocalServerRxAccepts,
        usdDhcpLocalServerRxRenews,
        usdDhcpLocalServerRxDeclines,
        usdDhcpLocalServerRxReleases,
        usdDhcpLocalServerRxInforms,
        usdDhcpLocalServerTxOffers,
        usdDhcpLocalServerTxAcks,
        usdDhcpLocalServerTxNaks,
        usdDhcpLocalServerUnknownMessages,
        usdDhcpLocalServerBadMessages,
        usdDhcpLocalServerPacketsIn,
        usdDhcpLocalServerPacketsOut,
        usdDhcpLocalServerBindingsPhysAddress,
        usdDhcpLocalServerBindingsInfinite,
        usdDhcpLocalServerBindingsExpireTime,
        usdDhcpLocalServerPoolDomainName,
        usdDhcpLocalServerPoolNetworkIpAddress,
        usdDhcpLocalServerPoolNetworkMask,
        usdDhcpLocalServerPoolNetBiosNodeType,
        usdDhcpLocalServerPoolLeaseTime,
        usdDhcpLocalServerPoolPrimaryDnsServer,
        usdDhcpLocalServerPoolSecondaryDnsServer,
        usdDhcpLocalServerPoolPrimaryNetBiosNameServer,
        usdDhcpLocalServerPoolSecondaryNetBiosNameServer,
        usdDhcpLocalServerPoolPrimaryDefaultRouter,
        usdDhcpLocalServerPoolSecondaryDefaultRouter,
        usdDhcpLocalServerPoolRowStatus,
        usdDhcpLocalServerPoolLinkName,
        usdDhcpLocalServerAttributesMode,
        usdDhcpLocalServerReservesEntryPoolName,
        usdDhcpLocalServerReservesEntryPhysAddress,
        usdDhcpLocalServerReservesEntryRowStatus,
        usdDhcpLocalServerCableModemServerEntryRowStatus,
        usdDhcpLocalServerCableModemRequestIn,
        usdDhcpLocalServerCableModemResponseIn,
        usdDhcpLocalServerCableModemRequestOut,
        usdDhcpLocalServerCableModemResponseOut,
        usdDhcpLocalServerCableModemRequestDropped,
        usdDhcpLocalServerCableModemResponseDropped,
        usdDhcpLocalServerCableModemRequestBad,
        usdDhcpLocalServerCableModemResponseBad,
        usdDhcpLocalServerCableModemRequestDeleted,
        usdDhcpLocalServerCableModemPacketsIn,
        usdDhcpLocalServerCableModemPacketsOut,
        usdDhcpLocalServerCableModemPacketsDropped }
    STATUS      current
    DESCRIPTION
        "The basic collection of objects providing management of DHCP Local
        Server functionality."
    ::= { usdDhcpMIBGroups 4 }

usdDhcpRelayGroup2 OBJECT-GROUP
    OBJECTS {
        usdDhcpRelayBadMessages,
        usdDhcpRelayUnknownMessages,
        usdDhcpRelayAgentInfoAlreadyPresents,
        usdDhcpRelayGatewayAddrSpoofs,
        usdDhcpRelayAgentCircuitIdEnable,
        usdDhcpRelayAgentRemoteIdEnable,
        usdDhcpRelayServerRowStatus }
    STATUS      current
    DESCRIPTION
        "The basic collection of objects providing management of DHCP Relay
        functionality."
    ::= { usdDhcpMIBGroups 5 }

END
