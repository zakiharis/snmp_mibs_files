-- MIB File Generated on 31-Oct-1995 at 13:51:13

UX25-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ux25 OBJECT IDENTIFIER ::= { nas 10 }

ux25AdmnChannelTable OBJECT-TYPE
SYNTAX SEQUENCE OF Ux25AdmnChannelEntry
ACCESS not-accessible
STATUS mandatory
DESCRIPTION
"Defines objects for the parameters of an X.25 interface 
which the administrator can read and set."
::= { ux25 1 }

ux25AdmnChannelEntry OBJECT-TYPE
SYNTAX Ux25AdmnChannelEntry
ACCESS not-accessible
STATUS mandatory
DESCRIPTION
"Entries of ux25AdmnChannelTable."
INDEX { ux25AdmnChanneIndex }
::= { ux25AdmnChannelTable 1 }

Ux25AdmnChannelEntry ::=
SEQUENCE {
ux25AdmnChanneIndex
    INTEGER,
ux25AdmnNetMode
    INTEGER,
ux25AdmnProtocolVersion
    INTEGER,
ux25AdmnInterfaceMode
    INTEGER,
ux25AdmnLowestPVCVal
    INTEGER,
ux25AdmnHighestPVCVal
    INTEGER,
ux25AdmnChannelLIC
    INTEGER,
ux25AdmnChannelHIC
    INTEGER,
ux25AdmnChannelLTC
    INTEGER,
ux25AdmnChannelHTC
    INTEGER,
ux25AdmnChannelLOC
    INTEGER,
ux25AdmnChannelHOC
    INTEGER
}

ux25AdmnChanneIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25AdmnChannelEntry 1 }

ux25AdmnNetMode OBJECT-TYPE
SYNTAX INTEGER{
  x25Llc(1),
  x2588(2),
  x2584(3),
  x2580(4),
  pss(5),
  austpac(6),
  datapac(7),
  ddn(8),
  telenet(9),
  transpac(10),
  tymnet(11),
  datexP(12),
  ddxP(13),
  venusP(14),
  accunet(15),
  itapac(16),
  datapak(17),
  datanet(18),
  dcs(19),
  telepac(20),
  fDatapac(21),
  finpac(22),
  pacnet(23),
  luxpac(24)
}
ACCESS read-write
STATUS mandatory
DESCRIPTION
"Selects the network protocol to be used.
Default=x2584(3)."
::= { ux25AdmnChannelEntry 2 }

ux25AdmnProtocolVersion OBJECT-TYPE
SYNTAX INTEGER{
  x25ver80(1),
  x25ver84(2),
  x25ver88(3)
}
ACCESS read-write
STATUS mandatory
DESCRIPTION
"Determines the X.25 protocol version being used on the 
network.  A network mode of X25_LLC overides this field to 
the 1984 standard.
Default=x25ver84(3)."
::= { ux25AdmnChannelEntry 3 }

ux25AdmnInterfaceMode OBJECT-TYPE
SYNTAX INTEGER{
  dceMode(1),
  dteMode(2),
  dxeMode(3)
}
ACCESS read-write
STATUS mandatory
DESCRIPTION
"Indicates the DTE/DCE nature of the link.  The DXE 
parameter is resolved using ISO 8208 for DTE-DTE operation. 

Default=dteMode(2)."
::= { ux25AdmnChannelEntry 4 }

ux25AdmnLowestPVCVal OBJECT-TYPE
SYNTAX INTEGER (0..4095)
ACCESS read-write
STATUS mandatory
DESCRIPTION
"Low end of the Permanent Virtual Circuit range.  If both 
the Low and High ends of the range are set to 0 there are 
no PVCs.
Default=0."
::= { ux25AdmnChannelEntry 5 }

ux25AdmnHighestPVCVal OBJECT-TYPE
SYNTAX INTEGER (0..4095)
ACCESS read-write
STATUS mandatory
DESCRIPTION
"High end of the Permanent Virtual Circuit range.  If both 
the Low and High ends of the range are set to 0 there are 
no PVCs.
Default=0."
::= { ux25AdmnChannelEntry 6 }

ux25AdmnChannelLIC OBJECT-TYPE
SYNTAX INTEGER (0..4095)
ACCESS read-write
STATUS mandatory
DESCRIPTION
"Low end of the one-way incoming logical channel.  If both 
Low and High ends of the channel are set to 0, there are no 
one-way incoming channels.
Default=0."
::= { ux25AdmnChannelEntry 7 }

ux25AdmnChannelHIC OBJECT-TYPE
SYNTAX INTEGER (0..4095)
ACCESS read-write
STATUS mandatory
DESCRIPTION
"High end of the one-way incoming logical channel.  If both 
Low and High ends of the channel are set to 0, there are no 
one-way incoming channels.
Default=0."
::= { ux25AdmnChannelEntry 8 }

ux25AdmnChannelLTC OBJECT-TYPE
SYNTAX INTEGER (0..4095)
ACCESS read-write
STATUS mandatory
DESCRIPTION
"Low end of the two-way incoming logical channel.  If both 
Low and High ends of the channel are set to 0, there are no 
two-way incoming channels.
Default=1024."
::= { ux25AdmnChannelEntry 9 }

ux25AdmnChannelHTC OBJECT-TYPE
SYNTAX INTEGER (0..4095)
ACCESS read-write
STATUS mandatory
DESCRIPTION
"High end of the two-way incoming logical channel.  If both 
Low and High ends of the channel are set to 0, there are no 
two-way incoming channels.
Default=1087."
::= { ux25AdmnChannelEntry 10 }

ux25AdmnChannelLOC OBJECT-TYPE
SYNTAX INTEGER (0..4095)
ACCESS read-write
STATUS mandatory
DESCRIPTION
"Low end of the one-way outgoing logical channel.  If both 
Low and High ends of the channel are set to 0, there are no 
one-way outgoing channels.
Default=0."
::= { ux25AdmnChannelEntry 11 }

ux25AdmnChannelHOC OBJECT-TYPE
SYNTAX INTEGER (0..4095)
ACCESS read-write
STATUS mandatory
DESCRIPTION
"High end of the one-way outgoing logical channel.  If both 
Low and High ends of the channel are set to 0, there are no 
one-way outgoing channels.
Default=0."
::= { ux25AdmnChannelEntry 12 }

ux25AdmnClassTable OBJECT-TYPE
SYNTAX SEQUENCE OF Ux25AdmnClassEntry
ACCESS not-accessible
STATUS mandatory
DESCRIPTION
"Defines objects for the parameters of an X.25 interface 
which the administrator can read and set."
::= { ux25 2 }

ux25AdmnClassEntry OBJECT-TYPE
SYNTAX Ux25AdmnClassEntry
ACCESS not-accessible
STATUS mandatory
DESCRIPTION
"Entries of ux25AdmnClassTable."
INDEX { ux25AdmnClassIndex }
::= { ux25AdmnClassTable 1 }

Ux25AdmnClassEntry ::=
SEQUENCE {
ux25AdmnClassIndex
    INTEGER,
ux25AdmnLocMaxThruPutClass
    INTEGER,
ux25AdmnRemMaxThruPutClass
    INTEGER,
ux25AdmnLocDefThruPutClass
    INTEGER,
ux25AdmnRemDefThruPutClass
    INTEGER,
ux25AdmnLocMinThruPutClass
    INTEGER,
ux25AdmnRemMinThruPutClass
    INTEGER,
ux25AdmnThclassNegToDef
    INTEGER,
ux25AdmnThclassType
    INTEGER,
ux25AdmnThclassWinMap
    DisplayString,
ux25AdmnThclassPackMap
    DisplayString
}

ux25AdmnClassIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25AdmnClassEntry 1 }

ux25AdmnLocMaxThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"The maximum value of the throughput class Quality of 
Service parameter which is supported. According to ISO 8208 
this parameter is bounded in the range >=3 and <=12 
corresponding to a range 75 to 48000 bits/second.  The 
range supported here is 0 to 15 for non-standard X.25 
implementations, which use the Throughput Class 
Window/Packet Parameters (Group II).
Default=12."
::= { ux25AdmnClassEntry 2 }

ux25AdmnRemMaxThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"The maximum value of the throughput class Quality of 
Service parameter which is supported. According to ISO 8208 
this parameter is bounded in the range >=3 and <=12 
corresponding to a range 75 to 48000 bits/second.  The 
range supported here is 0 to 15 for non-standard X.25 
implementations, which use the Throughput Class 
Window/Packet Parameters (Group II).
Default=12."
::= { ux25AdmnClassEntry 3 }

ux25AdmnLocDefThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"The default throughput class that is defined for the 
local-to-remote direction.  In some networks, such as 
TELENET, negotiation of throughput class is constrained to 
be towards a configured default throughput class.  In other 
PSDNs, this value should be set equal to the value of the 
Maximum Local Throughput Class.
Default=12."
::= { ux25AdmnClassEntry 4 }

ux25AdmnRemDefThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"The default throughput class value defined for 
remote-to-local direction.  In some networks, such as 
TELENET,  negotiation of throughput class is constrained to 
be towards a configured default throughput class.  In other 
PSDNs, this value should be set equal to the value of the 
Maximum Remote Throughput Class.
Default=12."
::= { ux25AdmnClassEntry 5 }

ux25AdmnLocMinThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"According to ISO 8208, the throughput class parameter is 
defined in the range of >=3 to <=12.  Some PSDNs may 
provide different mapping, in which case, this parameter is 
the minimum value.
Default=3."
::= { ux25AdmnClassEntry 6 }

ux25AdmnRemMinThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-write
STATUS mandatory
DESCRIPTION
"According to ISO 8208, the throughput class parameter is 
defined in the range of >=3 to <=12.  Some PSDNs may 
provide different mapping, in which case, this parameter is 
the minimum value.
Default=3."
::= { ux25AdmnClassEntry 7 }

ux25AdmnThclassNegToDef OBJECT-TYPE
SYNTAX INTEGER{
  disable(1),
  enable(2)
}
ACCESS read-write
STATUS mandatory
DESCRIPTION
"Determines if throughput class negotiation will be used for 
certain network procedures.
Default=disable(1)."
::= { ux25AdmnClassEntry 8 }

ux25AdmnThclassType OBJECT-TYPE
SYNTAX INTEGER{
  noTcType(1),
  loNibble(2),
  highNibble(3),
  bothNibbles(4)
}
ACCESS read-write
STATUS mandatory
DESCRIPTION
"Defines which throughput class encodings can be used to 
assign packet and window sizes.  Some implementations of 
X.25 do not use the X.25 packet and window negotiation and 
rely on mapping the throughput class to these 
parameters.
Default=noTcType(1)."
::= { ux25AdmnClassEntry 9 }

ux25AdmnThclassWinMap OBJECT-TYPE
SYNTAX DisplayString (SIZE(31..63))
ACCESS read-write
STATUS mandatory
DESCRIPTION
"The mapping between throughput class and a window 
parameter. Each number has a range of 1 to 
127.
Default=3.3.3.3.3.3.3.3.3.3.3.3.3.3.3.3"
::= { ux25AdmnClassEntry 10 }

ux25AdmnThclassPackMap OBJECT-TYPE
SYNTAX DisplayString (SIZE(31..47))
ACCESS read-write
STATUS mandatory
DESCRIPTION
"The mapping between the throughput class and a packet 
parameter. Each number has a range of 4 to 
12.
Default=7.7.7.7.7.7.7.7.7.7.7.7.7.7.7.7"
::= { ux25AdmnClassEntry 11 }

ux25AdmnPacketTable OBJECT-TYPE
SYNTAX SEQUENCE OF Ux25AdmnPacketEntry
ACCESS not-accessible
STATUS mandatory
DESCRIPTION
"Defines objects for the parameters of an X.25 interface 
which the administrator can read and set."
::= { ux25 3 }

ux25AdmnPacketEntry OBJECT-TYPE
SYNTAX Ux25AdmnPacketEntry
ACCESS not-accessible
STATUS mandatory
DESCRIPTION
"Entries of ux25AdmnPacketTable."
INDEX { ux25AdmnPacketIndex }
::= { ux25AdmnPacketTable 1 }

Ux25AdmnPacketEntry ::=
SEQUENCE {
ux25AdmnPacketIndex
    INTEGER,
ux25AdmnPktSequencing
    INTEGER,
ux25AdmnLocMaxPktSize
    INTEGER,
ux25AdmnRemMaxPktSize
    INTEGER,
ux25AdmnLocDefPktSize
    INTEGER,
ux25AdmnRemDefPktSize
    INTEGER,
ux25AdmnLocMaxWinSize
    INTEGER,
ux25AdmnRemMaxWinSize
    INTEGER,
ux25AdmnLocDefWinSize
    INTEGER,
ux25AdmnRemDefWinSize
    INTEGER,
ux25AdmnMaxNSDULimit
    INTEGER,
ux25AdmnAccNoDiagnostic
    INTEGER,
ux25AdmnUseDiagnosticPacket
    INTEGER,
ux25AdmnItutClearLen
    INTEGER,
ux25AdmnBarDiagnosticPacket
    INTEGER,
ux25AdmnDiscNzDiagnostic
    INTEGER,
ux25AdmnAcceptHexAdd
    INTEGER,
ux25AdmnBarNonPrivilegeListen
    INTEGER,
ux25AdmnIntlAddrRecognition
    INTEGER,
ux25AdmnDnic
    DisplayString,
ux25AdmnIntlPrioritized
    INTEGER,
ux25AdmnPrtyEncodeCtrl
    INTEGER,
ux25AdmnPrtyPktForcedVal
    INTEGER,
ux25AdmnSrcAddrCtrl
    INTEGER,
ux25AdmnDbitInAccept
    INTEGER,
ux25AdmnDbitOutAccept
    INTEGER,
ux25AdmnDbitInData
    INTEGER,
ux25AdmnDbitOutData
    INTEGER
}

ux25AdmnPacketIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25AdmnPacketEntry 1 }

ux25AdmnPktSequencing OBJECT-TYPE
SYNTAX INTEGER{
  pktSeq8(16),
  pktSeq128(32)
}
ACCESS read-write
STATUS mandatory
DESCRIPTION
"Indicates whether modulo 8 or 128 sequence numbering 
operates on the network.
Default=pktSeq8(16)."
::= { ux25AdmnPacketEntry 2 }

ux25AdmnLocMaxPktSize OBJECT-TYPE
SYNTAX INTEGER{
  maxPktSz128(7),
  maxPktSz256(8),
  maxPktSz512(9)
}
ACCESS read-write
STATUS mandatory
DESCRIPTION
"Maximum acceptable size of packets in the local-to-remote 
direction.  On an incoming call, a value for the packet 
size parameter greater than this value will be negotiated 
down to an acceptable size when the call is 
accepted.
Default=maxPktSz256(8)."
::= { ux25AdmnPacketEntry 3 }

ux25AdmnRemMaxPktSize OBJECT-TYPE
SYNTAX INTEGER{
  maxPktSz128(7),
  maxPktSz256(8),
  maxPktSz512(9)
}
ACCESS read-write
STATUS mandatory
DESCRIPTION
"Maximum acceptable size of packets in the remote-to-local 
direction.  On an incoming call, a value for the packet 
size parameter greater than this value will be negotiated 
down to an acceptable size when the call is 
accepted.
Default=maxPktSz256(8)."
::= { ux25AdmnPacketEntry 4 }

ux25AdmnLocDefPktSize OBJECT-TYPE
SYNTAX INTEGER{
  defPktSz16(4),
  defPktSz32(5),
  defPktSz64(6),
  defPktSz128(7),
  defPktSz256(8),
  defPktSz512(9)
}
ACCESS read-write
STATUS mandatory
DESCRIPTION
"Specifies the value of the default packet size for the 
direction local-to-remote, which may be nonstandard, 
provided the value is agreed between the communicating 
parties on the LAN or between the DTE and 
DCE.
Default=defPktSz256(8)."
::= { ux25AdmnPacketEntry 5 }

ux25AdmnRemDefPktSize OBJECT-TYPE
SYNTAX INTEGER{
  defPktSz16(4),
  defPktSz32(5),
  defPktSz64(6),
  defPktSz128(7),
  defPktSz256(8),
  defPktSz512(9)
}
ACCESS read-write
STATUS mandatory
DESCRIPTION
"Specifies the value of the default packet size for the 
direction remote-to-local, which may be nonstandard, 
provided the value is agreed between the communicating 
parties on the LAN or between the DTE and 
DCE.
Default=defPktSz256(8)."
::= { ux25AdmnPacketEntry 6 }

ux25AdmnLocMaxWinSize OBJECT-TYPE
SYNTAX INTEGER (2..127)
ACCESS read-write
STATUS mandatory
DESCRIPTION
"Specifies the maximum local window size.  NOTE: 127 allowed 
only for modulo 128 networks.
Default=7."
::= { ux25AdmnPacketEntry 7 }

ux25AdmnRemMaxWinSize OBJECT-TYPE
SYNTAX INTEGER (2..127)
ACCESS read-write
STATUS mandatory
DESCRIPTION
"Specifies the maximum remote window size.  NOTE: 127 
allowed only for modulo 128 networks.
Default=7."
::= { ux25AdmnPacketEntry 8 }

ux25AdmnLocDefWinSize OBJECT-TYPE
SYNTAX INTEGER (1..127)
ACCESS read-write
STATUS mandatory
DESCRIPTION
"Specifies the value of the default window size, which may 
be nonstandard, provided the value is agreed on by all 
parties on the LAN between the DTE and DCE.  NOTE: The 
sequence numbering scheme affects the range of this 
parameter.
Default=2."
::= { ux25AdmnPacketEntry 9 }

ux25AdmnRemDefWinSize OBJECT-TYPE
SYNTAX INTEGER (1..127)
ACCESS read-write
STATUS mandatory
DESCRIPTION
"Specifies the value of the default window size, which may 
be nonstandard, provided the value is agreed on by all 
parties on the LAN between the DTE and DCE.  NOTE: The 
sequence numbering scheme affects the range of this 
parameter.
Default=2."
::= { ux25AdmnPacketEntry 10 }

ux25AdmnMaxNSDULimit OBJECT-TYPE
SYNTAX INTEGER (0..32000)
ACCESS read-write
STATUS mandatory
DESCRIPTION
"The default maximum length beyond which concatenation is 
stopped and data currently held is passed to the Network 
Service user.
Default=256."
::= { ux25AdmnPacketEntry 11 }

ux25AdmnAccNoDiagnostic OBJECT-TYPE
SYNTAX INTEGER{
  disable(1),
  enable(2)
}
ACCESS read-write
STATUS mandatory
DESCRIPTION
"Allow the omission of the diagnostic byte in incoming 
RESTART, CLEAR and RESET INDICATION 
packets.
Default=disable(1)."
::= { ux25AdmnPacketEntry 12 }

ux25AdmnUseDiagnosticPacket OBJECT-TYPE
SYNTAX INTEGER{
  disable(1),
  enable(2)
}
ACCESS read-write
STATUS mandatory
DESCRIPTION
"Use diagnostic packets.
Default=disable(1)."
::= { ux25AdmnPacketEntry 13 }

ux25AdmnItutClearLen OBJECT-TYPE
SYNTAX INTEGER{
  disable(1),
  enable(2)
}
ACCESS read-write
STATUS mandatory
DESCRIPTION
"Restrict the length of a CLEAR INDICATION to 5 bytes and a 
CLEAR CONFIRM to 3 bytes.
Default=disable(1)."
::= { ux25AdmnPacketEntry 14 }

ux25AdmnBarDiagnosticPacket OBJECT-TYPE
SYNTAX INTEGER{
  disable(1),
  enable(2)
}
ACCESS read-write
STATUS mandatory
DESCRIPTION
"Bar diagnostic packets.
Default=disable(1)."
::= { ux25AdmnPacketEntry 15 }

ux25AdmnDiscNzDiagnostic OBJECT-TYPE
SYNTAX INTEGER{
  disable(1),
  enable(2)
}
ACCESS read-write
STATUS mandatory
DESCRIPTION
"Discard all diagnostic packets on a non-zero 
LCN.
Default=disable(1)."
::= { ux25AdmnPacketEntry 16 }

ux25AdmnAcceptHexAdd OBJECT-TYPE
SYNTAX INTEGER{
  disable(1),
  enable(2)
}
ACCESS read-write
STATUS mandatory
DESCRIPTION
"Allow DTE addresses to contain hexadecimal 
digits.
Default=disable(1)."
::= { ux25AdmnPacketEntry 17 }

ux25AdmnBarNonPrivilegeListen OBJECT-TYPE
SYNTAX INTEGER{
  disable(1),
  enable(2)
}
ACCESS read-write
STATUS mandatory
DESCRIPTION
"Disallow a non-privileged user (i.e without superuser 
privilege) from listening for incoming 
calls.
Default=enable(2)."
::= { ux25AdmnPacketEntry 18 }

ux25AdmnIntlAddrRecognition OBJECT-TYPE
SYNTAX INTEGER{
  notDistinguished(1),
  examineDnic(2),
  prefix1(3),
  prefix0(4)
}
ACCESS read-write
STATUS mandatory
DESCRIPTION
"Determine whether outgoing international calls are to be 
accepted. The values and their interpretation are:
1 - 
International calls are not distinguished.
2 - The DNIC of 
the called DTE address is examined and compared to that 
held in the psdn_local members dnic1 and dnic2. A mismatch 
implies an international call.
3 - International calls are 
distinguished by having a '1' prefix on the DTE address.
4 
- International calls are distinguished by having a '0' 
prefix on the DTE address.
Default=notDistinguished(1)."

::= { ux25AdmnPacketEntry 19 }

ux25AdmnDnic OBJECT-TYPE
SYNTAX DisplayString (SIZE(4..4))
ACCESS read-write
STATUS mandatory
DESCRIPTION
"This field contains the first four digits of DNIC and is 
only used when ux25AdmnIntlAddrRecognition is set to 
examineDnic(2). Note this field must contain exactly four 
BCD digits.
Default=0000."
::= { ux25AdmnPacketEntry 20 }

ux25AdmnIntlPrioritized OBJECT-TYPE
SYNTAX INTEGER{
  disable(1),
  enable(2)
}
ACCESS read-write
STATUS mandatory
DESCRIPTION
"Determine whether some prioritizing method is to used for 
international calls and is used in conjuction with 
ux25AdmnPrtyEncodeCtrl and ux25AdmnPrtyPktForced 
value.
Default=disable(1)."
::= { ux25AdmnPacketEntry 21 }

ux25AdmnPrtyEncodeCtrl OBJECT-TYPE
SYNTAX INTEGER{
  x2588(1),
  datapacPriority76(2),
  datapacTraffic80(3)
}
ACCESS read-write
STATUS mandatory
DESCRIPTION
"Describes how the priority request is to be encoded for 
this PSDN.
Default=x2588(1)."
::= { ux25AdmnPacketEntry 22 }

ux25AdmnPrtyPktForcedVal OBJECT-TYPE
SYNTAX INTEGER{
  prioPktSz0(1),
  prioPktSz4(5),
  prioPktSz5(6),
  prioPktSz6(7),
  prioPktSz7(8),
  prioPktSz8(9),
  prioPktSz9(10),
  prioPktSz10(11),
  prioPktSz11(12),
  prioPktSz12(13)
}
ACCESS read-write
STATUS mandatory
DESCRIPTION
"If this entry is other than prioPktSz1(1) all priority call 
requests and incoming calls should have the associated 
packet size parameter forced to this value. Note that the 
actual packet size is 2 to the power of this 
parameter.
Default=prioPktSz1(1)."
::= { ux25AdmnPacketEntry 23 }

ux25AdmnSrcAddrCtrl OBJECT-TYPE
SYNTAX INTEGER{
  noSaCntrl(1),
  omitDte(2),
  useLocal(3),
  forceLocal(4)
}
ACCESS read-write
STATUS mandatory
DESCRIPTION
"Provide a means to override or set the calling address in 
outgoing call requests for this PSDN.
Default=noSaCntrl(1)."
::= { ux25AdmnPacketEntry 24 }

ux25AdmnDbitInAccept OBJECT-TYPE
SYNTAX INTEGER{
  leaveDbit(1),
  zeroDbit(2),
  clearCall(3)
}
ACCESS read-write
STATUS mandatory
DESCRIPTION
"Defines the action to take when a Call Accept is received 
with the D-bit set and there is no local D-bit 
support.
Default=clearCall(3)."
::= { ux25AdmnPacketEntry 25 }

ux25AdmnDbitOutAccept OBJECT-TYPE
SYNTAX INTEGER{
  leaveDbit(1),
  zeroDbit(2),
  clearCall(3)
}
ACCESS read-write
STATUS mandatory
DESCRIPTION
"Defines the action to take when the remote user sends a 
Call Accept with the D-bit set when the local user did not 
request use of the D-bit.
Default=clearCall(3)."
::= { ux25AdmnPacketEntry 26 }

ux25AdmnDbitInData OBJECT-TYPE
SYNTAX INTEGER{
  leaveDbit(1),
  zeroDbit(2),
  clearCall(3)
}
ACCESS read-write
STATUS mandatory
DESCRIPTION
"Defines the action to take when a data packet is received 
with the D-bit set and the local user did not request use 
of the D-bit.
Default=clearCall(3)."
::= { ux25AdmnPacketEntry 27 }

ux25AdmnDbitOutData OBJECT-TYPE
SYNTAX INTEGER{
  leaveDbit(1),
  zeroDbit(2),
  clearCall(3)
}
ACCESS read-write
STATUS mandatory
DESCRIPTION
"Defines the action when the local user send a data packet 
with the D-bit set, but the remote party has not indicated 
D-bit support.
Default=clearCall(3)."
::= { ux25AdmnPacketEntry 28 }

ux25AdmnSubscriberTable OBJECT-TYPE
SYNTAX SEQUENCE OF Ux25AdmnSubscriberEntry
ACCESS not-accessible
STATUS mandatory
DESCRIPTION
"Defines objects for the parameters of an X.25 interface 
which the administrator can read and set."
::= { ux25 4 }

ux25AdmnSubscriberEntry OBJECT-TYPE
SYNTAX Ux25AdmnSubscriberEntry
ACCESS not-accessible
STATUS mandatory
DESCRIPTION
"Entries of ux25AdmnSubscriberTable."
INDEX { ux25AdmnSubscriberIndex }
::= { ux25AdmnSubscriberTable 1 }

Ux25AdmnSubscriberEntry ::=
SEQUENCE {
ux25AdmnSubscriberIndex
    INTEGER,
ux25AdmnSubCugIaoa
    INTEGER,
ux25AdmnSubCugPref
    INTEGER,
ux25AdmnSubCugoa
    INTEGER,
ux25AdmnSubCugia
    INTEGER,
ux25AdmnCugFormat
    INTEGER,
ux25AdmnBarInCug
    INTEGER,
ux25AdmnSubExtended
    INTEGER,
ux25AdmnBarExtended
    INTEGER,
ux25AdmnSubFstSelNoRstrct
    INTEGER,
ux25AdmnSubFstSelWthRstrct
    INTEGER,
ux25AdmnAccptRvsChrgng
    INTEGER,
ux25AdmnSubLocChargePrevent
    INTEGER,
ux25AdmnSubToaNpiFormat
    INTEGER,
ux25AdmnBarToaNpiFormat
    INTEGER,
ux25AdmnSubNuiOverride
    INTEGER,
ux25AdmnBarInCall
    INTEGER,
ux25AdmnBarOutCall
    INTEGER
}

ux25AdmnSubscriberIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25AdmnSubscriberEntry 1 }

ux25AdmnSubCugIaoa OBJECT-TYPE
SYNTAX INTEGER{
  disable(1),
  enable(2)
}
ACCESS read-write
STATUS mandatory
DESCRIPTION
"Specifies if this DTE subscribes to Closed User Groups with 
Incoming or Outgoing access.
Default=enable(2)."
::= { ux25AdmnSubscriberEntry 2 }

ux25AdmnSubCugPref OBJECT-TYPE
SYNTAX INTEGER{
  disable(1),
  enable(2)
}
ACCESS read-write
STATUS mandatory
DESCRIPTION
"Specifies if this DTE subscribes to a Preferential Closed 
User Groups.
Default=disable(1)."
::= { ux25AdmnSubscriberEntry 3 }

ux25AdmnSubCugoa OBJECT-TYPE
SYNTAX INTEGER{
  disable(1),
  enable(2)
}
ACCESS read-write
STATUS mandatory
DESCRIPTION
"Specifies if this DTE subscribes to Closed User Groups with 
Outgoing access.
Default=disable(1)."
::= { ux25AdmnSubscriberEntry 4 }

ux25AdmnSubCugia OBJECT-TYPE
SYNTAX INTEGER{
  disable(1),
  enable(2)
}
ACCESS read-write
STATUS mandatory
DESCRIPTION
"Specifies whether or not this DTE subscribes to Closed User 
Groups with Incoming Access.
Default=disable(1)."
::= { ux25AdmnSubscriberEntry 5 }

ux25AdmnCugFormat OBJECT-TYPE
SYNTAX INTEGER{
  basic(1),
  extended(2)
}
ACCESS read-write
STATUS mandatory
DESCRIPTION
"The maximum number of Closed User Groups that this DTE 
subscribes to. This will be one of two ranges: Basic (100 
or fewer) or Extended (between 101 and 
10000).
Default=basic(1)."
::= { ux25AdmnSubscriberEntry 6 }

ux25AdmnBarInCug OBJECT-TYPE
SYNTAX INTEGER{
  disable(1),
  enable(2)
}
ACCESS read-write
STATUS mandatory
DESCRIPTION
"Provides the means to force rejection of any incoming calls 
carrying the Closed User Group optional facility (which is 
necessary in some networks, such as DDN. When enabled, such 
calls will be rejected, otherwise incoming Closed User 
Group facilities are ignored.
Default=disable(1)."
::= { ux25AdmnSubscriberEntry 7 }

ux25AdmnSubExtended OBJECT-TYPE
SYNTAX INTEGER{
  disable(1),
  enable(2)
}
ACCESS read-write
STATUS mandatory
DESCRIPTION
"Subscribe to extended call packets (Window and Packet size 
negotiation is permitted).
Default=enable(2)."
::= { ux25AdmnSubscriberEntry 8 }

ux25AdmnBarExtended OBJECT-TYPE
SYNTAX INTEGER{
  disable(1),
  enable(2)
}
ACCESS read-write
STATUS mandatory
DESCRIPTION
"Treat window and packet size negotiation in incoming 
packets as a procedure error.
Default=disable(1)."
::= { ux25AdmnSubscriberEntry 9 }

ux25AdmnSubFstSelNoRstrct OBJECT-TYPE
SYNTAX INTEGER{
  disable(1),
  enable(2)
}
ACCESS read-write
STATUS mandatory
DESCRIPTION
"Subscribe to fast select with no restriction on 
response.
Default=enable(2)."
::= { ux25AdmnSubscriberEntry 10 }

ux25AdmnSubFstSelWthRstrct OBJECT-TYPE
SYNTAX INTEGER{
  disable(1),
  enable(2)
}
ACCESS read-write
STATUS mandatory
DESCRIPTION
"Subscribe to fast select with restriction on 
response.
Default=disable(1)."
::= { ux25AdmnSubscriberEntry 11 }

ux25AdmnAccptRvsChrgng OBJECT-TYPE
SYNTAX INTEGER{
  disable(1),
  enable(2)
}
ACCESS read-write
STATUS mandatory
DESCRIPTION
"Allow incoming calls to specify the reverse charging 
facility.
Default=disable(1)."
::= { ux25AdmnSubscriberEntry 12 }

ux25AdmnSubLocChargePrevent OBJECT-TYPE
SYNTAX INTEGER{
  disable(1),
  enable(2)
}
ACCESS read-write
STATUS mandatory
DESCRIPTION
"Subscribe to local charging 
prevention.
Default=disable(1)."
::= { ux25AdmnSubscriberEntry 13 }

ux25AdmnSubToaNpiFormat OBJECT-TYPE
SYNTAX INTEGER{
  disable(1),
  enable(2)
}
ACCESS read-write
STATUS mandatory
DESCRIPTION
"Subscribe to TOA/NPI Address Format.
Default=disable(1)."
::= { ux25AdmnSubscriberEntry 14 }

ux25AdmnBarToaNpiFormat OBJECT-TYPE
SYNTAX INTEGER{
  disable(1),
  enable(2)
}
ACCESS read-write
STATUS mandatory
DESCRIPTION
"Bar incoming call set-up and clearing packets which use the 
TOA/NPI Address Format.
Default=disable(1)."
::= { ux25AdmnSubscriberEntry 15 }

ux25AdmnSubNuiOverride OBJECT-TYPE
SYNTAX INTEGER{
  disable(1),
  enable(2)
}
ACCESS read-write
STATUS mandatory
DESCRIPTION
"Subscribe to NUI override.
Deafult=disable(1)."
::= { ux25AdmnSubscriberEntry 16 }

ux25AdmnBarInCall OBJECT-TYPE
SYNTAX INTEGER{
  disable(1),
  enable(2)
}
ACCESS read-write
STATUS mandatory
DESCRIPTION
"Bar incoming calls.
Default=disable(1)."
::= { ux25AdmnSubscriberEntry 17 }

ux25AdmnBarOutCall OBJECT-TYPE
SYNTAX INTEGER{
  disable(1),
  enable(2)
}
ACCESS read-write
STATUS mandatory
DESCRIPTION
"Bar outgoing calls.
Default=disable(1)."
::= { ux25AdmnSubscriberEntry 18 }

ux25AdmnTimerTable OBJECT-TYPE
SYNTAX SEQUENCE OF Ux25AdmnTimerEntry
ACCESS not-accessible
STATUS mandatory
DESCRIPTION
"Defines objects for the parameters of an X.25 interface 
which the administrator can read and set."
::= { ux25 5 }

ux25AdmnTimerEntry OBJECT-TYPE
SYNTAX Ux25AdmnTimerEntry
ACCESS not-accessible
STATUS mandatory
DESCRIPTION
"Entries of ux25AdmnTimerTable."
INDEX { ux25AdmnTimerIndex }
::= { ux25AdmnTimerTable 1 }

Ux25AdmnTimerEntry ::=
SEQUENCE {
ux25AdmnTimerIndex
    INTEGER,
ux25AdmnAckDelay
    INTEGER,
ux25AdmnRstrtTime
    INTEGER,
ux25AdmnCallTime
    INTEGER,
ux25AdmnRstTime
    INTEGER,
ux25AdmnClrTime
    INTEGER,
ux25AdmnWinStatTime
    INTEGER,
ux25AdmnWinRotTime
    INTEGER,
ux25AdmnIntrptTime
    INTEGER,
ux25AdmnIdleValue
    INTEGER,
ux25AdmnConnectValue
    INTEGER,
ux25AdmnRstrtCnt
    INTEGER,
ux25AdmnRstCnt
    INTEGER,
ux25AdmnClrCnt
    INTEGER,
ux25AdmnLocalDelay
    INTEGER,
ux25AdmnAccessDelay
    INTEGER
}

ux25AdmnTimerIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25AdmnTimerEntry 1 }

ux25AdmnAckDelay OBJECT-TYPE
SYNTAX INTEGER (0..32000)
ACCESS read-write
STATUS mandatory
DESCRIPTION
"The maximum number of ticks (0.1 second units) over which a 
pending acknowledgement is withheld.
Default=5."
::= { ux25AdmnTimerEntry 2 }

ux25AdmnRstrtTime OBJECT-TYPE
SYNTAX INTEGER (0..32000)
ACCESS read-write
STATUS mandatory
DESCRIPTION
"The number of ticks (0.1 second units) for the DTE timer 
parameter T20, the Restart Request Response 
Timer.
Default=1800." 
::= { ux25AdmnTimerEntry 3 }

ux25AdmnCallTime OBJECT-TYPE
SYNTAX INTEGER (0..32000)
ACCESS read-write
STATUS mandatory
DESCRIPTION
"The number of ticks (0.1 second units) for the DTE timer 
parameter T21, the Call Request Response 
Timer.
Default=2000." 
::= { ux25AdmnTimerEntry 4 }

ux25AdmnRstTime OBJECT-TYPE
SYNTAX INTEGER (0..32000)
ACCESS read-write
STATUS mandatory
DESCRIPTION
"The number of ticks (0.1 second units) for the DTE timer 
parameter T22, the Reset Request Response 
Timer.
Default=1800." 
::= { ux25AdmnTimerEntry 5 }

ux25AdmnClrTime OBJECT-TYPE
SYNTAX INTEGER (0..32000)
ACCESS read-write
STATUS mandatory
DESCRIPTION
"The number of ticks (0.1 second units) for the DTE timer 
parameter T23, the Clear Request Response 
Timer.
Default=1800." 
::= { ux25AdmnTimerEntry 6 }

ux25AdmnWinStatTime OBJECT-TYPE
SYNTAX INTEGER (0..32000)
ACCESS read-write
STATUS mandatory
DESCRIPTION
"Related, but does not correspond exactly to the DTE Window 
Status Transmission Timer, T24. Specifies the number of 
ticks (0.1 second units) for the maximum time that 
acknowledgments of data received from the remote 
transmitter will be witheld.  At timer expiration, any 
witheld acknowledgments will be carried by a X.25 level 3 
RNR packet.
Default=750." 
::= { ux25AdmnTimerEntry 7 }

ux25AdmnWinRotTime OBJECT-TYPE
SYNTAX INTEGER (0..32000)
ACCESS read-write
STATUS mandatory
DESCRIPTION
"The number of ticks (0.1 second units) for the DTE timer 
parameter T25, the Window Rotation Timer.
Default=1500." 
::= { ux25AdmnTimerEntry 8 }

ux25AdmnIntrptTime OBJECT-TYPE
SYNTAX INTEGER (0..32000)
ACCESS read-write
STATUS mandatory
DESCRIPTION
"The number of ticks (0.1 second units) for the DTE timer 
parameter T26, the Interrupt Response Timer.
Default=1800." 
::= { ux25AdmnTimerEntry 9 }

ux25AdmnIdleValue OBJECT-TYPE
SYNTAX INTEGER (0..32000)
ACCESS read-write
STATUS mandatory
DESCRIPTION
"The number of ticks (0.1 second units) during which a link 
level connection associated with no connections will be 
maintained. If the link is to a WAN then this value should 
be zero (infinity).  This timer is only used with X.25 on a 
LAN.
Default=0."
::= { ux25AdmnTimerEntry 10 }

ux25AdmnConnectValue OBJECT-TYPE
SYNTAX INTEGER (0..32000)
ACCESS read-write
STATUS mandatory
DESCRIPTION
"Specifies the number of ticks (0.1 second units), over 
which the DTE/DCE resolution phase be completely 
implemented in order to prevent the unlikely event that two 
packet level entities cannot resolve their DTE/DCE nature. 
When this expires, the link connection will be disconnected 
and all pending connections aborted.
Default=2000."
::= { ux25AdmnTimerEntry 11 }

ux25AdmnRstrtCnt OBJECT-TYPE
SYNTAX INTEGER (1..255)
ACCESS read-write
STATUS mandatory
DESCRIPTION
"The number of ticks (0.1 second units) for the DTE Restart 
Request Retransmission Count.
Default=1." 
::= { ux25AdmnTimerEntry 12 }

ux25AdmnRstCnt OBJECT-TYPE
SYNTAX INTEGER (1..255)
ACCESS read-write
STATUS mandatory
DESCRIPTION
"The number of ticks (0.1 second units) for the DTE Reset 
Request Retransmission Count.
Default=1." 
::= { ux25AdmnTimerEntry 13 }

ux25AdmnClrCnt OBJECT-TYPE
SYNTAX INTEGER (1..255)
ACCESS read-write
STATUS mandatory
DESCRIPTION
"The number of ticks (0.1 second units) for the DTE Clear 
Request Retransmission Count.
Default=1." 
::= { ux25AdmnTimerEntry 14 }

ux25AdmnLocalDelay OBJECT-TYPE
SYNTAX INTEGER (0..32000)
ACCESS read-write
STATUS mandatory
DESCRIPTION
"The transit delay (in 0.1 second units) attributed to 
internal processing.
Default=5."
::= { ux25AdmnTimerEntry 15 }

ux25AdmnAccessDelay OBJECT-TYPE
SYNTAX INTEGER (0..32000)
ACCESS read-write
STATUS mandatory
DESCRIPTION
"The transit delay (in 0.1 second units) attributed to the 
effect of the line transmission rate.
Default=5."
::= { ux25AdmnTimerEntry 16 }

ux25OperChannelTable OBJECT-TYPE
SYNTAX SEQUENCE OF Ux25OperChannelEntry
ACCESS not-accessible
STATUS mandatory
DESCRIPTION
"Defines objects that report the current parameters used by 
a running interface.  These objects are read only."
::= { ux25 6 }

ux25OperChannelEntry OBJECT-TYPE
SYNTAX Ux25OperChannelEntry
ACCESS not-accessible
STATUS mandatory
DESCRIPTION
"Entries of ux25OperChannelTable."
INDEX { ux25OperChannelIndex }
::= { ux25OperChannelTable 1 }

Ux25OperChannelEntry ::=
SEQUENCE {
ux25OperChannelIndex
    INTEGER,
ux25OperNetMode
    INTEGER,
ux25OperProtocolVersion
    INTEGER,
ux25OperInterfaceMode
    INTEGER,
ux25OperLowestPVCVal
    INTEGER,
ux25OperHighestPVCVal
    INTEGER,
ux25OperChannelLIC
    INTEGER,
ux25OperChannelHIC
    INTEGER,
ux25OperChannelLTC
    INTEGER,
ux25OperChannelHTC
    INTEGER,
ux25OperChannelLOC
    INTEGER,
ux25OperChannelHOC
    INTEGER
}

ux25OperChannelIndex OBJECT-TYPE
SYNTAX INTEGER
ACCESS read-only
STATUS mandatory
DESCRIPTION
""
::= { ux25OperChannelEntry 1 }

ux25OperNetMode OBJECT-TYPE
SYNTAX INTEGER{
  x25Llc(1),
  x2588(2),
  x2584(3),
  x2580(4),
  pss(5),
  austpac(6),
  datapac(7),
  ddn(8),
  telenet(9),
  transpac(10),
  tymnet(11),
  datexP(12),
  ddxP(13),
  venusP(14),
  accunet(15),
  itapac(16),
  datapak(17),
  datanet(18),
  dcs(19),
  telepac(20),
  fDatapac(21),
  finpac(22),
  pacnet(23),
  luxpac(24)
}
ACCESS read-only
STATUS mandatory
DESCRIPTION
""
::= { ux25OperChannelEntry 2 }

ux25OperProtocolVersion OBJECT-TYPE
SYNTAX INTEGER{
  x25ver80(1),
  x25ver84(2),
  x25ver88(3)
}
ACCESS read-only
STATUS mandatory
DESCRIPTION
""
::= { ux25OperChannelEntry 3 }

ux25OperInterfaceMode OBJECT-TYPE
SYNTAX INTEGER{
  dceMode(1),
  dteMode(2),
  dxeMode(3)
}
ACCESS read-only
STATUS mandatory
DESCRIPTION
""
::= { ux25OperChannelEntry 4 }

ux25OperLowestPVCVal OBJECT-TYPE
SYNTAX INTEGER (0..4095)
ACCESS read-only
STATUS mandatory
DESCRIPTION
""
::= { ux25OperChannelEntry 5 }

ux25OperHighestPVCVal OBJECT-TYPE
SYNTAX INTEGER (0..4095)
ACCESS read-only
STATUS mandatory
DESCRIPTION
""
::= { ux25OperChannelEntry 6 }

ux25OperChannelLIC OBJECT-TYPE
SYNTAX INTEGER (0..4095)
ACCESS read-only
STATUS mandatory
DESCRIPTION
""
::= { ux25OperChannelEntry 7 }

ux25OperChannelHIC OBJECT-TYPE
SYNTAX INTEGER (0..4095)
ACCESS read-only
STATUS mandatory
DESCRIPTION
""
::= { ux25OperChannelEntry 8 }

ux25OperChannelLTC OBJECT-TYPE
SYNTAX INTEGER (0..4095)
ACCESS read-only
STATUS mandatory
DESCRIPTION
""
::= { ux25OperChannelEntry 9 }

ux25OperChannelHTC OBJECT-TYPE
SYNTAX INTEGER (0..4095)
ACCESS read-only
STATUS mandatory
DESCRIPTION
""
::= { ux25OperChannelEntry 10 }

ux25OperChannelLOC OBJECT-TYPE
SYNTAX INTEGER (0..4095)
ACCESS read-only
STATUS mandatory
DESCRIPTION
""
::= { ux25OperChannelEntry 11 }

ux25OperChannelHOC OBJECT-TYPE
SYNTAX INTEGER (0..4095)
ACCESS read-only
STATUS mandatory
DESCRIPTION
""
::= { ux25OperChannelEntry 12 }

ux25OperClassTable OBJECT-TYPE
SYNTAX SEQUENCE OF Ux25OperClassEntry
ACCESS not-accessible
STATUS mandatory
DESCRIPTION
"Defines objects that report the current parameters used by 
a running interface.  These objects are read only."
::= { ux25 7 }

ux25OperClassEntry OBJECT-TYPE
SYNTAX Ux25OperClassEntry
ACCESS not-accessible
STATUS mandatory
DESCRIPTION
"Entries of ux25OperTable."
INDEX { ux25OperClassIndex }
::= { ux25OperClassTable 1 }

Ux25OperClassEntry ::=
SEQUENCE {
ux25OperClassIndex
    INTEGER,
ux25OperLocMaxThruPutClass
    INTEGER,
ux25OperRemMaxThruPutClass
    INTEGER,
ux25OperLocDefThruPutClass
    INTEGER,
ux25OperRemDefThruPutClass
    INTEGER,
ux25OperLocMinThruPutClass
    INTEGER,
ux25OperRemMinThruPutClass
    INTEGER,
ux25OperThclassNegToDef
    INTEGER,
ux25OperThclassType
    INTEGER,
ux25OperThclassWinMap
    DisplayString,
ux25OperThclassPackMap
    DisplayString
}

ux25OperClassIndex OBJECT-TYPE
SYNTAX INTEGER
ACCESS read-only
STATUS mandatory
DESCRIPTION
""
::= { ux25OperClassEntry 1 }

ux25OperLocMaxThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 2 }

ux25OperRemMaxThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 3 }

ux25OperLocDefThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 4 }

ux25OperRemDefThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 5 }

ux25OperLocMinThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 6 }

ux25OperRemMinThruPutClass OBJECT-TYPE
SYNTAX INTEGER{
  tcReserved0(1),
  tcReserved1(2),
  tcReserved2(3),
  tc75(4),
  tc150(5),
  tc300(6),
  tc600(7),
  tc1200(8),
  tc2400(9),
  tc4800(10),
  tc9600(11),
  tc19200(12),
  tc48000(13),
  tcReserved13(14),
  tcReserved14(15),
  tcReserved15(16)
}
ACCESS read-only
STATUS mandatory
DESCRIPTION
""
::= { ux25OperClassEntry 7 }

ux25OperThclassNegToDef OBJECT-TYPE
SYNTAX INTEGER{
  disable(1),
  enable(2)
}
ACCESS read-only
STATUS mandatory
DESCRIPTION
""
::= { ux25OperClassEntry 8 }

ux25OperThclassType OBJECT-TYPE
SYNTAX INTEGER{
  noTcType(1),
  loNibble(2),
  highNibble(3),
  bothNibbles(4)
}
ACCESS read-only
STATUS mandatory
DESCRIPTION
""
::= { ux25OperClassEntry 9 }

ux25OperThclassWinMap OBJECT-TYPE
SYNTAX DisplayString (SIZE(31..63))
ACCESS read-only
STATUS mandatory
DESCRIPTION
""
::= { ux25OperClassEntry 10 }

ux25OperThclassPackMap OBJECT-TYPE
SYNTAX DisplayString (SIZE(31..47))
ACCESS read-only
STATUS mandatory
DESCRIPTION
""
::= { ux25OperClassEntry 11 }

ux25OperPacketTable OBJECT-TYPE
SYNTAX SEQUENCE OF Ux25OperPacketEntry
ACCESS not-accessible
STATUS mandatory
DESCRIPTION
"Defines objects that report the current parameters used by 
a running interface.  These objects are read only."
::= { ux25 8 }

ux25OperPacketEntry OBJECT-TYPE
SYNTAX Ux25OperPacketEntry
ACCESS not-accessible
STATUS mandatory
DESCRIPTION
"Entries of ux25OperPacketTable."
INDEX { ux25OperPacketIndex }
::= { ux25OperPacketTable 1 }

Ux25OperPacketEntry ::=
SEQUENCE {
ux25OperPacketIndex
    INTEGER,
ux25OperPktSequencing
    INTEGER,
ux25OperLocMaxPktSize
    INTEGER,
ux25OperRemMaxPktSize
    INTEGER,
ux25OperLocDefPktSize
    INTEGER,
ux25OperRemDefPktSize
    INTEGER,
ux25OperLocMaxWinSize
    INTEGER,
ux25OperRemMaxWinSize
    INTEGER,
ux25OperLocDefWinSize
    INTEGER,
ux25OperRemDefWinSize
    INTEGER,
ux25OperMaxNSDULimit
    INTEGER,
ux25OperAccNoDiagnostic
    INTEGER,
ux25OperUseDiagnosticPacket
    INTEGER,
ux25OperItutClearLen
    INTEGER,
ux25OperBarDiagnosticPacket
    INTEGER,
ux25OperDiscNzDiagnostic
    INTEGER,
ux25OperAcceptHexAdd
    INTEGER,
ux25OperBarNonPrivilegeListen
    INTEGER,
ux25OperIntlAddrRecognition
    INTEGER,
ux25OperDnic
    DisplayString,
ux25OperIntlPrioritized
    INTEGER,
ux25OperPrtyEncodeCtrl
    INTEGER,
ux25OperPrtyPktForcedVal
    INTEGER,
ux25OperSrcAddrCtrl
    INTEGER,
ux25OperDbitInAccept
    INTEGER,
ux25OperDbitOutAccept
    INTEGER,
ux25OperDbitInData
    INTEGER,
ux25OperDbitOutData
    INTEGER
}

ux25OperPacketIndex OBJECT-TYPE
SYNTAX INTEGER
ACCESS read-only
STATUS mandatory
DESCRIPTION
""
::= { ux25OperPacketEntry 1 }

ux25OperPktSequencing OBJECT-TYPE
SYNTAX INTEGER{
  pktSeq8(16),
  pktSeq128(32)
}
ACCESS read-only
STATUS mandatory
DESCRIPTION
""
::= { ux25OperPacketEntry 2 }

ux25OperLocMaxPktSize OBJECT-TYPE
SYNTAX INTEGER{
  maxPktSz128(7),
  maxPktSz256(8),
  maxPktSz512(9)
}
ACCESS read-only
STATUS mandatory
DESCRIPTION
""
::= { ux25OperPacketEntry 3 }

ux25OperRemMaxPktSize OBJECT-TYPE
SYNTAX INTEGER{
  maxPktSz128(7),
  maxPktSz256(8),
  maxPktSz512(9)
}
ACCESS read-only
STATUS mandatory
DESCRIPTION
""
::= { ux25OperPacketEntry 4 }

ux25OperLocDefPktSize OBJECT-TYPE
SYNTAX INTEGER{
  defPktSz16(4),
  defPktSz32(5),
  defPktSz64(6),
  defPktSz128(7),
  defPktSz256(8),
  defPktSz512(9)
}
ACCESS read-only
STATUS mandatory
DESCRIPTION
""
::= { ux25OperPacketEntry 5 }

ux25OperRemDefPktSize OBJECT-TYPE
SYNTAX INTEGER{
  defPktSz16(4),
  defPktSz32(5),
  defPktSz64(6),
  defPktSz128(7),
  defPktSz256(8),
  defPktSz512(9)
}
ACCESS read-only
STATUS mandatory
DESCRIPTION
""
::= { ux25OperPacketEntry 6 }

ux25OperLocMaxWinSize OBJECT-TYPE
SYNTAX INTEGER (2..127)
ACCESS read-only
STATUS mandatory
DESCRIPTION
""
::= { ux25OperPacketEntry 7 }

ux25OperRemMaxWinSize OBJECT-TYPE
SYNTAX INTEGER (2..127)
ACCESS read-only
STATUS mandatory
DESCRIPTION
""
::= { ux25OperPacketEntry 8 }

ux25OperLocDefWinSize OBJECT-TYPE
SYNTAX INTEGER (1..127)
ACCESS read-only
STATUS mandatory
DESCRIPTION
""
::= { ux25OperPacketEntry 9 }

ux25OperRemDefWinSize OBJECT-TYPE
SYNTAX INTEGER (1..127)
ACCESS read-only
STATUS mandatory
DESCRIPTION
""
::= { ux25OperPacketEntry 10 }

ux25OperMaxNSDULimit OBJECT-TYPE
SYNTAX INTEGER (0..32000)
ACCESS read-only
STATUS mandatory
DESCRIPTION
""
::= { ux25OperPacketEntry 11 }

ux25OperAccNoDiagnostic OBJECT-TYPE
SYNTAX INTEGER{
  disable(1),
  enable(2)
}
ACCESS read-only
STATUS mandatory
DESCRIPTION
""
::= { ux25OperPacketEntry 12 }

ux25OperUseDiagnosticPacket OBJECT-TYPE
SYNTAX INTEGER{
  disable(1),
  enable(2)
}
ACCESS read-only
STATUS mandatory
DESCRIPTION
""
::= { ux25OperPacketEntry 13 }

ux25OperItutClearLen OBJECT-TYPE
SYNTAX INTEGER{
  disable(1),
  enable(2)
}
ACCESS read-only
STATUS mandatory
DESCRIPTION
""
::= { ux25OperPacketEntry 14 }

ux25OperBarDiagnosticPacket OBJECT-TYPE
SYNTAX INTEGER{
  disable(1),
  enable(2)
}
ACCESS read-only
STATUS mandatory
DESCRIPTION
""
::= { ux25OperPacketEntry 15 }

ux25OperDiscNzDiagnostic OBJECT-TYPE
SYNTAX INTEGER{
  disable(1),
  enable(2)
}
ACCESS read-only
STATUS mandatory
DESCRIPTION
""
::= { ux25OperPacketEntry 16 }

ux25OperAcceptHexAdd OBJECT-TYPE
SYNTAX INTEGER{
  disable(1),
  enable(2)
}
ACCESS read-only
STATUS mandatory
DESCRIPTION
""
::= { ux25OperPacketEntry 17 }

ux25OperBarNonPrivilegeListen OBJECT-TYPE
SYNTAX INTEGER{
  disable(1),
  enable(2)
}
ACCESS read-only
STATUS mandatory
DESCRIPTION
""
::= { ux25OperPacketEntry 18 }

ux25OperIntlAddrRecognition OBJECT-TYPE
SYNTAX INTEGER{
  notDistinguished(1),
  examineDnic(2),
  prefix1(3),
  prefix0(4)
}
ACCESS read-only
STATUS mandatory
DESCRIPTION
""
::= { ux25OperPacketEntry 19 }

ux25OperDnic OBJECT-TYPE
SYNTAX DisplayString (SIZE(4..4))
ACCESS read-only
STATUS mandatory
DESCRIPTION
""
::= { ux25OperPacketEntry 20 }

ux25OperIntlPrioritized OBJECT-TYPE
SYNTAX INTEGER{
  disable(1),
  enable(2)
}
ACCESS read-only
STATUS mandatory
DESCRIPTION
""
::= { ux25OperPacketEntry 21 }

ux25OperPrtyEncodeCtrl OBJECT-TYPE
SYNTAX INTEGER{
  x2588(1),
  datapacPriority76(2),
  datapacTraffic80(3)
}
ACCESS read-only
STATUS mandatory
DESCRIPTION
""
::= { ux25OperPacketEntry 22 }

ux25OperPrtyPktForcedVal OBJECT-TYPE
SYNTAX INTEGER{
  prioPktSz0(1),
  prioPktSz4(5),
  prioPktSz5(6),
  prioPktSz6(7),
  prioPktSz7(8),
  prioPktSz8(9),
  prioPktSz9(10),
  prioPktSz10(11),
  prioPktSz11(12),
  prioPktSz12(13)
}
ACCESS read-only
STATUS mandatory
DESCRIPTION
""
::= { ux25OperPacketEntry 23 }

ux25OperSrcAddrCtrl OBJECT-TYPE
SYNTAX INTEGER{
  noSaCntrl(1),
  omitDte(2),
  useLocal(3),
  forceLocal(4)
}
ACCESS read-only
STATUS mandatory
DESCRIPTION
""
::= { ux25OperPacketEntry 24 }

ux25OperDbitInAccept OBJECT-TYPE
SYNTAX INTEGER{
  leaveDbit(1),
  zeroDbit(2),
  clearCall(3)
}
ACCESS read-only
STATUS mandatory
DESCRIPTION
""
::= { ux25OperPacketEntry 25 }

ux25OperDbitOutAccept OBJECT-TYPE
SYNTAX INTEGER{
  leaveDbit(1),
  zeroDbit(2),
  clearCall(3)
}
ACCESS read-only
STATUS mandatory
DESCRIPTION
""
::= { ux25OperPacketEntry 26 }

ux25OperDbitInData OBJECT-TYPE
SYNTAX INTEGER{
  leaveDbit(1),
  zeroDbit(2),
  clearCall(3)
}
ACCESS read-only
STATUS mandatory
DESCRIPTION
""
::= { ux25OperPacketEntry 27 }

ux25OperDbitOutData OBJECT-TYPE
SYNTAX INTEGER{
  leaveDbit(1),
  zeroDbit(2),
  clearCall(3)
}
ACCESS read-only
STATUS mandatory
DESCRIPTION
""
::= { ux25OperPacketEntry 28 }

ux25OperSubscriberTable OBJECT-TYPE
SYNTAX SEQUENCE OF Ux25OperSubscriberEntry
ACCESS not-accessible
STATUS mandatory
DESCRIPTION
"Defines objects that report the current parameters used by 
a running interface.  These objects are read only."
::= { ux25 9 }

ux25OperSubscriberEntry OBJECT-TYPE
SYNTAX Ux25OperSubscriberEntry
ACCESS not-accessible
STATUS mandatory
DESCRIPTION
"Entries of ux25OperSubscriberTable."
INDEX { ux25OperSubscriberIndex }
::= { ux25OperSubscriberTable 1 }

Ux25OperSubscriberEntry ::=
SEQUENCE {
ux25OperSubscriberIndex
    INTEGER,
ux25OperSubCugIaoa
    INTEGER,
ux25OperSubCugPref
    INTEGER,
ux25OperSubCugoa
    INTEGER,
ux25OperSubCugia
    INTEGER,
ux25OperCugFormat
    INTEGER,
ux25OperBarInCug
    INTEGER,
ux25OperSubExtended
    INTEGER,
ux25OperBarExtended
    INTEGER,
ux25OperSubFstSelNoRstrct
    INTEGER,
ux25OperSubFstSelWthRstrct
    INTEGER,
ux25OperAccptRvsChrgng
    INTEGER,
ux25OperSubLocChargePrevent
    INTEGER,
ux25OperSubToaNpiFormat
    INTEGER,
ux25OperBarToaNpiFormat
    INTEGER,
ux25OperSubNuiOverride
    INTEGER,
ux25OperBarInCall
    INTEGER,
ux25OperBarOutCall
    INTEGER
}

ux25OperSubscriberIndex OBJECT-TYPE
SYNTAX INTEGER
ACCESS read-only
STATUS mandatory
DESCRIPTION
""
::= { ux25OperSubscriberEntry 1 }

ux25OperSubCugIaoa OBJECT-TYPE
SYNTAX INTEGER{
  disable(1),
  enable(2)
}
ACCESS read-only
STATUS mandatory
DESCRIPTION
""
::= { ux25OperSubscriberEntry 2 }

ux25OperSubCugPref OBJECT-TYPE
SYNTAX INTEGER{
  disable(1),
  enable(2)
}
ACCESS read-only
STATUS mandatory
DESCRIPTION
""
::= { ux25OperSubscriberEntry 3 }

ux25OperSubCugoa OBJECT-TYPE
SYNTAX INTEGER{
  disable(1),
  enable(2)
}
ACCESS read-only
STATUS mandatory
DESCRIPTION
""
::= { ux25OperSubscriberEntry 4 }

ux25OperSubCugia OBJECT-TYPE
SYNTAX INTEGER{
  disable(1),
  enable(2)
}
ACCESS read-only
STATUS mandatory
DESCRIPTION
""
::= { ux25OperSubscriberEntry 5 }

ux25OperCugFormat OBJECT-TYPE
SYNTAX INTEGER{
  basic(1),
  extended(2)
}
ACCESS read-only
STATUS mandatory
DESCRIPTION
""
::= { ux25OperSubscriberEntry 6 }

ux25OperBarInCug OBJECT-TYPE
SYNTAX INTEGER{
  disable(1),
  enable(2)
}
ACCESS read-only
STATUS mandatory
DESCRIPTION
""
::= { ux25OperSubscriberEntry 7 }

ux25OperSubExtended OBJECT-TYPE
SYNTAX INTEGER{
  disable(1),
  enable(2)
}
ACCESS read-only
STATUS mandatory
DESCRIPTION
""
::= { ux25OperSubscriberEntry 8 }

ux25OperBarExtended OBJECT-TYPE
SYNTAX INTEGER{
  disable(1),
  enable(2)
}
ACCESS read-only
STATUS mandatory
DESCRIPTION
""
::= { ux25OperSubscriberEntry 9 }

ux25OperSubFstSelNoRstrct OBJECT-TYPE
SYNTAX INTEGER{
  disable(1),
  enable(2)
}
ACCESS read-only
STATUS mandatory
DESCRIPTION
""
::= { ux25OperSubscriberEntry 10 }

ux25OperSubFstSelWthRstrct OBJECT-TYPE
SYNTAX INTEGER{
  disable(1),
  enable(2)
}
ACCESS read-only
STATUS mandatory
DESCRIPTION
""
::= { ux25OperSubscriberEntry 11 }

ux25OperAccptRvsChrgng OBJECT-TYPE
SYNTAX INTEGER{
  disable(1),
  enable(2)
}
ACCESS read-only
STATUS mandatory
DESCRIPTION
""
::= { ux25OperSubscriberEntry 12 }

ux25OperSubLocChargePrevent OBJECT-TYPE
SYNTAX INTEGER{
  disable(1),
  enable(2)
}
ACCESS read-only
STATUS mandatory
DESCRIPTION
""
::= { ux25OperSubscriberEntry 13 }

ux25OperSubToaNpiFormat OBJECT-TYPE
SYNTAX INTEGER{
  disable(1),
  enable(2)
}
ACCESS read-only
STATUS mandatory
DESCRIPTION
""
::= { ux25OperSubscriberEntry 14 }

ux25OperBarToaNpiFormat OBJECT-TYPE
SYNTAX INTEGER{
  disable(1),
  enable(2)
}
ACCESS read-only
STATUS mandatory
DESCRIPTION
""
::= { ux25OperSubscriberEntry 15 }

ux25OperSubNuiOverride OBJECT-TYPE
SYNTAX INTEGER{
  disable(1),
  enable(2)
}
ACCESS read-only
STATUS mandatory
DESCRIPTION
""
::= { ux25OperSubscriberEntry 16 }

ux25OperBarInCall OBJECT-TYPE
SYNTAX INTEGER{
  disable(1),
  enable(2)
}
ACCESS read-only
STATUS mandatory
DESCRIPTION
""
::= { ux25OperSubscriberEntry 17 }

ux25OperBarOutCall OBJECT-TYPE
SYNTAX INTEGER{
  disable(1),
  enable(2)
}
ACCESS read-only
STATUS mandatory
DESCRIPTION
""
::= { ux25OperSubscriberEntry 18 }

ux25OperTimerTable OBJECT-TYPE
SYNTAX SEQUENCE OF Ux25OperTimerEntry
ACCESS not-accessible
STATUS mandatory
DESCRIPTION
"Defines objects that report the current parameters used by 
a running interface.  These objects are read only."
::= { ux25 10 }

ux25OperTimerEntry OBJECT-TYPE
SYNTAX Ux25OperTimerEntry
ACCESS not-accessible
STATUS mandatory
DESCRIPTION
"Entries of ux25OperTimerTable."
INDEX { ux25OperTimerIndex }
::= { ux25OperTimerTable 1 }

Ux25OperTimerEntry ::=
SEQUENCE {
ux25OperTimerIndex
    INTEGER,
ux25OperAckDelay
    INTEGER,
ux25OperRstrtTime
    INTEGER,
ux25OperCallTime
    INTEGER,
ux25OperRstTime
    INTEGER,
ux25OperClrTime
    INTEGER,
ux25OperWinStatTime
    INTEGER,
ux25OperWinRotTime
    INTEGER,
ux25OperIntrptTime
    INTEGER,
ux25OperIdleValue
    INTEGER,
ux25OperConnectValue
    INTEGER,
ux25OperRstrtCnt
    INTEGER,
ux25OperRstCnt
    INTEGER,
ux25OperClrCnt
    INTEGER,
ux25OperLocalDelay
    INTEGER,
ux25OperAccessDelay
    INTEGER
}

ux25OperTimerIndex OBJECT-TYPE
SYNTAX INTEGER
ACCESS read-only
STATUS mandatory
DESCRIPTION
""
::= { ux25OperTimerEntry 1 }

ux25OperAckDelay OBJECT-TYPE
SYNTAX INTEGER (0..32000)
ACCESS read-only
STATUS mandatory
DESCRIPTION
""
::= { ux25OperTimerEntry 2 }

ux25OperRstrtTime OBJECT-TYPE
SYNTAX INTEGER (0..32000)
ACCESS read-only
STATUS mandatory
DESCRIPTION
""
::= { ux25OperTimerEntry 3 }

ux25OperCallTime OBJECT-TYPE
SYNTAX INTEGER (0..32000)
ACCESS read-only
STATUS mandatory
DESCRIPTION
""
::= { ux25OperTimerEntry 4 }

ux25OperRstTime OBJECT-TYPE
SYNTAX INTEGER (0..32000)
ACCESS read-only
STATUS mandatory
DESCRIPTION
""
::= { ux25OperTimerEntry 5 }

ux25OperClrTime OBJECT-TYPE
SYNTAX INTEGER (0..32000)
ACCESS read-only
STATUS mandatory
DESCRIPTION
""
::= { ux25OperTimerEntry 6 }

ux25OperWinStatTime OBJECT-TYPE
SYNTAX INTEGER (0..32000)
ACCESS read-only
STATUS mandatory
DESCRIPTION
""
::= { ux25OperTimerEntry 7 }

ux25OperWinRotTime OBJECT-TYPE
SYNTAX INTEGER (0..32000)
ACCESS read-only
STATUS mandatory
DESCRIPTION
""
::= { ux25OperTimerEntry 8 }

ux25OperIntrptTime OBJECT-TYPE
SYNTAX INTEGER (0..32000)
ACCESS read-only
STATUS mandatory
DESCRIPTION
""
::= { ux25OperTimerEntry 9 }

ux25OperIdleValue OBJECT-TYPE
SYNTAX INTEGER (0..32000)
ACCESS read-only
STATUS mandatory
DESCRIPTION
""
::= { ux25OperTimerEntry 10 }

ux25OperConnectValue OBJECT-TYPE
SYNTAX INTEGER (0..32000)
ACCESS read-only
STATUS mandatory
DESCRIPTION
""
::= { ux25OperTimerEntry 11 }

ux25OperRstrtCnt OBJECT-TYPE
SYNTAX INTEGER (1..255)
ACCESS read-only
STATUS mandatory
DESCRIPTION
""
::= { ux25OperTimerEntry 12 }

ux25OperRstCnt OBJECT-TYPE
SYNTAX INTEGER (1..255)
ACCESS read-only
STATUS mandatory
DESCRIPTION
""
::= { ux25OperTimerEntry 13 }

ux25OperClrCnt OBJECT-TYPE
SYNTAX INTEGER (1..255)
ACCESS read-only
STATUS mandatory
DESCRIPTION
""
::= { ux25OperTimerEntry 14 }

ux25OperLocalDelay OBJECT-TYPE
SYNTAX INTEGER (0..32000)
ACCESS read-only
STATUS mandatory
DESCRIPTION
""
::= { ux25OperTimerEntry 15 }

ux25OperAccessDelay OBJECT-TYPE
SYNTAX INTEGER (0..32000)
ACCESS read-only
STATUS mandatory
DESCRIPTION
""
::= { ux25OperTimerEntry 16 }

ux25StatTable OBJECT-TYPE
SYNTAX SEQUENCE OF Ux25StatEntry
ACCESS not-accessible
STATUS mandatory
DESCRIPTION
"Defines objects that report operational statistics for an 
X.25 interface."
::= { ux25 11 }

ux25StatEntry OBJECT-TYPE
SYNTAX Ux25StatEntry
ACCESS not-accessible
STATUS mandatory
DESCRIPTION
"Entries of ux25StatTable."
INDEX { ux25StatIndex }
::= { ux25StatTable 1 }

Ux25StatEntry ::=
SEQUENCE {
ux25StatIndex
    INTEGER,
ux25StatCallsRcvd
    INTEGER,
ux25StatCallsSent
    INTEGER,
ux25StatCallsRcvdEstab
    INTEGER,
ux25StatCallsSentEstab
    INTEGER,
ux25StatDataPktsRcvd
    INTEGER,
ux25StatDataPktsSent
    INTEGER,
ux25StatRestartsRcvd
    INTEGER,
ux25StatRestartsSent
    INTEGER,
ux25StatRcvrNotRdyRcvd
    INTEGER,
ux25StatRcvrNotRdySent
    INTEGER,
ux25StatRcvrRdyRcvd
    INTEGER,
ux25StatRcvrRdySent
    INTEGER,
ux25StatResetsRcvd
    INTEGER,
ux25StatResetsSent
    INTEGER,
ux25StatDiagPktsRcvd
    INTEGER,
ux25StatDiagPktsSent
    INTEGER,
ux25StatIntrptPktsRcvd
    INTEGER,
ux25StatIntrptPktsSent
    INTEGER,
ux25StatPVCsInDatTrnsfrState
    INTEGER,
ux25StatSVCsInDatTrnsfrState
    INTEGER
}

ux25StatIndex OBJECT-TYPE
SYNTAX INTEGER
ACCESS read-only
STATUS mandatory
DESCRIPTION
"A unique value for each X.25 subnetwork entity in the 
chassis.  The value of this object matches the value of the 
index of the corresponding X.25 subnetwork entity entry in 
the entity table of the chassis MIB."
::= { ux25StatEntry 1 }

ux25StatCallsRcvd OBJECT-TYPE
SYNTAX INTEGER
ACCESS read-only
STATUS mandatory
DESCRIPTION
"Number of incoming calls."
::= { ux25StatEntry 2 }

ux25StatCallsSent OBJECT-TYPE
SYNTAX INTEGER
ACCESS read-only
STATUS mandatory
DESCRIPTION
"Number of outgoing calls."
::= { ux25StatEntry 3 }

ux25StatCallsRcvdEstab OBJECT-TYPE
SYNTAX INTEGER
ACCESS read-only
STATUS mandatory
DESCRIPTION
"Number of incoming calls established."
::= { ux25StatEntry 4 }

ux25StatCallsSentEstab OBJECT-TYPE
SYNTAX INTEGER
ACCESS read-only
STATUS mandatory
DESCRIPTION
"Number of outgoing calls established."
::= { ux25StatEntry 5 }

ux25StatDataPktsRcvd OBJECT-TYPE
SYNTAX INTEGER
ACCESS read-only
STATUS mandatory
DESCRIPTION
"Number of data packets received."
::= { ux25StatEntry 6 }

ux25StatDataPktsSent OBJECT-TYPE
SYNTAX INTEGER
ACCESS read-only
STATUS mandatory
DESCRIPTION
"Number of data packets sent."
::= { ux25StatEntry 7 }

ux25StatRestartsRcvd OBJECT-TYPE
SYNTAX INTEGER
ACCESS read-only
STATUS mandatory
DESCRIPTION
"Number of restarts received."
::= { ux25StatEntry 8 }

ux25StatRestartsSent OBJECT-TYPE
SYNTAX INTEGER
ACCESS read-only
STATUS mandatory
DESCRIPTION
"Number of restarts sent."
::= { ux25StatEntry 9 }

ux25StatRcvrNotRdyRcvd OBJECT-TYPE
SYNTAX INTEGER
ACCESS read-only
STATUS mandatory
DESCRIPTION
"Number of receiver not ready received."
::= { ux25StatEntry 10 }

ux25StatRcvrNotRdySent OBJECT-TYPE
SYNTAX INTEGER
ACCESS read-only
STATUS mandatory
DESCRIPTION
"Number of receiver not ready sent."
::= { ux25StatEntry 11 }

ux25StatRcvrRdyRcvd OBJECT-TYPE
SYNTAX INTEGER
ACCESS read-only
STATUS mandatory
DESCRIPTION
"Number of receiver ready received."
::= { ux25StatEntry 12 }

ux25StatRcvrRdySent OBJECT-TYPE
SYNTAX INTEGER
ACCESS read-only
STATUS mandatory
DESCRIPTION
"Number of receiver ready sent."
::= { ux25StatEntry 13 }

ux25StatResetsRcvd OBJECT-TYPE
SYNTAX INTEGER
ACCESS read-only
STATUS mandatory
DESCRIPTION
"Number of resets received."
::= { ux25StatEntry 14 }

ux25StatResetsSent OBJECT-TYPE
SYNTAX INTEGER
ACCESS read-only
STATUS mandatory
DESCRIPTION
"Number of resets sent."
::= { ux25StatEntry 15 }

ux25StatDiagPktsRcvd OBJECT-TYPE
SYNTAX INTEGER
ACCESS read-only
STATUS mandatory
DESCRIPTION
"Number of diagnostic packets received."
::= { ux25StatEntry 16 }

ux25StatDiagPktsSent OBJECT-TYPE
SYNTAX INTEGER
ACCESS read-only
STATUS mandatory
DESCRIPTION
"Number of diagnostic packets sent."
::= { ux25StatEntry 17 }

ux25StatIntrptPktsRcvd OBJECT-TYPE
SYNTAX INTEGER
ACCESS read-only
STATUS mandatory
DESCRIPTION
"Number of interrupt packets received."
::= { ux25StatEntry 18 }

ux25StatIntrptPktsSent OBJECT-TYPE
SYNTAX INTEGER
ACCESS read-only
STATUS mandatory
DESCRIPTION
"Number of interrupt packets sent."
::= { ux25StatEntry 19 }

ux25StatPVCsInDatTrnsfrState OBJECT-TYPE
SYNTAX INTEGER
ACCESS read-only
STATUS mandatory
DESCRIPTION
"Number of PVCs in Data Transfer State."
::= { ux25StatEntry 20 }

ux25StatSVCsInDatTrnsfrState OBJECT-TYPE
SYNTAX INTEGER
ACCESS read-only
STATUS mandatory
DESCRIPTION
"Number of SVCs in Data Transfer State."
::= { ux25StatEntry 21 }

END
