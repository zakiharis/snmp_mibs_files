-- *****************************************************************************
-- Unisphere-Data-SLEP-MIB
--
-- Unisphere Networks Inc. Enterprise MIB
-- Serial Line Encapsulation Protocol MIB
--
-- Copyright (c) 2000, 2001 Unisphere Networks, Inc.  All Rights Reserved.
-- *****************************************************************************

Unisphere-Data-SLEP-MIB DEFINITIONS ::= BEGIN

IMPORTS
    MODULE-IDENTITY, OBJECT-TYPE, Counter32
        FROM SNMPv2-SMI

    RowStatus
        FROM SNMPv2-TC

    MODULE-COMPLIANCE, OBJECT-GROUP  
        FROM SNMPv2-CONF

    InterfaceIndex, InterfaceIndexOrZero
        FROM IF-MIB

    usDataMibs
        FROM Unisphere-Data-MIBs

    UsdNextIfIndex, UsdEnable
        FROM Unisphere-Data-TC;


usdSlepMIBS  MODULE-IDENTITY
    LAST-UPDATED "200104031910Z"  -- 03-Apr-01 03:10 PM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The Serial Line Encapulation Protocol (SLEP) MIB for the 
        Unisphere Networks Inc. enterprise."
    -- Revision History
    REVISION    "200104031910Z"  -- 03-Apr-01 03:10 PM EDT  - RX 3.1
    DESCRIPTION
        "Add usdSledDownWhenLooped attribute."
    REVISION    "200001030000Z"  --  3-Jan-00               - RX 1.3
    DESCRIPTION
        "Initial version of this MIB module."
    ::= { usDataMibs 15 }

-- ++++++++++++++++++++++++++++++++++++++++++++++++++++++++++++++++++++++
-- Textual conventions
-- ++++++++++++++++++++++++++++++++++++++++++++++++++++++++++++++++++++++

-- No textual conventions are defined in this MIB.


-- ++++++++++++++++++++++++++++++++++++++++++++++++++++++++++++++++++++++
-- Managed objects
-- ++++++++++++++++++++++++++++++++++++++++++++++++++++++++++++++++++++++

usdSlepObjects     OBJECT IDENTIFIER ::= { usdSlepMIBS 1 }

-- 
-- This MIB contains managed objects for the Serial Line Encapulation
--  Protocol sublayer interface.
--
-- Management objects are provided to query for an available
-- interface index, and to create/delete interfaces of that type.
-- Creating/deleting these interface types using this MIB has the
-- side effect of creating/deleting corresponding entries in the
-- Interface MIB ifTable/ifXTable, and in the Unisphere Enterprise
-- Interface MIB usdIfTable.
--

usdSlepIfLayer    OBJECT IDENTIFIER ::= { usdSlepObjects 1 }

-- //////////////////////////////////////////////////////////////////////
--
-- Serial Line Encapulation Interface Layer
--
-- This layer is managed with the following elements:
--
--  o NextIfIndex (generator for SLEP Ifndex selection)
--  o Interface Table (creation/configuration/deletion of SLEP interfaces)
--
-- //////////////////////////////////////////////////////////////////////

--
-- IfIndex selection for creating new SLEP interfaces
--

usdSlepNextIfIndex OBJECT-TYPE
    SYNTAX      UsdNextIfIndex
    MAX-ACCESS  read-only
    STATUS      current
    DESCRIPTION
        "Coordinate ifIndex value allocation for entries in usdSlepIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdSlepIfLayer 1 }

--
-- The Slep Interface Table
--

usdSlepIfTable OBJECT-TYPE
    SYNTAX      SEQUENCE OF UsdSlepIfEntry
    MAX-ACCESS  not-accessible
    STATUS      current
    DESCRIPTION
        "The parameters for the SLEP service on this interface."        
    ::= { usdSlepIfLayer 2 }

usdSlepIfEntry OBJECT-TYPE
    SYNTAX      UsdSlepIfEntry
    MAX-ACCESS  not-accessible
    STATUS      current
    DESCRIPTION
        "The Parameters for a particular SLEP interface. 

        Creating/deleting entries in this table causes corresponding entries for
        be created/deleted in ifTable/ifXTable/usdIfTable"

    INDEX   { usdSlepIfIndex }
    ::= { usdSlepIfTable 1 }

UsdSlepIfEntry ::= SEQUENCE {
    usdSlepIfIndex                  InterfaceIndex,
    usdSlepKeepAliveTimer           INTEGER, 
    usdSlepIfLowerIfIndex           InterfaceIndexOrZero,
    usdSlepIfRowStatus              RowStatus,
    usdSlepDownWhenLooped           UsdEnable
}

usdSlepIfIndex   OBJECT-TYPE
    SYNTAX      InterfaceIndex
    MAX-ACCESS  not-accessible 
    STATUS      current
    DESCRIPTION
        "The ifIndex value of the corresponding ifEntry."
    ::= { usdSlepIfEntry 1 }

usdSlepKeepAliveTimer OBJECT-TYPE
    SYNTAX     INTEGER (0..6553) 
    UNITS       "seconds"
    MAX-ACCESS  read-create
    STATUS      current
    DESCRIPTION
        "The interface keep alive timer for this entry.  The time in seconds
        that this entity will wait for sending a keep-alive-message to the
        remote SLEP entity, and the time in seconds that this entity will wait
        for the reception of a keep-alive-message from the remote SLEP entity."
    DEFVAL { 10 }
    ::= { usdSlepIfEntry 2 }

usdSlepIfLowerIfIndex OBJECT-TYPE
    SYNTAX      InterfaceIndexOrZero
    MAX-ACCESS  read-create
    STATUS      current
    DESCRIPTION
        "The ifIndex of an interface over which this SLEP interface is to be
        layered.  A value of zero indicates no layering.  An implementation may
        choose to require that a nonzero value be configured at entry creation."
    ::= { usdSlepIfEntry 3 }

usdSlepIfRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdSlepIfRowStatus
            usdSlepIfLowerIfIndex

        In addition, when creating an entry the following conditions must hold:

            A value for usdSlepIfIndex must have been determined previously, by
            reading usdSlepNextIfIndex.

            The interface identified by usdSlepIfLowerIfIndex must exist, and
            must be an interface type that permits layering of SLEP Interface
            above it.

        A corresponding entry in ifTable/ifXTable/usdIfTable is created/destroyed
        as a result of creating/destroying an entry in this table. "

    ::= { usdSlepIfEntry 4 }

usdSlepDownWhenLooped OBJECT-TYPE
    SYNTAX      UsdEnable
    MAX-ACCESS  read-create
    STATUS      current
    DESCRIPTION
        "The down-when-looped control for this entry.  This attribute determines
        if loop detection is enabled for the interface.  If set to disable, loop
        detection is disabled for the interface."
    DEFVAL { disable }
    ::= { usdSlepIfEntry 5 }

--
-- The Slep Interface Statistics Table
--

usdSlepIfStatisticsTable OBJECT-TYPE
    SYNTAX      SEQUENCE OF UsdSlepIfStatisticsEntry
    MAX-ACCESS  not-accessible
    STATUS      current
    DESCRIPTION
        "The statistics for the SLEP service on this interface."        
    ::= { usdSlepIfLayer 3 }

usdSlepIfStatisticsEntry OBJECT-TYPE
    SYNTAX      UsdSlepIfStatisticsEntry
    MAX-ACCESS  not-accessible
    STATUS      current
    DESCRIPTION
        "The statistics for a particular SLEP interface."
    INDEX   { usdSlepIfStatsIndex }
    ::= { usdSlepIfStatisticsTable 1 }

UsdSlepIfStatisticsEntry ::= SEQUENCE {
    usdSlepIfStatsIndex             InterfaceIndex,
    usdSlepKeepAliveFailures        Counter32,
    usdSlepLinkStatusTooLongPackets Counter32,
    usdSlepLinkStatusBadFCSs        Counter32
}

usdSlepIfStatsIndex OBJECT-TYPE
    SYNTAX      InterfaceIndex
    MAX-ACCESS  not-accessible 
    STATUS      current
    DESCRIPTION
        "The ifIndex value of that identifies this entry."
    ::= { usdSlepIfStatisticsEntry 1 }

usdSlepKeepAliveFailures OBJECT-TYPE
    SYNTAX      Counter32 
    MAX-ACCESS  read-only
    STATUS      current
    DESCRIPTION
        "The number of link drops due to keep-alive failures."
    ::= { usdSlepIfStatisticsEntry 2 }

usdSlepLinkStatusTooLongPackets OBJECT-TYPE
    SYNTAX      Counter32 
    MAX-ACCESS  read-only
    STATUS      current
    DESCRIPTION
        "The number of packets that were too long for this SLEP entity."
    ::= { usdSlepIfStatisticsEntry 3 }

usdSlepLinkStatusBadFCSs OBJECT-TYPE
    SYNTAX      Counter32 
    MAX-ACCESS  read-only
    STATUS      current
    DESCRIPTION
        "The number of FCS's errors for this SLEP entity."
    ::= { usdSlepIfStatisticsEntry 4 }


-- ++++++++++++++++++++++++++++++++++++++++++++++++++++++++++++++++++++++
-- Notification control objects
-- ++++++++++++++++++++++++++++++++++++++++++++++++++++++++++++++++++++++

-- No notifications are defined in this MIB. Placeholder follows.

-- usdSlepTrapControl      OBJECT IDENTIFIER ::= { usdSlepMIBS 2 }

-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdSlepTraps        OBJECT IDENTIFIER ::= { usdSlepMIBS 3 }
-- usdSlepPrefix       OBJECT IDENTIFIER ::= { usdSlepTraps 0 }


-- ++++++++++++++++++++++++++++++++++++++++++++++++++++++++++++++++++++++
-- Conformance information
-- ++++++++++++++++++++++++++++++++++++++++++++++++++++++++++++++++++++++

usdSlepConformance OBJECT IDENTIFIER ::= { usdSlepMIBS 4 }
usdSlepCompliances OBJECT IDENTIFIER ::= { usdSlepConformance 1 }
usdSlepGroups      OBJECT IDENTIFIER ::= { usdSlepConformance 2 }

-- compliance statements

usdSlepCompliance MODULE-COMPLIANCE
    STATUS      obsolete
    DESCRIPTION
        "Obsolete compliance statement for entities which implement the
        Unisphere SLEP MIB.  This compliance statement became obsolete when the
        usdSlepDownWhenLooped object was added."
    MODULE  -- this module
        MANDATORY-GROUPS { usdSlepGroup }
    ::= { usdSlepCompliances 1 }                                       -- RX 1.3

usdSlepCompliance2 MODULE-COMPLIANCE
    STATUS      current
    DESCRIPTION
        "The compliance statement for entities which implement the Unisphere
        SLEP MIB."
    MODULE  -- this module
        MANDATORY-GROUPS { usdSlepGroup2 }
    ::= { usdSlepCompliances 2 }                                       -- RX 3.1

-- units of conformance

usdSlepGroup OBJECT-GROUP
    OBJECTS {
        usdSlepNextIfIndex,
        usdSlepKeepAliveTimer, 
        usdSlepIfLowerIfIndex,
        usdSlepIfRowStatus,
        usdSlepKeepAliveFailures,
        usdSlepLinkStatusTooLongPackets,
        usdSlepLinkStatusBadFCSs
    }
    STATUS      obsolete
    DESCRIPTION
        "Obsolete collection of objects providing management of SLEP interfaces
        in a Unisphere product.  This group became obsolete when the
        usdSlepDownWhenLooped object was added."
    ::= { usdSlepGroups 1 }

usdSlepGroup2 OBJECT-GROUP
    OBJECTS {
        usdSlepNextIfIndex,
        usdSlepKeepAliveTimer, 
        usdSlepIfLowerIfIndex,
        usdSlepIfRowStatus,
        usdSlepDownWhenLooped,
        usdSlepKeepAliveFailures,
        usdSlepLinkStatusTooLongPackets,
        usdSlepLinkStatusBadFCSs
    }
    STATUS      current
    DESCRIPTION
        "A collection of objects providing management of SLEP interfaces in a
        Unisphere product."
    ::= { usdSlepGroups 2 }

END
