-- *****************************************************************************
-- Unisphere-Data-SMDS-MIB
--
-- Unisphere Networks Inc. Enterprise MIB
-- SMDS MIB
--
-- Copyright 2001 Unisphere Networks, Incorporated.  All Rights Reserved.
-- *****************************************************************************

Unisphere-Data-SMDS-MIB DEFINITIONS ::= BEGIN

IMPORTS
    MODULE-IDENTITY,
    OBJECT-TYPE,
    Counter32,
    Integer32
        FROM SNMPv2-SMI
    RowStatus
        FROM SNMPv2-TC
    MODULE-COMPLIANCE, 
    OBJECT-GROUP  
        FROM SNMPv2-CONF
    InterfaceIndex, InterfaceIndexOrZero
        FROM IF-MIB
    usDataMibs
        FROM Unisphere-Data-MIBs
    UsdNextIfIndex
        FROM Unisphere-Data-TC;

usdSmdsMIB  MODULE-IDENTITY
    LAST-UPDATED "200109201441Z"  -- 20-Sep-01 10:41 AM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The SMDS MIB for the Unisphere Networks Inc. enterprise."
    -- Revision History
    REVISION    "200109201441Z"  -- 20-Sep-01 10:41 AM EDT  - RX 4.0
    DESCRIPTION
        "Added support for major and sub interfaces."
    REVISION    "200103082016Z"  -- 08-Mar-01 03:16 PM EST  - RX 3.1
    DESCRIPTION
        "Initial version of this MIB module."
    ::= { usDataMibs 50 }

-- ++++++++++++++++++++++++++++++++++++++++++++++++++++++++++++++++++++++
-- Textual conventions
-- ++++++++++++++++++++++++++++++++++++++++++++++++++++++++++++++++++++++

-- No textual conventions are defined in this MIB module.

-- ++++++++++++++++++++++++++++++++++++++++++++++++++++++++++++++++++++++
-- Managed objects
-- ++++++++++++++++++++++++++++++++++++++++++++++++++++++++++++++++++++++

usdSmdsObjects     OBJECT IDENTIFIER ::= { usdSmdsMIB 1 }

-- 
-- This MIB contains managed objects for SMDS arrangements.
-- Management objects are provided to query for an available
-- interface index, and to create/delete interfaces of this type.
-- Creating/deleting this interface type using this MIB has
-- the side effect of creating/deleting corresponding entries
-- in the Interface MIB ifTable/ifXTable, and in the Unisphere
-- Enterprise Interface MIB usdIfTable.
--


-- //////////////////////////////////////////////////////////////////////
--
-- SMDS Interfaces
--
-- //////////////////////////////////////////////////////////////////////

--
-- IfIndex selection for creating new SMDS interfaces
--

usdSmdsNextIfIndex OBJECT-TYPE
    SYNTAX      UsdNextIfIndex
    MAX-ACCESS  read-only
    STATUS      current
    DESCRIPTION
        "Coordinate ifIndex value allocation for entries in usdSmdsIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdSmdsObjects 1 }

--
-- The SMDS Interface Table
--

usdSmdsIfTable OBJECT-TYPE
    SYNTAX      SEQUENCE OF UsdSmdsIfEntry
    MAX-ACCESS  not-accessible
    STATUS      current
    DESCRIPTION
        "This table contains entries for SMDS interfaces present in the system."
    ::= { usdSmdsObjects 2 }

usdSmdsIfEntry OBJECT-TYPE
    SYNTAX      UsdSmdsIfEntry
    MAX-ACCESS  not-accessible
    STATUS      current
    DESCRIPTION
        "Each entry describes the characteristics of an SMDS interface.
        Creating/deleting entries in this table causes corresponding entries for
        be created/deleted in ifTable/ifXTable/usdIfTable."
    INDEX   { usdSmdsIfIndex }
    ::= { usdSmdsIfTable 1 }

UsdSmdsIfEntry ::= SEQUENCE {
    usdSmdsIfIndex
        InterfaceIndex,
    usdSmdsIfRowStatus
        RowStatus,
    usdSmdsIfLowerIfIndex
        InterfaceIndexOrZero
    }

usdSmdsIfIndex OBJECT-TYPE
    SYNTAX      InterfaceIndex
    MAX-ACCESS  not-accessible
    STATUS      current
    DESCRIPTION
        "The ifIndex of the SMDS interface.  When creating entries in this
        table, suitable values for this object are determined by reading
        usdSmdsNextIfIndex."
    ::= { usdSmdsIfEntry 1 }

usdSmdsIfRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdSmdsIfRowStatus
            usdSmdsIfLowerIfIndex

        In addition, when creating an entry the following conditions must hold:

            A value for usdSmdsIfIndex must have been determined previously, by
            reading usdSmdsNextIfIndex.

            The interface identified by usdSmdsIfLowerIfIndex must exist.

        A corresponding entry in ifTable/ifXTable/usdIfTable is created/destroyed
        as a result of creating/destroying an entry in this table.  "
    ::= { usdSmdsIfEntry 2 }

usdSmdsIfLowerIfIndex OBJECT-TYPE
    SYNTAX      InterfaceIndexOrZero
    MAX-ACCESS  read-create
    STATUS      current
    DESCRIPTION
        "The ifIndex of an interface over which this SMDS interface is to be
        layered.  A value of zero indicates no layering.  An implementation may
        choose to require that a nonzero value be configured at entry creation."
    ::= { usdSmdsIfEntry 3 }

-- //////////////////////////////////////////////////////////////////////
--
-- SMDS Major Interfaces
--
-- //////////////////////////////////////////////////////////////////////

--
-- IfIndex selection for creating new SMDS major interfaces
--

usdSmdsMajorNextIfIndex OBJECT-TYPE
    SYNTAX      UsdNextIfIndex
    MAX-ACCESS  read-only
    STATUS      current
    DESCRIPTION
        "Coordinate ifIndex value allocation for entries in usdSmdsMajorIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { usdSmdsObjects 3 }

--
-- The SMDS Major Interface Table
--

usdSmdsMajorIfTable OBJECT-TYPE
    SYNTAX      SEQUENCE OF UsdSmdsMajorIfEntry
    MAX-ACCESS  not-accessible
    STATUS      current
    DESCRIPTION
        "This table contains entries for SMDS major interfaces present in the
        system."
    ::= { usdSmdsObjects 4 }

usdSmdsMajorIfEntry OBJECT-TYPE
    SYNTAX      UsdSmdsMajorIfEntry
    MAX-ACCESS  not-accessible
    STATUS      current
    DESCRIPTION
        "Each entry describes the characteristics of an SMDS major interface.
        Creating/deleting entries in this table causes corresponding entries for
        be created/deleted in ifTable/ifXTable/usdIfTable."
    INDEX   { usdSmdsMajorIfIndex }
    ::= { usdSmdsMajorIfTable 1 }

UsdSmdsMajorIfEntry ::= SEQUENCE {
    usdSmdsMajorIfIndex
        InterfaceIndex,
    usdSmdsMajorIfRowStatus
        RowStatus,
    usdSmdsMajorIfLowerIfIndex
        InterfaceIndexOrZero,
    usdSmdsMajorIfKeepalive
        Integer32
    }

usdSmdsMajorIfIndex OBJECT-TYPE
    SYNTAX      InterfaceIndex
    MAX-ACCESS  not-accessible
    STATUS      current
    DESCRIPTION
        "The ifIndex of the SMDS major interface.  When creating entries in this
        table, suitable values for this object are determined by reading
        usdSmdsMajorNextIfIndex."
    ::= { usdSmdsMajorIfEntry 1 }

usdSmdsMajorIfRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdSmdsMajorIfRowStatus
            usdSmdsMajorIfLowerIfIndex

        In addition, when creating an entry the following conditions must hold:

            A value for usdSmdsMajorIfIndex must have been determined previously,
            by reading usdSmdsMajorNextIfIndex.

            The interface identified by usdSmdsMajorIfLowerIfIndex must exist.

        A corresponding entry in ifTable/ifXTable/usdIfTable is created/destroyed
        as a result of creating/destroying an entry in this table.  "
    ::= { usdSmdsMajorIfEntry 2 }

usdSmdsMajorIfLowerIfIndex OBJECT-TYPE
    SYNTAX      InterfaceIndexOrZero
    MAX-ACCESS  read-create
    STATUS      current
    DESCRIPTION
        "The ifIndex of an interface over which this SMDS major interface is to
        be layered.  A value of zero indicates no layering.  An implementation
        may choose to require that a nonzero value be configured at entry
        creation."
    ::= { usdSmdsMajorIfEntry 3 }

usdSmdsMajorIfKeepalive OBJECT-TYPE
    SYNTAX      Integer32(0 | 5..32767)
    UNITS       "seconds"
    MAX-ACCESS  read-create
    STATUS      current
    DESCRIPTION
        "Keepalive interval in seconds.  A value of zero disables keepalive."
    ::= { usdSmdsMajorIfEntry 4 }


-- //////////////////////////////////////////////////////////////////////
--
-- SMDS SubInterfaces
--
-- //////////////////////////////////////////////////////////////////////

--
-- IfIndex selection for creating new SMDS subInterfaces
--

usdSmdsSubNextIfIndex OBJECT-TYPE
    SYNTAX      UsdNextIfIndex
    MAX-ACCESS  read-only
    STATUS      current
    DESCRIPTION
        "Coordinate ifIndex value allocation for entries in usdSmdsSubIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { usdSmdsObjects 5 }

--
-- The SMDS Subinterface Table
--

usdSmdsSubIfTable OBJECT-TYPE
    SYNTAX      SEQUENCE OF UsdSmdsSubIfEntry
    MAX-ACCESS  not-accessible
    STATUS      current
    DESCRIPTION
        "This table contains entries for SMDS subinterfaces present in the
        system."
    ::= { usdSmdsObjects 6 }

usdSmdsSubIfEntry OBJECT-TYPE
    SYNTAX      UsdSmdsSubIfEntry
    MAX-ACCESS  not-accessible
    STATUS      current
    DESCRIPTION
        "Each entry describes the characteristics of an SMDS subinterface.
        Creating/deleting entries in this table causes corresponding entries for
        be created/deleted in ifTable/ifXTable/usdIfTable."
    INDEX   { usdSmdsSubIfIndex }
    ::= { usdSmdsSubIfTable 1 }

UsdSmdsSubIfEntry ::= SEQUENCE {
    usdSmdsSubIfIndex
        InterfaceIndex,
    usdSmdsSubIfRowStatus
        RowStatus,
    usdSmdsSubIfLowerIfIndex
        InterfaceIndexOrZero,
    usdSmdsSubIfSmdsAddress
        OCTET STRING,
    usdSmdsSubIfSmdsMulticastIpAddress
        OCTET STRING,
    usdSmdsSubIfSmdsMulticastArpAddress
        OCTET STRING
    }

usdSmdsSubIfIndex OBJECT-TYPE
    SYNTAX      InterfaceIndex
    MAX-ACCESS  not-accessible
    STATUS      current
    DESCRIPTION
        "The ifIndex of the SMDS subinterface.  When creating entries in this
        table, suitable values for this object are determined by reading
        usdSmdsSubNextIfIndex."
    ::= { usdSmdsSubIfEntry 1 }

usdSmdsSubIfRowStatus OBJECT-TYPE
    SYNTAX      RowStatus
    MAX-ACCESS  read-create
    STATUS      current
    DESCRIPTION
        "Controls creation/deletion of entries in this table according to the
        RowStatus textual convention, constrained to support the following
        values only:

            createAndGo
            destroy
            
        To create an entry in this table, the following entry objects MUST be
        explicitly configured:

            usdSmdsSubIfRowStatus
            usdSmdsSubIfLowerIfIndex

        In addition, when creating an entry the following conditions must hold:

            A value for usdSmdsSubIfIndex must have been determined previously,
            by reading usdSmdsSubNextIfIndex.

            The interface identified by usdSmdsSubIfLowerIfIndex must exist.

        A corresponding entry in ifTable/ifXTable/usdIfTable is created/destroyed
        as a result of creating/destroying an entry in this table.  "
    ::= { usdSmdsSubIfEntry 2 }

usdSmdsSubIfLowerIfIndex OBJECT-TYPE
    SYNTAX      InterfaceIndexOrZero
    MAX-ACCESS  read-create
    STATUS      current
    DESCRIPTION
        "The ifIndex of an interface over which this SMDS subinterface is to be
        layered.  A value of zero indicates no layering.  An implementation may
        choose to require that a nonzero value be configured at entry creation."
    ::= { usdSmdsSubIfEntry 3 }

usdSmdsSubIfSmdsAddress OBJECT-TYPE
    SYNTAX      OCTET STRING (SIZE (8))
    MAX-ACCESS  read-create
    STATUS      current
    DESCRIPTION
        "The 64 bit E.164 SMDS address that has been assigned to this SMDS
        subinterface.  A value of 0 indicates no address is configured."
    ::= { usdSmdsSubIfEntry 4 }

usdSmdsSubIfSmdsMulticastIpAddress OBJECT-TYPE
    SYNTAX      OCTET STRING (SIZE (8))
    MAX-ACCESS  read-create
    STATUS      current
    DESCRIPTION
        "The 64 bit E.164 SMDS ip multicast address that has been assigned to
        this SMDS subinterface.  A value of 0 indicates no address is
        configured."
    ::= { usdSmdsSubIfEntry 5 }

usdSmdsSubIfSmdsMulticastArpAddress OBJECT-TYPE
    SYNTAX      OCTET STRING (SIZE (8))
    MAX-ACCESS  read-create
    STATUS      current
    DESCRIPTION
        "The 64 bit E.164 SMDS multicast arp address that has been assigned to
        this SMDS subinterface.  A value of 0 indicates no address is
        configured."
    ::= { usdSmdsSubIfEntry 6 }


--
-- The SMDS Major Interface Statistics Table
--

usdSmdsMajorIfStatsTable OBJECT-TYPE
    SYNTAX      SEQUENCE OF UsdSmdsMajorIfStatsEntry
    MAX-ACCESS  not-accessible
    STATUS      current
    DESCRIPTION
        "This table contains entries for SMDS major interface statistics present
        in the system."
    ::= { usdSmdsObjects 7 }

usdSmdsMajorIfStatsEntry OBJECT-TYPE
    SYNTAX      UsdSmdsMajorIfStatsEntry
    MAX-ACCESS  not-accessible
    STATUS      current
    DESCRIPTION
        "Each entry describes the statistics of an SMDS major interface."
    AUGMENTS    { usdSmdsMajorIfEntry }
    ::= { usdSmdsMajorIfStatsTable 1 }

UsdSmdsMajorIfStatsEntry ::= SEQUENCE {
    usdSmdsMajorIfStatsInKeepaliveRequests
        Counter32,
    usdSmdsMajorIfStatsOutKeepaliveRequests
        Counter32,
    usdSmdsMajorIfStatsInKeepaliveReplies
        Counter32,
    usdSmdsMajorIfStatsOutKeepaliveReplies
        Counter32,
    usdSmdsMajorIfStatsKeepaliveFailures
        Counter32
    }

usdSmdsMajorIfStatsInKeepaliveRequests OBJECT-TYPE
    SYNTAX      Counter32
    MAX-ACCESS  read-only
    STATUS      current
    DESCRIPTION
        "The number of keepalive requests received."
    ::= { usdSmdsMajorIfStatsEntry 1 }

usdSmdsMajorIfStatsOutKeepaliveRequests OBJECT-TYPE
    SYNTAX      Counter32
    MAX-ACCESS  read-only
    STATUS      current
    DESCRIPTION
        "The number of keepalive requests transmitted."
    ::= { usdSmdsMajorIfStatsEntry 2 }

usdSmdsMajorIfStatsInKeepaliveReplies OBJECT-TYPE
    SYNTAX      Counter32
    MAX-ACCESS  read-only
    STATUS      current
    DESCRIPTION
        "The number of keepalive replies received."
    ::= { usdSmdsMajorIfStatsEntry 3 }

usdSmdsMajorIfStatsOutKeepaliveReplies OBJECT-TYPE
    SYNTAX      Counter32
    MAX-ACCESS  read-only
    STATUS      current
    DESCRIPTION
        "The number of keepalive replies transmitted."
    ::= { usdSmdsMajorIfStatsEntry 4 }

usdSmdsMajorIfStatsKeepaliveFailures OBJECT-TYPE
    SYNTAX      Counter32
    MAX-ACCESS  read-only
    STATUS      current
    DESCRIPTION
        "The number of keepalive failures detected."
    ::= { usdSmdsMajorIfStatsEntry 5 }


-- ++++++++++++++++++++++++++++++++++++++++++++++++++++++++++++++++++++++
-- Notification control objects
-- ++++++++++++++++++++++++++++++++++++++++++++++++++++++++++++++++++++++

-- No notifications are defined in this MIB. Placeholder follows.

-- usdSmdsTrapControl      OBJECT IDENTIFIER ::= { usdSmdsMIB 2 }

-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdSmdsTraps            OBJECT IDENTIFIER ::= { usdSmdsMIB 3 }
-- usdSmdsTrapPrefix       OBJECT IDENTIFIER ::= { usdSmdsTraps 0 }


-- ++++++++++++++++++++++++++++++++++++++++++++++++++++++++++++++++++++++
-- Conformance information
-- ++++++++++++++++++++++++++++++++++++++++++++++++++++++++++++++++++++++

usdSmdsConformance OBJECT IDENTIFIER ::= { usdSmdsMIB 4 }
usdSmdsCompliances OBJECT IDENTIFIER ::= { usdSmdsConformance 1 }
usdSmdsGroups      OBJECT IDENTIFIER ::= { usdSmdsConformance 2 }

-- compliance statements

usdSmdsCompliance MODULE-COMPLIANCE
    STATUS      obsolete
    DESCRIPTION
        "Obsolete compliance statement for entities which implement the Unisphere
        SMDS MIB.  This statement became obsolete when support was added for
        major and sub interfaces."
    MODULE  -- this module
        MANDATORY-GROUPS { usdSmdsGroup }
    ::= { usdSmdsCompliances 1 }                                       -- RX 3.1

usdSmdsCompliance2 MODULE-COMPLIANCE
    STATUS      current
    DESCRIPTION
        "The compliance statement for entities which implement the Unisphere
        SMDS MIB."
    MODULE  -- this module
        MANDATORY-GROUPS { usdSmdsGroup2 }
    ::= { usdSmdsCompliances 2 }                                       -- RX 4.0


-- units of conformance

usdSmdsGroup OBJECT-GROUP
    OBJECTS {
        usdSmdsNextIfIndex,

        usdSmdsIfRowStatus,
        usdSmdsIfLowerIfIndex
    }
    STATUS      obsolete
    DESCRIPTION
        "Obsolete collection of objects providing management of SMDS interfaces
        in a Unisphere product.  This group became obsolete when support was
        added for major and sub interfaces."
    ::= { usdSmdsGroups 1 }

usdSmdsGroup2 OBJECT-GROUP
    OBJECTS {
        usdSmdsNextIfIndex,

        usdSmdsIfRowStatus,
        usdSmdsIfLowerIfIndex,

        usdSmdsMajorNextIfIndex,

        usdSmdsMajorIfRowStatus,
        usdSmdsMajorIfLowerIfIndex,
        usdSmdsMajorIfKeepalive,

        usdSmdsSubNextIfIndex,

        usdSmdsSubIfRowStatus,
        usdSmdsSubIfLowerIfIndex,
        usdSmdsSubIfSmdsAddress,
        usdSmdsSubIfSmdsMulticastIpAddress,
        usdSmdsSubIfSmdsMulticastArpAddress,

        usdSmdsMajorIfStatsInKeepaliveRequests,
        usdSmdsMajorIfStatsOutKeepaliveRequests,
        usdSmdsMajorIfStatsInKeepaliveReplies,
        usdSmdsMajorIfStatsOutKeepaliveReplies,
        usdSmdsMajorIfStatsKeepaliveFailures
    }
    STATUS  current
    DESCRIPTION
        "A collection of objects providing management of SMDS interfaces in a
        Unisphere product."
    ::= { usdSmdsGroups 2 }

END
