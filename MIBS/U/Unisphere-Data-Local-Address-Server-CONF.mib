-- *****************************************************************************
-- Unisphere-Data-Local-Address-Server-CONF
--
-- SNMP Agent Capabilities definitions for the Local Address Server MIB.
--
-- Copyright (c) 2001 Unisphere Networks, Inc.  All rights reserved.
-- *****************************************************************************

Unisphere-Data-Local-Address-Server-CONF DEFINITIONS ::= BEGIN

IMPORTS
    MODULE-IDENTITY
        FROM SNMPv2-SMI
    AGENT-CAPABILITIES
        FROM SNMPv2-CONF
    usDataAgents
        FROM Unisphere-Data-Agents
    usdAddressPoolGroup, usdAddressPoolGroup2, usdAddressPoolTrapGroup,
    usdAddressPoolGroup3
        FROM Unisphere-Data-ADDRESS-POOL-MIB;

usdLocalAddressServerAgent MODULE-IDENTITY
    LAST-UPDATED "200205061920Z"  -- 06-May-02 03:20 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Local Address Server
        component of the SNMP agent in the Unisphere Routing Switch family of
        products."
    -- Revision History
    REVISION    "200205061920Z"  -- 06-May-02 03:20 PM EDT  - RX 3.3
    DESCRIPTION
        "Added support for address pools with multiple address ranges."
    REVISION    "200105021322Z"  -- 02-May-01 09:22 AM EDT  - RX 3.2
    DESCRIPTION
        "The initial release of this management information module."
    ::= { usDataAgents 25 }


usdLocalAddressServerAgentV1 AGENT-CAPABILITIES
    PRODUCT-RELEASE
        "Version 1 of the Local Address Server component of the Unisphere
        Routing Switch SNMP agent.  This version of the Local Address Server
        component was supported in the Unisphere RX 1.3 thru RX 3.1 system
        releases."
    STATUS      obsolete
    DESCRIPTION
        "The MIB supported by the SNMP agent for the Local Address Server
        application in the Unisphere Data Routing Switch.  These capabilities
        became obsolete when pool exhaustion variables and notifications were
        added."
    SUPPORTS    Unisphere-Data-ADDRESS-POOL-MIB
        INCLUDES  {
            usdAddressPoolGroup }
    ::= { usdLocalAddressServerAgent 1 }

usdLocalAddressServerAgentV2 AGENT-CAPABILITIES
    PRODUCT-RELEASE
        "Version 2 of the Local Address Server component of the Unisphere
        Routing Switch SNMP agent.  This version of the Local Address Server
        component was supported in the Unisphere RX 3.2 system release."
    STATUS      obsolete
    DESCRIPTION
        "The MIB supported by the SNMP agent for the Local Address Server
        application in the Unisphere Data Routing Switch.  These capabilities
        became obsolete when support was added for address pools with multiple
        address ranges."
    SUPPORTS    Unisphere-Data-ADDRESS-POOL-MIB
        INCLUDES  {
            usdAddressPoolGroup2,
            usdAddressPoolTrapGroup }
    ::= { usdLocalAddressServerAgent 2 }

usdLocalAddressServerAgentV3 AGENT-CAPABILITIES
    PRODUCT-RELEASE
        "Version 3 of the Local Address Server component of the Unisphere
        Routing Switch SNMP agent.  This version of the Local Address Server
        component is supported in the Unisphere RX 3.3 and subsequent system
        releases."
    STATUS      current
    DESCRIPTION
        "The MIB supported by the SNMP agent for the Local Address Server
        application in the Unisphere Data Routing Switch."
    SUPPORTS    Unisphere-Data-ADDRESS-POOL-MIB
        INCLUDES  {
            usdAddressPoolGroup3,
            usdAddressPoolTrapGroup }
    ::= { usdLocalAddressServerAgent 3 }

END
