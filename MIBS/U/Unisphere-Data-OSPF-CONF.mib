-- *****************************************************************************
-- Unisphere-Data-OSPF-CONF
--
-- SNMP Agent Capabilities definitions for the OSPF MIBs.
--
-- Copyright (c) 2001 Unisphere Networks, Inc.  All rights reserved.
-- *****************************************************************************

Unisphere-Data-OSPF-CONF DEFINITIONS ::= BEGIN

IMPORTS
    MODULE-IDENTITY
        FROM SNMPv2-SMI
    AGENT-CAPABILITIES
        FROM SNMPv2-CONF
    usDataAgents
        FROM Unisphere-Data-Agents
    ospfBasicGroup, ospfAreaGroup, ospfStubAreaGroup, ospfLsdbGroup,
    ospfHostGroup, ospfIfGroup, ospfIfMetricGroup, ospfVirtIfGroup,
    ospfNbrGroup, ospfVirtNbrGroup, ospfExtLsdbGroup, ospfAreaAggregateGroup
        FROM OSPF-MIB
    ospfTrapControlGroup, ospfConfigErrorType, ospfPacketType, ospfPacketSrc
        FROM OSPF-TRAP-MIB
    usdOspfBasicGroup, usdOspfAreaGroup, usdOspfIfGroup, usdOspfVirtIfGroup,
    usdOspfNbrGroup, usdOspfSummImportGroup, usdOspfMd5IntfGroup,
    usdOspfMd5VirtIntfGroup, usdOspfNetRangeGroup, usdOspfBasicGroup2
        FROM Unisphere-Data-OSPF-MIB;

usdOspfAgent MODULE-IDENTITY
    LAST-UPDATED "200112061512Z"  -- 06-Dec-01 10:12 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Open Shortest Path First
        (OSPF) routing protocol component of the SNMP agent in the Unisphere
        Routing Switch family of products."
    -- Revision History
    REVISION    "200112061512Z"  -- 06-Dec-01 10:12 AM EST  - RX 4.0
    DESCRIPTION
        "New objects were added to the Unisphere-Data-OSPF-MIB
        usdOspfBasicGroup2."
    REVISION    "200103291334Z"  -- 29-Mar-01 08:34 AM EST  - RX 3.2
    DESCRIPTION
        "The initial release of this management information module."
    ::= { usDataAgents 28 }


-- *****************************************************************************
-- OSPF SNMP Agent Capabilities definitions
-- *****************************************************************************

usdOspfAgentV1 AGENT-CAPABILITIES
    PRODUCT-RELEASE
        "Version 1 of the OSPF component of the Unisphere Routing Switch SNMP
        agent.  This version of the OSPF component was supported in the
        Unisphere RX 2.x and 3.x system releases."
    STATUS      obsolete
    DESCRIPTION
        "The MIBs supported by the SNMP agent for the OSPF application in the
        Unisphere Routing Switch.  These capabilities became obsolete when
        new objects were added to the usdOspfBasicGroup."
    SUPPORTS    OSPF-MIB
        INCLUDES {
            ospfBasicGroup,
            ospfAreaGroup,
            ospfStubAreaGroup,
            ospfLsdbGroup,
            ospfHostGroup,
            ospfIfGroup,
            ospfIfMetricGroup,
            ospfVirtIfGroup,
            ospfNbrGroup,
            ospfVirtNbrGroup,
            ospfExtLsdbGroup,
            ospfAreaAggregateGroup }
    SUPPORTS    OSPF-TRAP-MIB
        INCLUDES {
            ospfTrapControlGroup }
        VARIATION   ospfConfigErrorType
            ACCESS      accessible-for-notify
            DESCRIPTION
                "Only provided within a notification."
        VARIATION   ospfPacketType
            ACCESS      accessible-for-notify
            DESCRIPTION
                "Only provided within a notification."
        VARIATION   ospfPacketSrc
            ACCESS      accessible-for-notify
            DESCRIPTION
                "Only provided within a notification."
    SUPPORTS    Unisphere-Data-OSPF-MIB
        INCLUDES {
            usdOspfBasicGroup,
            usdOspfAreaGroup,
            usdOspfIfGroup,
            usdOspfVirtIfGroup,
            usdOspfNbrGroup,
            usdOspfSummImportGroup,
            usdOspfMd5IntfGroup,
            usdOspfMd5VirtIntfGroup,
            usdOspfNetRangeGroup }
    ::= { usdOspfAgent 1 }

usdOspfAgentV2 AGENT-CAPABILITIES
    PRODUCT-RELEASE
        "Version 2 of the OSPF component of the Unisphere Routing Switch SNMP
        agent.  This version of the OSPF component is supported in the Unisphere
        RX 4.0 and subsequent system releases."
    STATUS      current
    DESCRIPTION
        "The MIBs supported by the SNMP agent for the OSPF application in the
        Unisphere Routing Switch."
    SUPPORTS    OSPF-MIB
        INCLUDES {
            ospfBasicGroup,
            ospfAreaGroup,
            ospfStubAreaGroup,
            ospfLsdbGroup,
            ospfHostGroup,
            ospfIfGroup,
            ospfIfMetricGroup,
            ospfVirtIfGroup,
            ospfNbrGroup,
            ospfVirtNbrGroup,
            ospfExtLsdbGroup,
            ospfAreaAggregateGroup }
    SUPPORTS    OSPF-TRAP-MIB
        INCLUDES {
            ospfTrapControlGroup }
        VARIATION   ospfConfigErrorType
            ACCESS      accessible-for-notify
            DESCRIPTION
                "Only provided within a notification."
        VARIATION   ospfPacketType
            ACCESS      accessible-for-notify
            DESCRIPTION
                "Only provided within a notification."
        VARIATION   ospfPacketSrc
            ACCESS      accessible-for-notify
            DESCRIPTION
                "Only provided within a notification."
    SUPPORTS    Unisphere-Data-OSPF-MIB
        INCLUDES {
            usdOspfBasicGroup2,
            usdOspfAreaGroup,
            usdOspfIfGroup,
            usdOspfVirtIfGroup,
            usdOspfNbrGroup,
            usdOspfSummImportGroup,
            usdOspfMd5IntfGroup,
            usdOspfMd5VirtIntfGroup,
            usdOspfNetRangeGroup }
    ::= { usdOspfAgent 2 }

END
