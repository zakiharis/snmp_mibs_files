-- *****************************************************************************
-- Unisphere-Data-ETHERNET-MIB
--
-- Unisphere Networks Inc. Enterprise MIB
-- Ethernet MIB
--
-- Copyright (c) 2000, 2001 Unisphere Networks, Inc.  All Rights Reserved.
-- *****************************************************************************

Unisphere-Data-ETHERNET-MIB DEFINITIONS ::= BEGIN

IMPORTS
    MODULE-IDENTITY, OBJECT-TYPE, Integer32
        FROM SNMPv2-SMI
    RowStatus, TruthValue
        FROM SNMPv2-TC
    InterfaceIndex, InterfaceIndexOrZero
        FROM IF-MIB
    MODULE-COMPLIANCE, OBJECT-GROUP
        FROM SNMPv2-CONF
    usDataMibs
        FROM Unisphere-Data-MIBs
    UsdNextIfIndex
        FROM Unisphere-Data-TC;

usdEthernetMIB  MODULE-IDENTITY
    LAST-UPDATED "200204051947Z"  -- 05-Apr-02 02:47 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Ethernet MIB for the Unisphere Networks enterprise."
    -- Revision History
    REVISION    "200204051947Z"  -- 05-Apr-02 02:47 PM EST  - RX 4.0
    DESCRIPTION
        "Added VLAN stack support."
    REVISION    "200101021655Z"  -- 02-Jan-01 11:55 AM EST  - RX 3.0
    DESCRIPTION
        "Added VLAN management support."
    REVISION    "200004180000Z"  -- 18-Apr-00               - RX 2.0
    DESCRIPTION
        "Added objects for Ethernet sub-interface creation.
         Added usdEthernetIfOperDuplexMode to report current duplex mode.
         Revised descriptions to note relationship to ifTable objects and to
            explain autonegotiation dependencies.
         Added speed1000Mbps enumeration value to usdEthernetIfSpeed.
         Changed lower bound of usdEthernetIfMtu from 18 to 64."
    REVISION    "200002030000Z"  --  3-Feb-00               - RX 1.3
    DESCRIPTION
        "Initial version of this MIB module."
    ::= { usDataMibs 34 }


-- +++++++++++++++++++++++++++++++++++++++++++++++++++++++++++++++++++++++++++++
-- Textual conventions
-- +++++++++++++++++++++++++++++++++++++++++++++++++++++++++++++++++++++++++++++
-- No textual conventions are defined in this MIB.


-- +++++++++++++++++++++++++++++++++++++++++++++++++++++++++++++++++++++++++++++
-- Managed objects
-- +++++++++++++++++++++++++++++++++++++++++++++++++++++++++++++++++++++++++++++
usdEthernetObjects     OBJECT IDENTIFIER ::= { usdEthernetMIB 1 }

--
-- This MIB contains managed objects for the Ethernet interfaces.
-- This MIB also contains managed objects for creation of Ethernet
-- subInterfaces.
--
-- Ethernet interface in the usdEthernetTable have the same
-- index value as interface in the ifTable.
--
usdEthernetIfLayer    OBJECT IDENTIFIER ::= { usdEthernetObjects 1 }
usdEthernetSubIfLayer OBJECT IDENTIFIER ::= { usdEthernetObjects 2 }
usdVlanMajorIfLayer   OBJECT IDENTIFIER ::= { usdEthernetObjects 3 }
usdVlanSubIfLayer     OBJECT IDENTIFIER ::= { usdEthernetObjects 4 }

-- /////////////////////////////////////////////////////////////////////////////
--
-- Ethernet Interface Layer
--
-- This layer is managed with the following elements:
--
--  o Interface Table (configuration of Ethernet interface parameters)
--
-- /////////////////////////////////////////////////////////////////////////////
--
-- The Ethernet Interface Table
--
usdEthernetIfTable OBJECT-TYPE
    SYNTAX      SEQUENCE OF UsdEthernetIfEntry
    MAX-ACCESS  not-accessible
    STATUS      current
    DESCRIPTION
        "The parameters for the Ethernet interface."
    ::= { usdEthernetIfLayer 1 }

usdEthernetIfEntry OBJECT-TYPE
    SYNTAX      UsdEthernetIfEntry
    MAX-ACCESS  not-accessible
    STATUS      current
    DESCRIPTION
        "The Parameters for a particular Ethernet interface.  Entries in this
        table correspond with entries in the ifTable/ifXTable/usdIfTable."
    INDEX   { usdEthernetIfIndex }
    ::= { usdEthernetIfTable 1 }

UsdEthernetIfEntry ::= SEQUENCE {
    usdEthernetIfIndex          InterfaceIndex,
    usdEthernetIfDuplexMode     INTEGER,
    usdEthernetIfSpeed          INTEGER,
    usdEthernetIfMtu            INTEGER,
    usdEthernetIfOperDuplexMode INTEGER }

usdEthernetIfIndex OBJECT-TYPE
    SYNTAX      InterfaceIndex
    MAX-ACCESS  not-accessible
    STATUS      current
    DESCRIPTION
        "The ifIndex value of the corresponding ethernet interface."
    ::= { usdEthernetIfEntry 1 }

usdEthernetIfDuplexMode OBJECT-TYPE
    SYNTAX      INTEGER {
                    autoDuplex(1),
                    halfDuplex(2),
                    fullDuplex(3) }
    MAX-ACCESS  read-write
    STATUS      current
    DESCRIPTION
        "The configured duplex setting for this ethernet interface.  The
        operational value is reported in this table entry's corresponding
        usdEthernetIfOperDuplexMode object.

        NOTE, configuration dependency:

        Setting this object to values other than 'autoDuplex' takes effect only
        when the corresponding usdEthernetIfSpeed object is simultaneously set to
        other than 'autoNegotiate'.

        Otherwise (i.e. this object is set to 'autoDuplex', AND/OR corresponding
        usdEthernetIfSpeed object is set to 'autoNegotiate'), duplex mode is
        negotiated."
    DEFVAL    { autoDuplex }
    ::= { usdEthernetIfEntry 2 }

usdEthernetIfSpeed OBJECT-TYPE
    SYNTAX      INTEGER {
                    autoNegotiate(1),
                    speed10Mbps(2),
                    speed100Mbps(3),
                    speed1000Mbps(4) }
    MAX-ACCESS  read-write
    STATUS      current
    DESCRIPTION
        "The configured speed setting for this ethernet interface.  The
        operational value is reported in the corresponding Interfaces MIB
        ifSpeed object.

        NOTE, configuration dependency:

        Setting this object to values other than 'autoNegotiate' takes effect
        only when the corresponding usdEthernetIfDuplexMode object is
        simultaneously set to other than 'autoDuplex'.

        Otherwise (i.e. this object is set to 'autoNegotiate', AND/OR the
        corresponding usdEthernetIfDuplexMode object is set to 'autoDuplex'),
        speed is negotiated."
    DEFVAL    { autoNegotiate }
    ::= { usdEthernetIfEntry 3 }

usdEthernetIfMtu OBJECT-TYPE
    SYNTAX      INTEGER (64..9188)
    MAX-ACCESS  read-write
    STATUS      current
    DESCRIPTION
        "The configured maximum transfer unit (MTU) for this ethernet interface.
        The operational value is reported in the corresponding Interfaces MIB
        ifMtu object."
    DEFVAL    { 1518 }
    ::= { usdEthernetIfEntry 4 }

usdEthernetIfOperDuplexMode OBJECT-TYPE
    SYNTAX      INTEGER {
                    autoDuplex(1),
                    halfDuplex(2),
                    fullDuplex(3) }
    MAX-ACCESS  read-only
    STATUS      current
    DESCRIPTION
        "The current operational duplex mode for this ethernet interface."
    ::= { usdEthernetIfEntry 5 }


-- +++++++++++++++++++++++++++++++++++++++++++++++++++++++++++++++++++++++++++++
-- Sub Interface Creation Mib
-- +++++++++++++++++++++++++++++++++++++++++++++++++++++++++++++++++++++++++++++
--
-- IfIndex selection for creating new Ethernet Subinterfaces
--
usdEthernetSubIfNextIfIndex OBJECT-TYPE
    SYNTAX      UsdNextIfIndex
    MAX-ACCESS  read-only
    STATUS      current
    DESCRIPTION
        "Coordinate ifIndex value allocation for entries in
        usdEthernetSubIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdEthernetSubIfLayer 1 }

--
-- The Ethernet Subinterface Table
--
usdEthernetSubIfTable OBJECT-TYPE
    SYNTAX      SEQUENCE OF UsdEthernetSubIfEntry
    MAX-ACCESS  not-accessible
    STATUS      current
    DESCRIPTION
        "This table contains entries for Ethernet Subinterfaces present in the
        system."
    ::= { usdEthernetSubIfLayer 2 }

usdEthernetSubIfEntry OBJECT-TYPE
    SYNTAX      UsdEthernetSubIfEntry
    MAX-ACCESS  not-accessible
    STATUS      current
    DESCRIPTION
        "Each entry describes the characteristics of an Ethernet Subinterface.
        Creating/deleting entries in this table causes corresponding entries for
        be created/deleted in ifTable/ifXTable/usdIfTable."
    INDEX     { usdEthernetSubIfIndex }
    ::= { usdEthernetSubIfTable 1 }

UsdEthernetSubIfEntry ::= SEQUENCE {
    usdEthernetSubIfIndex           InterfaceIndex,
    usdEthernetSubIfRowStatus       RowStatus,
    usdEthernetSubIfLowerIfIndex    InterfaceIndexOrZero,
    usdEthernetSubIfId              Integer32 }

usdEthernetSubIfIndex OBJECT-TYPE
    SYNTAX      InterfaceIndex
    MAX-ACCESS  not-accessible
    STATUS      current
    DESCRIPTION
        "The ifIndex of the Ethernet Subinterface.  When creating entries in
        this table, suitable values for this object are determined by reading
        usdEthernetSubNextIfIndex."
    ::= { usdEthernetSubIfEntry 1 }

usdEthernetSubIfRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdEthernetSubIfRowStatus
            usdEthernetSubIfLowerIfIndex

        In addition, when creating an entry the following conditions must hold:

            A value for usdEthernetSubIfIndex must have been determined
            previously, by reading usdEthernetSubIfNextIfIndex.

            The interface identified by usdEthernetSubIfLowerIfIndex must exist,
            and must be a Ethernet interface.

            A positive value configured for usdEthernetSubIfId must not already
            be assigned to another subinterface layered onto the same underlying
            Ethernet interface.

        A corresponding entry in ifTable/ifXTable/usdIfTable is created/destroyed
        as a result of creating/destroying an entry in this table."
    ::= { usdEthernetSubIfEntry 2 }

usdEthernetSubIfLowerIfIndex OBJECT-TYPE
    SYNTAX      InterfaceIndexOrZero
    MAX-ACCESS  read-create
    STATUS      current
    DESCRIPTION
        "The ifIndex of a Ethernet interface over which this Ethernet
        Subinterface is to be layered.  A value of zero indicates no layering.
        An implementation may choose to require that a nonzero value be
        configured at entry creation."
    ::= { usdEthernetSubIfEntry 3 }

usdEthernetSubIfId OBJECT-TYPE
    SYNTAX      Integer32 (-1..2147483647)
    MAX-ACCESS  read-create
    STATUS      current
    DESCRIPTION
        "An integer identifier for the Ethernet subinterface, used in
        conjunction with the command-line interface.  It is provided here for
        cross-reference purposes only.

        The value must be unique among subinterfaces configured on the same
        underlying Ethernet interface.
       
        If this object is not configured, or is configured with a value of -1, a
        nonzero value will be allocated internally and can be retrieved from
        this object after table entry creation has succeeded.

        A value of zero for this object is reserved for future use."
    DEFVAL    { -1 }
    ::= { usdEthernetSubIfEntry 4 }


-- +++++++++++++++++++++++++++++++++++++++++++++++++++++++++++++++++++++++++++++
-- VLAN Major Interface Creation
-- +++++++++++++++++++++++++++++++++++++++++++++++++++++++++++++++++++++++++++++
--
-- IfIndex selection for creating new Major VLAN Interfaces
--
usdVlanMajorNextIfIndex OBJECT-TYPE
    SYNTAX      UsdNextIfIndex
    MAX-ACCESS  read-only
    STATUS      current
    DESCRIPTION
        "Coordinate ifIndex value allocation for entries in usdVlanMajorIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { usdVlanMajorIfLayer 1 }


--
-- The VLAN Major Interface Table
--
usdVlanMajorIfTable OBJECT-TYPE
    SYNTAX      SEQUENCE OF UsdVlanMajorIfEntry
    MAX-ACCESS  not-accessible
    STATUS      current
    DESCRIPTION
        "This table contains entries for major VLAN interfaces present in the
        system."
    ::= { usdVlanMajorIfLayer 2 }

usdVlanMajorIfEntry OBJECT-TYPE
    SYNTAX      UsdVlanMajorIfEntry
    MAX-ACCESS  not-accessible
    STATUS      current
    DESCRIPTION
        "Each entry describes the characteristics of a major VLAN interface.
        Creating/deleting entries in this table causes corresponding entries for
        be created/deleted in ifTable/ifXTable/usdIfTable."
    INDEX     { usdVlanMajorIfIndex }
    ::= { usdVlanMajorIfTable 1 }

UsdVlanMajorIfEntry ::= SEQUENCE {
    usdVlanMajorIfIndex         InterfaceIndex,
    usdVlanMajorIfLowerIfIndex  InterfaceIndexOrZero,
    usdVlanMajorIfRowStatus     RowStatus }

usdVlanMajorIfIndex OBJECT-TYPE
    SYNTAX      InterfaceIndex
    MAX-ACCESS  not-accessible
    STATUS      current
    DESCRIPTION
        "The ifIndex of the major VLAN interface.  When creating entries in this
        table, suitable values for this object are determined by reading
        usdVlanMajorNextIfIndex."
    ::= { usdVlanMajorIfEntry 1 }

usdVlanMajorIfLowerIfIndex OBJECT-TYPE
    SYNTAX      InterfaceIndexOrZero
    MAX-ACCESS  read-create
    STATUS      current
    DESCRIPTION
        "The ifIndex of the interface over which this major VLAN interface is to
        be layered.  A value of zero indicates no layering.  An implementation
        may choose to require that a nonzero value be configured at entry
        creation."
    ::= { usdVlanMajorIfEntry 2 }

usdVlanMajorIfRowStatus OBJECT-TYPE
    SYNTAX      RowStatus
    MAX-ACCESS  read-create
    STATUS      current
    DESCRIPTION
        "Controls creation/deletion of entries in this table according to the
        RowStatus textual convention, constrained to support the following
        values only:
            createAndGo
            destroy
           
        To create or delete an entry in this table, the following entry objects
        MUST be explicitly configured:
            usdVlanMajorIfRowStatus
            usdVlanMajorIfLowerIfIndex

        In addition, when creating an entry the following conditions must hold:

            A value for usdVlanMajorIfIndex must have been determined previously
            by reading usdVlanMajorIfNextIfIndex.

            The interface identified by usdVlanMajorIfLowerIfIndex must exist.

        A corresponding entry in ifTable/ifXTable/usdIfTable is created/destroyed
        as a result of creating/destroying an entry in this table."
    ::= { usdVlanMajorIfEntry 3 }


-- +++++++++++++++++++++++++++++++++++++++++++++++++++++++++++++++++++++++++++++
-- VLAN SubInterface Creation
-- +++++++++++++++++++++++++++++++++++++++++++++++++++++++++++++++++++++++++++++
usdVlanSubNextIfIndex OBJECT-TYPE
    SYNTAX      UsdNextIfIndex
    MAX-ACCESS  read-only
    STATUS      current
    DESCRIPTION
        "Coordinate ifIndex value allocation for entries in usdVlanSubIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdVlanSubIfLayer 1 }

--
-- The VLAN Subinterface Table
--
usdVlanSubIfTable OBJECT-TYPE
    SYNTAX      SEQUENCE OF UsdVlanSubIfEntry
    MAX-ACCESS  not-accessible
    STATUS      current
    DESCRIPTION
        "This table contains entries for VLAN Subinterfaces present in the
        system."
    ::= { usdVlanSubIfLayer 2 }

usdVlanSubIfEntry OBJECT-TYPE
    SYNTAX      UsdVlanSubIfEntry
    MAX-ACCESS  not-accessible
    STATUS      current
    DESCRIPTION
        "Each entry describes the characteristics of a VLAN Subinterface.
        Creating/deleting entries in this table causes corresponding entries for
        be created/deleted in ifTable/ifXTable/usdIfTable."
    INDEX     { usdVlanSubIfIndex }
    ::= { usdVlanSubIfTable 1 }

UsdVlanSubIfEntry ::= SEQUENCE {
    usdVlanSubIfIndex               InterfaceIndex,
    usdVlanSubIfVlanId              Integer32,
    usdVlanSubIfVlanUntagged        TruthValue,
    usdVlanSubIfVlanStackId         Integer32,
    usdVlanSubIfVlanStackEthertype  INTEGER,
    usdVlanSubIfLowerIfIndex        InterfaceIndexOrZero,
    usdVlanSubIfRowStatus           RowStatus }

usdVlanSubIfIndex OBJECT-TYPE
    SYNTAX      InterfaceIndex
    MAX-ACCESS  not-accessible
    STATUS      current
    DESCRIPTION
        "The ifIndex of the VLAN Subinterface.  When creating entries in this
        table, suitable values for this object are determined by reading
        usdVlanSubNextIfIndex."
    ::= { usdVlanSubIfEntry 1 }

usdVlanSubIfVlanId OBJECT-TYPE
    SYNTAX      Integer32 (0..4095)
    MAX-ACCESS  read-create
    STATUS      current
    DESCRIPTION
        "An integer identifier or tag ID for this VLAN A value of zero indicates
        the default VLAN.

        When VLANs are enabled, the value must be unique among subinterfaces
        configured on the same underlying major VLAN interface.
        
        If the VLAN ID is non-zero, then the usdVlanSubIfVlanUntagged field must
        be disabled.

        Cannot be changed if the subinterface has upper bindings."
    ::= { usdVlanSubIfEntry 2 }

usdVlanSubIfVlanUntagged OBJECT-TYPE
    SYNTAX      TruthValue 
    MAX-ACCESS  read-create
    STATUS      current
    DESCRIPTION
        "When VLANs are enabled, this allows tagged frames to be received, while
        transmitted frames remain untagged.  This can only be enabled when the
        usdVlanSubIfVlanId field is zero.

        Cannot be changed if the vlan subinterface has upper bindings."
    ::= { usdVlanSubIfEntry 3 }

usdVlanSubIfVlanStackId OBJECT-TYPE
    SYNTAX      Integer32 (0..4095)
    MAX-ACCESS  read-create
    STATUS      current
    DESCRIPTION
        "An integer identifier or tag ID for this S-VLAN.

        When S-VLANs are enabled, the VLAN and S-VLAN ID valuse must be unique
        among subinterfaces configured on the same underlying major VLAN
        interface.
        
        If the S-VLANs are enabled, then the usdVlanSubIfVlanUntagged field must
        be disabled.

        Cannot be changed if the subinterface has upper bindings."
    ::= { usdVlanSubIfEntry 6 }

usdVlanSubIfVlanStackEthertype OBJECT-TYPE
    SYNTAX      INTEGER {
                    etherType9100h(37120),
                    etherType9200h(37376) }
    MAX-ACCESS  read-create
    STATUS      current
    DESCRIPTION
        "The ethertype is used to recognize and demultiplex traffic for this
        S-VLAN.  Must be either 0x9100 or 0x9200.  Cannot be changed if the
        subinterface has upper bindings."
    ::= { usdVlanSubIfEntry 7 }

usdVlanSubIfLowerIfIndex OBJECT-TYPE
    SYNTAX      InterfaceIndexOrZero
    MAX-ACCESS  read-create
    STATUS      current
    DESCRIPTION
        "The ifIndex of VLAN major interface over which this VLAN Subinterface
        is to be layered.  A value of zero indicates no layering.  An
        implementation may choose to require that a nonzero value be configured
        at entry creation."
    ::= { usdVlanSubIfEntry 4 }

usdVlanSubIfRowStatus OBJECT-TYPE
    SYNTAX      RowStatus
    MAX-ACCESS  read-create
    STATUS      current
    DESCRIPTION
        "Controls creation/deletion of entries in this table according to the
        RowStatus textual convention, constrained to support the following
        values only:
            createAndGo
            destroy
           
        To create an entry in this table, the following entry objects MUST be
        explicitly configured:
            usdVlanSubIfRowStatus
            usdVlanSubIfLowerIfIndex
            usdVlanSubIfVlanId
            usdVlanSubIfVlanUntagged

        To delete an entry in this table, the following entry objects MUST be
        explicitly configured:
            usdVlanSubIfRowStatus
            usdVlanSubIfLowerIfIndex

        In addition, when creating an entry the following conditions must hold:

            A value for usdVlanSubIfIndex must have been determined previously
            by reading usdVlanSubIfNextIfIndex.

            The interface identified by usdVlanSubIfLowerIfIndex must exist, and
            must be a Ethernet interface.

        A corresponding entry in ifTable/ifXTable/usdIfTable is created/destroyed
        as a result of creating/destroying an entry in this table."
    ::= { usdVlanSubIfEntry 5 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdEthernetTrapControl      OBJECT IDENTIFIER ::= { usdEthernetMIB 2 }

-- +++++++++++++++++++++++++++++++++++++++++++++++++++++++++++++++++++++++++++++
-- Notifications
-- ++++++++++++++++++++++++++++++++++++++++++++++++++++++++++++++++++++++++++++
-- No notifications are defined in this MIB.  Placeholder follows.
-- The following two OBJECT IDENTIFIERS are used to define SNMPv2 
-- Notifications that are easily translated into SNMPv1 Traps.
-- usdEthernetTraps        OBJECT IDENTIFIER ::= { usdEthernetMIB 3 }
-- usdEthernetPrefix       OBJECT IDENTIFIER ::= { usdEthernetTraps 0 }


-- +++++++++++++++++++++++++++++++++++++++++++++++++++++++++++++++++++++++++++++
-- Conformance information
-- +++++++++++++++++++++++++++++++++++++++++++++++++++++++++++++++++++++++++++++
usdEthernetConformance OBJECT IDENTIFIER ::= { usdEthernetMIB 4 }
usdEthernetCompliances OBJECT IDENTIFIER ::= { usdEthernetConformance 1 }
usdEthernetGroups      OBJECT IDENTIFIER ::= { usdEthernetConformance 2 }

--
-- compliance statements
--
usdEthernetCompliance MODULE-COMPLIANCE
    STATUS      obsolete
    DESCRIPTION
        "Obsolete compliance statement for entities which implement the
        Unisphere Ethernet MIB.  This statement became obsolete when support for
        VLANs was added."
    MODULE   -- this module
        MANDATORY-GROUPS {
            usdEthernetGroup,
            usdEthernetSubIfGroup }
    ::= { usdEthernetCompliances 1 }                                   -- RX 2.0

usdEthernetCompliance2 MODULE-COMPLIANCE
    STATUS      obsolete
    DESCRIPTION
        "Obsolete compliance statement for entities which implement the
        Unisphere Ethernet MIB.  This statement became obsolete when VLAN stack
        support was added."
    MODULE   -- this module
        MANDATORY-GROUPS {
            usdEthernetGroup,
            usdEthernetSubIfGroup }
        GROUP       usdVlanGroup
            DESCRIPTION
                "The usdVlanGroup is mandatory only for entities that support
                VLAN interfaces."
        GROUP       usdVlanSubIfGroup
            DESCRIPTION
                "The usdVlanSubIfGroup is mandatory only for entities that
                support a subinterface to major interface layer model for VLAN
                interfaces."
    ::= { usdEthernetCompliances 2 }                                   -- RX 3.0

usdEthernetCompliance3 MODULE-COMPLIANCE
    STATUS      current
    DESCRIPTION
        "The compliance statement for entities which implement the Unisphere
        Ethernet MIB."
    MODULE   -- this module
        MANDATORY-GROUPS {
            usdEthernetGroup,
            usdEthernetSubIfGroup }
        GROUP       usdVlanGroup
            DESCRIPTION
                "The usdVlanGroup is mandatory only for entities that support
                VLAN interfaces."
        GROUP       usdVlanSubIfGroup2
            DESCRIPTION
                "This group is mandatory only for entities that support a
                subinterface to major interface layer model for VLAN
                interfaces."
    ::= { usdEthernetCompliances 3 }                                   -- RX 4.0

--
-- units of conformance
--
usdEthernetGroup OBJECT-GROUP
    OBJECTS {
        usdEthernetIfDuplexMode, 
        usdEthernetIfSpeed,
        usdEthernetIfMtu,
        usdEthernetIfOperDuplexMode }
    STATUS      current
    DESCRIPTION
        "A collection of objects providing management of Ethernet interfaces in
        a Unisphere product."
    ::= { usdEthernetGroups 1 }

usdEthernetSubIfGroup OBJECT-GROUP
    OBJECTS {   
        usdEthernetSubIfNextIfIndex,
        usdEthernetSubIfRowStatus,
        usdEthernetSubIfLowerIfIndex,
        usdEthernetSubIfId }
    STATUS      current
    DESCRIPTION 
        "A collection of objects providing management of Ethernet SubInterfaces
        in a Unisphere product."
    ::= { usdEthernetGroups 2 }

usdVlanGroup OBJECT-GROUP
    OBJECTS {
        usdVlanMajorNextIfIndex, 
        usdVlanMajorIfLowerIfIndex,
        usdVlanMajorIfRowStatus }
    STATUS      current
    DESCRIPTION
        "A collection of objects providing management of Major VLAN interfaces
        in a Unisphere product."
    ::= { usdEthernetGroups 3 }

usdVlanSubIfGroup OBJECT-GROUP
    OBJECTS {
        usdVlanSubNextIfIndex, 
        usdVlanSubIfVlanId,
        usdVlanSubIfVlanUntagged,
        usdVlanSubIfLowerIfIndex,
        usdVlanSubIfRowStatus }
    STATUS      obsolete
    DESCRIPTION 
        "Obsolete collection of objects providing management of VLAN
        SubInterfaces in a Unisphere product.  This group became obsolete when
        VLAN stack support was added."
    ::= { usdEthernetGroups 4 }

usdVlanSubIfGroup2 OBJECT-GROUP
    OBJECTS {
        usdVlanSubNextIfIndex, 
        usdVlanSubIfVlanId,
        usdVlanSubIfVlanUntagged,
        usdVlanSubIfVlanStackId,
        usdVlanSubIfVlanStackEthertype,
        usdVlanSubIfLowerIfIndex,
        usdVlanSubIfRowStatus }
    STATUS      current
    DESCRIPTION 
        "A collection of objects providing management of VLAN SubInterfaces in a
        Unisphere product."
    ::= { usdEthernetGroups 5 }

END
