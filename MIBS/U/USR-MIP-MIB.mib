USR-MIP-MIB DEFINITIONS ::= BEGIN
	IMPORTS
		OBJECT-TYPE,
        MODULE-IDENTITY,
		Integer32,
		Counter32,
		IpAddress,
		Unsigned32,
		Gauge32
			FROM SNMPv2-SMI
		RowStatus,
		TruthValue,
        DisplayString
			FROM SNMPv2-TC
		NOTIFICATION-TYPE
			FROM SNMPv2-SMI
		OBJECT-IDENTITY
			FROM SNMPv2-SMI
        common,
		UsrConfigStatus,
        UsrSecretDisplay,
        UsrSpecialU32
			FROM USR-DEFINITIONS-MIB;
usrMIP  MODULE-IDENTITY
        LAST-UPDATED "200301221300Z"
        ORGANIZATION "CommWorks Corporation, a 3Com Company"
        CONTACT-INFO "Customer Support"
        DESCRIPTION   "Added usrMipHaSendICMPforPMTUDiscovery"
--      REVISION      "200301221300Z"
--      DESCRIPTION   "Added usrMipMultipleLoginsStatus,
--         usrMipHaDuplicateNaiDiscs, usrMipHaClearMBRDiscs."
--      REVISION      "200211061300Z"
--      DESCRIPTION   "Added usrMipHaDuplicateIPDiscs"
--      REVISION      "200211011330Z"
--      DESCRIPTION   "Added usrMipHaGarpUponRereg"
--      REVISION      "200208301200Z"
--      DESCRIPTION   "Added usrMipHaGarpUponRereg"
--      REVISION      "200208231825Z"
--      DESCRIPTION   "Clarified usage of objects usrMipHaTunnelDeleteAll,
--         usrMipHaTunDelByNAI, usrMipHaMnSaIndexKey, usrMipHaFaSaKey,
--         usrMipHaHacnSecret, usrMipHaMobilityBindingRegIDLow, 
--         usrMipHaMobilityBindingRegIDHigh, usrMipHaMobilityBindingNAI,
--         usrMipHaHacnStatus, usrMipHaIdleTimerStatus,
--         usrMipHaUsingBothPorts, usrMipHaBroadcastBit, usrMipHaStatusIPSec,
--         usrMipHaTrapThreshold, usrMipHaTrapIdleTimer, 
--         usrMipHaRunIPNetworkStatus."
--      REVISION      "200208151730Z"
--      DESCRIPTION   "Added structured trap comments"
--      REVISION      "200208021630Z"
--      DESCRIPTION   "Corrected definitions of usrMipHaMnSaIndexKey  
--                     and usrMipHaFaSaKey"
--      REVISION      "200208011400Z"
--      DESCRIPTION   "Added usrMipMNHAKeyPadding"
--      REVISION      "200207181445Z"
--      DESCRIPTION   "obsoleted usrMipHaTunnelByAddr"
--      REVISION      "200205051330Z"
--      DESCRIPTION   "Created MODULE-IDENTITY for Mobile IP MIB"
        ::= { common 82 }
	usrMipHaConfig           OBJECT IDENTIFIER ::= { usrMIP 1 }
	usrMipHaStats            OBJECT IDENTIFIER ::= { usrMIP 2 }
	usrMipHaCfmConfig        OBJECT IDENTIFIER ::= { usrMIP 3 }
	usrMipHaTrapsSettings    OBJECT IDENTIFIER ::= { usrMIP 4 }
	usrMipHaTraps            OBJECT IDENTIFIER ::= { usrMIP 5 }
	usrMipHaStatus           OBJECT IDENTIFIER ::= { usrMIP 6 }
	usrMipHaMobileInfo       OBJECT IDENTIFIER ::= { usrMIP 7 } 
	usrMipHaLoadInfo         OBJECT IDENTIFIER ::= { usrMIP 8 } 
	usrMipHacnSettings       OBJECT IDENTIFIER ::= { usrMIP 9 }
	usrMipHacnStats          OBJECT IDENTIFIER ::= { usrMIP 10 }
-- Home Agent MIP configurable parameters
	usrMipHaMaxLifetime OBJECT-TYPE
		SYNTAX Integer32 (5..65535)
		UNITS "seconds"
		MAX-ACCESS read-write
		STATUS current
		DESCRIPTION
			"The longest lifetime in seconds that the Home
			 Agent is willing to accept in any Registration
			 Request."
		--CONFIGURABLE
	::= { usrMipHaConfig 1 }
	usrMipHaDomainName OBJECT-TYPE
		SYNTAX OCTET STRING (SIZE(0..128))
		MAX-ACCESS read-write
		STATUS obsolete
		DESCRIPTION
			"The HA domain name.
			 OBSOLETE:
			 This object is never used on HA."
		--CONFIGURABLE
	::= { usrMipHaConfig 2 }
	usrMipHaDomainSpi OBJECT-TYPE
		SYNTAX Unsigned32 (0..4294967295) 
		MAX-ACCESS read-write
		STATUS obsolete
		DESCRIPTION
			"The SPI is the 4-byte opaque index within
			 the Mobility Security Association which
			 selects the specific security parameters
			 to be used to authenticate the peer.
			 OBSOLETE:
			 This object is never used on HA."
		--CONFIGURABLE
	::= { usrMipHaConfig 3 }
	usrMipHaDomainKey OBJECT-TYPE
		SYNTAX OCTET STRING (SIZE(0..16))
		MAX-ACCESS read-write
		STATUS obsolete
		DESCRIPTION
			"The shared secret key for the security associations.
			 Reading this object will always return zero length
			 value.
			 OBSOLETE:
			 This object is never used on HA."
		--CONFIGURABLE
	::= { usrMipHaConfig 4 }
	usrMipHaHacnAddress OBJECT-TYPE
		SYNTAX IpAddress
		MAX-ACCESS read-write
		STATUS current
		DESCRIPTION
			"Home Agent Control Node's RUN IP Address."
		--CONFIGURABLE
	::= { usrMipHaConfig 5 }
	usrMipFaDomainSpi OBJECT-TYPE
		SYNTAX Unsigned32 (0..4294967295)
		MAX-ACCESS read-write
		STATUS obsolete
		DESCRIPTION
			"The SPI is the 4-byte opaque index within
			 the Mobility Security Association which
			 selects the specific security parameters
			 to be used to authenticate the peer.
			 OBSOLETE:
			 This object is never used on HA."
		--CONFIGURABLE
	::= { usrMipHaConfig 6 }
	usrMipFaDomainKey OBJECT-TYPE
		SYNTAX OCTET STRING (SIZE(0..16))
		MAX-ACCESS read-write
		STATUS obsolete
		DESCRIPTION
			"The shared secret key for the security associations.
			 Reading this object will always return zero length
			 value.
			 OBSOLETE:
			 This object is never used on HA."
		--CONFIGURABLE
	::= { usrMipHaConfig 7 }
	usrMipHaTimeDrift OBJECT-TYPE
		SYNTAX INTEGER (0..255)
		UNITS "seconds"
		MAX-ACCESS read-write
		STATUS current
		DESCRIPTION
			"The value represents how close the timestamp,
			 contained in the Identification information element
			 of the Registration Request or the Registration
			 Acknowledge message, should be to the PDSN's time
			 of day clock.  This time tolerance is used in
			 conjunction with timestamp replay protection
			 against replay attacks."
		--CONFIGURABLE
	::= { usrMipHaConfig 8 }
	usrMipHaMaxTunnels OBJECT-TYPE
		SYNTAX INTEGER (0..10000)
		MAX-ACCESS read-write
		STATUS current
		DESCRIPTION
			"Maximum number of tunnels that can be established
			 by this Home Agent."
		--CONFIGURABLE
	::= { usrMipHaConfig 9 }
	usrMipHaHacnStatus OBJECT-TYPE
		SYNTAX INTEGER {
                    enabled(1),
                    disabled(2)
                    }
		MAX-ACCESS read-write
		STATUS current
		DESCRIPTION
       		"Specifies if the HACN Interface is available.
             When set for the first time all active HA tunnels will
             be deleted prior to initialization. Enabling an already
             active interface has no action and returns no error.
             Disabling an active interface will cause deleteion of
             all tunnels and services provided on the interface.
             Disabling an inactive interface has no action and
             returns no error."
		--CONFIGURABLE
	::= { usrMipHaConfig 10 }
	usrMipHaMobileRegDump OBJECT-TYPE
		SYNTAX TruthValue
		MAX-ACCESS read-write
		STATUS deprecated
		DESCRIPTION
			"Specifies if the MIP debugging is enabled.
            DEPRECATED:
            The CLI command Set Mobile Reg_dump on/off removed."
		--CONFIGURABLE
	::= { usrMipHaConfig 11 }
	usrMipHaMnSaTable OBJECT-TYPE
		SYNTAX SEQUENCE OF UsrMipHaMnSaEntry
		MAX-ACCESS not-accessible
		STATUS current
		DESCRIPTION
			"A table for configuring mobility security
			 associations between mobile nodes and the
			 Home Agent."
	::= { usrMipHaConfig 12 }
	usrMipHaMnSaEntryIndex OBJECT-TYPE
		SYNTAX UsrMipHaMnSaEntry
		MAX-ACCESS not-accessible
		STATUS current
		DESCRIPTION
			"An entry in the Home Agent Security Association
			 Table."
		INDEX { usrMipHaMnSaIndexNum }
	::= { usrMipHaMnSaTable 1 }
	UsrMipHaMnSaEntry ::= SEQUENCE {
		usrMipHaMnSaIndexNum    INTEGER,
		usrMipHaMnSaIndexSpi    Unsigned32,
		usrMipHaMnSaIndexKey    UsrSecretDisplay,
		usrMipHaMnSaIndexStatus RowStatus
	}
	usrMipHaMnSaIndexNum OBJECT-TYPE
		SYNTAX INTEGER (1..1000)
		MAX-ACCESS read-only
		STATUS current
		DESCRIPTION
			"Home Agent can support up to 1000 mobility
			 security associations."
	::= { usrMipHaMnSaEntryIndex 1 }
	usrMipHaMnSaIndexSpi OBJECT-TYPE
		SYNTAX Unsigned32 (256..4294967295) 
		MAX-ACCESS read-write
		STATUS current
		DESCRIPTION
			"The SPI is the 4-byte opaque index within
			 the Mobility Security Association which
			 selects the specific security parameters
			 to be used to authenticate the peer."
		--CONFIGURABLE
	::= { usrMipHaMnSaEntryIndex 2 }
	usrMipHaMnSaIndexKey OBJECT-TYPE
		SYNTAX     UsrSecretDisplay
		MAX-ACCESS read-write
		STATUS current
		DESCRIPTION
			"The shared secret key for the security associations."
		--CONFIGURABLE
	::= { usrMipHaMnSaEntryIndex 3 }
	usrMipHaMnSaIndexStatus OBJECT-TYPE
		SYNTAX RowStatus
		MAX-ACCESS read-write
		STATUS current
		DESCRIPTION
			"This object is used to add, modify, and delete
			 rows for the security association table."
		--CONFIGURABLE
	::= { usrMipHaMnSaEntryIndex 4 }
	usrMipHaTunIPToDel OBJECT-TYPE
		SYNTAX IpAddress
		MAX-ACCESS read-write
		STATUS current
		DESCRIPTION
			"Delete a tunnel specified by this IP address."
	::= { usrMipHaConfig 13 }
	usrMipHaTunnelDeleteAll OBJECT-TYPE
		SYNTAX TruthValue
		MAX-ACCESS read-write
		STATUS current
		DESCRIPTION
		"When this flag is FALSE it indicates that HACN should not be 
             updated with a delete MBR. This case will happen if the HACN 
             interface is disabled on HA and re-enabled before HACN can 
             find out that it happened. If this happens then at least HACN 
             can download MBRs to the this HA. If this flag is set to TRUE
             all MBR's are deleted from HA. This flag will always return
             FALSE on a read."
	::= { usrMipHaConfig 14 }
	usrMipHaHacnSoftbusy OBJECT-TYPE
   		SYNTAX  INTEGER {
			disabled(0),
			enabled(1)
		}
   		MAX-ACCESS  read-write
   		STATUS  current
   		DESCRIPTION
       		"HA is softbusy or not.
            From 3.0 onwards it means that this HA will try to forward the
            Registration Request received by it and in case it can not find 
            a HA to which Registration Request can be forwarded, this HA 
            will process that request.
            Softbusy state can be changed only for ACTIVE non IPSec HA."
	::= { usrMipHaConfig 15 }
	usrMipHaHacnSecret OBJECT-TYPE
   		SYNTAX  UsrSecretDisplay
   		MAX-ACCESS  read-write
   		STATUS  current
   		DESCRIPTION
       		"Secret shared between HA and HACN."
		--CONFIGURABLE
	::= { usrMipHaConfig 16 }
	usrMipHaIdleTimer OBJECT-TYPE
		SYNTAX Unsigned32 (5..600)
		UNITS "seconds"
		MAX-ACCESS read-write
		STATUS current
		DESCRIPTION
			"The value represents the time interval when a process 
             will be run to delete the MBRs for the MNs on which 
             there have been no activity for certain time (which
             is equal to maximum idle time). This value should be
			 less than MaxIdleTime. The default is 10 secs."
		--CONFIGURABLE
	::= { usrMipHaConfig 17 }
	usrMipHaIdleTimerStatus OBJECT-TYPE
   		SYNTAX INTEGER {
                    enabled(1),
                    disabled(2)
                    } 
   		MAX-ACCESS  read-write
   		STATUS  current
   		DESCRIPTION
       		"Idle Timer Enabled or Disabled. The default is Disabled.
             Attempting to enable/disable the Idle TImer while any
             call is active will return an error."
        --CONFIGURABLE
	::= { usrMipHaConfig 18 }
	usrMipHaMaxIdleTime OBJECT-TYPE
		SYNTAX Unsigned32 (10..65535)
		UNITS "seconds"
		MAX-ACCESS read-write
		STATUS current
		DESCRIPTION
			"The value represents the time for the maximum idle
             time. If for this much time there is no activity  
             (data transfer), then the MBR for this MN will be 
             deleted. This value should be greater than 
             IdleTimer. The default value is 65535 secs."
		--CONFIGURABLE
	::= { usrMipHaConfig 19 }
	usrMipHaWAPCCStatus OBJECT-TYPE
		SYNTAX INTEGER {
                    enabled(1),
                    disabled(2)
                    }
		MAX-ACCESS read-write
		STATUS current
		DESCRIPTION
       		"Specifies if WAP Call Clearing is enabled.
             Enabling if already enabled has no action and no
             error is returned. Disabling this feature while
             any update message is pending will return an error."
		--CONFIGURABLE
	::= { usrMipHaConfig 20 }
	usrMipHaTunnelByAddr OBJECT-TYPE
		SYNTAX IpAddress
		MAX-ACCESS read-write
		STATUS obsolete
		DESCRIPTION
			"Display a tunnel specified by this IP address.
			 OBSOLETE:
			 This object is never used on HA."
	::= { usrMipHaConfig 21 }
    usrMipHaStatsResetTime OBJECT-TYPE
        SYNTAX	Unsigned32 
		MAX-ACCESS  read-write
		STATUS  current
		DESCRIPTION
                "Reading:
				Time the HA statistics counters were last 
			 	reset. The HA statistics are valid from 
				usrMipHAStatsResetTime until present.
	        		Resetting counters causes a discontinuity in 
				the monotonically increasing value of counters.
				Management stations that sample these counters
				need also to sample this object so that they 
				can know that a discontinuity occurred with 
				respect to the previous sample.  
                Its value is in NTP format.
		        Writing:
		   	    Writing 0 causes update of usrMipHAStatsResetTime
				and the HA counters to be reset to 0."
	::= { usrMipHaConfig 22 }
	usrMipHaUsingBothPorts OBJECT-TYPE
		SYNTAX INTEGER {
                    enabled(1),
                    disabled(2)
                    }
		MAX-ACCESS read-write
		STATUS current
		DESCRIPTION
   			"Specifies if HA is using both ports. Port 1 (eth:1) will
             always be used for interfacing with PDSN/FA/HACN"
		--CONFIGURABLE
	::= { usrMipHaConfig 23 }
	usrMipHaTunDelByNAI OBJECT-TYPE
		SYNTAX     DisplayString 
		MAX-ACCESS read-write
		STATUS current
		DESCRIPTION
			"Delete tunnel(s) specified by this NAI. Reading this
             value returns NULL."
	::= { usrMipHaConfig 24 }
	usrMipHaBroadcastBit OBJECT-TYPE
		SYNTAX INTEGER {
                    enabled(1),
                    disabled(2)
                    }
		MAX-ACCESS read-write
		STATUS current
		DESCRIPTION
   			"This flag specifies if HA should accept a registration
             request with B bit set in registration flags or not. By
             default this bit is set and HA will accept reg req with 
             B bit set."
		--CONFIGURABLE
	::= { usrMipHaConfig 25 }
	usrMipHaNAICheck OBJECT-TYPE
		SYNTAX INTEGER {
                    enabled(1),
                    disabled(2)
                    }
		MAX-ACCESS read-write
		STATUS current
		DESCRIPTION
   			"Specifies if HA is checking NAI for re-registration requests
             or not. If it is enable then NAI is checked for each
             Re-Registration Requests otherwise NAI is not checked. By
             default NAI check is enabled."
		--CONFIGURABLE
	::= { usrMipHaConfig 26 }
	usrMipHaFaSaTable OBJECT-TYPE
		SYNTAX SEQUENCE OF UsrMipHaFaSaEntry
		MAX-ACCESS not-accessible
		STATUS current
		DESCRIPTION
			"A table for configuring FA security
			 associations between PDSN/FA and the
			 Home Agent."
	::= { usrMipHaConfig 27 }
	usrMipHaFaSaEntryIndex OBJECT-TYPE
		SYNTAX UsrMipHaFaSaEntry
		MAX-ACCESS not-accessible
		STATUS current
		DESCRIPTION
			"An entry in the FA-HA Security Association
			 Table."
		INDEX { usrMipHaFaSaIndexNum }
	::= { usrMipHaFaSaTable 1 }
	UsrMipHaFaSaEntry ::= SEQUENCE {
		usrMipHaFaSaIndexNum    INTEGER,
		usrMipHaFaSaIpAddress   IpAddress,
		usrMipHaFaSaSpi         Unsigned32,
		usrMipHaFaSaKey         UsrSecretDisplay,
		usrMipHaFaSaStatus      RowStatus
	}
	usrMipHaFaSaIndexNum OBJECT-TYPE
		SYNTAX INTEGER (1..100)
		MAX-ACCESS read-only
		STATUS current
		DESCRIPTION
			"Home Agent can support up to 100 FA-HA
			 security associations."
	::= { usrMipHaFaSaEntryIndex 1 }
	usrMipHaFaSaIpAddress OBJECT-TYPE
		SYNTAX IpAddress 
		MAX-ACCESS read-write
		STATUS current
		DESCRIPTION
			"The IP address of PDSN/FA."
		--CONFIGURABLE
	::= { usrMipHaFaSaEntryIndex 2 }
	usrMipHaFaSaSpi OBJECT-TYPE
		SYNTAX Unsigned32 (256..4294967295) 
		MAX-ACCESS read-write
		STATUS current
		DESCRIPTION
			"The SPI is the 4-byte opaque index within
			 the FA-HA Security Association which
			 selects the specific security parameters
			 to be used to authenticate the peer."
		--CONFIGURABLE
	::= { usrMipHaFaSaEntryIndex 3 }
	usrMipHaFaSaKey OBJECT-TYPE
		SYNTAX     UsrSecretDisplay
		MAX-ACCESS read-write
		STATUS current
		DESCRIPTION
			"The shared secret key for the security associations."
		--CONFIGURABLE
	::= { usrMipHaFaSaEntryIndex 4 }
	usrMipHaFaSaStatus OBJECT-TYPE
		SYNTAX RowStatus
		MAX-ACCESS read-write
		STATUS current
		DESCRIPTION
			"This object is used to add, modify, and delete
			 rows for the security association table."
		--CONFIGURABLE
	::= { usrMipHaFaSaEntryIndex 5 }
-- HA Load information table
	usrMipHaLoadInfoSystemLoad OBJECT-TYPE
		SYNTAX Unsigned32
		MAX-ACCESS read-only
		STATUS current
		DESCRIPTION
			"This specifies the average load on the system. This is calculated
            by HACN and distributed to all the HAs in the heartbeat ack
            message."
	::= { usrMipHaLoadInfo 1 }
	usrMipHaLoadInfoLLHA1 OBJECT-TYPE
		SYNTAX IpAddress
		MAX-ACCESS read-only
		STATUS current
		DESCRIPTION
			"IP address of the least loaded HA 1 in the system. This information
            is passed by HACN."
	::= { usrMipHaLoadInfo 2 }
	usrMipHaLoadInfoLLHA2 OBJECT-TYPE
		SYNTAX IpAddress
		MAX-ACCESS read-only
		STATUS current
		DESCRIPTION
			"IP address of the least loaded HA 2 in the system. This information
            is passed by HACN."
	::= { usrMipHaLoadInfo 3 }
	usrMipHaLoadInfoLLHA3 OBJECT-TYPE
		SYNTAX IpAddress
		MAX-ACCESS read-only
		STATUS current
		DESCRIPTION
			"IP address of the least loaded HA 3 in the system. This information
            is passed by HACN."
	::= { usrMipHaLoadInfo 4 }
	usrMipHaLoadInfoLLHA4 OBJECT-TYPE
		SYNTAX IpAddress
		MAX-ACCESS read-only
		STATUS current
		DESCRIPTION
			"IP address of the least loaded HA 4 in the system. This information
            is passed by HACN."
	::= { usrMipHaLoadInfo 5 }
	usrMipHaLoadInfoLoadHA1 OBJECT-TYPE
		SYNTAX Unsigned32
		MAX-ACCESS read-only
		STATUS current
		DESCRIPTION
			"Current load of least loaded HA1."
	::= { usrMipHaLoadInfo 6 }
	usrMipHaLoadInfoLoadHA2 OBJECT-TYPE
		SYNTAX Unsigned32
		MAX-ACCESS read-only
		STATUS current
		DESCRIPTION
			"Current load of least loaded HA2."
	::= { usrMipHaLoadInfo 7 }
	usrMipHaLoadInfoLoadHA3 OBJECT-TYPE
		SYNTAX Unsigned32
		MAX-ACCESS read-only
		STATUS current
		DESCRIPTION
			"Current load of least loaded HA3."
	::= { usrMipHaLoadInfo 8 }
	usrMipHaLoadInfoLoadHA4 OBJECT-TYPE
		SYNTAX Unsigned32
		MAX-ACCESS read-only
		STATUS current
		DESCRIPTION
			"Current load of least loaded HA4."
	::= { usrMipHaLoadInfo 9 }
	usrMipHaStatusIPSec OBJECT-TYPE
		SYNTAX INTEGER {
                    enabled(1),
                    disabled(2)
                    }
		MAX-ACCESS read-write
		STATUS current
   		DESCRIPTION
       		"Indicates this HA is IPSec enabled or not. If enabled 
             then this HA will be used to service IPSec calls. 
            In case HACN is present, this HA will accept only ipsec 
            enabled virtual HA profile during role assignment."
		--CONFIGURABLE
	::= { usrMipHaConfig 28 }
	usrMipAuthenticationStyle OBJECT-TYPE
   		SYNTAX  INTEGER {
			rfc2002(1),
			rfc2002bis(2)
		}
		MAX-ACCESS read-write
		STATUS current
   		DESCRIPTION
       		"Indicates the authentication style on HA for registration requests.
            The HA can authenticate request according to RFC2002 standards or 
            RFC2002bis standards.
            RFC2002 and RFC2002BIS are the only two valid values
            Value 1 will specify RFC2002 Auth Style and 
            value 2 will specify RFC2002BIS Auth Style."
		--CONFIGURABLE
	::= { usrMipHaConfig 29 }
	usrMipMNHAKeyTransportScheme OBJECT-TYPE
   		SYNTAX  INTEGER {
			threecom-vsa(1),
			is-835(2)
		}
		MAX-ACCESS read-write
		STATUS current
   		DESCRIPTION
       		"Indicates the MN_HA Key Transport Scheme for access request to AAA.
            The radius attribute returned by AAA for MN-HA secret will depend upon
            the Key Transport Scheme. 
            ThreeCom-VSA and IS-835 are the only two valid values
            Value 1 will specify 3Com VSA and 
            value 2 will specify IS-835."
		--CONFIGURABLE
	::= { usrMipHaConfig 30 }
    usrMipMNHAKeyPadding OBJECT-TYPE
		SYNTAX TruthValue
		MAX-ACCESS read-write
		STATUS current
   		DESCRIPTION
       		"Indicates whether HA has MN-HA Key padding enabled or disabled.
            If enabled, the key will be padded and if disabled the exact
            length of the key will be taken.
            Padding can be set only if there are no calls up in the system.
            By default the Key will be padded."
		--CONFIGURABLE
	::= { usrMipHaConfig 31 }
    usrMipLoadBalancingStatus OBJECT-TYPE
		SYNTAX TruthValue
		MAX-ACCESS read-write
		STATUS current
   		DESCRIPTION
       		"Indicates whether HA will forward MIP Registration Requests to
            other HAs for Load Balancing or not. If enabled HA will do load
            balancing else it will not forward MIP RRQ.
            By default the HA will do Load Balancing."
		--CONFIGURABLE
	::= { usrMipHaConfig 32 }
    usrMipHaGarpUponRereg OBJECT-TYPE
   		SYNTAX  INTEGER {
			enabled(1),
			disabled(2)
		}
		MAX-ACCESS read-write
		STATUS current
   		DESCRIPTION
       		"Indicates whether G-ARP upon MIP Re-Registration is enabled or disabled.
            If enabled, the HA will send G-ARP for the MN address for
            Re-Registration request else it will not be sent. G-ARP is always sent 
            for Initial Registration request."
		--CONFIGURABLE
	::= { usrMipHaConfig 33 }
    usrMipHaSendICMPforPMTUDiscovery OBJECT-TYPE
   		SYNTAX  INTEGER {
			enabled(1),
			disabled(2)
		}
		MAX-ACCESS read-write
		STATUS current
   		DESCRIPTION
       		"Indicates whether HA will send ICMP message when it receives a packet
             with size bigger than Tunnel MTU size for Path MTU Discovery.
             Note: The CLI description was later changed to 'Check Tunnel MTU'. 
             CEM should also change the description to the same."
        DEFVAL { enabled }
		--CONFIGURABLE
	::= { usrMipHaConfig 34 }
    usrMipMultipleLoginsStatus OBJECT-TYPE
   		SYNTAX  INTEGER {
			enabled(1),
			disabled(2)
		}
		MAX-ACCESS read-write
		STATUS current
   		DESCRIPTION
       		"Indicates whether HA will allow Multiple Logins for same user or not."
        DEFVAL { enabled }
		--CONFIGURABLE
	::= { usrMipHaConfig 44 }
-- Home Agent registration counters for all mobile nodes.
	usrMipHaRegReqsIn OBJECT-TYPE
		SYNTAX Counter32
		MAX-ACCESS read-only
		STATUS current
		DESCRIPTION
			"Total number of Registration Requests processed
			 by the home agent."
	::= { usrMipHaStats 1 }
	usrMipHaRegAccptsSent OBJECT-TYPE
		SYNTAX Counter32
		MAX-ACCESS read-only
		STATUS current
		DESCRIPTION
			"Total number of Registrations Requests accepted
			 by the home agent (Code 0)."
	::= { usrMipHaStats 2 }
	usrMipHaRegRejsSent OBJECT-TYPE
		SYNTAX Counter32
		MAX-ACCESS read-only
		STATUS current
		DESCRIPTION
			"Total number Registration Requests denied by the
			 home agent."
	::= { usrMipHaStats 3 }
	usrMipHaRegReqsDropped OBJECT-TYPE
		SYNTAX Counter32
		MAX-ACCESS read-only
		STATUS current
		DESCRIPTION
			"Total number of Registration Requests that were
			 discarded by the home agent."
	::= { usrMipHaStats 4 }
	usrMipHaMnAuthFailures OBJECT-TYPE
		SYNTAX Counter32
		MAX-ACCESS read-only
		STATUS current
		DESCRIPTION
			"Total number of Registration Requests denied by
			 the home agent - mobile node failed authentication
			 (Code 131)."
	::= { usrMipHaStats 5 }
	usrMipHaFaAuthFailures OBJECT-TYPE
		SYNTAX Counter32
 		MAX-ACCESS read-only
		STATUS current
		DESCRIPTION
			"Total number of Registration Requests denied by
			 the home agent - foreign agent failed
			 authentication (Code 132)."
	::= { usrMipHaStats 6 }
	usrMipHaRegsMalformedIn OBJECT-TYPE
		SYNTAX Counter32
		MAX-ACCESS read-only
		STATUS current
		DESCRIPTION
			"Total number of Registration Requests denied by
			 the home agent - poorly formed request (Code 134.)"
	::= { usrMipHaStats 7 }
	usrMipHaRegReqsBadHaIn OBJECT-TYPE
		SYNTAX Counter32
		MAX-ACCESS read-only
		STATUS current
		DESCRIPTION
			"Total number of Registration Requests denied by
			 the home agent - unknown home agent address
			 (Code 136.)"
	::= { usrMipHaStats 8 }
	usrMipHaTimeCheckFailures OBJECT-TYPE
		SYNTAX Counter32
		MAX-ACCESS read-only
		STATUS current
		DESCRIPTION
			"Total number of Time Check Failures."
	::= { usrMipHaStats 9 }
	usrMipHaNAICheckFailures OBJECT-TYPE
		SYNTAX Counter32
		MAX-ACCESS read-only
		STATUS current
		DESCRIPTION
			"Total number of NAI Check Failures."
	::= { usrMipHaStats 10 }
	usrMipHaInsuffResources OBJECT-TYPE
		SYNTAX Counter32
		MAX-ACCESS read-only
   		STATUS current
   		DESCRIPTION
			"Total number of Registration Requests denied by
			 the home agent - insufficient resources
			 (Code 130.)"
	::= { usrMipHaStats 11 }
	usrMipHaLifetimeDiscs OBJECT-TYPE
		SYNTAX Counter32
   		MAX-ACCESS read-only
		STATUS current
   		DESCRIPTION
			"Total number of home agent initiated disconnects
			 due to Lifetime expiry event."
	::= { usrMipHaStats 12 }
	usrMipHaDeregDiscs OBJECT-TYPE
		SYNTAX Counter32
		MAX-ACCESS read-only
		STATUS current
		DESCRIPTION
			"Total number of Registration Requests received
			 by the home agent with a Lifetime of zero
			 (requests to deregister)."
	::= { usrMipHaStats 13 }
	usrMipHaManualDiscs OBJECT-TYPE
		SYNTAX Counter32
		MAX-ACCESS read-only
		STATUS current
		DESCRIPTION
			"Total number of manual disconnects initiated
			 by this home agent."
	::= { usrMipHaStats 14 }
	usrMipHaTotalSessions OBJECT-TYPE
		SYNTAX Counter32
		MAX-ACCESS read-only
		STATUS current
		DESCRIPTION
			"Total number of sessions handled by this home
			 agent."
	::= { usrMipHaStats 15 }
	usrMipHaUnsupEncapFailures OBJECT-TYPE
		SYNTAX Counter32
		MAX-ACCESS read-only
   		STATUS deprecated
		DESCRIPTION
			"Total number of Registration Requests denied by
			 the home agent - Unsupported Encapsulation (Code 139.)
			DEPRECATED:
			HA does not report this error code any more.
			If HA receives M Bit in registration request, it gives 129 error
			code."
	::= { usrMipHaStats 17 }
	usrMipHaCurrentSessions OBJECT-TYPE
		SYNTAX Counter32
		MAX-ACCESS read-only
   		STATUS current
		DESCRIPTION
			"Current number of active sessions."
	::= { usrMipHaStats 16 }
-- More statistics counter after Home agent binding list
-- Home Agent mobility binding list
	usrMipHaMobilityBindingTable OBJECT-TYPE
		SYNTAX SEQUENCE OF UsrMipHaMobilityBindingEntry
		MAX-ACCESS not-accessible
		STATUS current
		DESCRIPTION
			"A table containing the home agent's mobility
			 binding list.  The home agent updates this
			 table in response to registration events from
			 mobile nodes."
	::= { usrMipHaStats 18 }
	usrMipHaMobilityBindingEntry OBJECT-TYPE
		SYNTAX UsrMipHaMobilityBindingEntry
		MAX-ACCESS not-accessible
		STATUS current
		DESCRIPTION
			"An entry in the mobility binding list."
		INDEX { usrMipHaMobilityBindingIndex }
	::= { usrMipHaMobilityBindingTable 1 }
	UsrMipHaMobilityBindingEntry ::= SEQUENCE {
		usrMipHaMobilityBindingIndex         INTEGER,
		usrMipHaMobilityBindingMN            IpAddress,
		usrMipHaMobilityBindingCOA           IpAddress,
		usrMipHaMobilityBindingRegFlags      INTEGER,
		usrMipHaMobilityBindingRegIDLow      UsrSpecialU32,
		usrMipHaMobilityBindingRegIDHigh     UsrSpecialU32,
		usrMipHaMobilityBindingTimeGranted   Integer32,
		usrMipHaMobilityBindingTimeRemaining Gauge32,
		usrMipHaMobilityBindingMtu           Unsigned32,
		usrMipHaMobilityBindingNAI           DisplayString,
        usrMipHaMobilitySetupTime            Unsigned32,
        usrMipHaMobilityBindingNextHop       IpAddress
		}
	usrMipHaMobilityBindingIndex OBJECT-TYPE
		SYNTAX INTEGER (1..10000)
		MAX-ACCESS read-only
		STATUS current
		DESCRIPTION
			"Index of the entry in the Mobility Binding Table."
	::= { usrMipHaMobilityBindingEntry 1 }
	usrMipHaMobilityBindingMN OBJECT-TYPE
		SYNTAX IpAddress
		MAX-ACCESS read-only
		STATUS current
		DESCRIPTION
			"Mobile node's home (IP) address."
	::= { usrMipHaMobilityBindingEntry 2 }
	usrMipHaMobilityBindingCOA OBJECT-TYPE
		SYNTAX IpAddress
		MAX-ACCESS read-only
		STATUS current
		DESCRIPTION
			"Mobile node's care-of-address.  One mobile node
			 can have multiple bindings with different
			 care-of-addresses."
	::= { usrMipHaMobilityBindingEntry 3 }
	usrMipHaMobilityBindingRegFlags OBJECT-TYPE
		SYNTAX INTEGER (0..255)
		MAX-ACCESS read-only
		STATUS current
		DESCRIPTION
			"Registration flags sent by mobile node.
			 This is a bit-mapped value with the following
			 representation:
			   7   6   5   4   3   2   1   0
			 +---+---+---+---+---+---+---+---+
			 | S | B | D | M | G | V | T | R |
			 +---+---+---+---+---+---+---+---+
			 where,
			 S - Simultaneous Bindings
			 B - Broadcast Datagrams
			 D - Decapsulation by mobile node
			 M - Minimal Encapsulation
			 G - GRE Encapsulation
			 V - V.J. Compression
			 T - Reverse Tunneling
			 R - Reserved Bit"
	::= { usrMipHaMobilityBindingEntry 4 }
	usrMipHaMobilityBindingRegIDLow OBJECT-TYPE
		SYNTAX UsrSpecialU32
		MAX-ACCESS read-only
		STATUS current
		DESCRIPTION
			"Low 32 bits of Identification used in that
			 binding by the mobile node."
	::= { usrMipHaMobilityBindingEntry 5 }
	usrMipHaMobilityBindingRegIDHigh OBJECT-TYPE
		SYNTAX UsrSpecialU32
		MAX-ACCESS read-only
		STATUS current
		DESCRIPTION
			"High 32 bits of Identification used in that
			 binding by the mobile node."
	::= { usrMipHaMobilityBindingEntry 6 }
	usrMipHaMobilityBindingTimeGranted OBJECT-TYPE
		SYNTAX Integer32
		UNITS "seconds"
		MAX-ACCESS read-only
		STATUS current
		DESCRIPTION
			"The lifetime in seconds granted to the mobile
			 node for this registration."
	::= { usrMipHaMobilityBindingEntry 7 }
	usrMipHaMobilityBindingTimeRemaining OBJECT-TYPE
		SYNTAX Gauge32
		UNITS "seconds"
		MAX-ACCESS read-only
		STATUS current
		DESCRIPTION
			"The number of seconds remaining until the
			 registration is expired. It has the same initial
			 value as usrMipHaMobilityBindingTimeGranted,
			 and is counted down by the home agent."
	::= {usrMipHaMobilityBindingEntry 8 }
	usrMipHaMobilityBindingMtu OBJECT-TYPE
		SYNTAX Unsigned32
		MAX-ACCESS read-only
		STATUS current
		DESCRIPTION
			"The size of the MTU."
	::= {usrMipHaMobilityBindingEntry 9 }
	usrMipHaMobilityBindingNAI OBJECT-TYPE
		SYNTAX DisplayString
		MAX-ACCESS read-only
		STATUS current
		DESCRIPTION
			"User name ( NAI )."
	::= {usrMipHaMobilityBindingEntry 10 }
	usrMipHaMobilitySetupTime OBJECT-TYPE
		SYNTAX Unsigned32
		MAX-ACCESS read-only
		STATUS current
		DESCRIPTION
			"Actual time when the tunnel was setup on this HA. Time is in NTP 
            format."
	::= {usrMipHaMobilityBindingEntry 11 }
    usrMipHaMobilityBindingNextHop OBJECT-TYPE
		SYNTAX IpAddress
		MAX-ACCESS read-only
		STATUS current
		DESCRIPTION
			"Next hop gateway address returned by AAA, used for VLAN tagging
            feature."
	::= { usrMipHaMobilityBindingEntry 14 }
--	usrMipHaTunnelPacketOut OBJECT-TYPE
--		SYNTAX Unsigned32
--		MAX-ACCESS read-only
--		STATUS current
--		DESCRIPTION
--			"Number of packets sent on tunnel."
--	::= {usrMipHaMobilityBindingEntry 12 }
--	usrMipHaTunnelPacketIn OBJECT-TYPE
--		SYNTAX Unsigned32
--		MAX-ACCESS read-only
--		STATUS current
--		DESCRIPTION
--			"Number of packets received from the tunnel."
--	::= {usrMipHaMobilityBindingEntry 13 }
-- Home agent statistics counter
	usrMipHaTotalSessionReleased OBJECT-TYPE
		SYNTAX Counter32
		MAX-ACCESS read-only
   		STATUS current
		DESCRIPTION
			"Total number of Registration Requests denied by
			 the home agent - Unsupported Encapsulation (Code 139.)"
	::= { usrMipHaStats 19 }
	usrMipHaNewRegReqRcvd OBJECT-TYPE
		SYNTAX Counter32
		MAX-ACCESS read-only
   		STATUS current
		DESCRIPTION
			"Total number of new Registration Requests received by
			 the home agent."
	::= { usrMipHaStats 20 }
	usrMipHaNewRegReqAccepted OBJECT-TYPE
		SYNTAX Counter32
		MAX-ACCESS read-only
   		STATUS current
		DESCRIPTION
			"Total number of new Registration Requests accepted by
			 the home agent."
	::= { usrMipHaStats 21 }
	usrMipHaNewRegReqRejected OBJECT-TYPE
		SYNTAX Counter32
		MAX-ACCESS read-only
   		STATUS current
		DESCRIPTION
			"Total number of new Registration Requests rejected by
			 the home agent."
	::= { usrMipHaStats 22 }
	usrMipHaReRegReqRcvd OBJECT-TYPE
		SYNTAX Counter32
		MAX-ACCESS read-only
   		STATUS current
		DESCRIPTION
			"Total number of Re-Registration Requests received by
			 the home agent."
	::= { usrMipHaStats 23 }
	usrMipHaReRegReqAccepted OBJECT-TYPE
		SYNTAX Counter32
		MAX-ACCESS read-only
   		STATUS current
		DESCRIPTION
			"Total number of Re-Registration Requests accepted by
			 the home agent."
	::= { usrMipHaStats 24 }
	usrMipHaReRegReqRejected OBJECT-TYPE
		SYNTAX Counter32
		MAX-ACCESS read-only
   		STATUS current
		DESCRIPTION
			"Total number of Re-Registration Requests rejected by
			 the home agent."
	::= { usrMipHaStats 25 }
	usrMipHaDeRegReqRcvd OBJECT-TYPE
		SYNTAX Counter32
		MAX-ACCESS read-only
   		STATUS current
		DESCRIPTION
			"Total number of De-Registration Requests received by
			 the home agent."
	::= { usrMipHaStats 26 }
	usrMipHaDeRegReqAccepted OBJECT-TYPE
		SYNTAX Counter32
		MAX-ACCESS read-only
   		STATUS current
		DESCRIPTION
			"Total number of De-Registration Requests accepted by
			 the home agent."
	::= { usrMipHaStats 27 }
	usrMipHaDeRegReqRejected OBJECT-TYPE
		SYNTAX Counter32
		MAX-ACCESS read-only
   		STATUS current
		DESCRIPTION
			"Total number of De-Registration Requests rejected by
			 the home agent."
	::= { usrMipHaStats 28 }
	usrMipHaAdminProhibited OBJECT-TYPE
		SYNTAX Counter32
		MAX-ACCESS read-only
   		STATUS current
		DESCRIPTION
			"Total number of Registration Requests rejected by
			 the home agent with error code 129"
	::= { usrMipHaStats 29 }
	usrMipHaRegReqForwarded OBJECT-TYPE
		SYNTAX Counter32
		MAX-ACCESS read-only
   		STATUS current
		DESCRIPTION
			"Total number of Registration Requests forwarded by
			 the home agent."
	::= { usrMipHaStats 30 }
	usrMipHaForwardedRegReq OBJECT-TYPE
		SYNTAX Counter32
		MAX-ACCESS read-only
   		STATUS current
		DESCRIPTION
			"Total number of forwarded Registration Requests received by
			 the home agent."
	::= { usrMipHaStats 31 }
   	usrMipHaDuplicateIPDiscs OBJECT-TYPE
		SYNTAX Counter32
		MAX-ACCESS read-only
		STATUS current
		DESCRIPTION
			"Total number of disconnects due to duplicate IP address.
             This can happen when an MBR already exists with the
             same address as as assigned to MN."
	::= { usrMipHaStats 32 }
  	usrMipHaDuplicateNaiDiscs OBJECT-TYPE
		SYNTAX Counter32
		MAX-ACCESS read-only
		STATUS current
		DESCRIPTION
			"Total number of disconnects due to duplicate NAI.
             This can happen when Multiple Logins is disabled and
             an MBR already exists with the same NAI."
	::= { usrMipHaStats 39 }
  	usrMipHaClearMBRDiscs OBJECT-TYPE
		SYNTAX Counter32
		MAX-ACCESS read-only
		STATUS current
		DESCRIPTION
			"Total number of disconnects due to Clear MBR message 
             received from HACN. This can happen in two scenarios, 
             first when HACN detects Duplicate MN IP, it sends Clear
             MBR message to first HA. Second when Multiple Logins is
             disabled and HACN detects Duplicate NAI. It will send 
             Clear MBR to first HA."
	::= { usrMipHaStats 40 }
-- Home Agent MIP CFM Configuration Group
	usrMipHaConfigFileName OBJECT-TYPE
		SYNTAX DisplayString (SIZE(0..64))
		MAX-ACCESS read-write
		STATUS current
		DESCRIPTION
			"The name of the configuration file for HA MIP.  If
			 this value is empty, then the default file name
			 is @file://MipHandler.cfg."
	::= { usrMipHaCfmConfig 1 }
	usrMipHaCfmStatus OBJECT-TYPE
		SYNTAX UsrConfigStatus
		MAX-ACCESS read-write
		STATUS current
		DESCRIPTION
			"The Configuration File Manager Flag for
			 saving Home Agent MIP configurable parameters."
	::= { usrMipHaCfmConfig 2 }
-- Home Agent MIP Interface Events Settings Group
	usrMipHaUpperThreshold OBJECT-TYPE
		SYNTAX INTEGER (1..100)
		MAX-ACCESS read-write
		STATUS current
		DESCRIPTION
       			"Specifies the upper Water Mark for Active Session
                         Threshold. If the active call capacity exceeds this
                         limit, then a trap is sent."
		--CONFIGURABLE
	::= { usrMipHaTrapsSettings 1 }
	usrMipHaLowerThreshold OBJECT-TYPE
		SYNTAX INTEGER (1..100)
		MAX-ACCESS read-write
		STATUS current
		DESCRIPTION
       			"Specifies the lower Water Mark for Active Session
                         Threshold. If the active call capacity touches 
                         this lower threshold after touching the Upper
                         threshold, then only a trap will be sent whenever
                         next time it exceeds the Upper Threshold."
		--CONFIGURABLE
	::= { usrMipHaTrapsSettings 2 }
	usrMipHaTrapThreshold OBJECT-TYPE
   		SYNTAX INTEGER {
                    enabled(1),
                    disabled(2)
                    }
   		MAX-ACCESS  read-write
   		STATUS  current
   		DESCRIPTION
	        "Threshold Trap Enabled or Disabled."
        --CONFIGURABLE
	::= { usrMipHaTrapsSettings 3 }
	usrMipHaTrapIdleTimer OBJECT-TYPE
   		SYNTAX INTEGER {
                    enabled(1),
                    disabled(2)
                    }
   		MAX-ACCESS  read-write
   		STATUS  current
   		DESCRIPTION
	        "Idle Timer Trap Enabled or Disabled."
        --CONFIGURABLE
	::= { usrMipHaTrapsSettings 4 }
-- Home Agent MIP Interface Events Group
    usrMipHaTrapsV2 OBJECT-IDENTITY
        STATUS  current
        DESCRIPTION "The Traps for MIP"
        ::= {usrMipHaTraps 0}
	usrMipHaActiveSessionThresholdReached NOTIFICATION-TYPE
		OBJECTS {    
                    usrMipHaUpperThreshold,
                    usrMipHaLowerThreshold,
	                usrMipHaCurrentSessions
		}
        STATUS  current
		DESCRIPTION
			"This trap is generated when Active Session Threshold 
             is reached based on the calculation -
             (ActiveSessions * 100) / MaxTunnels being greater
             than the UpperThreshold."
	    --#TYPE	"Interface Capacity Alarm"
	    --#SUMMARY	"Total Sessions %d reached upper threshold of %d"
	    --#ARGUMENTS { 2 0 }
	    --#SEVERITY MAJOR
	    --#STATE	OPERATIONAL
	    --#PROBABLECAUSE "resourceAtOrNearingCapacity"
        ::= {usrMipHaTrapsV2 1}
	usrMipHaIdleTimerExpired NOTIFICATION-TYPE
		OBJECTS {    
		        usrMipHaMobilityBindingMN
		}
        STATUS  current
		DESCRIPTION
			"This trap is generated when the Idle Timer has expired
             and the tunnel has been disconnected. The trap contains
             the MobileNode's home IP address."
	    --#TYPE	"Timeout"
	    --#SUMMARY	"Tunnel disconnected for MN %d"
	    --#ARGUMENTS { 0 }
	    --#SEVERITY MINOR
	    --#STATE	OPERATIONAL
	    --#PROBABLECAUSE "communicationsProblem"
        ::= {usrMipHaTrapsV2 2}
-- Home Agent status
	usrMipHaStatusHacnInterfaceStatus OBJECT-TYPE
		SYNTAX DisplayString
		MAX-ACCESS read-only
		STATUS current
   		DESCRIPTION
       		"HACN Interface status"
	::= { usrMipHaStatus 1 }
	usrMipHaStatusHaRole OBJECT-TYPE
		SYNTAX DisplayString
		MAX-ACCESS read-only
		STATUS current
   		DESCRIPTION
       		"HA Role. This makes sense only if HACN interface is enabled. If
            HACN interface is not enabled, then HA role will be unassigned."
	::= { usrMipHaStatus 2 }
	usrMipHaStatus2EthPortStatus OBJECT-TYPE
		SYNTAX DisplayString
		MAX-ACCESS read-only
		STATUS current
   		DESCRIPTION
       		"Status of second ethernet port. If both port are in use and
            second ethernet port goes down then HA stops accepting reg req."
	::= { usrMipHaStatus 3 }
	usrMipHaStatusHaRunIp OBJECT-TYPE
		SYNTAX IpAddress
		MAX-ACCESS read-only
		STATUS deprecated
		DESCRIPTION
			"Home Agent RUN IP Address.
			DEPRECATED:
			This object has been replaced by usrMipHacnSettingsHaRunIp"
	::= { usrMipHaStatus 4 }
	usrMipHaStatusHacnResponding OBJECT-TYPE
		SYNTAX DisplayString
		MAX-ACCESS read-only
		STATUS current
   		DESCRIPTION
       		"This indicates whether HACN is responding to heartbeats or not."
	::= { usrMipHaStatus 5 }
	usrMipHaRunIPNetworkStatus OBJECT-TYPE
   		SYNTAX INTEGER {
                    enabled(1),
                    disabled(2)
                    }
   		MAX-ACCESS  read-write
   		STATUS  current
   		DESCRIPTION
            "HA RunIP Network added on HA Enabled or Disabled.
             If the HA role is not active then no action, enabled
             or disabled, is allowed; an error will be returned.
             An error will also be returned if an attempt is made
             to enable/disable and active calls exist."
        --CONFIGURABLE
	::= { usrMipHaStatus 6 }
-- Home Agent Control Node settings
	usrMipHacnSettingsHaRunIp OBJECT-TYPE
		SYNTAX IpAddress
		MAX-ACCESS read-only
		STATUS current
		DESCRIPTION
			"Home Agent RUN IP Address."
	::= { usrMipHacnSettings 1 }
	usrMipHacnSettingsHeartbeatPeriod OBJECT-TYPE
		SYNTAX Unsigned32
		MAX-ACCESS read-only
		STATUS current
		DESCRIPTION
			"Heartbeat period set by HACN. This value is set in HACN and is
            sent to HA during Role Assignment and in each Heartbeat ACK. This
            is the time period after which HA is supposed to send a heartbeat
            message to HACN."
	::= { usrMipHacnSettings 2 }
	usrMipHacnSettingsPacketRetryPeriod OBJECT-TYPE
		SYNTAX Unsigned32
		MAX-ACCESS read-only
		STATUS current
		DESCRIPTION
			"Packet Retry period set by HACN. This value is set in HACN and is
            sent to HA during Role Assignment and in each Heartbeat ACK. This
            is the time period after which HA is supposed to retry a message
            in case HA does not gets a ack for the previous message."
	::= { usrMipHacnSettings 3 }
	usrMipHacnSettingsPacketRetryCount OBJECT-TYPE
		SYNTAX Unsigned32
		MAX-ACCESS read-only
		STATUS current
		DESCRIPTION
			"Packet Retry count set by HACN. This value is set in HACN and is
            sent to HA during Role Assignment and in each Heartbeat ACK. This
            is the number of times a retry message will be sent to HACN."
	::= { usrMipHacnSettings 4 }
-- Home Agent Control Node statistics
	usrMipHacnStatsHeartbeatSent OBJECT-TYPE
		SYNTAX Unsigned32
		MAX-ACCESS read-only
		STATUS current
		DESCRIPTION
			"Total Number of heartbeats sent to HACN."
	::= { usrMipHacnStats 1 }
	usrMipHacnStatsHeartbeatAckRcvd OBJECT-TYPE
		SYNTAX Unsigned32
		MAX-ACCESS read-only
		STATUS current
		DESCRIPTION
			"Total Number of heartbeat ack received from HACN."
	::= { usrMipHacnStats 2 }
	usrMipHacnStatsHeartbeatRetried OBJECT-TYPE
		SYNTAX Unsigned32
		MAX-ACCESS read-only
		STATUS current
		DESCRIPTION
			"Total Number of heartbeats retried."
	::= { usrMipHacnStats 3 }
    usrMipHacnStatsResetTime OBJECT-TYPE
        SYNTAX	Unsigned32 
		MAX-ACCESS  read-write
		STATUS  current
		DESCRIPTION
                "Reading:
				Time the HACN statistics counters were last 
			 	reset. The HACN statistics are valid from 
				usrMipHacnStatsResetTime until present.
	        		Resetting counters causes a discontinuity in 
				the monotonically increasing value of counters.
				Management stations that sample these counters
				need also to sample this object so that they 
				can know that a discontinuity occurred with 
				respect to the previous sample.  
                Its value is in NTP format.
		        Writing:
		   	    Writing 0 causes update of usrMipHacnStatsResetTime
				and the HACN counters to be reset to 0."
	::= { usrMipHacnStats 4 }
-- Mobile Node Information
        usrMobileInfoTable OBJECT-TYPE
		SYNTAX SEQUENCE OF UsrMobileInfoEntry
		MAX-ACCESS not-accessible
		STATUS current
		DESCRIPTION
                        "A table containing Mobile Node Information."
	::= {usrMipHaMobileInfo 1 }
	usrMobileInfoEntry OBJECT-TYPE
		SYNTAX UsrMobileInfoEntry
		MAX-ACCESS not-accessible
		STATUS current
		DESCRIPTION
			"An entry in the Mobile Node Information list."
		INDEX { usrMipHaMobilityBindingIndex }
	::= { usrMobileInfoTable 1 }
        UsrMobileInfoEntry ::= SEQUENCE {
                usrMipHaMobilePacketOut    Unsigned32,
                usrMipHaMobilePacketIn     Unsigned32,
                usrMipHaMobileByteOut      Unsigned32,
                usrMipHaMobileByteIn       Unsigned32
        }
	usrMipHaMobilePacketOut OBJECT-TYPE
		SYNTAX Unsigned32
		MAX-ACCESS read-only
		STATUS current
		DESCRIPTION
			"Number of packets sent out on the tunnel."
	::= {usrMobileInfoEntry 1 }
	usrMipHaMobilePacketIn OBJECT-TYPE
		SYNTAX Unsigned32
		MAX-ACCESS read-only
		STATUS current
		DESCRIPTION
			"Number of packets received from the tunnel."
	::= {usrMobileInfoEntry 2 }
	usrMipHaMobileByteOut OBJECT-TYPE
		SYNTAX Unsigned32
		MAX-ACCESS read-only
		STATUS current
		DESCRIPTION
			"Number of data bytes sent out on the tunnel."
	::= {usrMobileInfoEntry 3 }
	usrMipHaMobileByteIn OBJECT-TYPE
		SYNTAX Unsigned32
		MAX-ACCESS read-only
		STATUS current
		DESCRIPTION
			"Number of data bytes received from the tunnel."
	::= {usrMobileInfoEntry 4 }
END	-- USR-MIP-MIB Definitions
