-- *****************************************************************************
-- Unisphere-Data-HOST-MIB
--
-- Unisphere Networks Inc. Enterprise MIB
-- HOST MIB
--
-- Copyright (c) 2000, 2001 Unisphere Networks Inc.  All Rights Reserved.
-- *****************************************************************************

Unisphere-Data-HOST-MIB DEFINITIONS ::= BEGIN

IMPORTS
    MODULE-IDENTITY, 
    OBJECT-TYPE,
    IpAddress
        FROM SNMPv2-SMI

    DisplayString,
    RowStatus
        FROM SNMPv2-TC

    MODULE-COMPLIANCE, 
    OBJECT-GROUP  
        FROM SNMPv2-CONF

    usDataMibs
        FROM Unisphere-Data-MIBs;

usdHostMIB MODULE-IDENTITY
    LAST-UPDATED "200105071702Z"  -- 07-May-01 01:02 PM EDT
    ORGANIZATION "Unisphere Networks, Inc."
    CONTACT-INFO
        "       Unisphere Networks, Inc.
        Postal: 10 Technology Park Road
                Westford, MA 01886
                USA
        Tel:    +1 978 589 5800
        E-mail: mib@UnisphereNetworks.com"
    DESCRIPTION
        "The host configuration MIB for Unisphere Networks Inc.
        enterprise."
    -- Revision History
    REVISION    "200105071702Z"  -- 07-May-01 01:02 PM EDT  - RX 3.0
    DESCRIPTION
        "Increase the max lenght of the host name."
    REVISION    "200001260000Z"  -- 26-Jan-00               - RX 1.3
    DESCRIPTION
        "Initial version of this MIB module."
    ::= { usDataMibs 33 }


-- ++++++++++++++++++++++++++++++++++++++++++++++++++++++++++++++++++++++
-- Textual conventions
-- ++++++++++++++++++++++++++++++++++++++++++++++++++++++++++++++++++++++

-- No textual conventions are currently defined.


-- ++++++++++++++++++++++++++++++++++++++++++++++++++++++++++++++++++++++
-- Managed object groups
-- ++++++++++++++++++++++++++++++++++++++++++++++++++++++++++++++++++++++

usdHostObjects              OBJECT IDENTIFIER ::= {usdHostMIB 1}

usdHost                     OBJECT IDENTIFIER ::= {usdHostObjects 1 }

-- ++++++++++++++++++++++++++++++++++++++++++++++++++++++++++++++++++++++
-- Managed objects for Host 
-- ++++++++++++++++++++++++++++++++++++++++++++++++++++++++++++++++++++++

usdHostTable OBJECT-TYPE
    SYNTAX      SEQUENCE OF UsdHostEntry
    MAX-ACCESS  not-accessible
    STATUS      current
    DESCRIPTION
        "The entries in this table describe host configuration information." 
    ::= { usdHost 1 }

usdHostEntry OBJECT-TYPE
    SYNTAX      UsdHostEntry
    MAX-ACCESS  not-accessible
    STATUS      current
    DESCRIPTION
        "An entry describing the configuration of a host."
    INDEX { IMPLIED usdHostName }
    ::= { usdHostTable 1 }

UsdHostEntry ::= SEQUENCE {
    usdHostName                      DisplayString,
    usdHostIpAddress                 IpAddress,
    usdHostProtocol                  INTEGER,
    usdHostUserName                  DisplayString,
    usdHostUserPassword              DisplayString,
    usdHostRowStatus                 RowStatus
}

usdHostName OBJECT-TYPE
    SYNTAX      DisplayString (SIZE (1..40))
    MAX-ACCESS  read-only
    STATUS      current
    DESCRIPTION
        "The hostname identifier associated with this host entry."
    ::= { usdHostEntry 1 }

usdHostIpAddress OBJECT-TYPE
    SYNTAX      IpAddress 
    MAX-ACCESS  read-create 
    STATUS      current
    DESCRIPTION
        "The IP address associated with this host entry."
    ::= { usdHostEntry 2 }

usdHostProtocol OBJECT-TYPE
    SYNTAX      INTEGER { usdHostFtp(1) }
    MAX-ACCESS  read-create 
    STATUS      current
    DESCRIPTION
        "The file transfer protocol associated with this host entry."
    ::= { usdHostEntry 3 }

usdHostUserName OBJECT-TYPE
    SYNTAX      DisplayString (SIZE (0..20))
    MAX-ACCESS  read-create 
    STATUS      current
    DESCRIPTION
        "The username associated with this host entry."
    ::= { usdHostEntry 4 }

usdHostUserPassword OBJECT-TYPE
    SYNTAX      DisplayString (SIZE (0..25))
    MAX-ACCESS  read-create 
    STATUS      current
    DESCRIPTION
        "The password associated with this host entry.  Reading this object
        returns a null DisplayString to avoid security breaches.  However, a
        null string is not accepted for create or write operations."
    ::= { usdHostEntry 5 }

usdHostRowStatus OBJECT-TYPE
    SYNTAX      RowStatus
    MAX-ACCESS  read-create
    STATUS      current
    DESCRIPTION
        "Controls creation/deletion of entries in this table.
        Only the values 'createAndGo' and 'destroy' may be SET."
    ::= { usdHostEntry 6 }


-- ++++++++++++++++++++++++++++++++++++++++++++++++++++++++++++++++++++++
-- Notification control objects
-- ++++++++++++++++++++++++++++++++++++++++++++++++++++++++++++++++++++++

-- No notifications are defined in this MIB. Placeholder follows.

-- usdHostTrapControl      OBJECT IDENTIFIER ::= { usdHostMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdHostTraps            OBJECT IDENTIFIER ::= { usdHostMIB 3 }
-- usdHostTrapPrefix       OBJECT IDENTIFIER ::= { usdHostTraps 0 }

-- ++++++++++++++++++++++++++++++++++++++++++++++++++++++++++++++++++++++
-- Conformance information
-- ++++++++++++++++++++++++++++++++++++++++++++++++++++++++++++++++++++++

usdHostMIBConformance OBJECT IDENTIFIER ::= { usdHostMIB 4 }

usdHostMIBCompliances OBJECT IDENTIFIER ::= { usdHostMIBConformance 1 }

usdHostMIBGroups OBJECT IDENTIFIER ::= { usdHostMIBConformance 2 }


-- compliance statements

usdHostCompliance MODULE-COMPLIANCE
    STATUS      current
    DESCRIPTION
        "The compliance statement for systems supporting host configuration."
    MODULE  -- this module
    MANDATORY-GROUPS { usdHostGroup }
    ::= { usdHostMIBCompliances 1 }                                    -- RX 1.3


-- units of conformance

usdHostGroup OBJECT-GROUP
    OBJECTS {
             usdHostName,
             usdHostIpAddress,
             usdHostProtocol,
             usdHostUserName,
             usdHostUserPassword,
             usdHostRowStatus
    }
    STATUS      current
    DESCRIPTION
        "The basic collection of objects providing management of host
        configuration functionality in a Unisphere product."
    ::= { usdHostMIBGroups 1 }

END
