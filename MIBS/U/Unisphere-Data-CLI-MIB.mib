-- *****************************************************************
-- Unisphere-Data-CLI-MIB
--
-- Unisphere Networks Inc. Enterprise MIB
-- Command Line Interface (CLI) security MIB
--
-- Copyright (c) 1998, 1999 Redstone Communications, Incorporated.
-- Copyright (c) 1999, 2002 Unisphere Networks, Incorporated.
-- All Rights Reserved.
-- *****************************************************************

Unisphere-Data-CLI-MIB DEFINITIONS ::= BEGIN

IMPORTS
    MODULE-IDENTITY,
    OBJECT-TYPE,
    NOTIFICATION-TYPE
        FROM SNMPv2-SMI

    DisplayString,
    DateAndTime,
    TruthValue
        FROM SNMPv2-TC

    MODULE-COMPLIANCE,
    OBJECT-GROUP,
    NOTIFICATION-GROUP
        FROM SNMPv2-CONF

    usDataMibs
        FROM Unisphere-Data-MIBs

    UsdLogSeverity
        FROM Unisphere-Data-TC;


usdCliMIB  MODULE-IDENTITY
    LAST-UPDATED "200009261350Z" -- 26-Sep-00 9:50 AM EDT
    ORGANIZATION "Unisphere Networks, Inc."
    CONTACT-INFO
        "       Unisphere Networks, Inc.
        Postal: 10 Technology Park Drive
                Westford MA  01886
                USA
        Tel:    +1 978 589 5800
        Email:  mib@UnisphereNetworks.com"
    DESCRIPTION
        "The Command Line Interface (CLI) security MIB for the
        Unisphere Networks Inc. enterprise."
    -- Revision History
    REVISION      "200009261350Z" -- 26-Sep-00 9:50 AM EDT  kwc
    DESCRIPTION
        "Make it SMIv2 conformant."
    REVISION      "9912010000Z" -- 01-Dec-99
    DESCRIPTION
        "Initial version of this MIB module."
    ::= { usDataMibs 30 }

-- ++++++++++++++++++++++++++++++++++++++++++++++++++++++++++++++++++++++
-- Textual conventions
-- ++++++++++++++++++++++++++++++++++++++++++++++++++++++++++++++++++++++


-- ++++++++++++++++++++++++++++++++++++++++++++++++++++++++++++++++++++++
-- MIB Structure
-- ++++++++++++++++++++++++++++++++++++++++++++++++++++++++++++++++++++++

usdCliTrap          OBJECT IDENTIFIER ::= { usdCliMIB 0 }
usdCliObjects       OBJECT IDENTIFIER ::= { usdCliMIB 1 }
usdCliConformance   OBJECT IDENTIFIER ::= { usdCliMIB 2 }

-- ++++++++++++++++++++++++++++++++++++++++++++++++++++++++++++++++++++++
-- Managed objects
-- ++++++++++++++++++++++++++++++++++++++++++++++++++++++++++++++++++++++

--
-- Object Groups
--
usdCliGeneral       OBJECT IDENTIFIER ::= { usdCliObjects 1 }
usdCliSecurity      OBJECT IDENTIFIER ::= { usdCliObjects 2 }

usdCliSecurityTrapEnable OBJECT-TYPE
    SYNTAX      TruthValue
    MAX-ACCESS  read-write
    STATUS      current
    DESCRIPTION
        "An indication of whether the usdCliSecurityAlert notifications are
        enabled."
    ::= { usdCliGeneral 1 }


-- ++++++++++++++++++++++++++++++++++++++++++++++++++++++++++++++++++++++
-- Traps & Trap Control
-- ++++++++++++++++++++++++++++++++++++++++++++++++++++++++++++++++++++++

usdCliSecurityAlertPriority OBJECT-TYPE
    SYNTAX      UsdLogSeverity 
    MAX-ACCESS  accessible-for-notify
    STATUS      current
    DESCRIPTION
        "The priority level of the cli security alert" 
    ::= { usdCliSecurity 1 }

usdCliSecurityAlertMessage OBJECT-TYPE
    SYNTAX      DisplayString 
    MAX-ACCESS  accessible-for-notify
    STATUS      current
    DESCRIPTION
        "The cli security alert message." 
    ::= { usdCliSecurity 2 }

usdCliSecurityAlertTime OBJECT-TYPE
    SYNTAX      DateAndTime
    MAX-ACCESS  accessible-for-notify
    STATUS      current
    DESCRIPTION
        "The date and time of this cliSecurityAlert."
    ::= { usdCliSecurity 3 }
   

usdCliSecurityAlert NOTIFICATION-TYPE
    OBJECTS {
        usdCliSecurityAlertPriority,
        usdCliSecurityAlertMessage,
        usdCliSecurityAlertTime }
    STATUS      current
    DESCRIPTION
        "Reports a cli security alert.  Events such as the following generate
        this notification when it is enabled:
            - Logins/logouts from telnet or console access
            - Logins/logout from SSH
            - Access from unknown IP addreses
            - Access list accept or failures
            - Successful and unsuccessful authentications"
    ::= { usdCliTrap 1 }


-- ++++++++++++++++++++++++++++++++++++++++++++++++++++++++++++++++++++++
-- Conformance information
-- ++++++++++++++++++++++++++++++++++++++++++++++++++++++++++++++++++++++

usdCliCompliances OBJECT IDENTIFIER ::= { usdCliConformance 1 }
usdCliGroups      OBJECT IDENTIFIER ::= { usdCliConformance 2 }

-- compliance statements

usdCliCompliance MODULE-COMPLIANCE
    STATUS  current
    DESCRIPTION
        "The compliance statement for entities that implement the Unisphere CLI
        MIB."
    MODULE  -- this module
        MANDATORY-GROUPS {
            usdCliGroup,
            usdCliSecurityAlertGroup,
            usdCliSecurityTrapGroup }
    ::= { usdCliCompliances 1 }

-- units of conformance

usdCliGroup OBJECT-GROUP
    OBJECTS { usdCliSecurityTrapEnable }
    STATUS  current
    DESCRIPTION
        "A management object pertaining to CLI security configuration."
    ::= { usdCliGroups 1 }

usdCliSecurityAlertGroup OBJECT-GROUP
    OBJECTS {
        usdCliSecurityAlertPriority,
        usdCliSecurityAlertMessage,
        usdCliSecurityAlertTime }
    STATUS  current
    DESCRIPTION
        "A collection of management objects pertaining to CLI security alert
        notification."
    ::= { usdCliGroups 2 }

usdCliSecurityTrapGroup NOTIFICATION-GROUP
    NOTIFICATIONS { usdCliSecurityAlert }
    STATUS  current
    DESCRIPTION
        "A management notification pertaining to CLI security operations."
    ::= { usdCliGroups 3 }

END
