-- *****************************************************************************
-- Unisphere-Data-ACCOUNTING-MIB
--
-- Unisphere Networks Inc. Enterprise MIB
-- Accounting MIB
--
-- Copyright (c) 1999 Redstone Communications, Incorporated.
-- Copyright (c) 1999, 2002 Unisphere Networks, Incorporated.
-- All Rights Reserved.
-- *****************************************************************************

Unisphere-Data-ACCOUNTING-MIB DEFINITIONS ::= BEGIN

IMPORTS
    Integer32, MODULE-IDENTITY, OBJECT-TYPE, OBJECT-IDENTITY
        FROM SNMPv2-SMI
    MODULE-COMPLIANCE, OBJECT-GROUP
        FROM SNMPv2-CONF
    RowStatus,
    DisplayString
        FROM SNMPv2-TC
    InterfaceIndex
        FROM IF-MIB
    acctngSelectionEntry, acctngSelectionIndex, acctngFileEntry
        FROM ACCOUNTING-CONTROL-MIB
    usDataMibs
        FROM Unisphere-Data-MIBs
    usdIfType
        FROM Unisphere-Data-IF-MIB
    UsdAcctngOperType, UsdAcctngAdminType
        FROM Unisphere-Data-TC
    UsdPolicyAttachmentType
        FROM Unisphere-Data-POLICY-MIB;

usdAcctngMIB  MODULE-IDENTITY
    LAST-UPDATED "200112051416Z"  -- 05-Dec-01 09:16 AM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The accounting MIB for the Unisphere Networks enterprise.  This
        MIB augments the Connection Oriented Accounting MIB (ACCOUNTING-CONTROL-
        MIB) specified in RFC2513."
    -- Revision History
    REVISION    "200112051416Z"  -- 05-Dec-01 09:16 AM EST  - RX 4.0
    DESCRIPTION
        "Key revisions include:
            o  Added usdAcctngSelectionPolicyName and usdAcctngSelectionPolicyType
               objects to usdAcctngSelectionTable
            o  Added usdAcctngSelectionSchemaPolicy and associated policy
               statistic OIDs"
    REVISION    "200111191900Z"  -- 19-Nov-01 02:00 PM EST  - RX 3.3
    DESCRIPTION
        "Key revisions include:
            o  Added usdAcctngifInMulticastPkts
            o  Added usdAcctngifInBroadcastPkts
            o  Added usdAcctngifOutMulticastPkts
            o  Added usdAcctngifOutBroadcastPkts"
    REVISION    "200103261322Z"  -- 26-Mar-01 08:22 AM EST  - RX 3.2
    DESCRIPTION
        "Key revisions include:
            o  Added usdAcctngSelectionSchemaSystem
            o  Deprecated usdAcctngSelectionSubtreeType"
    REVISION    "200011071900Z"  -- 07-Nov-00 03:00 PM EDT  - RX 2.6
    DESCRIPTION
        "Key revisions include:
            o  Added usdAcctngIfTimeOffset"
    REVISION    "200007210000Z"  -- 21-Jul-00               - RX 2.2
    DESCRIPTION
        "Key revisions include:
            o  Added usdAcctngIfCorrelator
            o  Added usdAcctngIfInPolicedOctets
            o  Added usdAcctngIfInPolicedPkts
            o  Added usdAcctngIfInSpoofedPkts
            o  Added usdAcctngIfOutPolicedOctets
            o  Added usdAcctngIfOutPolicedPkts
            o  Added usdAcctngIfOutSchedulerDropOctets
            o  Added usdAcctngIfOutSchedulerDropPkts
            o  Added usdAcctngIfLowerInterface"
    REVISION    "200003200000Z"  -- 20-Mar-00              - RX 2.0
    DESCRIPTION
        "Key revisions include:
            o  Moved usdAcctngSelectionMaxIfStackLevels
            o  Added usdAcctngSelectionSubtreeType
            o  Added usdAcctngIfCorrelator
            o  Removed usdAcctngSelectionSchemaPpp"
    REVISION    "200001170000Z"  -- 17-Jan-00              - RX 1.3
    DESCRIPTION
        "Key revisions include:
            o  Added usdAcctngSelectionMaxIfStackLevels
            o  Added usdAcctngSelectionIfStackStartTable
            o  Added usdAcctngSelectionSchemaIfStack"
    REVISION      "9910180000Z"  -- 18-Oct-99              - RX 1.1
    DESCRIPTION
        "Initial version of this MIB module."
    ::= { usDataMibs 24 }

-- +++++++++++++++++++++++++++++++++++++++++++++++++++++++++++++++++++++++++++++
-- Textual conventions
-- +++++++++++++++++++++++++++++++++++++++++++++++++++++++++++++++++++++++++++++

-- +++++++++++++++++++++++++++++++++++++++++++++++++++++++++++++++++++++++++++++
-- MIB Structure
-- +++++++++++++++++++++++++++++++++++++++++++++++++++++++++++++++++++++++++++++

usdAcctngMIBObjects       OBJECT IDENTIFIER ::= { usdAcctngMIB 1 }

usdAcctngSelectionControl OBJECT IDENTIFIER ::= { usdAcctngMIBObjects 1 }
usdAcctngFileControl      OBJECT IDENTIFIER ::= { usdAcctngMIBObjects 2 }
usdAcctngInterfaceControl OBJECT IDENTIFIER ::= { usdAcctngMIBObjects 3 }

-- +++++++++++++++++++++++++++++++++++++++++++++++++++++++++++++++++++++++++++++
-- MIB Objects
-- +++++++++++++++++++++++++++++++++++++++++++++++++++++++++++++++++++++++++++++

-- The Accounting Information Selection table

usdAcctngSelectionTable OBJECT-TYPE
    SYNTAX      SEQUENCE OF UsdAcctngSelectionEntry
    MAX-ACCESS  not-accessible
    STATUS      current
    DESCRIPTION
        "A list of accounting information selection entries.

        Note that additions, modifications and deletions of entries in this
        table can occur at any time, but such changes only take effect on the
        next occasion when collection begins into a new interval.  Thus, between
        modification and the next 'swap', the content of this table does not
        reflect the current selection."
    ::= { usdAcctngSelectionControl 1 }

usdAcctngSelectionEntry OBJECT-TYPE
    SYNTAX      UsdAcctngSelectionEntry
    MAX-ACCESS  not-accessible
    STATUS      current
    DESCRIPTION
        "An entry used to extend the the selection entry in
        acctngSelectionEntry.  This conceptual row extension is used for
        Unisphere accounting extensions for connectionless data collection."
    AUGMENTS  { acctngSelectionEntry }
    ::= { usdAcctngSelectionTable 1 }

UsdAcctngSelectionEntry ::= SEQUENCE {
    usdAcctngSelectionType               BITS,
    usdAcctngSelectionMode               INTEGER,
    usdAcctngSelectionSubtreeType        INTEGER,
    usdAcctngSelectionMaxIfStackLevels   Integer32,
    usdAcctngSelectionPolicyName         DisplayString,
    usdAcctngSelectionPolicyType         UsdPolicyAttachmentType
}

usdAcctngSelectionType OBJECT-TYPE
    SYNTAX      BITS {
                    ietfAccountControl(0),
                    connectionLessLayer2(1) }
    MAX-ACCESS  read-write
    STATUS      current
    DESCRIPTION
        "Indicates the types of connections for which the information selected
        by this entry are to be collected.  The ietfAccountControl(0) bit
        position indicates that the ACCOUNTING-CONTROL-MIB.acctngSelectionType
        in the base conceptual row determines the selection type.  All other bit
        positions for this object over-ride the acctngSelectionType in the base
        conceptual row.  When the value of this object over-rides the
        acctngSelectionType object, the following objects have no meaning:

            ACCOUNTING-CONTROL-MIB.acctngFileCollectFailedAttempts
            ACCOUNTING-CONTROL-MIB.acctngFileMinAge

        because they control or are related to connection oriented accounting."
    ::= { usdAcctngSelectionEntry 1 }

usdAcctngSelectionMode OBJECT-TYPE
    SYNTAX      INTEGER {
                    absoluteCounterValues(1),
                    deltaCounterValues(2) }
    MAX-ACCESS  read-write
    STATUS      current
    DESCRIPTION
        "Indicates the data collection mode."
    DEFVAL    { deltaCounterValues }
    ::= { usdAcctngSelectionEntry 2 }

usdAcctngSelectionSubtreeType OBJECT-TYPE
    SYNTAX      INTEGER {
                    unknown(0),
                    lineCard(1),
                    systemController(2) }
    MAX-ACCESS  read-only
    STATUS      deprecated
    DESCRIPTION
        "Indicates the origin of the collection, given the row's subtree.  The
        architecture implementation for statistics collection imposes that rows
        with distinct usdAcctngSelectionSubtreeType may not be collected into the
        same accounting file. Conversely, different files (configured from
        acctngSelectionFile) entries are necessary in order to collect from
        subtrees (configured from acctngSelectionSubtree) that imply into
        different subtree types (usdAcctngSelectionSubtreeType)."
    ::= { usdAcctngSelectionEntry 3 }

usdAcctngSelectionMaxIfStackLevels OBJECT-TYPE
    SYNTAX      Integer32
    MAX-ACCESS  read-write
    STATUS      current
    DESCRIPTION
        "Indicates the maximum number of levels in the ifStack table to be
        returned when using the ifStack accounting schema.  This object is
        ignored if acctngSelectionSubtree is not set to
        usdAcctngSelectionSchemaIfStack.  When this object is zero, the entire
        stack above the starting point(s) given will be returned.  When this
        object is set to 1, only ifIndexes stacked above the starting point(s)
        given will be returned."
    DEFVAL    { 0 }
    ::= { usdAcctngSelectionEntry 4 }

usdAcctngSelectionPolicyName OBJECT-TYPE
    SYNTAX      DisplayString(SIZE(0..40))
    MAX-ACCESS  read-write
    STATUS      current
    DESCRIPTION
        "Specifies the name of the policy associated with the statistics
        collected when using the policy accounting schema.  This object is
        ignored if acctngSelectionSubtree is not set to
        usdAcctngSelectionSchemaPolicy."
    DEFVAL { "" }
    ::= { usdAcctngSelectionEntry 5 }

usdAcctngSelectionPolicyType OBJECT-TYPE
    SYNTAX      UsdPolicyAttachmentType
    MAX-ACCESS  read-write
    STATUS      current
    DESCRIPTION
        "Specifies the attachment point for the policy associated with the
        statistics collected when using the policy accounting schema.  This
        object is ignored if acctngSelectionSubtree is not set to
        usdAcctngSelectionSchemaPolicy."
    ::= { usdAcctngSelectionEntry 6 }

-- The Accounting Information ifStack Selection

usdAcctngSelectionIfStackStartTable OBJECT-TYPE
    SYNTAX      SEQUENCE OF UsdAcctngSelectionIfStackStartEntry
    MAX-ACCESS  not-accessible
    STATUS      current
    DESCRIPTION
        "A list of ifIndexes to be used as starting point when using the ifStack
        selection schema.

        Note that additions, modifications and deletions of entries in this
        table can occur at any time, but such changes only take effect on the
        next occasion when collection begins into a new interval.  Thus, between
        modification and the next 'swap', the content of this table does not
        reflect the current selection."
    ::= { usdAcctngSelectionControl 3 }

usdAcctngSelectionIfStackStartEntry OBJECT-TYPE
    SYNTAX      UsdAcctngSelectionIfStackStartEntry
    MAX-ACCESS  not-accessible
    STATUS      current
    DESCRIPTION
        "An entry used to determine the starting point entry when using the
        ifStack schema."
    INDEX     { acctngSelectionIndex,
                usdAcctngSelectionIfStackIfIndex }
    ::= { usdAcctngSelectionIfStackStartTable 1 }

UsdAcctngSelectionIfStackStartEntry ::= SEQUENCE {
    usdAcctngSelectionIfStackIfIndex     InterfaceIndex,
    usdAcctngSelectionIfStackRowStatus   RowStatus
}

usdAcctngSelectionIfStackIfIndex OBJECT-TYPE
    SYNTAX      InterfaceIndex
    MAX-ACCESS  not-accessible
    STATUS      current
    DESCRIPTION
        "The ifIndex to be used as a starting point in the interface stack
        configuration.  The interfaces to be returned in the ifStack schema will
        start from this value, going up."
    ::= { usdAcctngSelectionIfStackStartEntry 1 }

usdAcctngSelectionIfStackRowStatus OBJECT-TYPE
    SYNTAX      RowStatus
    MAX-ACCESS  read-create
    STATUS      current
    DESCRIPTION
        "Controls creation/deletion of entries in this table."
    ::= { usdAcctngSelectionIfStackStartEntry 2 }

-- The Accounting File Table

usdAcctngFileTable OBJECT-TYPE
    SYNTAX      SEQUENCE OF UsdAcctngFileEntry
    MAX-ACCESS  not-accessible
    STATUS      current
    DESCRIPTION
        "A unique value identifying the file transfer behavior and the the file
        to where accounting data is to be stored."
    ::= { usdAcctngFileControl 1 }

usdAcctngFileEntry OBJECT-TYPE
    SYNTAX      UsdAcctngFileEntry
    MAX-ACCESS  not-accessible
    STATUS      current
    DESCRIPTION
        "An entry used to extend the file management of acctngFileEntry.  This
        conceptual row extension is used for Unisphere accounting extensions to
        automate the transfer of accounting data to remote hosts."
    AUGMENTS  { acctngFileEntry }
    ::= { usdAcctngFileTable 1 }

UsdAcctngFileEntry ::= SEQUENCE {
    usdAcctngFileXferMode            INTEGER,
    usdAcctngFileXferIndex           INTEGER,
    usdAcctngFileXferSecondaryIndex  INTEGER
}

usdAcctngFileXferMode OBJECT-TYPE
    SYNTAX    INTEGER {
                  usdAcctngManualTransfer(1),
                  usdAcctngAutomatedTransfer(2),
                  usdAcctngTransferOnFileFull(3),
                  usdAcctngRedundantTransfer(4) }
    MAX-ACCESS  read-write
    STATUS      current
    DESCRIPTION
        "Indicates the mode to use for transfering accounting data to remote
        client.

        usdAcctngManualTransfer - Administrator is responsible for manually
        transfering collected accounting data off of the system.

        usdAcctngAutomatedTransfer - The agent will automatically transfer the
        collected accounting data based at a acctngFileIntervals using an entry
        in the usdFileXferTable pointed to by usdAcctngFileXferIndex.  If a
        manager sets this object to this value, a corresponding row in the
        usdFileXferTable must exist, otherwise the set command will fail.

        usdActngTransferOnFileFull - The agent will automatically transfer the
        collected accounting data when the file reaches the maximum size defined
        by acctngFileMaximumSize.  If a manager sets this object to this value,
        a corresponding row in the usdFileXferTable must exist, otherwise the set
        command will fail.

        usdAcctngRedundantTransfer - The agent will automatically transfer two
        copies of the accounting data based on the acctngFileInterval.  One copy
        will go to the usdFileXferTable entry identified by usdAcctngFileXferIndex
        and one copy will go the the usdFileXferTable entry identified by
        usdAcctngFileXferSecondaryIndex"
    ::= { usdAcctngFileEntry 1 }

usdAcctngFileXferIndex OBJECT-TYPE
    SYNTAX      INTEGER (1..65535)
    MAX-ACCESS  read-write
    STATUS      current
    DESCRIPTION
        "Identifies an entry in the usdFileXferTable, which defines the file
        transfer parameters to use when the agent is configured to automatically
        transfer collected accounting data files.  A set to this object will
        fail if a corresponding entry in the usdFileXferTable does not exist or
        it is not set to usdFileXferAcctngStatistics."
    ::= { usdAcctngFileEntry 2 }

usdAcctngFileXferSecondaryIndex OBJECT-TYPE
    SYNTAX      INTEGER (1..65535)
    MAX-ACCESS  read-write
    STATUS      current
    DESCRIPTION
        "Identifies a backup or secondary entry in the usdFileXferTable, which
        defines the file transfer parameters to use when the agent is configured
        to automatically transfer collected accounting data files.  A set to
        this object will fail if a corresponding entry in the usdFileXferTable
        does not exist or it is not set to usdFileXferAcctngStatistics."
    ::= { usdAcctngFileEntry 3 }
--  Per-interface Type Control Table

usdAcctngInterfaceTable OBJECT-TYPE
    SYNTAX      SEQUENCE OF UsdAcctngInterfaceEntry
    MAX-ACCESS  not-accessible
    STATUS      current
    DESCRIPTION
        "A table controlling the collection of accounting data on specific
        interfaces types.  This table provides an efficient mechanism to enable
        and/or disable data collection on all interfaces of a specified type."
    ::= { usdAcctngInterfaceControl 1 }

usdAcctngInterfaceEntry OBJECT-TYPE
    SYNTAX      UsdAcctngInterfaceEntry
    MAX-ACCESS  not-accessible
    STATUS      current
    DESCRIPTION
        "An entry which controls whether accounting data is to be collected on
        interfaces of a specific type."
    INDEX     { usdIfType }
    ::= { usdAcctngInterfaceTable 1 }

UsdAcctngInterfaceEntry ::= SEQUENCE {
    usdAcctngInterfaceAdminStatus        UsdAcctngAdminType,
    usdAcctngInterfaceOperStatus         UsdAcctngOperType,
    usdAcctngInterfaceRowStatus          RowStatus,
    usdAcctngInterfaceAccntgFileIndex    Integer32
}

usdAcctngInterfaceAdminStatus OBJECT-TYPE
    SYNTAX      UsdAcctngAdminType
    MAX-ACCESS  read-create
    STATUS      current
    DESCRIPTION
        "The desired administrative state for accounting data collection for
        interfaces defined by the type of this entry.  The administrative scope
        is for all interfaces of the type defined by the corresponding usdIfType
        for this entry."
    ::= { usdAcctngInterfaceEntry 1 }

usdAcctngInterfaceOperStatus OBJECT-TYPE
    SYNTAX      UsdAcctngOperType
    MAX-ACCESS  read-only
    STATUS      current
    DESCRIPTION
        "The operational state for accounting data collection on for all
        interfaces corresponding to this entries type."
    ::= { usdAcctngInterfaceEntry 2 }

usdAcctngInterfaceRowStatus OBJECT-TYPE
    SYNTAX      RowStatus
    MAX-ACCESS  read-create
    STATUS      current
    DESCRIPTION
        "Controls creation/deletion of entries in this table."
    ::= { usdAcctngInterfaceEntry 3 }

usdAcctngInterfaceAccntgFileIndex OBJECT-TYPE
    SYNTAX      Integer32 (0..65535)
    MAX-ACCESS  read-create
    STATUS      current
    DESCRIPTION
        "This object selects the acctngFileTable entry for the collection
        statistics for this interface type.  If there is not an entry in the
        acctngFileTable with the index indicated by this object, the
        usdAcctngInterface row will be ignored, unless the following conditions
        are met: (1) usdAcctngInterfaceAccntgFileIndex is set to zero, which is
        its default value, and (2) there is only one entry in the
        acctngFileTable.  When the two conditions are met, the interface type
        will apply to the one existing acctngFileTable entry."
    DEFVAL    { 0 }
    ::= { usdAcctngInterfaceEntry 4 }

-- enterprise schema information

usdAcctngSelectionSchema OBJECT-IDENTITY
    STATUS      current
    DESCRIPTION
        "The root OBJECT IDENTIFIER under which accounting selection tree
        objects are assigned."
    ::= { usdAcctngMIB 2 }


usdAcctngSelectionSchemaIf        OBJECT IDENTIFIER
    ::= { usdAcctngSelectionSchema 1 }

usdAcctngIfInOctets               OBJECT IDENTIFIER
    ::= { usdAcctngSelectionSchemaIf 1 }
usdAcctngIfInUcastPkts            OBJECT IDENTIFIER
    ::= { usdAcctngSelectionSchemaIf 2 }
usdAcctngIfInDiscards             OBJECT IDENTIFIER
    ::= { usdAcctngSelectionSchemaIf 3 }
usdAcctngIfInErrors               OBJECT IDENTIFIER
    ::= { usdAcctngSelectionSchemaIf 4 }
usdAcctngIfInUnknownProtos        OBJECT IDENTIFIER
    ::= { usdAcctngSelectionSchemaIf 5 }
usdAcctngIfOutOctets              OBJECT IDENTIFIER
    ::= { usdAcctngSelectionSchemaIf 6 }
usdAcctngIfOutUcastPkts           OBJECT IDENTIFIER
    ::= { usdAcctngSelectionSchemaIf 7 }
usdAcctngIfOutDiscards            OBJECT IDENTIFIER
    ::= { usdAcctngSelectionSchemaIf 8 }
usdAcctngIfOutErrors              OBJECT IDENTIFIER
    ::= { usdAcctngSelectionSchemaIf 9 }
usdAcctngIfCorrelator             OBJECT IDENTIFIER
    ::= { usdAcctngSelectionSchemaIf 10 }
usdAcctngIfInPolicedOctets        OBJECT IDENTIFIER
    ::= { usdAcctngSelectionSchemaIf 11 }
usdAcctngIfInPolicedPkts          OBJECT IDENTIFIER
    ::= { usdAcctngSelectionSchemaIf 12 }
usdAcctngIfInSpoofedPkts          OBJECT IDENTIFIER
    ::= { usdAcctngSelectionSchemaIf 13 }
usdAcctngIfOutPolicedOctets       OBJECT IDENTIFIER
    ::= { usdAcctngSelectionSchemaIf 14 }
usdAcctngIfOutPolicedPkts         OBJECT IDENTIFIER
    ::= { usdAcctngSelectionSchemaIf 15 }
usdAcctngIfOutSchedulerDropOctets OBJECT IDENTIFIER
    ::= { usdAcctngSelectionSchemaIf 16 }
usdAcctngIfOutSchedulerDropPkts   OBJECT IDENTIFIER
    ::= { usdAcctngSelectionSchemaIf 17 }
usdAcctngIfLowerInterface         OBJECT IDENTIFIER
    ::= { usdAcctngSelectionSchemaIf 18 }
usdAcctngIfTimeOffset             OBJECT IDENTIFIER
    ::= { usdAcctngSelectionSchemaIf 19 }
usdAcctngifInMulticastPkts        OBJECT IDENTIFIER 
    ::= { usdAcctngSelectionSchemaIf 20 }
usdAcctngifInBroadcastPkts        OBJECT IDENTIFIER 
    ::= { usdAcctngSelectionSchemaIf 21 }
usdAcctngifOutMulticastPkts       OBJECT IDENTIFIER 
    ::= { usdAcctngSelectionSchemaIf 22 }
usdAcctngifOutBroadcastPkts       OBJECT IDENTIFIER 
    ::= { usdAcctngSelectionSchemaIf 23 }

usdAcctngSelectionSchemaIfStack   OBJECT IDENTIFIER
    ::= { usdAcctngSelectionSchema 3 }
usdAcctngSelectionSchemaSystem    OBJECT IDENTIFIER
    ::= { usdAcctngSelectionSchema 4 }

usdAcctngSelectionSchemaPolicy    OBJECT IDENTIFIER
    ::= { usdAcctngSelectionSchema 5 }

usdAcctngGreenPackets             OBJECT IDENTIFIER
    ::= { usdAcctngSelectionSchemaPolicy 1 }
usdAcctngUpperGreenPackets        OBJECT IDENTIFIER
    ::= { usdAcctngSelectionSchemaPolicy 2 }
usdAcctngYellowPackets            OBJECT IDENTIFIER
    ::= { usdAcctngSelectionSchemaPolicy 3 }
usdAcctngUpperYellowPackets       OBJECT IDENTIFIER
    ::= { usdAcctngSelectionSchemaPolicy 4 }
usdAcctngRedPackets               OBJECT IDENTIFIER
    ::= { usdAcctngSelectionSchemaPolicy 5 }
usdAcctngUpperRedPackets          OBJECT IDENTIFIER
    ::= { usdAcctngSelectionSchemaPolicy 6 }
usdAcctngGreenBytes               OBJECT IDENTIFIER
    ::= { usdAcctngSelectionSchemaPolicy 7 }
usdAcctngUpperGreenBytes          OBJECT IDENTIFIER
    ::= { usdAcctngSelectionSchemaPolicy 8 }
usdAcctngYellowBytes              OBJECT IDENTIFIER
    ::= { usdAcctngSelectionSchemaPolicy 9 }
usdAcctngUpperYellowBytes         OBJECT IDENTIFIER
    ::= { usdAcctngSelectionSchemaPolicy 10 }
usdAcctngRedBytes                 OBJECT IDENTIFIER
    ::= { usdAcctngSelectionSchemaPolicy 11 }
usdAcctngUpperRedBytes            OBJECT IDENTIFIER
    ::= { usdAcctngSelectionSchemaPolicy 12 }

-- conformance information

usdAcctngConformance OBJECT IDENTIFIER ::= { usdAcctngMIB 3 }
usdAcctngGroups      OBJECT IDENTIFIER ::= { usdAcctngConformance 1 }
usdAcctngCompliances OBJECT IDENTIFIER ::= { usdAcctngConformance 2 }

usdAcctngCompliance MODULE-COMPLIANCE
    STATUS      obsolete
    DESCRIPTION
        "Obsolete compliance statement for switches that implement the RedStone
        Accounting Control MIB.  This statement became obsolete when the
        usdAcctngSelectionSubtreeType object was deprecated."
    MODULE  -- this module
        MANDATORY-GROUPS { usdAcctngBasicGroup }
    ::= { usdAcctngCompliances 1 }                                     -- RX 2.0

usdAcctngCompliance2 MODULE-COMPLIANCE
    STATUS      obsolete
    DESCRIPTION
        "Obsolete compliance statement for switches that implement the RedStone
        Accounting Control MIB.  This statement became obsolete when selection
        policy name and type objects were added."
    MODULE  -- this module
        MANDATORY-GROUPS { usdAcctngBasicGroup2 }
    ::= { usdAcctngCompliances 2 }                                     -- RX 3.2

usdAcctngCompliance3 MODULE-COMPLIANCE
    STATUS      current
    DESCRIPTION
        "The compliance statement for switches that implement the RedStone
        Accounting Control MIB."
    MODULE  -- this module
        MANDATORY-GROUPS { usdAcctngBasicGroup3 }
    ::= { usdAcctngCompliances 3 }                                     -- RX 4.0


-- units of conformance

usdAcctngBasicGroup OBJECT-GROUP
    OBJECTS {
        usdAcctngSelectionType,
        usdAcctngSelectionMode,
        usdAcctngSelectionSubtreeType,
        usdAcctngSelectionMaxIfStackLevels,
        usdAcctngSelectionIfStackRowStatus,
        usdAcctngFileXferMode,
        usdAcctngFileXferIndex,
        usdAcctngFileXferSecondaryIndex,
        usdAcctngInterfaceAdminStatus,
        usdAcctngInterfaceOperStatus,
        usdAcctngInterfaceRowStatus,
        usdAcctngInterfaceAccntgFileIndex }
    STATUS      obsolete
    DESCRIPTION
        "Obsolete collection of objects providing control of the basic
        collection of accounting data for connection-less networks.  This group
        became obsolete when usdAcctngSelectionSubtreeType was deprecated."
    ::= { usdAcctngGroups 1 }

usdAcctngBasicGroup2 OBJECT-GROUP
    OBJECTS {
        usdAcctngSelectionType,
        usdAcctngSelectionMode,
        usdAcctngSelectionMaxIfStackLevels,
        usdAcctngSelectionIfStackRowStatus,
        usdAcctngFileXferMode,
        usdAcctngFileXferIndex,
        usdAcctngFileXferSecondaryIndex,
        usdAcctngInterfaceAdminStatus,
        usdAcctngInterfaceOperStatus,
        usdAcctngInterfaceRowStatus,
        usdAcctngInterfaceAccntgFileIndex }
    STATUS      obsolete
    DESCRIPTION
        "Obsolete collection of objects providing control of the basic
        collection of accounting data for connection-less networks.  This group
        became obsolete when selection policy name and type objects were added."
    ::= { usdAcctngGroups 2 }

usdAcctngBasicGroup3 OBJECT-GROUP
    OBJECTS {
        usdAcctngSelectionType,
        usdAcctngSelectionMode,
        usdAcctngSelectionMaxIfStackLevels,
        usdAcctngSelectionPolicyName,
        usdAcctngSelectionPolicyType,
        usdAcctngSelectionIfStackRowStatus,
        usdAcctngFileXferMode,
        usdAcctngFileXferIndex,
        usdAcctngFileXferSecondaryIndex,
        usdAcctngInterfaceAdminStatus,
        usdAcctngInterfaceOperStatus,
        usdAcctngInterfaceRowStatus,
        usdAcctngInterfaceAccntgFileIndex }
    STATUS      current
    DESCRIPTION
        "A collection of objects providing control of the basic collection of
        accounting data for connection-less networks."
    ::= { usdAcctngGroups 3 }

END
