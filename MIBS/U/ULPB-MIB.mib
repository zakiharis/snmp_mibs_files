-- MIB File Generated on 14-Sep-1995 at 17:23:55

ULPB-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

ulpb OBJECT IDENTIFIER ::= { nas 9 }

ulpbAdmnTable OBJECT-TYPE
SYNTAX SEQUENCE OF UlpbAdmnEntry
ACCESS not-accessible
STATUS mandatory
DESCRIPTION
"This table defines the objects that can be changed to 
manage a LAPB interface. Changing one of these parameters 
may take effect in the operating LAPB immediately or may 
wait until the interface is restarted depending on the 
details of the implementation."
::= { ulpb 1 }

ulpbAdmnEntry OBJECT-TYPE
SYNTAX UlpbAdmnEntry
ACCESS not-accessible
STATUS mandatory
DESCRIPTION
"Configure parameter values for a specific LAPB."
INDEX { ulpbAdmnIndex }
::= { ulpbAdmnTable 1 }

UlpbAdmnEntry ::=
SEQUENCE {
ulpbAdmnIndex
    INTEGER,
ulpbAdmnN2ReXmitVal
    INTEGER,
ulpbAdmnT1AckTime
    INTEGER,
ulpbAdmnTpfVal
    INTEGER,
ulpbAdmnTrejVal
    INTEGER,
ulpbAdmnTbusyVal
    INTEGER,
ulpbAdmnLinkIdleTime
    INTEGER,
ulpbAdmnT2AckDelayTime
    INTEGER,
ulpbAdmnRecKWindowSz
    INTEGER,
ulpbAdmnXmitKWindowSz
    INTEGER,
ulpbAdmnLocProbe
    INTEGER,
ulpbAdmnMaxRecFrmSz
    INTEGER,
ulpbAdmnIgnUaError
    INTEGER,
ulpbAdmnFrmrFrmrError
    INTEGER,
ulpbAdmnFrmrInvrspError
    INTEGER,
ulpbAdmnSframePbit
    INTEGER,
ulpbAdmnDmOnAdm
    INTEGER
}

ulpbAdmnIndex OBJECT-TYPE
SYNTAX INTEGER
ACCESS read-only
STATUS mandatory
DESCRIPTION
"A unique value for each X.25 subnetwork entity running LAPB 
in the chassis.  The value of this object matches the value 
of the index of the corresponding X.25 subnetwork entity 
running LAPB entry in the entity table of the chassis MIB."
::= { ulpbAdmnEntry 1 }

ulpbAdmnN2ReXmitVal OBJECT-TYPE
SYNTAX INTEGER (1..255)
ACCESS read-write
STATUS mandatory
DESCRIPTION
"The maximum number of times a PDU is sent after the Ack, 
P-bit or Reject timer expires.  It also limits RR w/P-bit 
sends with remote busy true and the Busy timer 
expiring.
Default=10." 
::= { ulpbAdmnEntry 2 }

ulpbAdmnT1AckTime OBJECT-TYPE
SYNTAX INTEGER (1..3000)
ACCESS read-write
STATUS mandatory
DESCRIPTION
"The time interval during which the LAPB expects to receive 
a response to an outstanding IPDU or unexpected response to 
a sent unnumbered PDU. Value is in 0.1 second 
units.
Default=10."
::= { ulpbAdmnEntry 3 }

ulpbAdmnTpfVal OBJECT-TYPE
SYNTAX INTEGER (1..3000)
ACCESS read-write
STATUS mandatory
DESCRIPTION
"The time interval during which the LAPB expects to receive 
a PDU with the F-bit set to 1 in response to a command with 
the P-bit set to 1. Value is in 0.1 second 
units.
Default=7."
::= { ulpbAdmnEntry 4 }

ulpbAdmnTrejVal OBJECT-TYPE
SYNTAX INTEGER (1..10000)
ACCESS read-write
STATUS mandatory
DESCRIPTION
"The time interval during which the LAPB expects to receive 
a reply to a sent REJ TPDU. Value is in 0.1 second 
units.
Default=25."
::= { ulpbAdmnEntry 5 }

ulpbAdmnTbusyVal OBJECT-TYPE
SYNTAX INTEGER (1..30000)
ACCESS read-write
STATUS mandatory
DESCRIPTION
"The time interval during which the LAPB waits for an 
indication of the clearance of a busy condition at the 
other LAPB. Value is in 0.1 second units.
Default=100."
::= { ulpbAdmnEntry 6 }

ulpbAdmnLinkIdleTime OBJECT-TYPE
SYNTAX INTEGER (0..32000)
ACCESS read-write
STATUS mandatory
DESCRIPTION
"The time interval during which the LAPB expexts to receive 
a PDU from the other LAPB.  At expiration, the P/F cycle, 
which may result in disconnection is initiated.  Value is 
in 0.1 second units.  A value of 0 disables the 
timer.
Default=250."
::= { ulpbAdmnEntry 7 }

ulpbAdmnT2AckDelayTime OBJECT-TYPE
SYNTAX INTEGER (0..3000)
ACCESS read-write
STATUS mandatory
DESCRIPTION
"The maximum time delay before sending a delayed RR.  This 
must be considerably less than the Ack time value.  Value 
is in 0.1 second units.
Default=4."
::= { ulpbAdmnEntry 8 }

ulpbAdmnRecKWindowSz OBJECT-TYPE
SYNTAX INTEGER (0..127)
ACCESS read-write
STATUS mandatory
DESCRIPTION
"The maximum number of unacknowledged IPDUs that can be 
received before the acknowledgement RR must be 
sent.
Default=3."
::= { ulpbAdmnEntry 9 }

ulpbAdmnXmitKWindowSz OBJECT-TYPE
SYNTAX INTEGER (1..127)
ACCESS read-write
STATUS mandatory
DESCRIPTION
"The maximum number of unacknowledged PDUs that may be sent 
before a response is required.
Normal Mode = 1-7.
Extended 
Mode = 1-127.
Default=7."
::= { ulpbAdmnEntry 10 }

ulpbAdmnLocProbe OBJECT-TYPE
SYNTAX INTEGER (0..127)
ACCESS read-write
STATUS mandatory
DESCRIPTION
"The position before the window is closed at which an I PDU 
is sent with the P-bit set to solicit an acknowledgment 
from the receiver.
Default=0."
::= { ulpbAdmnEntry 11 }

ulpbAdmnMaxRecFrmSz OBJECT-TYPE
SYNTAX INTEGER (133..519)
ACCESS read-write
STATUS mandatory
DESCRIPTION
"The maximum allowable received I frame size.  It consists 
of X25 data + x25 protocol + LAPB protocol.
Default=300."
::= { ulpbAdmnEntry 12 }

ulpbAdmnIgnUaError OBJECT-TYPE
SYNTAX INTEGER{
  disable(1),
  enable(2)
}
ACCESS read-write
STATUS mandatory
DESCRIPTION
"When the connection is in ERROR state, this parameter 
defines whether or not to ignore any UA frames 
received.
Default=disable(1)."
::= { ulpbAdmnEntry 13 }

ulpbAdmnFrmrFrmrError OBJECT-TYPE
SYNTAX INTEGER{
  disable(1),
  enable(2)
}
ACCESS read-write
STATUS mandatory
DESCRIPTION
"When the connection is in ERROR state, this parameter 
defines whether or not to re-transmit a frame reject if one 
is received.
Default=disable(1)."
::= { ulpbAdmnEntry 14 }

ulpbAdmnFrmrInvrspError OBJECT-TYPE
SYNTAX INTEGER{
  disable(1),
  enable(2)
}
ACCESS read-write
STATUS mandatory
DESCRIPTION
"When the connection is in ERROR state, this parameter 
defines whether or not to transmit a frame reject if an 
invalid frame response is received.
Default=disable(1)."
::= { ulpbAdmnEntry 15 }

ulpbAdmnSframePbit OBJECT-TYPE
SYNTAX INTEGER{
  disable(1),
  enable(2)
}
ACCESS read-write
STATUS mandatory
DESCRIPTION
"This parameter defines whether or not to send a frame 
reject if an S-Frame is received without the P-bit 
set.
Default=disable(1)."
::= { ulpbAdmnEntry 16 }

ulpbAdmnDmOnAdm OBJECT-TYPE
SYNTAX INTEGER{
  disable(1),
  enable(2)
}
ACCESS read-write
STATUS mandatory
DESCRIPTION
"This parameter defines whether or not to send a DM on entry 
to ADM state.
Default=enable(2)."
::= { ulpbAdmnEntry 17 }

ulpbOperTable OBJECT-TYPE
SYNTAX SEQUENCE OF UlpbOperEntry
ACCESS not-accessible
STATUS mandatory
DESCRIPTION
"This table contains configuration information about 
interface parameters currently set in the interface.  These 
objects are read-only."
::= { ulpb 2 }

ulpbOperEntry OBJECT-TYPE
SYNTAX UlpbOperEntry
ACCESS not-accessible
STATUS mandatory
DESCRIPTION
"Entries of ulpbOperTable."
INDEX { ulpbOperIndex }
::= { ulpbOperTable 1 }

UlpbOperEntry ::=
SEQUENCE {
ulpbOperIndex
    INTEGER,
ulpbOperN2ReXmitVal
    INTEGER,
ulpbOperT1AckTime
    INTEGER,
ulpbOperTpfVal
    INTEGER,
ulpbOperTrejVal
    INTEGER,
ulpbOperTbusyVal
    INTEGER,
ulpbOperLinkIdleTime
    INTEGER,
ulpbOperT2AckDelayTime
    INTEGER,
ulpbOperRecKWindowSz
    INTEGER,
ulpbOperXmitKWindowSz
    INTEGER,
ulpbOperLocProbe
    INTEGER,
ulpbOperMaxRecFrmSz
    INTEGER,
ulpbOperIgnUaError
    INTEGER,
ulpbOperFrmrFrmrError
    INTEGER,
ulpbOperFrmrInvrspError
    INTEGER,
ulpbOperSframePbit
    INTEGER,
ulpbOperDmOnAdm
    INTEGER
}

ulpbOperIndex OBJECT-TYPE
SYNTAX INTEGER
ACCESS read-only
STATUS mandatory
DESCRIPTION
""
::= { ulpbOperEntry 1 }

ulpbOperN2ReXmitVal OBJECT-TYPE
SYNTAX INTEGER (1..255)
ACCESS read-only
STATUS mandatory
DESCRIPTION
""
::= { ulpbOperEntry 2 }

ulpbOperT1AckTime OBJECT-TYPE
SYNTAX INTEGER (1..3000)
ACCESS read-only
STATUS mandatory
DESCRIPTION
""
::= { ulpbOperEntry 3 }

ulpbOperTpfVal OBJECT-TYPE
SYNTAX INTEGER (1..3000)
ACCESS read-only
STATUS mandatory
DESCRIPTION
""
::= { ulpbOperEntry 4 }

ulpbOperTrejVal OBJECT-TYPE
SYNTAX INTEGER (1..10000)
ACCESS read-only
STATUS mandatory
DESCRIPTION
""
::= { ulpbOperEntry 5 }

ulpbOperTbusyVal OBJECT-TYPE
SYNTAX INTEGER (1..30000)
ACCESS read-only
STATUS mandatory
DESCRIPTION
""
::= { ulpbOperEntry 6 }

ulpbOperLinkIdleTime OBJECT-TYPE
SYNTAX INTEGER (0..32000)
ACCESS read-only
STATUS mandatory
DESCRIPTION
""
::= { ulpbOperEntry 7 }

ulpbOperT2AckDelayTime OBJECT-TYPE
SYNTAX INTEGER (0..3000)
ACCESS read-only
STATUS mandatory
DESCRIPTION
""
::= { ulpbOperEntry 8 }

ulpbOperRecKWindowSz OBJECT-TYPE
SYNTAX INTEGER (0..127)
ACCESS read-only
STATUS mandatory
DESCRIPTION
""
::= { ulpbOperEntry 9 }

ulpbOperXmitKWindowSz OBJECT-TYPE
SYNTAX INTEGER (1..127)
ACCESS read-only
STATUS mandatory
DESCRIPTION
""
::= { ulpbOperEntry 10 }

ulpbOperLocProbe OBJECT-TYPE
SYNTAX INTEGER (0..127)
ACCESS read-only
STATUS mandatory
DESCRIPTION
""
::= { ulpbOperEntry 11 }

ulpbOperMaxRecFrmSz OBJECT-TYPE
SYNTAX INTEGER (133..519)
ACCESS read-only
STATUS mandatory
DESCRIPTION
""
::= { ulpbOperEntry 12 }

ulpbOperIgnUaError OBJECT-TYPE
SYNTAX INTEGER{
  disable(1),
  enable(2)
}
ACCESS read-only
STATUS mandatory
DESCRIPTION
""
::= { ulpbOperEntry 13 }

ulpbOperFrmrFrmrError OBJECT-TYPE
SYNTAX INTEGER{
  disable(1),
  enable(2)
}
ACCESS read-only
STATUS mandatory
DESCRIPTION
""
::= { ulpbOperEntry 14 }

ulpbOperFrmrInvrspError OBJECT-TYPE
SYNTAX INTEGER{
  disable(1),
  enable(2)
}
ACCESS read-only
STATUS mandatory
DESCRIPTION
""
::= { ulpbOperEntry 15 }

ulpbOperSframePbit OBJECT-TYPE
SYNTAX INTEGER{
  disable(1),
  enable(2)
}
ACCESS read-only
STATUS mandatory
DESCRIPTION
""
::= { ulpbOperEntry 16 }

ulpbOperDmOnAdm OBJECT-TYPE
SYNTAX INTEGER{
  disable(1),
  enable(2)
}
ACCESS read-only
STATUS mandatory
DESCRIPTION
""
::= { ulpbOperEntry 17 }

ulpbStatTable OBJECT-TYPE
SYNTAX SEQUENCE OF UlpbStatEntry
ACCESS not-accessible
STATUS mandatory
DESCRIPTION
"Statistics information about this LAPB interface."
::= { ulpb 3 }

ulpbStatEntry OBJECT-TYPE
SYNTAX UlpbStatEntry
ACCESS not-accessible
STATUS mandatory
DESCRIPTION
"Entries of ulpbStatTrable."
INDEX { ulpbStatIndex }
::= { ulpbStatTable 1 }

UlpbStatEntry ::=
SEQUENCE {
ulpbStatIndex
    INTEGER,
ulpbStatRRCmdsRcvd
    INTEGER,
ulpbStatRRCmdsTrnsmt
    INTEGER,
ulpbStatRRRspsRcvd
    INTEGER,
ulpbStatRRRspsTrnsmt
    INTEGER,
ulpbStatRNRCmdsRcvd
    INTEGER,
ulpbStatRNRCmdsTrnsmt
    INTEGER,
ulpbStatRNRRspsRcvd
    INTEGER,
ulpbStatRNRRspsTrnsmt
    INTEGER,
ulpbStatREJCmdsRcvd
    INTEGER,
ulpbStatREJCmdsTrnsmt
    INTEGER,
ulpbStatREJRspsRcvd
    INTEGER,
ulpbStatREJRspsTrnsmt
    INTEGER,
ulpbStatSABMCmdsRcvd
    INTEGER,
ulpbStatSABMCmdsTrnsmt
    INTEGER,
ulpbStatDISCCmdsRcvd
    INTEGER,
ulpbStatDISCCmdsTrnsmt
    INTEGER,
ulpbStatDMRspsRcvd
    INTEGER,
ulpbStatDMRspsTrnsmt
    INTEGER,
ulpbStatUARspsRcvd
    INTEGER,
ulpbStatUARspsTrnsmt
    INTEGER,
ulpbStatFRMRRspsRcvd
    INTEGER,
ulpbStatFRMRRspsTrnsmt
    INTEGER,
ulpbStatIFrameCmdsRcvd
    INTEGER,
ulpbStatIFrameCmdsTrnsmt
    INTEGER
}

ulpbStatIndex OBJECT-TYPE
SYNTAX INTEGER
ACCESS read-only
STATUS mandatory
DESCRIPTION
"A unique value for each X.25 subnetwork entity running LAPB 
in the chassis.  The value of this object matches the value 
of the index of the corresponding X.25 subnetwork entity 
running LAPB entry in the entity table of the chassis MIB."
::= { ulpbStatEntry 1 }

ulpbStatRRCmdsRcvd OBJECT-TYPE
SYNTAX INTEGER
ACCESS read-only
STATUS mandatory
DESCRIPTION
"Number of RR commands received."
::= { ulpbStatEntry 2 }

ulpbStatRRCmdsTrnsmt OBJECT-TYPE
SYNTAX INTEGER
ACCESS read-only
STATUS mandatory
DESCRIPTION
"Number of RR commands transmitted."
::= { ulpbStatEntry 3 }

ulpbStatRRRspsRcvd OBJECT-TYPE
SYNTAX INTEGER
ACCESS read-only
STATUS mandatory
DESCRIPTION
"Number of RR response received."
::= { ulpbStatEntry 4 }

ulpbStatRRRspsTrnsmt OBJECT-TYPE
SYNTAX INTEGER
ACCESS read-only
STATUS mandatory
DESCRIPTION
"Number or RR response transmitted."
::= { ulpbStatEntry 5 }

ulpbStatRNRCmdsRcvd OBJECT-TYPE
SYNTAX INTEGER
ACCESS read-only
STATUS mandatory
DESCRIPTION
"Number of RNR commands received."
::= { ulpbStatEntry 6 }

ulpbStatRNRCmdsTrnsmt OBJECT-TYPE
SYNTAX INTEGER
ACCESS read-only
STATUS mandatory
DESCRIPTION
"Number of RNR commands transmitted."
::= { ulpbStatEntry 7 }

ulpbStatRNRRspsRcvd OBJECT-TYPE
SYNTAX INTEGER
ACCESS read-only
STATUS mandatory
DESCRIPTION
"Number of RNR response received."
::= { ulpbStatEntry 8 }

ulpbStatRNRRspsTrnsmt OBJECT-TYPE
SYNTAX INTEGER
ACCESS read-only
STATUS mandatory
DESCRIPTION
"Number of RNR response transmitted."
::= { ulpbStatEntry 9 }

ulpbStatREJCmdsRcvd OBJECT-TYPE
SYNTAX INTEGER
ACCESS read-only
STATUS mandatory
DESCRIPTION
"Number of REJ commands received."
::= { ulpbStatEntry 10 }

ulpbStatREJCmdsTrnsmt OBJECT-TYPE
SYNTAX INTEGER
ACCESS read-only
STATUS mandatory
DESCRIPTION
"Number of REJ commands transmitted."
::= { ulpbStatEntry 11 }

ulpbStatREJRspsRcvd OBJECT-TYPE
SYNTAX INTEGER
ACCESS read-only
STATUS mandatory
DESCRIPTION
"Number of REJ responses received."
::= { ulpbStatEntry 12 }

ulpbStatREJRspsTrnsmt OBJECT-TYPE
SYNTAX INTEGER
ACCESS read-only
STATUS mandatory
DESCRIPTION
"Number of REJ responses transmitted."
::= { ulpbStatEntry 13 }

ulpbStatSABMCmdsRcvd OBJECT-TYPE
SYNTAX INTEGER
ACCESS read-only
STATUS mandatory
DESCRIPTION
"Number of SABM commands received."
::= { ulpbStatEntry 14 }

ulpbStatSABMCmdsTrnsmt OBJECT-TYPE
SYNTAX INTEGER
ACCESS read-only
STATUS mandatory
DESCRIPTION
"Number of SABM commands transmitted."
::= { ulpbStatEntry 15 }

ulpbStatDISCCmdsRcvd OBJECT-TYPE
SYNTAX INTEGER
ACCESS read-only
STATUS mandatory
DESCRIPTION
"Number of DISC commands received."
::= { ulpbStatEntry 16 }

ulpbStatDISCCmdsTrnsmt OBJECT-TYPE
SYNTAX INTEGER
ACCESS read-only
STATUS mandatory
DESCRIPTION
"Number of DISC commands transmitted."
::= { ulpbStatEntry 17 }

ulpbStatDMRspsRcvd OBJECT-TYPE
SYNTAX INTEGER
ACCESS read-only
STATUS mandatory
DESCRIPTION
"Number of DM response received."
::= { ulpbStatEntry 18 }

ulpbStatDMRspsTrnsmt OBJECT-TYPE
SYNTAX INTEGER
ACCESS read-only
STATUS mandatory
DESCRIPTION
"Number of DM response transmitted."
::= { ulpbStatEntry 19 }

ulpbStatUARspsRcvd OBJECT-TYPE
SYNTAX INTEGER
ACCESS read-only
STATUS mandatory
DESCRIPTION
"Number of UA response received."
::= { ulpbStatEntry 20 }

ulpbStatUARspsTrnsmt OBJECT-TYPE
SYNTAX INTEGER
ACCESS read-only
STATUS mandatory
DESCRIPTION
"Number of UA response transmitted."
::= { ulpbStatEntry 21 }

ulpbStatFRMRRspsRcvd OBJECT-TYPE
SYNTAX INTEGER
ACCESS read-only
STATUS mandatory
DESCRIPTION
"Number of FRMR response received."
::= { ulpbStatEntry 22 }

ulpbStatFRMRRspsTrnsmt OBJECT-TYPE
SYNTAX INTEGER
ACCESS read-only
STATUS mandatory
DESCRIPTION
"Number of FRMR response transmitted."
::= { ulpbStatEntry 23 }

ulpbStatIFrameCmdsRcvd OBJECT-TYPE
SYNTAX INTEGER
ACCESS read-only
STATUS mandatory
DESCRIPTION
"Number of I-frame command received."
::= { ulpbStatEntry 24 }

ulpbStatIFrameCmdsTrnsmt OBJECT-TYPE
SYNTAX INTEGER
ACCESS read-only
STATUS mandatory
DESCRIPTION
"Number of I-frame commands transmitted."
::= { ulpbStatEntry 25 }

END
