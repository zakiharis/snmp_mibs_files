-- 7 UB Internetworking MIB
UB-INTERNETWORKING-MIB DEFINITIONS ::= BEGIN
		
		
IMPORTS
		DisplayString FROM SNMPv2-TC
mgmt, OBJECT-TYPE, NetworkAddress, IpAddress, Counter, Gauge, TimeTicks,

enterprises		FROM RFC1155-SMI
transmission		FROM RFC1213-MIB;

-- iso org dod internet private enterprises ubNode 

ubNode			OBJECT IDENTIFIER ::= { enterprises 75 }
ubEquip			OBJECT IDENTIFIER ::= { ubNode 1 }	
ubInternetworking	OBJECT IDENTIFIER ::= { ubEquip 2 }
ubRISCFddiBrouter	OBJECT IDENTIFIER ::= { ubInternetworking 1 }
ubRISCMPET		OBJECT IDENTIFIER ::= { ubInternetworking 2 }
ubRISCTokenRing		OBJECT IDENTIFIER ::= { ubInternetworking 3 }
ubTrapAttrs		OBJECT IDENTIFIER ::= {ubNode 3 }
ubSystem		OBJECT IDENTIFIER ::= {ubNode 4}
ubProduct		OBJECT IDENTIFIER ::= {ubNode 5}
ubExperimental		OBJECT IDENTIFIER ::= {ubNode 6}
ubExpInternetworking	OBJECT IDENTIFIER ::= {ubExperimental 2 }
ubInExp1		OBJECT IDENTIFIER ::= {ubExpInternetworking 1 }
ubExtensions		OBJECT IDENTIFIER ::= { ubNode 7 }
ubExtInternetworking	OBJECT IDENTIFIER ::= {ubNode 2}
ubInExt1		OBJECT IDENTIFIER ::= {ubExtInternetworking 1 }

-- 7.1  Enclosure    [RISC UB]

ubInEnc		OBJECT IDENTIFIER ::= {ubRISCFddiBrouter 1 }
		
	encSlots   OBJECT-TYPE
		SYNTAX	INTEGER
		ACCESS	read-only
		STATUS	mandatory
		 DESCRIPTION
		"Number of slots in the enclosure"
		::= { ubInEnc 1 }
		
-- 7.2  Entity    

ubInEntity	OBJECT IDENTIFIER ::= {ubRISCFddiBrouter 2 }
		
-- 7.3  Card     

ubInCard	OBJECT IDENTIFIER ::= {ubRISCFddiBrouter 3 }
		
-- 7.3.1 Control Group     [RISC UB]
		
controlUb1	OBJECT IDENTIFIER ::= { ubInCard 1}

	login   OBJECT-TYPE
		SYNTAX	DisplayString
		ACCESS	read-write
		STATUS	mandatory
		 DESCRIPTION
		"ASCII string with the following (case sensitive) format:
		CommunityString:Password"
		::= { controlUb1 1 }
		
-- 7.3.2  Configuration group [RISC UB]

configurationUb1	OBJECT IDENTIFIER ::= { ubInCard 2 }

	slotNum   OBJECT-TYPE
		SYNTAX	INTEGER
		ACCESS	read-only
		STATUS	mandatory
		 DESCRIPTION
		"Slot Number of this card"
		::= { configurationUb1 1 }

	qeContentionOwner   OBJECT-TYPE
		SYNTAX	INTEGER
		ACCESS	read-only
		STATUS	mandatory
		 DESCRIPTION
		"Owner of QE Contention in this enclosure"
		::= { configurationUb1 2 }
		
-- 7.4  Port 
ubInPort	OBJECT IDENTIFIER ::= {ubRISCFddiBrouter 4}
		
-- 7.4.1   Plus Bus group     [RISC UB]
		
--  this is the MIB module for the UB plusbus
		
plusbus		OBJECT IDENTIFIER ::= {ubInPort 1 }
		
-- 7.4.1.1 Generic Plus Bus Group     [RISC UB]
		
		-- the Generic Plus Bus group
		-- Implementation of this group is mandatory for all 
		-- internetworking systems that attach to the plus bus.
		
	plusbusTable OBJECT-TYPE
		SYNTAX  SEQUENCE OF PlusbusEntry
		ACCESS  not-accessible
		STATUS  mandatory
		 DESCRIPTION
		 "Status information and control variables for a 
		 collection of ethernet-like interfaces attached to
		 a particular system."
		::= { plusbus 1 }
	plusbusEntry OBJECT-TYPE
		SYNTAX  PlusbusEntry
		ACCESS  not-accessible
		STATUS  mandatory
		 DESCRIPTION
		 "Status information and control variables for a 
		 plus bus interface."
		INDEX   { plusbusIndex }
		::= { plusbusTable 1 }
		PlusbusEntry ::= SEQUENCE {
			plusbusIndex
			INTEGER,
			plusbusAdminstate
			INTEGER
		}
	plusbusIndex OBJECT-TYPE
		SYNTAX  INTEGER
		ACCESS  read-only
		STATUS  mandatory
		 DESCRIPTION
		 "An index value that uniquely identifies an interface 
		 to the plus bus.  The interface 
		 identified by a particular value of this INDEX is 
		 the same interface as identified by the same value 
		 of ifIndex."
		::= { plusbusEntry 1 }
	plusbusAdminstate OBJECT-TYPE
		SYNTAX  INTEGER {
		enabled(2),
		disabled(3)
		}
		ACCESS  read-write
		STATUS  mandatory
		 DESCRIPTION
		 "The state variable for a particular interface
		 The value disabled(3) signifies that transmission
		 and reception on the plus bus is disabled."
		::= { plusbusEntry 2}
	plusbusAccess OBJECT-TYPE
		SYNTAX	OCTET STRING
		ACCESS	read-write
		STATUS	mandatory
		 DESCRIPTION
		 "Information configured into the bridge by 
		 (local or network) management specifying the set of 
		 cards from which frames may NOT be accepted via
		 the plusbus.  Each octet within the 
		 value of this object specifies a set of eight cards, 
		 with the first octet specifying slots 1 through 8, the 
		 second octet specifying slots 9 through 16, etc. Within 
		 each octet, the most significant bit represents the 
		 lowest numbered card, and the least significant bit 
		 represents the highest numbered card. Thus, each card 
		 of the bridge is represented by a single bit within the 
		 value of this object. If that bit has a value of '1' 
		 then that card is included in the set of cards; the 
		 card is not included if its bit has a value of '0'. 
		 (Note that the setting of the bit corresponding to the 
		 card being queried is irrelevant.)"
		::= { plusbusEntry 3 }
-- 7.4.1.2 Plus Bus Statistics Group     [RISC UB]
		
		-- Implementation of this group is mandatory.  
		
	plusbusStatsTable OBJECT-TYPE
		SYNTAX  SEQUENCE OF PlusbusStatsEntry
		ACCESS  not-accessible
		STATUS  mandatory
		 DESCRIPTION
		 "Statistics for a collection of plus bus interfaces 
		 attached to a particular system."
		::= { plusbus 2 }
	plusbusStatsEntry OBJECT-TYPE
		SYNTAX  PlusbusStatsEntry
		ACCESS  not-accessible
		STATUS  mandatory
		 DESCRIPTION
		 "Statistics for a particular interface to the plus bus."
		INDEX   { plusbusStatsIndex }
		::= { plusbusStatsTable 1 }
		PlusbusStatsEntry ::= SEQUENCE {
			plusbusStatsIndex
			INTEGER,
			plusbusStatsTxErrors
			Counter,
			plusbusStatsTxlostacks
			Counter,
			plusbusStatstxtimeouts
			Counter,
			plusbusStatsrxerrors
			Counter,
			plusbusStatsrxtimeouts
			Counter,
			plusbusStatsRxFifoUnderflows
			Counter
		}
	plusbusStatsIndex OBJECT-TYPE
		SYNTAX  INTEGER
		ACCESS  read-only
		STATUS  mandatory
		 DESCRIPTION
		 "An index value that uniquely identifies an interface 
		 to the plus bus.  The interface 
		 identified by a particular value of this INDEX 
		 is the same interface as identified by the same 
		 value of ifIndex."
		::= { plusbusStatsEntry 1 }
	plusbusStatsTxErrors OBJECT-TYPE
		SYNTAX  Counter
		ACCESS  read-only
		STATUS  mandatory
		 DESCRIPTION
		 "A count of negative acknowledgements received
		 on transmission. "
		::= { plusbusStatsEntry 2 }
	plusbusStatsTxlostacks OBJECT-TYPE
		SYNTAX  Counter
		ACCESS  read-only
		STATUS  mandatory
		 DESCRIPTION
		 "A count of acknowledgements not
		 received on transmission. "
		::= { plusbusStatsEntry 3 }
	plusbusStatsTxtimeouts OBJECT-TYPE
		SYNTAX  Counter
		ACCESS  read-only
		STATUS  mandatory
		 DESCRIPTION
		 "A count of bus timeouts that occurred
		 during transmissions. "
		::= { plusbusStatsEntry 4}
	plusbusStatsRxErrors OBJECT-TYPE
		SYNTAX  Counter
		ACCESS  read-only
		STATUS  mandatory
		 DESCRIPTION
		 "A count of frames received with CRC or
		  frame length errors"
		::= { plusbusStatsEntry 5 }
	plusbusStatsRxtimeouts OBJECT-TYPE
		SYNTAX  Counter
		ACCESS  read-only
		STATUS  mandatory
		 DESCRIPTION
		 "A count of bus timeouts that occurred during
		 frame reception."
		::= { plusbusStatsEntry 6 }
	plusbusStatsclocklosses OBJECT-TYPE
		SYNTAX  Counter
		ACCESS  read-only
		STATUS  mandatory
		 DESCRIPTION
		 "A count of plusbus clock losses-detected."
		::= { plusbusStatsEntry 7 }
		rxFifoUnderflows OBJECT-TYPE
		SYNTAX  Counter
		ACCESS  read-only
		STATUS  mandatory
DESCRIPTION ""
		::= { plusbusStatsEntry 8 }
		
-- 7.5 UB Downloader Group

ubNVM	OBJECT IDENTIFIER ::= {ubRISCFddiBrouter 5 }
ubDownloader	OBJECT IDENTIFIER ::= { ubNVM 1 }
ubOptions	OBJECT IDENTIFIER ::= { ubDownloader 1 }
ubBOOTP		OBJECT IDENTIFIER ::= { ubDownloader 2 }
ubTFTP		OBJECT IDENTIFIER ::= { ubDownloader 3 }
ubDefaults	OBJECT IDENTIFIER ::= { ubDownloader 4 }
		
	ubDnloadOptions OBJECT-TYPE
		SYNTAX  UbDnloadOptions
		ACCESS  not-accessible
		STATUS  mandatory
		DESCRIPTION
		"Download parameters."
		::= { ubOptions 1 }
		UbDnloadOptions ::= SEQUENCE {
			dlVersionID
			INTEGER,
			dlMaxLoadAttempts
			INTEGER,
			dlMaxBOOTPAttempts
			INTEGER,
			dlBOOTPRetransTime
			INTEGER,
			dlMaxRARPAttempts
			INTEGER,
			dlRARPRetransTime
			INTEGER,
			dlMaxTFTPAttempts
			INTEGER,
			dlTFTPRetransTime
			INTEGER
		}
	dlVersionID OBJECT-TYPE
		SYNTAX  INTEGER
		ACCESS  read-only
		STATUS  mandatory
		DESCRIPTION
		"Version number of load option file
		to be downloaded."
		::= { ubDnloadOptions 1 }
		
	dlMaxLoadAttempts OBJECT-TYPE
		SYNTAX  INTEGER (1..255)
		ACCESS  read-write
		STATUS  mandatory
		DESCRIPTION
		"Maximum number of load attempts
		before PROM bridge becomes operational."
		::= { ubDnloadOptions 2 }
		
	dlMaxBOOTPAttempts OBJECT-TYPE
		SYNTAX  INTEGER (1..255)
		ACCESS  read-write
		STATUS  mandatory
		DESCRIPTION
		"Maximum number of BootP attempts before
		trying Rarp instead."
		::= { ubDnloadOptions 3 }
		
	dlBOOTPRetransTime OBJECT-TYPE
		SYNTAX  INTEGER (1..255)
		ACCESS  read-write
		STATUS  mandatory
		DESCRIPTION
		"The retransmission time between BootP
		attempts."
		::= { ubDnloadOptions 4 }
		
	dlMaxRARPAttempts OBJECT-TYPE
		SYNTAX  INTEGER (0..255)
		ACCESS  read-write
		STATUS  mandatory
		DESCRIPTION
		"Maximum number of Rarp attempts
		before continuing with TFTP."
		::= { ubDnloadOptions 5 }
		
	dlRARPRetransTime OBJECT-TYPE
		SYNTAX  INTEGER (0..255)
		ACCESS  read-write
		STATUS  mandatory
		DESCRIPTION
		"The retransmission time between RARP
		attempts."
		::= { ubDnloadOptions 6 }
		
	dlMaxTFTPAttempts OBJECT-TYPE
		SYNTAX  INTEGER (0..255)
		ACCESS  read-write
		STATUS  mandatory
		DESCRIPTION
		"The maximum number of times to attempt
		TFTP download before initiating the PROM bridge."
		::= { ubDnloadOptions 7 }
		
	dlTFTPRetransTime OBJECT-TYPE
		SYNTAX  INTEGER (0..255)
		ACCESS  read-write
		STATUS  mandatory
		DESCRIPTION
		"The retransmission time between TFTP
		attempts."
		::= { ubDnloadOptions 8 }
		
	dlBOOTPOptionsTbl OBJECT-TYPE
		SYNTAX  SEQUENCE OF DlBOOTPOptions
		ACCESS  not-accessible
		STATUS  mandatory
		DESCRIPTION
		"BootP options table."
		::= { ubBOOTP 1 }

	dlBOOTPOptionsEntry OBJECT-TYPE
		SYNTAX  DlBOOTPOptions
		ACCESS  not-accessible
		STATUS  mandatory
		DESCRIPTION
		"BootP options table entry."
		INDEX	{ dlBOOTPOptionTblEntry }
		::= { dlBOOTPOptionsTbl 1 }

		DlBOOTPOptions ::= SEQUENCE {
			dlBOOTPOptionTblEntry
			INTEGER,
			dlBOOTPHostName
			DisplayString
		}

	dlBOOTPOptionTblEntry OBJECT-TYPE
		SYNTAX  INTEGER (1..3)
		ACCESS  read-only
		STATUS  mandatory
		DESCRIPTION
		"The number of entries in the ubBootPOptionsTbl."
		::= { dlBOOTPOptionsEntry 1 }

	dlBOOTPHostName OBJECT-TYPE
		SYNTAX  DisplayString
		ACCESS  read-write
		STATUS  mandatory
		DESCRIPTION
		"Host name of the card for this port."
		::= { dlBOOTPOptionsEntry 2 }
		
	dlBOOTPPortAssignTbl OBJECT-TYPE
		SYNTAX  SEQUENCE OF DlBOOTPPorts
		ACCESS  not-accessible
		STATUS  mandatory
		DESCRIPTION
		"BootP Port Assignment Table."
		::= { ubBOOTP 2 }

	dlBOOTPPortAssignEntry OBJECT-TYPE
		SYNTAX  DlBOOTPPorts
		ACCESS  not-accessible
		STATUS  mandatory
		DESCRIPTION
		"BOOTP Port assignment entry."
		INDEX	{ dlBOOTPPortId }
		::= { dlBOOTPPortAssignTbl 1 }

		DlBOOTPPorts ::= SEQUENCE {
			dlBOOTPPortId
			INTEGER,
			dlBOOTPOptionsRunning
			INTEGER
		}

	dlBOOTPPortId OBJECT-TYPE
		SYNTAX  INTEGER {
		plusbus(1),
		qe(2),
		fddi(3)
		}
		ACCESS  read-only
		STATUS  mandatory
		DESCRIPTION
		"Id of port on which BootP transmissions can
		be sent."
		::= { dlBOOTPPortAssignEntry 1 }
		
	dlBOOTPOptionsRunning OBJECT-TYPE
		SYNTAX  INTEGER {
		none(1),	-- reset all running options
		opt-1(2),	-- run option 1 only
		opt-2(3),	-- run option 2 only
		opts-1-2(4),	-- run options 1 and 2 
		opt-3(5),	-- run option 3 only
		opts-1-3(6),	-- run options 1 and 3
		opts-2-3(7),	-- run options 2 and 3
		opts-1-2-3(8)	-- run options 1,2 and 3
		}
		--SYNTAX	INTEGER (0..7)
		ACCESS  read-write
		STATUS  mandatory
		DESCRIPTION
		"The options being run by this Port ID. This is bit mapped"
		::= { dlBOOTPPortAssignEntry 2 }
		
	dlTFTPOptionsTbl OBJECT-TYPE
		SYNTAX  SEQUENCE OF DlTFTPOptions
		ACCESS  not-accessible
		STATUS  mandatory
		DESCRIPTION
		"TFTP options table."
		::= { ubTFTP 1 }
		
	dlTFTPOptionsEntry OBJECT-TYPE
		SYNTAX  DlTFTPOptions
		ACCESS  not-accessible
		STATUS  mandatory
		DESCRIPTION
		"TFTP options table entry."
		INDEX	{ dlTFTPOptionTblEntry }
		::= { dlTFTPOptionsTbl 1 }

		DlTFTPOptions ::= SEQUENCE {
			dlTFTPOptionTblEntry
			INTEGER,
			dlTFTPServerIpAddr
			IpAddress,
			dlTFTPServerFileName
			DisplayString
		}

	dlTFTPOptionTblEntry OBJECT-TYPE
		SYNTAX  INTEGER (1..3)
		ACCESS  read-only
		STATUS  mandatory
		DESCRIPTION
		"The number of entries in the ubTFTPOptionsTbl."
		::= { dlTFTPOptionsEntry 1 }
		
	dlTFTPServerIpAddr OBJECT-TYPE
		SYNTAX  IpAddress
		ACCESS  read-write
		STATUS  mandatory
		DESCRIPTION
		"Address of TFTP server located out this port."
		::= { dlTFTPOptionsEntry 2 }
		
	dlTFTPServerFileName OBJECT-TYPE
		SYNTAX  DisplayString
		ACCESS  read-write
		STATUS  mandatory
		DESCRIPTION
		"Path name of Load Information File on
		download server."
		::= { dlTFTPOptionsEntry 3 }
		
	dlTFTPPortAssignTbl OBJECT-TYPE
		SYNTAX  SEQUENCE OF DlTFTPPorts
		ACCESS  not-accessible
		STATUS  mandatory
		DESCRIPTION
		"TFTP options table."
		::= { ubTFTP 2 }
		
	dlTFTPPortAssignEntry OBJECT-TYPE
		SYNTAX  DlTFTPPorts
		ACCESS  not-accessible
		STATUS  mandatory
		DESCRIPTION
		"TFTP options table entry."
		INDEX	{ dlTFTPPortId }
		::= { dlTFTPPortAssignTbl 1 }

		DlTFTPPorts ::= SEQUENCE {
			dlTFTPPortId
			INTEGER,
			dlTFTPOptionsRunning
			INTEGER
		}

	dlTFTPPortId OBJECT-TYPE
		SYNTAX  INTEGER {
		plusbus(1),
		qe(2),
		fddi(3)
		}
		ACCESS  read-only
		STATUS  mandatory
		DESCRIPTION
		"Id of port on which TFTP transmissions
		can be sent."
		::= { dlTFTPPortAssignEntry 1 }
		
	dlTFTPOptionsRunning OBJECT-TYPE
		SYNTAX  INTEGER {
		none(1),	-- reset all running options
		opt-1(2),	-- run option 1 only
		opt-2(3),	-- run option 2 only
		opts-1-2(4),	-- run options 1 and 2 
		opt-3(5),	-- run option 3 only
		opts-1-3(6),	-- run options 1 and 3
		opts-2-3(7),	-- run options 2 and 3
		opts-1-2-3(8)	-- run options 1,2 and 3
		}
		--SYNTAX  INTEGER (0..7)
		ACCESS  read-write
		STATUS  mandatory
		DESCRIPTION
		"Bit-Mapping of Options that can be run on a given Port ID."
		::= { dlTFTPPortAssignEntry 2 }
		
	dlDefaultTFTPParams OBJECT-TYPE
		SYNTAX  DlDefaultTFTPParams
		ACCESS  not-accessible
		STATUS  mandatory
		DESCRIPTION
		"Default TFTP parameters for a device that fails BOOTP."
		::= { ubDefaults 1 }

		DlDefaultTFTPParams ::= SEQUENCE {
			dlTFTPDefaultNodeIpAddr
			IpAddress,
			dlTFTPDefaultSubnetMask
			IpAddress,
			dlTFTPDefaultGatewayIpAddr
			IpAddress
		}

	dlTFTPDefaultNodeIpAddr OBJECT-TYPE
		SYNTAX  IpAddress
		ACCESS  read-write
		STATUS  mandatory
		DESCRIPTION
		"TFTP server default address."
		::= { dlDefaultTFTPParams 1 }
		
	dlTFTPDefaultSubnetMask OBJECT-TYPE
		SYNTAX  IpAddress
		ACCESS  read-write
		STATUS  mandatory
		DESCRIPTION
		"TFTP server default subnet mask."
		::= { dlDefaultTFTPParams 2 }
		
	dlTFTPDefaultGatewayIpAddr OBJECT-TYPE
		SYNTAX  IpAddress
		ACCESS  read-write
		STATUS  mandatory
		DESCRIPTION
		"Path name of Load Information File on
		default TFTP server."
		::= { dlDefaultTFTPParams 3 }
		
	ubBridgeParams OBJECT-TYPE
		SYNTAX  UbBridgeParams
		ACCESS  not-accessible
		STATUS  mandatory
		DESCRIPTION
		"Bridge parameters."
		::= { ubNVM 2 }

		UbBridgeParams ::= SEQUENCE {
			ubAgingTime
			INTEGER,
			ubPreForwardingTime
			INTEGER,
			ubAppleTalkSupport
			INTEGER
		}
		
	ubAgingTime OBJECT-TYPE
		SYNTAX	INTEGER
		ACCESS	read-write
		STATUS	mandatory
		DESCRIPTION
		"The timeout period in seconds for learning addresses
		on a segment before bridge will forward packets."
		::= { ubBridgeParams 1 }
		
	ubPreForwardingTime OBJECT-TYPE
		SYNTAX	INTEGER (0..300)
		ACCESS	read-write
		STATUS	mandatory
		DESCRIPTION
		"The timeout period in seconds for learning addresses
		on a segment before bridge will forward packets."
		::= { ubBridgeParams 2 }
		
	ubAppleTalkSupport OBJECT-TYPE
		SYNTAX INTEGER {
		phase2(1),
		phase1(2)
		}
		ACCESS read-write
		STATUS mandatory
DESCRIPTION ""
		::= { ubBridgeParams 3 }


	ubSystemParams OBJECT-TYPE
		SYNTAX  UbSystemParams
		ACCESS  not-accessible
		STATUS  mandatory
		DESCRIPTION
		"Software Versions"
		::= { ubNVM 3 }
		UbSystemParams ::= SEQUENCE {
			ubBroadcastPktLmt
			Counter,
			ubUnicastPktLmt
			Counter,
			ubQuickReset
			INTEGER,
			ubBasePromCode
			DisplayString,
			ubOpswPromCode
			DisplayString,
			ubDownloadedCode
			DisplayString
		}

	ubBroadcastPktLmt OBJECT-TYPE
		SYNTAX  Counter
		ACCESS  read-write
		STATUS  mandatory
		DESCRIPTION
		"Maximum number of broadcast packets that can be
		placed on the QE bus per second."
		::= { ubSystemParams 1 }
		
	ubUnicastPktLmt OBJECT-TYPE
		SYNTAX  Counter
		ACCESS  read-write
		STATUS  mandatory
		DESCRIPTION
		"Maximum number of unicast packets that can be
		placed on the QE bus per second."
		::= { ubSystemParams 2 } 
		
	ubQuickReset OBJECT-TYPE
		SYNTAX INTEGER {
		disabled(1),
		enabled(2)
		}
		ACCESS read-write
		STATUS mandatory
DESCRIPTION ""
		::= { ubSystemParams 3 }

	ubBasePromCode OBJECT-TYPE
		SYNTAX DisplayString (SIZE (0..255))
		ACCESS  read-only
		STATUS  mandatory
		DESCRIPTION
		"Code version number of the Base Prom (Prom 1)"
		::= { ubSystemParams 4 }

	ubOpswPromCode OBJECT-TYPE
		SYNTAX DisplayString (SIZE (0..255))
		ACCESS  read-only
		STATUS  mandatory
		DESCRIPTION
		"Code version number of the Operational Software
		Prom (Prom 2)"
		::= { ubSystemParams 5 }

	ubDownloadedCode OBJECT-TYPE
		SYNTAX DisplayString (SIZE (0..255))
		ACCESS  read-only
		STATUS  mandatory
		DESCRIPTION
		"Code version of the Downloaded code running."
		::= { ubSystemParams 6 }

		
-- 7.9 dot1d MIB Extensions     [UB]

ubdot1dExt	OBJECT IDENTIFIER ::= { ubInExt1 1 }
		
-- dot1dBase group Extensions

ubdot1dBaseExt	OBJECT IDENTIFIER ::= { ubdot1dExt 1 }
		
	ubdot1dAdminState OBJECT-TYPE
		SYNTAX	INTEGER {
		enabled(2),
		disabled(3)
		}
		ACCESS	read-write
		STATUS	mandatory
		 DESCRIPTION
		 "Administrative state of bridging.  If state 
		 is disabled, no bridging will be performed,
		 regardless of any filtering specified in the
		 protocol filter table or in the forwarding database
		 even if the administrative state of all routing protocols
		 is disabled"
		::= { ubdot1dBaseExt 1 }
		
		-- The Generic Bridge Port Table Extensions
	ubdot1dBasePortTable OBJECT-TYPE
		SYNTAX	SEQUENCE OF Ubdot1dBasePortEntry
		ACCESS	not-accessible
		STATUS	mandatory
		 DESCRIPTION
		 "Widening of 'standard' dot1dBasePort table
		 Entries are manipulated in conjunction with 
		 operations in the standard table."
		::= {ubdot1dBaseExt 2  }

	ubdot1dBasePortEntry OBJECT-TYPE
		SYNTAX	Ubdot1dBasePortEntry
		ACCESS	not-accessible
		STATUS	mandatory
		 DESCRIPTION
		 "A list of information for each port of the bridge."
		 REFERENCE
		 "P802.1d/D9, July 14, 1989: Section 6.4.2, 6.6.1"
		INDEX { ubdot1dBasePort }
		::= { ubdot1dBasePortTable 1 }

		Ubdot1dBasePortEntry ::= SEQUENCE {
			ubdot1dBasePort
			INTEGER,
			ubdot1dBasePortBlockedFrames 
			Counter
		}

	ubdot1dBasePort OBJECT-TYPE
		SYNTAX	INTEGER
		ACCESS	read-only
		STATUS	mandatory
		 DESCRIPTION
		 "The port number of the port for which this entry 
		 contains bridge management information."
		::= { ubdot1dBasePortEntry 1 }
		
		
	ubdot1dBasePortBlockedFrames OBJECT-TYPE
		SYNTAX	Counter
		ACCESS	read-only
		STATUS	mandatory
		 DESCRIPTION
		 "The number of frames discarded by this
		  port due to an adminstrative request to block 
		 frames of a particular protocol type(s)."
		::= { ubdot1dBasePortEntry 2 }
		
		-- The Protocol Filtering Table Database
		
	ubdot1dProtocolFilterTable OBJECT-TYPE
		SYNTAX	SEQUENCE OF Ubdot1dProtFiltEntry
		ACCESS	not-accessible
		STATUS	mandatory
		 DESCRIPTION
		 "A table containing filtering information configured 
		 into the bridge by (local or network) management 
		 specifying the set of ports to which frames received 
		 from specific ports and of  specific protocol types 
		 are allowed to be forwarded. The value of 
		 zero in this table as the port number from which frames 
		 with a specific destination address are received, is 
		 used to specify all ports for which there is no 
		 specific entry in this table for that particular 
		 protocol type. Entries are valid for unicast and 
		 for group/broadcast addresses."
		::= { ubdot1dExt 2}

	ubdot1dProtFiltEntry OBJECT-TYPE
		SYNTAX	Ubdot1dProtFiltEntry
		ACCESS	not-accessible
		STATUS	mandatory
		 DESCRIPTION
		 "Filtering information configured into the bridge by 
		 (local or network) management specifying the set of 
		 ports to which frames received from a specific port and 
		 of a particular protocol type are allowed 
		 to be forwarded."
		INDEX { ubdot1dProtFiltType, ubdot1dProtFiltReceivePort }
		::= { ubdot1dProtocolFilterTable 1 }

		Ubdot1dProtFiltEntry ::= SEQUENCE {
			ubdot1dProtFiltType
			INTEGER,
			ubdot1dProtFiltReceivePort
			INTEGER,
			ubdot1dProtFiltAllowedToGo
			INTEGER 
		}
		
	ubdot1dProtFiltType OBJECT-TYPE
		SYNTAX	 INTEGER {
		unknown(2)
		}
		ACCESS	read-write
		STATUS	mandatory
		 DESCRIPTION
		 "The protocol type in a frame to which this 
		 entry's filtering information applies."
		::= { ubdot1dProtFiltEntry 1 }

	ubdot1dProtFiltReceivePort OBJECT-TYPE
		SYNTAX	INTEGER
		ACCESS	read-write
		STATUS	mandatory
		 DESCRIPTION
		 "Either the value '0', or the port number of the port 
		 from which a frame must be received in order for this 
		 entry's filtering information to apply. A value of zero 
		 indicates that this entry applies on all ports of the 
		 bridge for which there is no other applicable entry."
		::= { ubdot1dProtFiltEntry 2 }

	ubdot1dProtFiltAllowedToGoTo OBJECT-TYPE
		SYNTAX	OCTET STRING
		ACCESS	read-write
		STATUS	mandatory
		 DESCRIPTION
		 "The set of ports to which frames received from a 
		 specific port with a specific protocol type, 
		 are allowed to be forwarded. Each octet within the 
		 value of this object specifies a set of eight ports, 
		 with the first octet specifying ports 1 through 8, the 
		 second octet specifying ports 9 through 16, etc. Within 
		 each octet, the most significant bit represents the 
		 lowest numbered port, and the least significant bit 
		 represents the highest numbered port. Thus, each port 
		 of the bridge is represented by a single bit within the 
		 value of this object. If that bit has a value of '1' 
		 then that port is included in the set of ports; the 
		 port is not included if its bit has a value of '0'. 
		 (Note that the setting of the bit corresponding to the 
		 port from which a frame is received is irrelevant.)"
		::= { ubdot1dProtFiltEntry 3 }
		END
