--
--      usr-definitions.mib - Common definitions to be used in all 
--                            CommWorks' MIB files.
--
--
-- Author:         Jim Halpin
--
-- +==========================================================================+
-- |                 CommWorks Corporation a 3COM Company
-- |                         Copyright (c)  2001
-- |
-- |    The information in this software is subject to change without  notice
-- |               and shall not be construed as a commitment by
-- |                            CommWorks Corporation.
-- |
-- +==========================================================================+

-- The enterprise for the Carrier Systems Group or CommWorks Corporation is 429.
-- This node has previously been called "usRobotics".

USR-DEFINITIONS-MIB DEFINITIONS ::= BEGIN

        IMPORTS
                enterprises             FROM RFC1155-SMI
                Integer32, Unsigned32               FROM SNMPv2-SMI
                TEXTUAL-CONVENTION      FROM SNMPv2-TC;



--      MIB-II (same prefix as MIB-I)
--      mib-2                    OBJECT IDENTIFIER ::= { mgmt 1 }
--      interfaces               OBJECT IDENTIFIER ::= { mib-2 2 }
--      transmission             OBJECT IDENTIFIER ::= { mib-2 10 }



--      DESCRIPTION OF THE enterprises.csg3Com BRANCH:
--     
--       + enterprises
--       |
--       + - - + usr (429)
--             |
--             + - - - +  usrSysOIDs  (2)
--             |       |
--             |       + - - - > chas17Slot          (1)
--             |       + - - - > chas7Slot           (2)
--             |       + - - - > wanHubAccessServer  (3)
--             |       + - - - > S/AloneAccessServer (4)
--             |       + - - - > netServer8-16       (5)
--             |       + - - - > modemPool16         (6)
--             |       + - - - > modemPool8          (7)
--             |       + - - - > chas17SlotHp        (8)
--             |       + - - - > chas17SlotClk       (9)
--             |       + - - - > netServerII8        (10)
--             |       + - - - > netServerII16       (11)
--             |       + - - - > lanLinkerBRI        (12)
--             |       + - - - > lanLinkerD56k       (13)
--             |       + - - - > netServerII8imdm    (14)
--             |       + - - - > netServerII16imdm   (15)
--             |       + - - - > pilgrimCore         (16)
--             |       + - - - > lanLinkerDSL        (17)
--             |       + - - - > lanLinkerDslCO      (18)
--             |       + - - - > usrHiPerArc         (19)
--             |       + - - - > positronRM          (20)  Access-Router 3000
--             |       + - - - > lanLinkerDualAnalog (21)
--             |       + - - - > DSLAMCoMux          (22)
--             |       + - - - > hiPerCableRouter    (23)
--             |       + - - - > dynatronRM          (24)  Access-Router 1000
--             |       + - - - > positronEM          (25)  EdgeServerPro 3000
--             |
--             |
--             + - - - +  usrExp      (3)
--             |
--             |
--             + - - - +  common      (4)
--             |       |
--             |       + - - - > usrConfig           (1)
--             |       + - - - > usruserMan          (2)
--             |       + - - - > roboExec            (3)
--             |       + - - - > usrIpx              (4)
--             |       + - - - > usrSnmp             (5)
--             |       + - - - > atcfgFwd            (6)
--             |       + - - - > atprivateFwd        (7)
--             |       + - - - > atcfgRtmp           (8) obsolete
--             |       + - - - > usrEventHandler     (9)
--             |       + - - - > usrCip              (10)
--             |       + - - - > usrPPP              (11)
--             |       + - - - > usrIp               (12)
--             |       + - - - > usrIpCfg            (13)
--             |       + - - - > usrBridge           (14)
--             |       + - - - > usrFR               (15)
--             |       + - - - > usrFilter           (16)
--             |       + - - - > usrDns              (17)
--             |       + - - - > usrTermProt         (18)
--             |       + - - - > usrIpRouting        (19)
--             |       + - - - > usrIpxCfg           (20)
--             |       + - - - > usrIsdnMib          (21)
--             |       + - - - > usrCli              (22)
--             |       + - - - > usrD56k             (23)
--             |       + - - - > usrTftp             (24)
--             |       + - - - > usrDialout          (25)
--             |       + - - - > usrAdsl             (26)
--             |       + - - - > usrDS1              (27)
--             |       + - - - > usrDS0              (28)
--             |       + - - - > usrStack            (29)  Stackables
--             |       + - - - > usrModem            (30)
--             |       + - - - > usrTopology         (31)  Stackables
--             |       + - - - > usrPN               (32)  Private Network
--             |       + - - - > usrPPTP             (33)
--             |       + - - - > usrNTP              (34)  obsolete
--             |       + - - - > usrSLIP             (35)
--             |       + - - - > usrPing             (36)  obsolete
--             |       + - - - > usrRemotePing       (37)
--             |       + - - - > usrGWCBSP           (38)
--             |       + - - - > usrRM               (39)  Positron-RM
--             |       + - - - > usrTraceRoute       (40)
--             |       + - - - > usrChassis          (41)
--             |       + - - - > usrCable            (42)
--             |       + - - - > usrDsx3             (43)  DS3/E3
--             |       + - - - > usrTraps            (44)  Stackables
--             |       + - - - > usrTcp              (45)
--             |       + - - - > usrIpoa             (46)
--             |       + - - - > usrAtm1483Pvc       (47)
--             |       + - - - > usrMdmTemplate      (48)
--             |       + - - - > usrAtmArp           (49)
--             |       + - - - > usrAtmCrossConnect  (50)
--             |       + - - - > usrAtm1577Pvc       (51)
--             |       + - - - > usrAtmCfg           (52)
--             |       + - - - > usrIgmp             (53)
--             |       + - - - > usrMPIP             (54)
--             |       + - - - > usrL2TP             (55)
--             |       + - - - > usrPptp             (56)
--             |       + - - - > usrTap              (57)
--             |       + - - - > usrGwcwan           (58)
--             |       + - - - > usrDhcp             (59)
--             |       + - - - > usrNat              (60)
--             |       + - - - > usrFcp              (61)
--             |       + - - - > usrNos              (62)
--             |       + - - - > usrOspf             (63)
--             |       + - - - > usrFRExt            (64)
--             |       + - - - > usrDvmrp            (66)  not implemented
--             |       + - - - > usrMulticast        (67)  not implemented
--             |       + - - - > usrTundisp          (68)
--             |       + - - - > usrPm               (69)
--             |       + - - - > usrVTP              (70)
--             |       + - - - > usrGre              (72)
--             |       + - - - > usrInverseARP       (73)   Frame Relay PTMP IP Networks
--             |       + - - - > usrRsh              (74)
--             |       + - - - > usrBetaSite         (76)
--             |       + - - - > usrSS7              (77)
--             |       + - - - > usripNat            (78)
--             |       + - - - > usrPPPoE            (79)
--             |       + - - - > usrIpSec            (80) 
--             |       + - - - > usrMIP              (82)   Mobile IP Home Agent MIB
--             |       + - - - > usrFA               (83)   Mobile IP Foreign Agent MIB
--             |       + - - - > usrVHA              (84)   3G PDSN R-P Interface MIB
--             |       + - - - > usrFCNI             (85)   3G FACN Interface MIB
--             |       + - - - > usrLDAP             (86)
--             |       + - - - > usrUniport          (87)
--             |       + - - - > usrOc3              (88)
--             |       + - - - > usrAPU              (89)
--             |       
--             |
--             + - - - +  usrProducts (6)
--                     |
--                     + - - - + usrPositron  (1)
--                     |       |
--                     |       + - - - > adm  (1)
--                     |       + - - - > em   (2)
--                     |
--                     |
--                     + - - - + usrDynatron  (2)
--                     |       |
--                     |       + - - - > drm  (1)
--                     |       + - - - > pem  (2)
--                     |       + - - - > mms  (3)
--		       |       + - - - > dynabri (4)
--                     |       | 
--                     |       + - - - + usrDynatronCommon (9)
--                     |               |
--                     |               + - - - > TVsetup   (1)
--                     |               + - - - > SDL       (2)
--                     |               + - - - > PSU       (3)
--                     |               + - - - > OTS       (4)
--                     |               + - - - > BulkDL    (5)
--                     |
--
--

        csg3Com      OBJECT IDENTIFIER ::= { enterprises 429 }


        usrSysOIDs               OBJECT IDENTIFIER ::= { csg3Com 2 }

        usrExp                   OBJECT IDENTIFIER ::= { csg3Com 3 }

        common                   OBJECT IDENTIFIER ::= { csg3Com 4 }

usrConfig OBJECT IDENTIFIER ::= { common 1 }   

   usrUserMan OBJECT IDENTIFIER ::= { common 2 }

   roboExec OBJECT IDENTIFIER ::= { common 3 }

   usrIpx OBJECT IDENTIFIER ::= { common 4 }

   usrSnmp OBJECT IDENTIFIER ::= { common 5 }

   -- AppleTalk Configuration tables
   atcfgFwd OBJECT IDENTIFIER ::= { common 6 }
   atprivateFwd OBJECT IDENTIFIER ::= { common 7 }
   --   atcfgRtmp OBJECT IDENTIFIER ::= { common 8 }

   usrEventHandler OBJECT IDENTIFIER ::= { common 9 }
   
   usrCip OBJECT IDENTIFIER ::= { common 10 }

   usrPPP OBJECT IDENTIFIER ::= { common 11 }

   usrIp OBJECT IDENTIFIER ::= { common 12 }

   usrIpCfg OBJECT IDENTIFIER ::= { common 13 }

   usrBridge OBJECT IDENTIFIER ::= { common 14 }

   usrFR OBJECT IDENTIFIER ::= { common 15 }

   usrFilter OBJECT IDENTIFIER ::= { common 16 }

   usrDns OBJECT IDENTIFIER ::= { common 17 }

   usrTermProt OBJECT IDENTIFIER ::= { common 18 }

   usrIpRouting OBJECT IDENTIFIER ::= { common 19 }

   usrIpxCfg OBJECT IDENTIFIER ::= { common 20 }

   usrIsdnMib OBJECT IDENTIFIER ::= { common 21 }

   usrCli OBJECT IDENTIFIER ::= { common 22 }

   usrD56k OBJECT IDENTIFIER ::= { common 23 }

   usrTftp OBJECT IDENTIFIER ::= { common 24 }

   usrDialout OBJECT IDENTIFIER ::= { common 25 }

   usrAdsl OBJECT IDENTIFIER ::= { common 26 }

   usrLLLed OBJECT IDENTIFIER ::= { common 27 }

   usrDhcp OBJECT IDENTIFIER ::= { common 28 }

   usrVatmMib OBJECT IDENTIFIER ::= { common 29 }

   usrLldaMib OBJECT IDENTIFIER ::= { common 30 }

   usrNat OBJECT IDENTIFIER ::= { common 31 }

   usrAdslf OBJECT IDENTIFIER ::= { common 32 }
   
   usrADI OBJECT IDENTIFIER ::= { common 33 }
  
   usrFtp OBJECT IDENTIFIER ::= { common 34 }

   usrHtml OBJECT IDENTIFIER ::= { common 35 }

   usrHdsl OBJECT IDENTIFIER ::= { common 36 }

   usrFR2 OBJECT IDENTIFIER ::= { common 37 }
   
   usrAdslc6x OBJECT IDENTIFIER ::= { common 38 }

   usrHdlc OBJECT IDENTIFIER ::= { common 39 }

   usrHub OBJECT IDENTIFIER ::= { common 40 }

   usrAlc OBJECT IDENTIFIER ::= { common 41 }
   usrDhcpClient OBJECT IDENTIFIER ::= { common 42 }
   usrIAA OBJECT IDENTIFIER ::= { common 43 }
   usrAccess	 OBJECT IDENTIFIER ::= { common 44 }
   
   
   DisplayString ::=  OCTET STRING

UsrDisplayString	::= DisplayString ( SIZE ( 0..255 ) )
UsrLongString	::= OCTET STRING ( SIZE ( 0..2500 ) )

   ProductID ::= OBJECT IDENTIFIER

   PhysAddress ::=    OCTET STRING

   InterfaceIndex ::= TEXTUAL-CONVENTION
       DISPLAY-HINT "d"
       STATUS       current
       DESCRIPTION
               "A unique value, greater than zero, for each interface
               or interface sub-layer in the managed system.  It is
               recommended that values are assigned contiguously
               starting from 1.  The value for each interface sub-
               layer must remain constant at least from one re-
               initialization of the entity's network management
               system to the next re-initialization."
       SYNTAX       Integer32

       SnmpAdminString ::= TEXTUAL-CONVENTION
            DISPLAY-HINT "255a"
            STATUS       current
            DESCRIPTION "An octet string containing administrative
                         information, preferably in human-readable form.
 
                         To facilitate internationalization, this
                         information is represented using the ISO/IEC
                         IS 10646-1 character set, encoded as an octet
                         string using the UTF-8 transformation format
                         described in [RFC2044].
 
                         Since additional code points are added by
                         amendments to the 10646 standard from time
                         to time, implementations must be prepared to
                         encounter any code point from 0x00000000 to
                         0x7fffffff.

                         The use of control codes should be avoided.
 
                         When it is necessary to represent a newline,
                         the control code sequence CR LF should be used.
 
                         The use of leading or trailing white space should
                         be avoided.
 
                         For code points not directly supported by user
                         interface hardware or software, an alternative
                         means of entry and display, such as hexadecimal,
                         may be provided.
 
                         For information encoded in 7-bit US-ASCII,
                         the UTF-8 encoding is identical to the
                         US-ASCII encoding.
 
                        Note that when this TC is used for an object that
                        is used or envisioned to be used as an index, then
                        a SIZE restriction must be specified so that the
						number of sub-identifiers for any object instance
                        does not exceed the limit of 128, as defined by
                        [RFC1905].
                           "
                SYNTAX       OCTET STRING (SIZE (0..255))


	UsrConfigStatus ::= INTEGER {	normal(1),
							save(2),
							saving(3),
							load(4),
                              	loading(5) }

   -- I'm not sure what this datatype will be. For now define it as an
   -- integer, but use the lexical convention to make it easy to change
   -- in the future.

Time1970	::= Unsigned32	 
Time1900	::= Unsigned32	 
UsrNetLogicalId	::= INTEGER ( -2147483648..2147483647 )	 
UsrUserName	::= UsrDisplayString ( 1..64 )	 
UsrFilterName	::= DisplayString ( SIZE ( 0..20 ) )	 
UsrPolicyfileName	::= DisplayString ( SIZE ( 0..20 ) )	 
UsrNetAddress	::= OCTET STRING ( SIZE ( 0..21 ) )	 
UsrSPI	::= Integer32	 
UsrSpecialU32	::= Unsigned32	
-- DISPLAY-HINT "x"  
UsrRegID	::= OCTET STRING ( SIZE ( 4 ) )	 
UsrSecretDisplay	::= UsrDisplayString ( 0..16 )	 
UsrAAADisplay	::= UsrDisplayString ( 0..20 )	 
UsrDisplayIntAsHex	::= Integer32



   -- Define all Pilgrim based SYSOIDs here.

   netServerII8 OBJECT IDENTIFIER ::= {usrSysOIDs 10 }

   netServerII16 OBJECT IDENTIFIER ::= {usrSysOIDs 11 }

   lanLinkerBRI OBJECT IDENTIFIER ::= {usrSysOIDs 12 }

   lanLinkerD56k OBJECT IDENTIFIER ::= {usrSysOIDs 13 }

   netServerII8imdm OBJECT IDENTIFIER ::= {usrSysOIDs 14 }

   netServerII16imdm OBJECT IDENTIFIER ::= {usrSysOIDs 15 }

   pilgrimCore OBJECT IDENTIFIER ::= {usrSysOIDs 16 }


        usrProducts              OBJECT IDENTIFIER ::= { csg3Com 6 }


        usrPositron              OBJECT IDENTIFIER ::= { usrProducts 1 }
        adm                      OBJECT IDENTIFIER ::= { usrPositron 1 }
        em                       OBJECT IDENTIFIER ::= { usrPositron 2 }

        usrDynatron              OBJECT IDENTIFIER ::= { usrProducts 2 }
        usrDrm                   OBJECT IDENTIFIER ::= { usrDynatron 1 }
        usrPem                   OBJECT IDENTIFIER ::= { usrDynatron 2 }
        usrMms                   OBJECT IDENTIFIER ::= { usrDynatron 3 }
        usrDynaBri               OBJECT IDENTIFIER ::= { usrDynatron 4 }


        usrDynatronCommon        OBJECT IDENTIFIER ::= { usrDynatron 9 }




   -- DEFINE ALL THE COMMON GROUPS HERE, TO PREVENT DUPLICATE NUMBER
   -- ASSIGNMENTS.

        usrConfig                OBJECT IDENTIFIER ::= { common 1 }   

        usrUserMan               OBJECT IDENTIFIER ::= { common 2 }
        roboExec                 OBJECT IDENTIFIER ::= { common 3 }

        usrIpx                   OBJECT IDENTIFIER ::= { common 4 }

        usrSnmp                  OBJECT IDENTIFIER ::= { common 5 }

   -- AppleTalk Configuration tables
        atcfgFwd                 OBJECT IDENTIFIER ::= { common 6 }
        atprivateFwd             OBJECT IDENTIFIER ::= { common 7 }
   --   atcfgRtmp                OBJECT IDENTIFIER ::= { common 8 }

        usrEventHandler          OBJECT IDENTIFIER ::= { common 9 }
   
        usrCip                   OBJECT IDENTIFIER ::= { common 10 }

        usrPPP                   OBJECT IDENTIFIER ::= { common 11 }

        usrIp                    OBJECT IDENTIFIER ::= { common 12 }

        usrIpCfg                 OBJECT IDENTIFIER ::= { common 13 }

        usrBridge                OBJECT IDENTIFIER ::= { common 14 }

        usrFR                    OBJECT IDENTIFIER ::= { common 15 }

        usrFilter                OBJECT IDENTIFIER ::= { common 16 }

        usrDns                   OBJECT IDENTIFIER ::= { common 17 }

        usrTermProt              OBJECT IDENTIFIER ::= { common 18 }

        usrIpRouting             OBJECT IDENTIFIER ::= { common 19 }

        usrIpxCfg                OBJECT IDENTIFIER ::= { common 20 }

        usrIsdnMib               OBJECT IDENTIFIER ::= { common 21 }

        usrCli                   OBJECT IDENTIFIER ::= { common 22 }

        usrD56k                  OBJECT IDENTIFIER ::= { common 23 }

        usrTftp                  OBJECT IDENTIFIER ::= { common 24 }

        usrDialout               OBJECT IDENTIFIER ::= { common 25 }

        usrAdsl                  OBJECT IDENTIFIER ::= { common 26 }

        usrDS1                   OBJECT IDENTIFIER ::= { common 27 }

        usrDS0                   OBJECT IDENTIFIER ::= { common 28 }

        usrStack                 OBJECT IDENTIFIER ::= { common 29 }

        usrModem                 OBJECT IDENTIFIER ::= { common 30 }

        usrTopology              OBJECT IDENTIFIER ::= { common 31 }

        usrPN                    OBJECT IDENTIFIER ::= { common 32 }

        usrPPTP                  OBJECT IDENTIFIER ::= { common 33 }

--      usrNTP                   OBJECT IDENTIFIER ::= { common 34 }

        usrSLIP                  OBJECT IDENTIFIER ::= { common 35 }

--      usrPing                  OBJECT IDENTIFIER ::= { common 36 }

        usrRemotePing            OBJECT IDENTIFIER ::= { common 37 }

        usrGWCBSP                OBJECT IDENTIFIER ::= { common 38 }

        usrRM                    OBJECT IDENTIFIER ::= { common 39 }

        usrTraceroute            OBJECT IDENTIFIER ::= { common 40 }

        usrChassis               OBJECT IDENTIFIER ::= { common 41 }

        usrCable                 OBJECT IDENTIFIER ::= { common 42 }

        usrDsx3  		         OBJECT IDENTIFIER ::= { common 43 }

        usrTraps                 OBJECT IDENTIFIER ::= { common 44 }

        usrTcp                   OBJECT IDENTIFIER ::= { common 45 }

        usrIpoa                  OBJECT IDENTIFIER ::= { common 46 }

        usrAtm1483Pvc            OBJECT IDENTIFIER ::= { common 47 }

        usrMdmTemplate           OBJECT IDENTIFIER ::= { common 48 }

        usrAtmArp                OBJECT IDENTIFIER ::= { common 49 }

        usrAtmCrossConnect       OBJECT IDENTIFIER ::= { common 50 }

        usrAtm1577Pvc            OBJECT IDENTIFIER ::= { common 51 }

        usrAtmCfg                OBJECT IDENTIFIER ::= { common 52 }

        usrIgmp                  OBJECT IDENTIFIER ::= { common 53 }

        usrMPIP                  OBJECT IDENTIFIER ::= { common 54 }

        usrL2TP                  OBJECT IDENTIFIER ::= { common 55 }

        usrPptp                  OBJECT IDENTIFIER ::= { common 56 }

        usrTap                   OBJECT IDENTIFIER ::= { common 57 } 

   	    usrGwcwan				 OBJECT IDENTIFIER ::= { common 58 }

   	    usrDhcp  	             OBJECT IDENTIFIER ::= { common 59 }

   	    usrNat                   OBJECT IDENTIFIER ::= { common 60 }

   	    usrFcp                   OBJECT IDENTIFIER ::= { common 61 }

   	    usrNos                   OBJECT IDENTIFIER ::= { common 62 }

        usrOspf                  OBJECT IDENTIFIER ::= { common 63 }

        usrFRExt                 OBJECT IDENTIFIER ::= { common 64 }

        usrTundisp               OBJECT IDENTIFIER ::= { common 68 }

        usrPm               	 OBJECT IDENTIFIER ::= { common 69 }

        usrVTP               	 OBJECT IDENTIFIER ::= { common 70 }

        usrGre               	 OBJECT IDENTIFIER ::= { common 72 }

        usrInverseARP            OBJECT IDENTIFIER ::= { common 73 }

	    usrRsh                   OBJECT IDENTIFIER ::= { common 74 }

	    usrBetaSite              OBJECT IDENTIFIER ::= { common 76 }

		usrSS7                   OBJECT IDENTIFIER ::= { common 77 }

        usripNat               	 OBJECT IDENTIFIER ::= { common 78 }

        usrPPPoE                 OBJECT IDENTIFIER ::= { common 79 }

		usrIpSec                 OBJECT IDENTIFIER ::= { common 80 }

		usrMIP                   OBJECT IDENTIFIER ::= { common 82 }

		usrFA                    OBJECT IDENTIFIER ::= { common 83 }

		usrVHA                   OBJECT IDENTIFIER ::= { common 84 }
		usrFCNI                  OBJECT IDENTIFIER ::= { common 85 }




--      DATA TYPES AND TEXTUAL CONVENTIONS.
--

--        DisplayString   ::= OCTET STRING

--        ProductID       ::=  OBJECT IDENTIFIER

--        PhysAddress     ::= OCTET STRING

/*        InterfaceIndex  ::= TEXTUAL-CONVENTION
          DISPLAY-HINT "d"
          STATUS       current
          DESCRIPTION
            "A unique value, greater than zero, for each interface
             or interface sub-layer in the managed system.  It is
             recommended that values are assigned contiguously
             starting from 1.  The value for each interface sub-
             layer must remain constant at least from one re-
             initialization of the entity's network management
             system to the next re-initialization."
          SYNTAX       Integer32*/

	   InterfaceIndexOrZero ::= InterfaceIndex

/*        UsrConfigStatus ::= INTEGER {
                                   normal(1),
                                   save(2),
                                   saving(3),
                                   load(4),
                                   loading(5)
                                   }*/


--      NOT SURE WHAT THIS DATATYPE WILL BE. 
--      FOR NOW,  DEFINE IT AS AN INTEGER, 
--      ... BUT USE THE LEXICAL CONVENTION TO MAKE IT EASY TO CHANGE IN THE FUTURE.
                                
--        UsrNetLogicalId ::= INTEGER(-2147483648..2147483647)
                                
--        UsrUserName     ::= DisplayString(SIZE (1..64))
                                
--        UsrFilterName   ::= DisplayString(SIZE (1..20))
 
	UsrPolicyfileName   ::= DisplayString(SIZE (1..20))

                                


--      DEFINE ALL PILGRIM BASED SYSOIDs HERE ....
                                
        chas17Slot               OBJECT IDENTIFIER ::= { usrSysOIDs 1 }
        chas7Slot                OBJECT IDENTIFIER ::= { usrSysOIDs 2 }
                                        
        wanHubAccessServer       OBJECT IDENTIFIER ::= { usrSysOIDs 3 }
                                        
        standAloneAccessServer   OBJECT IDENTIFIER ::= { usrSysOIDs 4 }
                                        
        netServer8-16            OBJECT IDENTIFIER ::= { usrSysOIDs 5 }
                                        
        modemPool16              OBJECT IDENTIFIER ::= { usrSysOIDs 6 }
        modemPool8               OBJECT IDENTIFIER ::= { usrSysOIDs 7 }
                                        
        chas17SlotHp             OBJECT IDENTIFIER ::= { usrSysOIDs 8 }
        chas17SlotClk            OBJECT IDENTIFIER ::= { usrSysOIDs 9 }
                                        
        netServerII8             OBJECT IDENTIFIER ::= { usrSysOIDs 10 }
        netServerII16            OBJECT IDENTIFIER ::= { usrSysOIDs 11 }
                                        
        lanLinkerBRI             OBJECT IDENTIFIER ::= { usrSysOIDs 12 }
        lanLinkerD56k            OBJECT IDENTIFIER ::= { usrSysOIDs 13 }
                                        
        netServerII8imdm         OBJECT IDENTIFIER ::= { usrSysOIDs 14 }
        netServerII16imdm        OBJECT IDENTIFIER ::= { usrSysOIDs 15 }
                                        
        pilgrimCore              OBJECT IDENTIFIER ::= { usrSysOIDs 16 }
                                        
        lanLinkerDSL             OBJECT IDENTIFIER ::= { usrSysOIDs 17 }
        lanLinkerDslCO           OBJECT IDENTIFIER ::= { usrSysOIDs 18 }
                                        
        usrHiPerArc              OBJECT IDENTIFIER ::= { usrSysOIDs 19 }
                                        
--      ACCESS-ROUTER  3000
        positronRM               OBJECT IDENTIFIER ::= { usrSysOIDs 20 }
                                        
        lanLinkerDualAnalogModem OBJECT IDENTIFIER ::= { usrSysOIDs 21 }
                                
        dSLAMCoMux               OBJECT IDENTIFIER ::= { usrSysOIDs 22 }
                                
        hiPerCableRouter         OBJECT IDENTIFIER ::= { usrSysOIDs 23 }
                                
--      ACCESS-ROUTER  1000
        dynatronRM               OBJECT IDENTIFIER ::= { usrSysOIDs 24 }
                                
--      EDGESERVER-PRO 3000
        positronEM               OBJECT IDENTIFIER ::= { usrSysOIDs 25 }
                                
END
