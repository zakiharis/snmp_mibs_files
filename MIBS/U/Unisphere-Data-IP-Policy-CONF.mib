-- *****************************************************************************
-- Unisphere-Data-IP-Policy-CONF
--
-- SNMP Agent Capabilities definitions for the IP Policy MIB.
--
-- Copyright (c) 2001 Unisphere Networks, Inc.  All rights reserved.
-- *****************************************************************************

Unisphere-Data-IP-Policy-CONF DEFINITIONS ::= BEGIN

IMPORTS
    MODULE-IDENTITY
        FROM SNMPv2-SMI
    AGENT-CAPABILITIES
        FROM SNMPv2-CONF
    usDataAgents
        FROM Unisphere-Data-Agents
    usdIpAccessListGroup,
    usdIpNamedAccessListGroup,
    usdIpAspAccessListGroup,
    usdIpAspAccessPolicy,
    usdIpAspAccessExpression,
    usdIpAspAccessRowStatus,
    usdIpPrefixListGroup,
    usdIpPrefixListPolicy,
    usdIpPrefixListGeValue,
    usdIpPrefixListLeValue,
    usdIpPrefixListDescription,
    usdIpPrefixListRowStatus,
    usdIpPrefixTreeGroup,
    usdIpPrefixTreePolicy,
    usdIpPrefixTreeDescription,
    usdIpPrefixTreeRowStatus,
    usdIpCommunityListGroup,
    usdIpCommunityListExtended,
    usdIpCommunityListPolicy,
    usdIpCommunityListExpression,
    usdIpCommunityListRowStatus,
    usdIpExtCommunityListGroup,
    usdIpExtCommunityListPolicy,
    usdIpExtCommunityListExpression,
    usdIpExtCommunityListRowStatus,
    usdIpRedistributeGroup,
    usdIpDynRedistributeState,
    usdIpDynRedistributeRowStatus,
    usdIpRedistributeState,
    usdIpRedistributeRouteMapName,
    usdIpRedistributeRowStatus,
    usdIpRouteMapGroup
        FROM Unisphere-Data-IP-POLICY-MIB;

usdIpPolicyAgent MODULE-IDENTITY
    LAST-UPDATED "200105012013Z"  -- 01-May-01 04:13 PM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the IP Policy component of the
        SNMP agent in the Unisphere Routing Switch family of products."
    -- Revision History
    REVISION    "200105012013Z"  -- 01-May-01 04:13 PM EDT  - RX 3.2
    DESCRIPTION
        "The initial release of this management information module."
    ::= { usDataAgents 22 }

usdIpPolicyAgentV1 AGENT-CAPABILITIES
    PRODUCT-RELEASE
        "Version 1 of the IP Policy component of the Unisphere Routing Switch
        SNMP agent.  This version of the IP Policy component was supported in
        the Unisphere RX 1.x system releases."
    STATUS      obsolete
    DESCRIPTION
        "The MIB supported by the SNMP agent for the IP Policy application in
        the Unisphere Routing Switch.  These capabilities became obsolete when
        support was added for the IP Named Access List."

    SUPPORTS    Unisphere-Data-IP-POLICY-MIB
        INCLUDES  { 
            usdIpAccessListGroup }

    ::= { usdIpPolicyAgent 1 }

usdIpPolicyAgentV2 AGENT-CAPABILITIES
    PRODUCT-RELEASE
        "Version 2 of the IP Policy component of the Unisphere Routing Switch
        SNMP agent.  This version of the IP Policy component was supported in
        the Unisphere RX 2.x system releases."
    STATUS      obsolete
    DESCRIPTION
        "The MIB supported by the SNMP agent for the IP Policy application in
        the Unisphere Routing Switch.  These capabilities became obsolete when
        support was added for the IP ASP Access List, the IP Prefix List, the IP
        Prefix Tree, the IP Community List, the IP Extended Community List, IP
        Dynamic Route Redistribution, and the IP Route Map."

    SUPPORTS    Unisphere-Data-IP-POLICY-MIB
        INCLUDES  { 
            usdIpAccessListGroup,
            usdIpNamedAccessListGroup }

    ::= { usdIpPolicyAgent 2 }

usdIpPolicyAgentV3 AGENT-CAPABILITIES
    PRODUCT-RELEASE
        "Version 3 of the IP Policy component of the Unisphere Routing Switch
        SNMP agent.  This version of the IP Policy component is supported in the
        Unisphere RX 3.0 and subsequent system releases."
    STATUS      current
    DESCRIPTION
        "The MIB supported by the SNMP agent for the IP Policy application in
        the Unisphere Routing Switch."

    SUPPORTS    Unisphere-Data-IP-POLICY-MIB
        INCLUDES  { 
            usdIpAccessListGroup,
            usdIpNamedAccessListGroup,
            usdIpAspAccessListGroup,
            usdIpPrefixListGroup,
            usdIpPrefixTreeGroup,
            usdIpCommunityListGroup,
            usdIpExtCommunityListGroup,
            usdIpRedistributeGroup,
            usdIpRouteMapGroup }
        VARIATION   usdIpAspAccessPolicy
            ACCESS      read-only
            DESCRIPTION
                "Entries in the usdIpAspAccessTable cannot be created/modified."
        VARIATION   usdIpAspAccessExpression
            ACCESS      read-only
            DESCRIPTION
                "Entries in the usdIpAspAccessTable cannot be created/modified."
        VARIATION   usdIpAspAccessRowStatus
            ACCESS      read-only
            DESCRIPTION
                "Entries in the usdIpAspAccessTable cannot be created/modified."
        VARIATION   usdIpPrefixListPolicy
            ACCESS      read-only
            DESCRIPTION
                "Entries in the usdIpPrefixListTable cannot be created or
                modified."
        VARIATION   usdIpPrefixListGeValue
            ACCESS      read-only
            DESCRIPTION
                "Entries in the usdIpPrefixListTable cannot be created or
                modified."
        VARIATION   usdIpPrefixListLeValue
            ACCESS      read-only
            DESCRIPTION
                "Entries in the usdIpPrefixListTable cannot be created or
                modified."
        VARIATION   usdIpPrefixListDescription
            ACCESS      read-only
            DESCRIPTION
                "Entries in the usdIpPrefixListTable cannot be created or
                modified."
        VARIATION   usdIpPrefixListRowStatus
            ACCESS      read-only
            DESCRIPTION
                "Entries in the usdIpPrefixListTable cannot be created or
                modified."
        VARIATION   usdIpPrefixTreePolicy
            ACCESS      read-only
            DESCRIPTION
                "Entries in the usdIpPrefixTreeTable cannot be created or
                modified."
        VARIATION   usdIpPrefixTreeDescription
            ACCESS      read-only
            DESCRIPTION
                "Entries in the usdIpPrefixTreeTable cannot be created or
                modified."
        VARIATION   usdIpPrefixTreeRowStatus
            ACCESS      read-only
            DESCRIPTION
                "Entries in the usdIpPrefixTreeTable cannot be created or
                modified."
        VARIATION   usdIpCommunityListExtended
            ACCESS      read-only
            DESCRIPTION
                "Entries in the usdIpCommunityListTable cannot be created or
                modified."
        VARIATION   usdIpCommunityListPolicy
            ACCESS      read-only
            DESCRIPTION
                "Entries in the usdIpCommunityListTable cannot be created or
                modified."
        VARIATION   usdIpCommunityListExpression
            ACCESS      read-only
            DESCRIPTION
                "Entries in the usdIpCommunityListTable cannot be created or
                modified."
        VARIATION   usdIpCommunityListRowStatus
            ACCESS      read-only
            DESCRIPTION
                "Entries in the usdIpCommunityListTable cannot be created or
                modified."
        VARIATION   usdIpExtCommunityListPolicy
            ACCESS      read-only
            DESCRIPTION
                "Entries in the usdIpExtCommunityListTable cannot be created or
                modified."
        VARIATION   usdIpExtCommunityListExpression
            ACCESS      read-only
            DESCRIPTION
                "Entries in the usdIpExtCommunityListTable cannot be created or
                modified."
        VARIATION   usdIpExtCommunityListRowStatus
            ACCESS      read-only
            DESCRIPTION
                "Entries in the usdIpExtCommunityListTable cannot be created or
                modified."
        VARIATION   usdIpDynRedistributeState
            ACCESS      read-only
            DESCRIPTION
                "Entries in the usdIpDynRedistributeTable cannot be created or
                modified."
        VARIATION   usdIpDynRedistributeRowStatus
            ACCESS      read-only
            DESCRIPTION
                "Entries in the usdIpDynRedistributeTable cannot be created or
                modified."
        VARIATION   usdIpRedistributeState
            ACCESS      read-only
            DESCRIPTION
                "Entries in the usdIpRedistributeTable cannot be created or
                modified."
        VARIATION   usdIpRedistributeRouteMapName
            ACCESS      read-only
            DESCRIPTION
                "Entries in the usdIpRedistributeTable cannot be created or
                modified."
        VARIATION   usdIpRedistributeRowStatus
            ACCESS      read-only
            DESCRIPTION
                "Entries in the usdIpRedistributeTable cannot be created or
                modified."

    ::= { usdIpPolicyAgent 3 }

END
