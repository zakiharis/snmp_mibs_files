-- *****************************************************************************
-- Unisphere-Data-IS-IS-CONF
--
-- SNMP Agent Capabilities definitions for the IS-IS MIB.
--
-- Copyright (c) 2001, 2002 Unisphere Networks, Inc.  All rights reserved.
-- *****************************************************************************

Unisphere-Data-IS-IS-CONF DEFINITIONS ::= BEGIN

IMPORTS
    MODULE-IDENTITY
        FROM SNMPv2-SMI
    AGENT-CAPABILITIES
        FROM SNMPv2-CONF
    usDataAgents
        FROM Unisphere-Data-Agents
    usdIsisSystemMgmtGroup, usdIsisCircuitMgmtGroup, usdIsisCircuitMgmtGroup2,
    usdIsisSystemMgmtGroup2
        FROM Unisphere-Data-ISIS-MIB;

usdIsisAgent MODULE-IDENTITY
    LAST-UPDATED "200204042037Z"  -- 04-Apr-02 03:37 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the intermediate system to
        intermediate system (IS-IS) protocol management component of the SNMP
        agent in the Unisphere Data Routing Switch family of products."
    -- Revision History
    REVISION    "200204042037Z"  -- 04-Apr-02 03:37 PM EST  - RX 4.0
    DESCRIPTION
        "Added MPLS support."
    REVISION    "200104241930Z"  -- 24-Apr-01 03:30 PM EDT  - RX 3.2
    DESCRIPTION
        "The initial release of this management information module."
    ::= { usDataAgents 23 }

usdIsisAgentV1 AGENT-CAPABILITIES
    PRODUCT-RELEASE
        "Version 1 of the IS-IS component of the Unisphere Routing Switch SNMP
        agent.  This version of the IS-IS component was supported in the
        Unisphere RX 2.x system releases."
    STATUS      obsolete
    DESCRIPTION
        "The MIB supported by the SNMP agent for the intermediate system to
        intermediate system (IS-IS) protocol application in the Unisphere
        Routing Switch.  These capabilities became obsolete when the
        usdIsisCircState object was added."
    SUPPORTS    Unisphere-Data-ISIS-MIB
        INCLUDES  {
            usdIsisSystemMgmtGroup,
            usdIsisCircuitMgmtGroup }
    ::= { usdIsisAgent 1 }

usdIsisAgentV2 AGENT-CAPABILITIES
    PRODUCT-RELEASE
        "Version 2 of the IS-IS component of the Unisphere Routing Switch SNMP
        agent.  This version of the IS-IS component was supported in the
        Unisphere RX 3.x system releases."
    STATUS      current
    DESCRIPTION
        "The MIB supported by the SNMP agent for the intermediate system to
        intermediate system (IS-IS) protocol application in the Unisphere
        Routing Switch.  These capabilities became obsolete when MPLS support
        was added."
    SUPPORTS    Unisphere-Data-ISIS-MIB
        INCLUDES  {
            usdIsisSystemMgmtGroup,
            usdIsisCircuitMgmtGroup2 }
    ::= { usdIsisAgent 2 }

usdIsisAgentV3 AGENT-CAPABILITIES
    PRODUCT-RELEASE
        "Version 3 of the IS-IS component of the Unisphere Routing Switch SNMP
        agent.  This version of the IS-IS component is supported in the
        Unisphere RX 4.0 and subsequent system releases."
    STATUS      current
    DESCRIPTION
        "The MIB supported by the SNMP agent for the intermediate system to
        intermediate system (IS-IS) protocol application in the Unisphere
        Routing Switch."
    SUPPORTS    Unisphere-Data-ISIS-MIB
        INCLUDES  {
            usdIsisSystemMgmtGroup2,
            usdIsisCircuitMgmtGroup2 }
    ::= { usdIsisAgent 3 }

END
