-- *****************************************************************************
-- Unisphere-Data-Router-CONF
--
-- SNMP Agent Capabilities definitions for the Router MIB.
--
-- Copyright (c) 2001, 2002 Unisphere Networks, Inc.  All rights reserved.
-- *****************************************************************************

Unisphere-Data-Router-CONF DEFINITIONS ::= BEGIN

IMPORTS
    MODULE-IDENTITY
        FROM SNMPv2-SMI
    AGENT-CAPABILITIES
        FROM SNMPv2-CONF
    usDataAgents
        FROM Unisphere-Data-Agents
    usdRouterGroup, usdRouterGroup2, usdRouterVrfGroup, usdRouterGroup3
        FROM Unisphere-Data-ROUTER-MIB;

usdRouterAgent MODULE-IDENTITY
    LAST-UPDATED "200205101906Z"  -- 10-May-02 03:06 PM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Router component of the SNMP
        agent in the Unisphere Routing Switch family of products."
    -- Revision History
    REVISION    "200205101906Z"  -- 10-May-02 03:06 PM EDT  - RX 4.0
    DESCRIPTION
        "Added router context name support."
    REVISION    "200103291817Z"  -- 29-Mar-01 01:17 PM EST  - RX 3.2
    DESCRIPTION
        "The initial release of this management information module."
    ::= { usDataAgents 37 }


usdRouterAgentV1  AGENT-CAPABILITIES
    PRODUCT-RELEASE
        "Version 1 of the Router component of the Unisphere Routing Switch SNMP
        agent.  This version of the Router component was supported in the
        Unisphere RX 1.3 and 2.x system releases."
    STATUS      obsolete
    DESCRIPTION
        "The MIB supported by the SNMP agent for the Router application in the
        Unisphere Routing Switch.  These capabilities became obsolete when
        virtual router forwarder (VFR) support was added."
    SUPPORTS    Unisphere-Data-ROUTER-MIB
        INCLUDES  {
            usdRouterGroup }
    ::= { usdRouterAgent 1 }

usdRouterAgentV2  AGENT-CAPABILITIES
    PRODUCT-RELEASE
        "Version 2 of the Router component of the Unisphere Routing Switch SNMP
        agent.  This version of the Router component was supported in the
        Unisphere RX 3.x system releases."
    STATUS      obsolete
    DESCRIPTION
        "The MIB supported by the SNMP agent for the Router application in the
        Unisphere Routing Switch.  These capabilities became obsolete when
        router context name support was added."
    SUPPORTS    Unisphere-Data-ROUTER-MIB
        INCLUDES  {
            usdRouterGroup2,
            usdRouterVrfGroup }
    ::= { usdRouterAgent 2 }

usdRouterAgentV3  AGENT-CAPABILITIES
    PRODUCT-RELEASE
        "Version 3 of the Router component of the Unisphere Routing Switch SNMP
        agent.  This version of the Router component is supported in the
        Unisphere RX 4.0 and subsequent system releases."
    STATUS      current
    DESCRIPTION
        "The MIB supported by the SNMP agent for the Router application in the
        Unisphere Routing Switch."
    SUPPORTS    Unisphere-Data-ROUTER-MIB
        INCLUDES  {
            usdRouterGroup3,
            usdRouterVrfGroup }
    ::= { usdRouterAgent 3 }

END
