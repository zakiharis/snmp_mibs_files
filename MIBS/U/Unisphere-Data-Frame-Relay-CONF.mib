-- *****************************************************************************
-- Unisphere-Data-Frame-Relay-CONF
--
-- SNMP Agent Capabilities definitions for the Frame Relay MIBs.
--
-- Copyright (c) 2001 Unisphere Networks, Inc.  All rights reserved.
-- *****************************************************************************

Unisphere-Data-Frame-Relay-CONF DEFINITIONS ::= BEGIN

IMPORTS
    MODULE-IDENTITY
        FROM SNMPv2-SMI
    AGENT-CAPABILITIES
        FROM SNMPv2-CONF
    usDataAgents
        FROM Unisphere-Data-Agents
    frPortGroup,
    frCircuitGroup
        FROM FRAME-RELAY-DTE-MIB
    usdFrGroup,
    usdFrSubIfGroup
        FROM Unisphere-Data-FRAME-RELAY-MIB;

usdFrameRelayAgent MODULE-IDENTITY
    LAST-UPDATED "200104181926Z"  -- 18-Apr-01 03:26 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Frame Relay component of the
        SNMP agent in the Unisphere Routing Switch family of products."
    -- Revision History
    REVISION    "200104181926Z"  -- 18-Apr-01 03:26 PM EDT  - RX 3.2
    DESCRIPTION
        "The initial release of this management information module."
    ::= { usDataAgents 17 }

usdFrameRelayAgentV1 AGENT-CAPABILITIES
    PRODUCT-RELEASE
        "Version 1 of the Frame Relay component of the Unisphere Routing Switch
        SNMP agent.  This version of the Frame Relay component is supported in
        the Unisphere RX 1.0 and subsequent system releases."
    STATUS      current
    DESCRIPTION
        "The MIBs supported by the SNMP agent for the Frame Relay application in
        the Unisphere Routing Switch."

    SUPPORTS        FRAME-RELAY-DTE-MIB
        INCLUDES  { frPortGroup,
                    frCircuitGroup }

    SUPPORTS        Unisphere-Data-FRAME-RELAY-MIB
        INCLUDES  { usdFrGroup,
                    usdFrSubIfGroup }

    ::= { usdFrameRelayAgent 1 }

END
