-- *****************************************************************
-- Unisphere-Data-IP-TUNNEL-MIB
--
-- Unisphere Networks Inc. Enterprise MIB
-- Extensions for IP Tunnel management
--
-- Copyright (c) 2001 Unisphere Networks, Inc.  All Rights Reserved.
-- *****************************************************************

Unisphere-Data-IP-TUNNEL-MIB DEFINITIONS ::= BEGIN

IMPORTS
    MODULE-IDENTITY,
    OBJECT-TYPE,
    IpAddress
        FROM SNMPv2-SMI

    InterfaceIndex
        FROM IF-MIB

    RowStatus,
    DisplayString,
    TruthValue
        FROM SNMPv2-TC

    MODULE-COMPLIANCE,
    OBJECT-GROUP
        FROM SNMPv2-CONF

    UsdNextIfIndex,
    UsdName
        FROM Unisphere-Data-TC

    usDataMibs
        FROM Unisphere-Data-MIBs;

usdIpTunnelMIB  MODULE-IDENTITY
    LAST-UPDATED "200107232057Z"  -- 23-Jul-01 04:57 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The IP Tunnel MIB for the Unisphere Networks Inc. enterprise."
    -- Revision History
    REVISION    "200107232057Z"  -- 23-Jul-01 04:57 PM EDT  - RX 3.2
    DESCRIPTION
        "Initial version of this MIB module."
    ::= { usDataMibs 51 }

-- ++++++++++++++++++++++++++++++++++++++++++++++++++++++++++++++++++++++
-- Textual conventions
-- ++++++++++++++++++++++++++++++++++++++++++++++++++++++++++++++++++++++

-- ++++++++++++++++++++++++++++++++++++++++++++++++++++++++++++++++++++++
-- Managed objects
-- ++++++++++++++++++++++++++++++++++++++++++++++++++++++++++++++++++++++

usdIpTunnelInterfaceObjects    OBJECT IDENTIFIER ::= { usdIpTunnelMIB 1 }


-- +++++++++++++++++++++++++++++++++++++++++++++++++++++++++++++++++++++++++++++
-- IP Tunnel Interface Objects 
-- +++++++++++++++++++++++++++++++++++++++++++++++++++++++++++++++++++++++++++++

--
-- IfIndex selection for creating IP tunnel interfaces
--

usdIpTunnelNextIfIndex OBJECT-TYPE
    SYNTAX      UsdNextIfIndex
    MAX-ACCESS  read-only
    STATUS      current
    DESCRIPTION
        "Coordinate ifIndex value allocation for entries in usdIpTunnelIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdIpTunnelInterfaceObjects 1 }

--
-- The IP Tunnel Interface Table
--

usdIpTunnelInterfaceTable OBJECT-TYPE
    SYNTAX      SEQUENCE OF UsdIpTunnelInterfaceEntry
    MAX-ACCESS  not-accessible
    STATUS      current
    DESCRIPTION
        "This table contains entries of IP Tunnel interfaces."
    ::= { usdIpTunnelInterfaceObjects 2 }

usdIpTunnelInterfaceEntry OBJECT-TYPE
    SYNTAX      UsdIpTunnelInterfaceEntry
    MAX-ACCESS  not-accessible
    STATUS      current
    DESCRIPTION
        "Each entry describes the characteristics of a single IP Tunnel
        interface.

        Creating/deleting entries in this table causes corresponding entries for
        be created/deleted in ifTable/ifXTable/usdIfTable"
    INDEX   { usdIpTunnelIfIndex }
    ::= { usdIpTunnelInterfaceTable 1 }

UsdIpTunnelInterfaceEntry ::= SEQUENCE {
    usdIpTunnelIfIndex
        InterfaceIndex,
    usdIpTunnelName
        DisplayString,
    usdIpTunnelMode
        INTEGER,
    usdIpTunnelVirtualRouter
        UsdName,
    usdIpTunnelChecksum
        TruthValue,
    usdIpTunnelMtu
        INTEGER,
    usdIpTunnelSource
        IpAddress,
    usdIpTunnelDestination
        IpAddress,
    usdIpTunnelRowStatus
        RowStatus
}

usdIpTunnelIfIndex OBJECT-TYPE
    SYNTAX      InterfaceIndex 
    MAX-ACCESS  not-accessible
    STATUS      current
    DESCRIPTION
        "The ifIndex of the IP tunnel interface.  When creating entries in this
        table, suitable values for this object are determined by reading
        usdIpTunnelNextIfIndex."
    ::= { usdIpTunnelInterfaceEntry 1 }

usdIpTunnelName OBJECT-TYPE
    SYNTAX      DisplayString(SIZE(0..80))
    MAX-ACCESS  read-create
    STATUS      current
    DESCRIPTION
        "The administratively assigned name for this IP Tunnel interface.
        Before configuring other tunnel attributes, IP tunnel has to be created
        with minimum attributes (tunnel name, mode and rowStatus)."
    ::= { usdIpTunnelInterfaceEntry 2 }

usdIpTunnelMode OBJECT-TYPE
    SYNTAX      INTEGER {
                    ipTunnelModeGre(0),
                    ipTunnelModeDvmrp(1)
                }
    MAX-ACCESS  read-create
    STATUS      current
    DESCRIPTION
        "The configured mode for this IP Tunnel interface."
    ::= { usdIpTunnelInterfaceEntry 3 }

usdIpTunnelVirtualRouter OBJECT-TYPE
    SYNTAX     UsdName
    MAX-ACCESS read-create
    STATUS     current
    DESCRIPTION
        "The transport virtual router associated with this IP tunnel interface.
        This object need not be set when creating row entries.  Note that the
        default when this object is not specified is the router associated with
        the agent acting on the management request."
    DEFVAL { "default" }
    ::= { usdIpTunnelInterfaceEntry 4 }

usdIpTunnelChecksum OBJECT-TYPE
    SYNTAX     TruthValue
    MAX-ACCESS read-create
    STATUS     current
    DESCRIPTION
        "The Tunnel checksum configuration for this entry.  Setting this object
        to true(1) will enabled end-to-end checksumming and will cause the
        system to drop packets with bad checksums received on this interface.
        Setting this object to false(2) will disable this feature."
    DEFVAL { false }
    ::= { usdIpTunnelInterfaceEntry 5 }

usdIpTunnelMtu OBJECT-TYPE
    SYNTAX     INTEGER (1024 ..10240)
    MAX-ACCESS read-create
    STATUS     current
    DESCRIPTION
        "The tunnel MTU."
    DEFVAL { 10240 }
    ::= { usdIpTunnelInterfaceEntry 6 }

usdIpTunnelDestination OBJECT-TYPE
    SYNTAX     IpAddress
    MAX-ACCESS read-create
    STATUS     current
    DESCRIPTION
        "The tunnel destination IP address."
    DEFVAL { 0 }
    ::= { usdIpTunnelInterfaceEntry 7 } 

usdIpTunnelSource OBJECT-TYPE
    SYNTAX     IpAddress
    MAX-ACCESS read-create
    STATUS     current
    DESCRIPTION
        "The tunnel source IP address."
    DEFVAL { 0 }
    ::= { usdIpTunnelInterfaceEntry 8 }

usdIpTunnelRowStatus OBJECT-TYPE
    SYNTAX     RowStatus
    MAX-ACCESS read-create
    STATUS     current
    DESCRIPTION
        "Controls creation/deletion of entries in this table according to the
        RowStatus textual convention, constrained to support the following
        values only:

            createAndGo
            destroy

        To create an entry in this table, the following entry objects MUST be
        explicitly configured:

            usdIpTunnelIfRowStatus
            usdIpTunnelName
            usdIpTunnelMode

        In addition, when creating an entry the following conditions must hold:

            A value for usdIpTunnelIfIndex must have been determined previously,
            typically by reading usdIpTunnelNextIfIndex.

        Once created, the following objects may not be modified:

            usdIpTunnelName
            usdIpTunnelMode
            usdIpTunnelVirtualRouter

        A corresponding entry in ifTable/ifXTable/usdIfTable is created/destroyed
        as a result of creating/destroying an entry in this table."
    ::= { usdIpTunnelInterfaceEntry 9 }

-- ++++++++++++++++++++++++++++++++++++++++++++++++++++++++++++++++++++++
-- Conformance information
-- ++++++++++++++++++++++++++++++++++++++++++++++++++++++++++++++++++++++

usdIpTunnelConformance     OBJECT IDENTIFIER ::= { usdIpTunnelMIB 2 }
usdIpTunnelCompliances     OBJECT IDENTIFIER ::= { usdIpTunnelConformance 1 }
usdIpTunnelGroups          OBJECT IDENTIFIER ::= { usdIpTunnelConformance 2 }

-- compliance statements

usdIpTunnnelCompliance MODULE-COMPLIANCE
    STATUS  current
    DESCRIPTION
        "The compliance statement for entities that implement the Unisphere IP
        Tunnel MIB."
    MODULE  -- this module
        MANDATORY-GROUPS {
            usdIpTunnelInterfaceGroup }
    ::= { usdIpTunnelCompliances 1 }

-- units of conformance

usdIpTunnelInterfaceGroup OBJECT-GROUP
    OBJECTS {
            usdIpTunnelNextIfIndex,
            usdIpTunnelName,
            usdIpTunnelMode,
            usdIpTunnelVirtualRouter,
            usdIpTunnelChecksum,
            usdIpTunnelMtu,
            usdIpTunnelSource,
            usdIpTunnelDestination,
            usdIpTunnelRowStatus
    }
    STATUS  current
    DESCRIPTION
        "A collection of objects for managing IP Tunnel capabilities in a
        Unisphere product."
    ::= { usdIpTunnelGroups 1 }

END
