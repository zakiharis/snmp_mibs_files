-- *****************************************************************************
-- Unisphere-Data-DNS-CONF
--
-- SNMP Agent Capabilities definitions for the DNS MIB.
--
-- Copyright (c) 2001 Unisphere Networks, Inc.  All rights reserved.
-- *****************************************************************************

Unisphere-Data-DNS-CONF DEFINITIONS ::= BEGIN

IMPORTS
    MODULE-IDENTITY
        FROM SNMPv2-SMI
    AGENT-CAPABILITIES
        FROM SNMPv2-CONF
    usDataAgents
        FROM Unisphere-Data-Agents
    usdDnsEnableGroup,
    usdDnsServerListGroup,
    usdDnsLocalDomainNameListGroup
        FROM Unisphere-Data-DNS-MIB;

usdDnsAgent MODULE-IDENTITY
    LAST-UPDATED "200103272300Z"  -- 27-Mar-01 06:00 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the DNS component of the SNMP
        agent in the Unisphere Routing Switch family of products."
    -- Revision History
    REVISION    "200103272300Z"  -- 27-Mar-01 06:00 PM EST  - RX 3.2
    DESCRIPTION
        "The initial release of this management information module."
    ::= { usDataAgents 9 }

usdDnsAgentV1 AGENT-CAPABILITIES
    PRODUCT-RELEASE
        "Version 1 of the DNS component of the Unisphere Routing Switch SNMP
        agent.  This version of the DNS component is supported in the Unisphere
        RX 3.0 and subsequent system releases."
    STATUS      current
    DESCRIPTION
        "The MIB supported by the SNMP agent for the DNS application in the
        Unisphere Routing Switch."

    SUPPORTS        Unisphere-Data-DNS-MIB
        INCLUDES  { usdDnsEnableGroup,
                    usdDnsServerListGroup,
                    usdDnsLocalDomainNameListGroup }

    ::= { usdDnsAgent 1 }

END
