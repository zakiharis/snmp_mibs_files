-- *****************************************************************************
-- Unisphere-Data-PPPOE-PROFILE-MIB
--
-- Juniper Networks Enterprise MIB
--   Point-to-Point Protocol over Ethernet (PPPoE) Profile MIB
--
-- Copyright (c) 2001, 2002 Unisphere Networks, Inc.
-- Copyright (c) 2002 Juniper Networks, Inc.
--   All Rights Reserved.
-- *****************************************************************************

Unisphere-Data-PPPOE-PROFILE-MIB DEFINITIONS ::= BEGIN

IMPORTS
    MODULE-IDENTITY, OBJECT-TYPE, Integer32, Unsigned32
        FROM SNMPv2-SMI
    DisplayString
        FROM SNMPv2-TC
    MODULE-COMPLIANCE, OBJECT-GROUP
        FROM SNMPv2-CONF
    usDataMibs
        FROM Unisphere-Data-MIBs
    UsdSetMap, UsdEnable
        FROM Unisphere-Data-TC;

usdPppoeProfileMIB  MODULE-IDENTITY
    LAST-UPDATED "200208152034Z"  -- 15-Aug-02 04:34 PM EDT
    ORGANIZATION "Juniper Networks, Inc."
    CONTACT-INFO
        "       Juniper Networks, Inc.
        Postal: 10 Technology Park Drive
                Westford, MA  01886
                USA
        Tel:    +1 978 589 5800
        Email:  mib@UnisphereNetworks.com"
    DESCRIPTION
        "The point-to-point protocol over Ethernet (PPPoE) profile MIB for the
        Juniper enterprise."
    -- Revision History
    REVISION    "200208152034Z"  -- 15-Aug-02 04:34 PM EDT  - RX 4.0
    DESCRIPTION
        "Added PADI flag and packet trace support."
    REVISION    "200208151907Z"  -- 15-Aug-02 03:07 PM EDT  - RX 3.2
    DESCRIPTION
        "Added duplicate MAC address indicator and AC-NAME tag objects."
    REVISION    "200103211832Z"  -- 21-Mar-01 01:32 PM EST  - RX 3.0
    DESCRIPTION
        "Initial version of this MIB module."
    ::= { usDataMibs 46 }


-- +++++++++++++++++++++++++++++++++++++++++++++++++++++++++++++++++++++++++++++
-- Managed objects
-- +++++++++++++++++++++++++++++++++++++++++++++++++++++++++++++++++++++++++++++
usdPppoeProfileObjects     OBJECT IDENTIFIER ::= { usdPppoeProfileMIB 1 }
usdPppoeProfile            OBJECT IDENTIFIER ::= { usdPppoeProfileObjects 1 }

--
-- This MIB defines configuration profile structure for PPPoE interfaces.
-- The creation/deletion of profiles and mapping of profile names to profile
-- indices is coordinated in the Unisphere-Data-PROFILE-MIB.
--

--
-- The PPPoE Profile Table
--
usdPppoeProfileTable  OBJECT-TYPE
    SYNTAX      SEQUENCE OF UsdPppoeProfileEntry
    MAX-ACCESS  not-accessible
    STATUS      current
    DESCRIPTION
        "This table contains profiles for configuring PPPoE interfaces/sessions.

        Entries in this table are created/deleted as a side-effect of
        corresponding operations to the usdProfileNameTable in the
        Unisphere-Data-PROFILE-MIB."
    ::= { usdPppoeProfile 1 }

usdPppoeProfileEntry  OBJECT-TYPE
    SYNTAX      UsdPppoeProfileEntry
    MAX-ACCESS  not-accessible
    STATUS      current
    DESCRIPTION
        "A profile describing configuration of a PPPoE interface and its
        subinterfaces (sessions)."
    INDEX     { usdPppoeProfileId }
    ::= { usdPppoeProfileTable 1 }

UsdPppoeProfileEntry ::= SEQUENCE {
    usdPppoeProfileId               Unsigned32,
    usdPppoeProfileSetMap           UsdSetMap,
    usdPppoeProfileMaxNumSessions   Integer32,
    usdPppoeProfileSubMotm          DisplayString,
    usdPppoeProfileSubUrl           DisplayString,
    usdPppoeProfileDupProtect       UsdEnable,
    usdPppoeProfileAcName           DisplayString,
    usdPppoeProfilePadiFlag         UsdEnable,
    usdPppoeProfilePacketTrace      UsdEnable }

usdPppoeProfileId  OBJECT-TYPE
    SYNTAX      Unsigned32
    MAX-ACCESS  not-accessible
    STATUS      current
    DESCRIPTION
        "The integer identifier associated with this profile.  A value for this
        identifier is determined by locating or creating a profile name in the
        usdProfileNameTable."
    ::= { usdPppoeProfileEntry 1 }

usdPppoeProfileSetMap  OBJECT-TYPE
    SYNTAX      UsdSetMap
    MAX-ACCESS  read-write
    STATUS      current
    DESCRIPTION
        "A bitmap representing which objects in this entry have been explicitly
        configured.  See the definition of the UsdSetMap TEXTUAL-CONVENTION for
        details of use.

        The INDEX object(s) and this object are excluded from representation
        (i.e. their bits are never set).

        When a SET request does not explicitly configure UsdSetMap, bits in
        UsdSetMap are set as a side-effect of configuring other profile
        attributes in the same entry.

        If, however, a SET request explicitly configures UsdSetMap, the
        explicitly configured value overrides 1) any previous bit settings, and
        2) any simultaneous 'side-effect' settings that would otherwise occur.

        Once set, bits can only be cleared by explicitly configuring UsdSetMap."
    ::= { usdPppoeProfileEntry 2 }


--
-- PPPoE main interface parameters
--
usdPppoeProfileMaxNumSessions  OBJECT-TYPE
    SYNTAX      Integer32 (0..65535)
    MAX-ACCESS  read-write
    STATUS      current
    DESCRIPTION
        "The maximum number of PPPoE sessions (subinterfaces) that can be
        configured on the main PPPoE interface created using this profile.  A
        value of zero indicates no bound is configured."
    DEFVAL    { 0 }
    ::= { usdPppoeProfileEntry 3 }


--
-- Other major parameters follow the sub interface parameters
--
--
-- PPPoE subinterface parameters
--
usdPppoeProfileSubMotm  OBJECT-TYPE
    SYNTAX      DisplayString (SIZE(0..127))
    MAX-ACCESS  read-write
    STATUS      current
    DESCRIPTION
        "A message to send via a PADM on the sub-interface when this profile is
        applied to the IP interface above this PPPoE sub- interface.  A client
        may choose to display this message to the user."
    ::= { usdPppoeProfileEntry 4 }

usdPppoeProfileSubUrl  OBJECT-TYPE
    SYNTAX      DisplayString (SIZE(0..127))
    MAX-ACCESS  read-write
    STATUS      current
    DESCRIPTION
        "A URL to be sent via a PADM on the sub-interface when this profile is
        applied to the IP interface above this PPPoE sub-interface.  The string
        entered here can have several substitutions applied:
                %D   is replaced with the profile name
                %d   is replaced with the domain name
                %u   is replaced with the user name
                %U   is replaced with the user/domain name together
                %%   is replaced with the % character

        The resulting string must not be greater than 127 octets long.  The
        client may use this URL as the initial web-page for the user."
    ::= { usdPppoeProfileEntry 5 }

usdPppoeProfileDupProtect  OBJECT-TYPE
    SYNTAX      UsdEnable
    MAX-ACCESS  read-write
    STATUS      current
    DESCRIPTION
        "Flag to control whether duplicate MAC addresses are allowed"
    DEFVAL    { disable }
    ::= { usdPppoeProfileEntry 6 }

usdPppoeProfileAcName  OBJECT-TYPE
    SYNTAX      DisplayString (SIZE(0..64))
    MAX-ACCESS  read-write
    STATUS      current
    DESCRIPTION
        "The name to use for the AC-NAME tag that is sent in any PADO that is
        sent on this interface."
    ::= { usdPppoeProfileEntry 7 }

usdPppoeProfilePadiFlag  OBJECT-TYPE
    SYNTAX      UsdEnable
    MAX-ACCESS  read-write
    STATUS      current
    DESCRIPTION
        "The PPPoE major interface parameter PADI flag controls whether to
        always repsond to a PADI with a PADO regardless of the ability to create
        the session and allow the session establish phase to resolve it."
    DEFVAL    { disable }
    ::= { usdPppoeProfileEntry 8 }

usdPppoeProfilePacketTrace  OBJECT-TYPE
    SYNTAX      UsdEnable
    MAX-ACCESS  read-write
    STATUS      current
    DESCRIPTION
        "The PPPoE major interface parameter packet tracing flag controls
        whether packet tracing is enable or not."
    DEFVAL    { disable }
    ::= { usdPppoeProfileEntry 9 }


-- +++++++++++++++++++++++++++++++++++++++++++++++++++++++++++++++++++++++++++++
-- Notifications
-- +++++++++++++++++++++++++++++++++++++++++++++++++++++++++++++++++++++++++++++
-- No notifications are defined in this MIB.


-- +++++++++++++++++++++++++++++++++++++++++++++++++++++++++++++++++++++++++++++
-- Conformance information
-- +++++++++++++++++++++++++++++++++++++++++++++++++++++++++++++++++++++++++++++
usdPppoeProfileConformance OBJECT IDENTIFIER ::= { usdPppoeProfileMIB 4 }
usdPppoeProfileCompliances OBJECT IDENTIFIER ::= { usdPppoeProfileConformance 1 }
usdPppoeProfileGroups      OBJECT IDENTIFIER ::= { usdPppoeProfileConformance 2 }

--
-- compliance statements
--
usdPppoeProfileCompliance MODULE-COMPLIANCE
    STATUS      obsolete
    DESCRIPTION
        "Obsolete compliance statement for entities which implement the
        Juniper PPPoE Profile MIB.  This statement became obsolete when the
        duplicate MAC address indicator and AC-NAME tag were added."
    MODULE   -- this module
        MANDATORY-GROUPS {
            usdPppoeProfileGroup }
    ::= { usdPppoeProfileCompliances 1 }                               -- RX 3.0

usdPppoeCompliance2  MODULE-COMPLIANCE
    STATUS  obsolete
    DESCRIPTION
        "Obsolete compliance statement for entities which implement the
        Juniper PPPoE profile MIB.  This statement became obsolete when PADI
        flag, AC-name and packet trace objects were added."
    MODULE   -- this module
        MANDATORY-GROUPS {
            usdPppoeProfileGroup2 }
    ::= { usdPppoeProfileCompliances 2 }                               -- RX 3.2

usdPppoeCompliance3  MODULE-COMPLIANCE
    STATUS      current
    DESCRIPTION
        "The compliance statement for entities which implement the Juniper PPPoE
        Profile MIB."
    MODULE   -- this module
        MANDATORY-GROUPS {
            usdPppoeProfileGroup3 }
    ::= { usdPppoeProfileCompliances 3 }                               -- RX 4.0


--
-- units of conformance
--
usdPppoeProfileGroup  OBJECT-GROUP
    OBJECTS {
        usdPppoeProfileSetMap,

        usdPppoeProfileMaxNumSessions,

        usdPppoeProfileSubMotm,
        usdPppoeProfileSubUrl }
    STATUS      obsolete
    DESCRIPTION
        "Obsolete collection of objects providing management of profile
        functionality for PPPoE interfaces in a Juniper product.  This group
        became obsolete when the duplicate MAC address indicator and AC-NAME tag
        objects were added."
    ::= { usdPppoeProfileGroups 1 }

usdPppoeProfileGroup2  OBJECT-GROUP
    OBJECTS {
        usdPppoeProfileSetMap,

        usdPppoeProfileMaxNumSessions,

        usdPppoeProfileSubMotm,
        usdPppoeProfileSubUrl,
        usdPppoeProfileDupProtect,
        usdPppoeProfileAcName }
    STATUS      obsolete
    DESCRIPTION
        "Obsolete collection of objects providing management of profile
        functionality for PPPOE interfaces in a Unisphere product.  This group
        became obsolete when PADI flag, AC-name and packet trace objects were
        added."
    ::= { usdPppoeProfileGroups 2 }

usdPppoeProfileGroup3 OBJECT-GROUP
    OBJECTS {
        usdPppoeProfileSetMap,

        usdPppoeProfileMaxNumSessions,

        usdPppoeProfileSubMotm,
        usdPppoeProfileSubUrl,
        usdPppoeProfileDupProtect,
        usdPppoeProfileAcName,
        usdPppoeProfilePadiFlag,
        usdPppoeProfilePacketTrace }
    STATUS      current
    DESCRIPTION
        "A collection of objects providing management of profile functionality
        for PPPOE interfaces in a Unisphere product."
    ::= { usdPppoeProfileGroups 3 }

END
