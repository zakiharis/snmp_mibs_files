-- *****************************************************************
-- Unisphere-Data-PROFILE-MIB
--
-- Unisphere Networks Inc. Enterprise MIB
-- Profile MIB
--
-- Copyright (c) 1999 Redstone Communications, Inc.
-- Copyright (c) 1999, 2002 Unisphere Networks, Inc.
-- All Rights Reserved.
-- *****************************************************************

Unisphere-Data-PROFILE-MIB DEFINITIONS ::= BEGIN

IMPORTS
    MODULE-IDENTITY, 
    OBJECT-TYPE,
    Unsigned32
        FROM SNMPv2-SMI

    TEXTUAL-CONVENTION,
    DisplayString,
    RowStatus
        FROM SNMPv2-TC

    MODULE-COMPLIANCE, 
    OBJECT-GROUP  
        FROM SNMPv2-CONF

    InterfaceIndex
        FROM IF-MIB

    usDataMibs
        FROM Unisphere-Data-MIBs;


usdProfileMIB MODULE-IDENTITY
    LAST-UPDATED "200211192047Z"  -- 19-Nov-02 03:47 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Profile MIB for the Unisphere Networks Inc. enterprise."
    -- Revision History
    REVISION    "200211192047Z"  -- 19-Nov-02 03:47 PM EST  - RX 4.0.2
    DESCRIPTION
        "Added bridgedEthernet(19) to UsdProfileIfEncaps TEXTUAL-CONVENTION."
    REVISION    "200104041250Z"  -- 04-Apr-01 08:50 AM EDT  - RX 3.0
    DESCRIPTION
        "Added ppp(1), pppoe(17) and any(127) to UsdProfileIfEncaps
        TEXTUAL-CONVENTION."
    REVISION    "200004200000Z"  -- 20-Apr-00               - RX 2.0
    DESCRIPTION
        "Added usdProfAssignIfTable, usdProfToIfMapTable to configure and report
        assignments of profiles to interface/encapsulation pairs."
    REVISION      "9906010000Z"  --  1-Jun-99               - RX 1.1
    DESCRIPTION
        "Initial version of this MIB module."
    ::= { usDataMibs 25 }


-- ++++++++++++++++++++++++++++++++++++++++++++++++++++++++++++++++++++++
-- Textual conventions
-- ++++++++++++++++++++++++++++++++++++++++++++++++++++++++++++++++++++++

UsdProfileIfEncaps ::= TEXTUAL-CONVENTION
    STATUS      current
    DESCRIPTION
        "Encapsulated protocol type.  The 'any' value is a wildcard value.  The
        DESCRIPTION clause for an object having this syntax must describe how
        the 'any' value applies, if at all."
    SYNTAX      INTEGER {
                    ip(0),
                    ppp(1),
                    pppoe(17),
                    bridgedEthernet(19),
                    any(127)
                }


-- ++++++++++++++++++++++++++++++++++++++++++++++++++++++++++++++++++++++
-- Managed object groups
-- ++++++++++++++++++++++++++++++++++++++++++++++++++++++++++++++++++++++

usdProfileObjects                OBJECT IDENTIFIER ::= {usdProfileMIB 1}

-- Functional groups

usdProfileName                   OBJECT IDENTIFIER ::= {usdProfileObjects 1}
usdProfileAssign                 OBJECT IDENTIFIER ::= {usdProfileObjects 2}

-- ++++++++++++++++++++++++++++++++++++++++++++++++++++++++++++++++++++++
-- Managed objects for Profile Names
-- ++++++++++++++++++++++++++++++++++++++++++++++++++++++++++++++++++++++

usdProfileNameTable OBJECT-TYPE
    SYNTAX      SEQUENCE OF UsdProfileNameEntry
    MAX-ACCESS  not-accessible
    STATUS      current
    DESCRIPTION
        "The entries in this table provide mappings of configuration profile
        names to local integer identifiers for those profiles.  These integers
        are used as indexes into other MIB tables containing profile
        configuration parameters associated with the same profile name."
    ::= { usdProfileName 1 }

usdProfileNameEntry OBJECT-TYPE
    SYNTAX      UsdProfileNameEntry
    MAX-ACCESS  not-accessible
    STATUS      current
    DESCRIPTION
        "A mapping of a profile name to an integer identifier for that name."
    INDEX { IMPLIED usdProfileNameName }
    ::= { usdProfileNameTable 1 }

UsdProfileNameEntry ::= SEQUENCE {
    usdProfileNameName               DisplayString,
    usdProfileNameRowStatus          RowStatus,
    usdProfileNameId                 Unsigned32
}

usdProfileNameName OBJECT-TYPE
    SYNTAX      DisplayString(SIZE(1..80))
    MAX-ACCESS  read-only
    STATUS      current
    DESCRIPTION
        "The profile name uniquely identifying this entry."
    ::= { usdProfileNameEntry 1 }

usdProfileNameRowStatus OBJECT-TYPE
    SYNTAX      RowStatus
    MAX-ACCESS  read-create
    STATUS      current
    DESCRIPTION
        "Controls creation/deletion of entries in this table.
        Only the values 'createAndGo' and 'destroy' may be SET."
    ::= { usdProfileNameEntry 2 }

usdProfileNameId OBJECT-TYPE
    SYNTAX      Unsigned32
    MAX-ACCESS  read-only
    STATUS      current
    DESCRIPTION
        "The integer identifier associated with this profile name.

        This value of this identifier is assigned by the device when 
        an entry in this table is created."
    ::= { usdProfileNameEntry 3 }


usdProfileIdTable OBJECT-TYPE
    SYNTAX      SEQUENCE OF UsdProfileIdEntry
    MAX-ACCESS  not-accessible
    STATUS      current
    DESCRIPTION
        "Provides inverse mapping of profile IDs to profile names."
    ::= { usdProfileName 2 }

usdProfileIdEntry OBJECT-TYPE
    SYNTAX      UsdProfileIdEntry
    MAX-ACCESS  not-accessible
    STATUS      current
    DESCRIPTION
        "A mapping of an integer identifier to a profile name."
    INDEX { usdProfileIdId }
    ::= { usdProfileIdTable 1 }

UsdProfileIdEntry ::= SEQUENCE {
    usdProfileIdId                  Unsigned32,
    usdProfileIdName                DisplayString
}

usdProfileIdId OBJECT-TYPE
    SYNTAX      Unsigned32
    MAX-ACCESS  not-accessible
    STATUS      current
    DESCRIPTION
        "The integer identifier associated with this profile name."
    ::= { usdProfileIdEntry 1 }

usdProfileIdName OBJECT-TYPE
    SYNTAX      DisplayString(SIZE(1..80))
    MAX-ACCESS  read-only
    STATUS      current
    DESCRIPTION
        "The profile name having the associated identifier."
    ::= { usdProfileIdEntry 2 }


-- ++++++++++++++++++++++++++++++++++++++++++++++++++++++++++++++++++++++
-- Managed objects for Profile Assignments
-- ++++++++++++++++++++++++++++++++++++++++++++++++++++++++++++++++++++++

usdProfAssignIf      OBJECT IDENTIFIER ::= { usdProfileAssign 1 }

--
-- Assign profile to interface/encapsulation pair.
--
usdProfAssignIfTable OBJECT-TYPE
    SYNTAX      SEQUENCE OF UsdProfAssignIfEntry
    MAX-ACCESS  not-accessible
    STATUS      current
    DESCRIPTION
        "Table providing profile assignment to interface/encapsulation pair.

        The entries in this table specify which profile to use when
        creating and configuring a dynamic interface (whose type
        is identified by the encapsulation) above a specified interface."
    ::= { usdProfAssignIf 1 }

usdProfAssignIfEntry OBJECT-TYPE
    SYNTAX      UsdProfAssignIfEntry
    MAX-ACCESS  not-accessible
    STATUS      current
    DESCRIPTION
        "An assignment of a profile to an interface/encapsulation pair."
    INDEX { usdProfAssignIfIndex, usdProfAssignIfEncaps }
    ::= { usdProfAssignIfTable 1 }

UsdProfAssignIfEntry ::= SEQUENCE {
    usdProfAssignIfIndex               InterfaceIndex,
    usdProfAssignIfEncaps              UsdProfileIfEncaps,
    usdProfAssignIfRowStatus           RowStatus,
    usdProfAssignIfProfileId           Unsigned32
}

usdProfAssignIfIndex OBJECT-TYPE
    SYNTAX      InterfaceIndex
    MAX-ACCESS  not-accessible
    STATUS      current
    DESCRIPTION
        "The ifIndex of the interface to which the profile is assigned."
    ::= { usdProfAssignIfEntry 1 }

usdProfAssignIfEncaps OBJECT-TYPE
    SYNTAX      UsdProfileIfEncaps
    MAX-ACCESS  not-accessible
    STATUS      current
    DESCRIPTION
        "The encapsulated protocol type to which the assigned profile pertains.
        An interface may have a different profile assigned for each
        encapsulation it supports.
        
        If an entry for a specific encapsulation is absent, the profile
        assigned for the 'any' encapsulation will be used (if that
        assignment is present in this table)."
    ::= { usdProfAssignIfEntry 2 }

usdProfAssignIfRowStatus OBJECT-TYPE
    SYNTAX      RowStatus
    MAX-ACCESS  read-create
    STATUS      current
    DESCRIPTION
        "For SET, supports only createAndGo(4) and destroy(6).
        Returns active(1) when read."
    ::= { usdProfAssignIfEntry 3 }

usdProfAssignIfProfileId OBJECT-TYPE
    SYNTAX      Unsigned32
    MAX-ACCESS  read-create
    STATUS      current
    DESCRIPTION
        "The ID of the profile assigned to this interface/encapsulation pair."
    ::= { usdProfAssignIfEntry 4 }

--
-- Profile-to-interface/encapsulation mappings.
--
usdProfToIfMapTable OBJECT-TYPE
    SYNTAX      SEQUENCE OF UsdProfToIfMapEntry
    MAX-ACCESS  not-accessible
    STATUS      current
    DESCRIPTION
        "Table to report the set of interface/encapsulation pairs assigned
        to each profile."
    ::= { usdProfAssignIf 2 }

usdProfToIfMapEntry OBJECT-TYPE
    SYNTAX      UsdProfToIfMapEntry
    MAX-ACCESS  not-accessible
    STATUS      current
    DESCRIPTION
        "Reports an interface/encapsulation pair assigned to a profile."
    INDEX { usdProfToIfMapProfileId,
            usdProfToIfMapIndex, 
            usdProfToIfMapEncaps }
    ::= { usdProfToIfMapTable 1 }

UsdProfToIfMapEntry ::= SEQUENCE {
    usdProfToIfMapProfileId           Unsigned32,
    usdProfToIfMapIndex               InterfaceIndex,
    usdProfToIfMapEncaps              UsdProfileIfEncaps
}

usdProfToIfMapProfileId OBJECT-TYPE
    SYNTAX      Unsigned32
    MAX-ACCESS  not-accessible
    STATUS      current
    DESCRIPTION
        "The ID of the profile assigned to this interface/encapsulation pair."
    ::= { usdProfToIfMapEntry 1 }

usdProfToIfMapIndex OBJECT-TYPE
    SYNTAX      InterfaceIndex
    MAX-ACCESS  not-accessible
    STATUS      current
    DESCRIPTION
        "The ifIndex of the interface to which the profile is assigned."
    ::= { usdProfToIfMapEntry 2 }

-- read-only auxiliary object (since all objects are used in index, at least
-- one must be accessible)
usdProfToIfMapEncaps OBJECT-TYPE
    SYNTAX      UsdProfileIfEncaps
    MAX-ACCESS  read-only
    STATUS      current
    DESCRIPTION
        "The encapsulation type to which the assigned profile pertains.
        An interface may have a different profile assigned for each
        encapsulation type it supports."
    ::= { usdProfToIfMapEntry 3 }


-- ++++++++++++++++++++++++++++++++++++++++++++++++++++++++++++++++++++++
-- Notification control objects
-- ++++++++++++++++++++++++++++++++++++++++++++++++++++++++++++++++++++++

-- No notifications are defined in this MIB. Placeholder follows.

-- usdProfileTrapControl      OBJECT IDENTIFIER ::= { usdProfileMIB 2 }


-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdProfileTraps            OBJECT IDENTIFIER ::= { usdProfileMIB 3 }
-- usdProfileTrapPrefix       OBJECT IDENTIFIER ::= { usdProfileTraps 0 }


-- ++++++++++++++++++++++++++++++++++++++++++++++++++++++++++++++++++++++
-- Conformance information
-- ++++++++++++++++++++++++++++++++++++++++++++++++++++++++++++++++++++++

usdProfileMIBConformance
             OBJECT IDENTIFIER ::= { usdProfileMIB 4 }
usdProfileMIBCompliances
             OBJECT IDENTIFIER ::= { usdProfileMIBConformance 1 }
usdProfileMIBGroups
             OBJECT IDENTIFIER ::= { usdProfileMIBConformance 2 }

-- compliance statements

usdProfileCompliance MODULE-COMPLIANCE
    STATUS      obsolete
    DESCRIPTION
        "Obsolete compliance statement for systems supporting naming of
        configuration profiles.  This statement became obsolete when the
        interface profile assignment group was added."
    MODULE  -- this module
        MANDATORY-GROUPS { usdProfileGroup }
    ::= { usdProfileMIBCompliances 1 }                                 -- RX 1.1

usdProfileCompliance2 MODULE-COMPLIANCE
    STATUS      current
    DESCRIPTION
        "The compliance statement for systems supporting naming of configuration
        profiles and profile assignment to interfaces."
    MODULE  -- this module
        MANDATORY-GROUPS { usdProfileGroup, usdProfileIfGroup }
    ::= { usdProfileMIBCompliances 2 }                                 -- RX 2.0


-- units of conformance

usdProfileGroup OBJECT-GROUP
    OBJECTS {
        usdProfileNameName,
        usdProfileNameRowStatus,
        usdProfileNameId,

        usdProfileIdName
    }
    STATUS      current
    DESCRIPTION
        "The basic collection of objects providing management of Profile naming
        functionality in a Unisphere product."
    ::= { usdProfileMIBGroups 1 }

usdProfileIfGroup OBJECT-GROUP
    OBJECTS {
        usdProfAssignIfRowStatus,
        usdProfAssignIfProfileId,
        
        usdProfToIfMapEncaps
    }
    STATUS      current
    DESCRIPTION
        "The basic collection of objects providing management of Profile
        assignment to interfaces in a Unisphere product."
    ::= { usdProfileMIBGroups 2 }

END
