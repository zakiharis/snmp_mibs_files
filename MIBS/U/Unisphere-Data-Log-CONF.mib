-- *****************************************************************************
-- Unisphere-Data-Log-CONF
--
-- SNMP Agent Capabilities definitions for the Log MIB.
--
-- Copyright (c) 2001 Unisphere Networks, Inc.  All rights reserved.
-- *****************************************************************************

Unisphere-Data-Log-CONF DEFINITIONS ::= BEGIN

IMPORTS
    MODULE-IDENTITY
        FROM SNMPv2-SMI
    AGENT-CAPABILITIES
        FROM SNMPv2-CONF
    usDataAgents
        FROM Unisphere-Data-Agents
    usdLogGroup,
    usdLogGroup2,
    usdLogTrapGroup
        FROM Unisphere-Data-LOG-MIB;

usdLogAgent MODULE-IDENTITY
    LAST-UPDATED "200103282207Z"  -- 28-Mar-01 05:07 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the logging managment component
        of the SNMP agent in the Unisphere Routing Switch family of products."
    -- Revision History
    REVISION    "200103282207Z"  -- 28-Mar-01 05:07 PM EST  - RX 3.2
    DESCRIPTION
        "The initial release of this management information module."
    ::= { usDataAgents 26 }

usdLogAgentV1 AGENT-CAPABILITIES
    PRODUCT-RELEASE
        "Version 1 of the logging managment component of the Unisphere Routing
        Switch SNMP agent.  This version of the Log component was supported in
        the Unisphere RX 1.3 system release."
    STATUS      obsolete
    DESCRIPTION
        "The MIB supported by the SNMP agent for the logging managment
        application in the Unisphere Routing Switch.  These capabilities became
        obsolete when the single syslog destination was replaced with a table of
        syslog destinations and the syslog facility was added."

    SUPPORTS        Unisphere-Data-LOG-MIB
        INCLUDES  { usdLogGroup,
                    usdLogTrapGroup }

    ::= { usdLogAgent 1 }

usdLogAgentV2 AGENT-CAPABILITIES
    PRODUCT-RELEASE
        "Version 2 of the logging managment component of the Unisphere Routing
        Switch SNMP agent.  This version of the Log component is supported in
        the Unisphere RX 2.0 and subsequent system releases."
    STATUS      current
    DESCRIPTION
        "The MIB supported by the SNMP agent for the logging managment
        application in the Unisphere Routing Switch."

    SUPPORTS        Unisphere-Data-LOG-MIB
        INCLUDES  { usdLogGroup2,
                    usdLogTrapGroup }

    ::= { usdLogAgent 2 }

END
