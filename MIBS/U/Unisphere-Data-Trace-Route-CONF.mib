-- *****************************************************************************
-- Unisphere-Data-Trace-Route-CONF
--
-- SNMP Agent Capabilities definitions for the Trace Route MIB.
--
-- Copyright (c) 2001 Unisphere Networks, Inc.  All rights reserved.
-- *****************************************************************************

Unisphere-Data-Trace-Route-CONF DEFINITIONS ::= BEGIN

IMPORTS
    MODULE-IDENTITY
        FROM SNMPv2-SMI
    AGENT-CAPABILITIES
        FROM SNMPv2-CONF
    usDataAgents
        FROM Unisphere-Data-Agents
    traceRouteGroup,
    traceRouteTimeStampGroup,
    traceRouteHopsTableGroup,
    traceRouteNotificationsGroup
        FROM DISMAN-TRACEROUTE-MIB;

usdTraceRouteAgent MODULE-IDENTITY
    LAST-UPDATED "200103291907Z"  -- 29-Mar-01 02:07 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Trace Route component of the
        SNMP agent in the Unisphere Routing Switch family of products."
    -- Revision History
    REVISION    "200103291907Z"  -- 29-Mar-01 02:07 PM EST  - RX 3.2
    DESCRIPTION
        "The initial release of this management information module."
    ::= { usDataAgents 43 }

usdTraceRouteAgentV1 AGENT-CAPABILITIES
    PRODUCT-RELEASE
        "Version 1 of the Trace Route component of the Unisphere Routing Switch
        SNMP agent.  This version of the Trace Route component is supported in
        the Unisphere RX 3.0 and subsequent system releases."
    STATUS      current
    DESCRIPTION
        "The MIB supported by the SNMP agent for the Trace Route application in
        the Unisphere Routing Switch."

    SUPPORTS        DISMAN-TRACEROUTE-MIB
        INCLUDES  { traceRouteGroup,
                    traceRouteTimeStampGroup,
                    traceRouteHopsTableGroup,
                    traceRouteNotificationsGroup } 

    ::= { usdTraceRouteAgent 1 }

END
