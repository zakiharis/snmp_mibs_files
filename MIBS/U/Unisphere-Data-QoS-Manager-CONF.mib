-- *****************************************************************************
-- Unisphere-Data-QoS-Manager-CONF
--
-- SNMP Agent Capabilities definitions for the QoS Manager MIB.
--
-- Copyright (c) 2001 Unisphere Networks, Inc.  All rights reserved.
-- *****************************************************************************

Unisphere-Data-QoS-Manager-CONF DEFINITIONS ::= BEGIN

IMPORTS
    MODULE-IDENTITY
        FROM SNMPv2-SMI
    AGENT-CAPABILITIES
        FROM SNMPv2-CONF
    usdQosCapabilityGroup, usdQosScalarGroup, usdQosTrafficClassListGroup,
    usdQosTrafficClassGroupListGroup, usdQosQueueProfileListGroup,
    usdQosSchedulerProfileListGroup, usdQosProfileListGroup,
    usdQosProfileElementGroup, usdQosIfAttachGroup,
    usdQosQosPortTypeProfileGroup, usdQosQueueStatisticsGroup
        FROM Unisphere-Data-QoS-MIB
    usDataAgents
        FROM Unisphere-Data-Agents;

usdQosManagerAgent MODULE-IDENTITY
    LAST-UPDATED "200112061609Z"  -- 06-Dec-01 11:09 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the Quality of Service (QoS)
        Manager component of the SNMP agent in the Unisphere Routing Switch
        family of products."
    -- Revision History
    REVISION    "200112061609Z"  -- 06-Dec-01 11:09 AM EST  - RX 4.0
    DESCRIPTION
        "The initial release of this management information module."
    ::= { usDataAgents 50 }


-- *****************************************************************************
-- QoS Manager SNMP Agent Capabilities definitions
-- *****************************************************************************

usdQosManagerAgentV1 AGENT-CAPABILITIES
    PRODUCT-RELEASE
        "Version 1 of the QoS Manager component of the Unisphere Routing Switch
        SNMP agent.  This version of the QoS Manager component is supported in
        the Unisphere RX 4.0 and subsequent system releases."
    STATUS      current
    DESCRIPTION
        "The MIB supported by the SNMP agent for the QoS Manager application in
        the Unisphere Routing Switch."
    SUPPORTS    Unisphere-Data-QoS-MIB
        INCLUDES  {
            usdQosCapabilityGroup,
            usdQosScalarGroup,
            usdQosTrafficClassListGroup,
            usdQosTrafficClassGroupListGroup,
            usdQosQueueProfileListGroup,
            usdQosSchedulerProfileListGroup,
            usdQosProfileListGroup,
            usdQosProfileElementGroup,
            usdQosIfAttachGroup,
            usdQosQosPortTypeProfileGroup,
            usdQosQueueStatisticsGroup }
    ::= { usdQosManagerAgent 1 }

END
