-- *****************************************************************
-- Unisphere-Data-IP-PROFILE-MIB
--
-- Unisphere Networks Inc. Enterprise MIB
-- IP Profile MIB
--
-- Copyright (c) 1999 Redstone Communications, Inc.
-- Copyright (c) 1999, 2002 Unisphere Networks, Inc.
-- All Rights Reserved.
-- *****************************************************************

Unisphere-Data-IP-PROFILE-MIB DEFINITIONS ::= BEGIN

IMPORTS
    MODULE-IDENTITY, 
    OBJECT-TYPE,
    Integer32,
    Unsigned32,
    IpAddress
        FROM SNMPv2-SMI

    RowStatus
        FROM SNMPv2-TC

    MODULE-COMPLIANCE, 
    OBJECT-GROUP  
        FROM SNMPv2-CONF

    InterfaceIndexOrZero
        FROM IF-MIB

    usDataMibs
        FROM Unisphere-Data-MIBs

    UsdEnable,
    UsdName,
    UsdSetMap
        FROM Unisphere-Data-TC;


usdIpProfileMIB MODULE-IDENTITY
    LAST-UPDATED "200101242006Z"  -- 24-Jan-01 03:06 PM EST
    ORGANIZATION "Unisphere Networks Inc."
    CONTACT-INFO
        "       Unisphere Networks, Inc.
        Postal: 10 Technology Park Drive
                Westford MA  01886
                USA
        Tel:    +1 978 589 5800
        Email:  mib@UnisphereNetworks.com"
    DESCRIPTION
        "The IP Profile MIB for the Unisphere Networks Inc. enterprise."
    -- Revision History
    REVISION    "200101242006Z"  -- 24-Jan-01 03:06 PM EST  - RX 3.0
    DESCRIPTION
        "Deprecated usdIpProfileRowStatus; the table is now dense and populated
        as a side-effect of creation of an entry in the usdProfileNameTable in
        Unisphere-Data-PROFILE-MIB.  Also, added usdIpProfileSetMap and
        usdIpProfileSrcAddrValidEnable."
    REVISION    "200005080000Z"  --  8-May-00               - RX 2.0
    DESCRIPTION
        "Obsoleted usdIpProfileLoopbackIfIndex, replacing it with
        usdIpProfileLoopback."
    REVISION      "9908250000Z"  -- 25-Aug-99               - RX 1.1
    DESCRIPTION
        "Initial version of this MIB module."
    ::= { usDataMibs 26 }


-- ++++++++++++++++++++++++++++++++++++++++++++++++++++++++++++++++++++++
-- Textual conventions
-- ++++++++++++++++++++++++++++++++++++++++++++++++++++++++++++++++++++++

-- No textual conventions are currently defined.


-- ++++++++++++++++++++++++++++++++++++++++++++++++++++++++++++++++++++++
-- Managed object groups
-- ++++++++++++++++++++++++++++++++++++++++++++++++++++++++++++++++++++++

usdIpProfileObjects              OBJECT IDENTIFIER ::= {usdIpProfileMIB 1}

usdIpProfile                     OBJECT IDENTIFIER ::= {usdIpProfileObjects 1 }

-- ++++++++++++++++++++++++++++++++++++++++++++++++++++++++++++++++++++++
-- Managed objects for IP Profiles
-- ++++++++++++++++++++++++++++++++++++++++++++++++++++++++++++++++++++++

-- 
-- This MIB defines configuration profile structure for IP interfaces.
-- The creation/deletion of profiles and mapping of profile names to profile
-- indices is coordinated in the Unisphere-Data-PROFILE-MIB.
--

--
-- The IP Profile Table
--

usdIpProfileTable OBJECT-TYPE
    SYNTAX      SEQUENCE OF UsdIpProfileEntry
    MAX-ACCESS  not-accessible
    STATUS      current
    DESCRIPTION
        "The entries in this table describe profiles for configuring IP
        interfaces.

        Entries in this table are created/deleted as a side-effect of
        corresponding operations to the usdProfileNameTable in the
        Unisphere-Data-PROFILE-MIB."
    ::= { usdIpProfile 1 }

usdIpProfileEntry OBJECT-TYPE
    SYNTAX      UsdIpProfileEntry
    MAX-ACCESS  not-accessible
    STATUS      current
    DESCRIPTION
        "A profile describing configuration of an IP interface."
    INDEX { usdIpProfileId }
    ::= { usdIpProfileTable 1 }

UsdIpProfileEntry ::= SEQUENCE {
    usdIpProfileId                  Unsigned32,
    usdIpProfileRowStatus           RowStatus,
    usdIpProfileRouterName          UsdName,
    usdIpProfileIpAddr              IpAddress,
    usdIpProfileIpMask              IpAddress,
    usdIpProfileDirectedBcastEnable UsdEnable,
    usdIpProfileIcmpRedirectEnable  UsdEnable,
    usdIpProfileAccessRoute         UsdEnable,
    usdIpProfileMtu                 Integer32,
    usdIpProfileLoopbackIfIndex     InterfaceIndexOrZero,
    usdIpProfileLoopback            Integer32,
    usdIpProfileSetMap              UsdSetMap,
    usdIpProfileSrcAddrValidEnable  UsdEnable
}

usdIpProfileId OBJECT-TYPE
    SYNTAX      Unsigned32
    MAX-ACCESS  not-accessible
    STATUS      current
    DESCRIPTION
        "The integer identifier associated with this profile.  A value for this
        identifier is determined by locating or creating a profile name in the
        usdProfileNameTable."
    ::= { usdIpProfileEntry 1 }

usdIpProfileRowStatus OBJECT-TYPE
    SYNTAX      RowStatus
    MAX-ACCESS  read-create
    STATUS      deprecated
    DESCRIPTION
        "Controls creation/deletion of entries in this table.  Only the values
        'createAndGo' and 'destroy' may be SET.
        
        The value of usdIpProfileId must match that of a profile name configured
        in usdProfileNameTable."
    ::= { usdIpProfileEntry 2 }

usdIpProfileRouterName OBJECT-TYPE
    SYNTAX      UsdName
    MAX-ACCESS  read-create
    STATUS      current
    DESCRIPTION
        "The virtual router to which an IP interface configured by this profile
        will be assigned, if other mechanisms do not otherwise specify a virtual
        router assignment."
    DEFVAL { "" }
    ::= { usdIpProfileEntry 3 }

usdIpProfileIpAddr OBJECT-TYPE
    SYNTAX      IpAddress
    MAX-ACCESS  read-create
    STATUS      current
    DESCRIPTION
        "An IP address to be used by an IP interface configured by this profile.
        This object will have a value of 0.0.0.0 for an unnumbered interface."
    DEFVAL { 0 }
    ::= { usdIpProfileEntry 4 }

usdIpProfileIpMask OBJECT-TYPE
    SYNTAX      IpAddress
    MAX-ACCESS  read-create
    STATUS      current
    DESCRIPTION
        "An IP address mask to be used by an IP interface configured by this
        profile.  This object will have a value of 0.0.0.0 for an unnumbered
        interface."
    DEFVAL { 0 }
    ::= { usdIpProfileEntry 5 }

usdIpProfileDirectedBcastEnable OBJECT-TYPE
    SYNTAX      UsdEnable
    MAX-ACCESS  read-create
    STATUS      current
    DESCRIPTION
        "Enable/disable forwarding of directed broadcasts on this IP network
        interface."
    DEFVAL { disable }
    ::= { usdIpProfileEntry 6 }

usdIpProfileIcmpRedirectEnable OBJECT-TYPE
    SYNTAX      UsdEnable
    MAX-ACCESS  read-create
    STATUS      current
    DESCRIPTION
        "Enable/disable transmission of ICMP Redirect messages on this IP
        network interface."
    DEFVAL { disable }
    ::= { usdIpProfileEntry 7 }

usdIpProfileAccessRoute OBJECT-TYPE
    SYNTAX      UsdEnable
    MAX-ACCESS  read-create
    STATUS      current
    DESCRIPTION
        "Enable/disable whether a host route is automatically created for a
        remote host attached to an IP interface that is configured using this
        profile."
    DEFVAL { enable }
    ::= { usdIpProfileEntry 8 }

usdIpProfileMtu OBJECT-TYPE
    SYNTAX      Integer32(0 | 512..10240)
    MAX-ACCESS  read-create
    STATUS      current
    DESCRIPTION
        "The configured MTU size for this IP network interface.  If set to zero,
        the default MTU size, as determined by the underlying network media, is
        used."
    DEFVAL { 0 } 
    ::= { usdIpProfileEntry 9 }

usdIpProfileLoopbackIfIndex OBJECT-TYPE
    SYNTAX      InterfaceIndexOrZero
    MAX-ACCESS  read-create
    STATUS      obsolete
    DESCRIPTION
        "For unnumbered interfaces, the IfIndex of the IP loopback interface
        whose IP address is used as the source address for transmitted IP
        packets.  A value of zero means the loopback interface is unspecified
        (e.g., when the interface is numbered)."
    DEFVAL { 0 }
    ::= { usdIpProfileEntry 10 }

usdIpProfileLoopback OBJECT-TYPE
    SYNTAX      Integer32(-1..2147483647)
    MAX-ACCESS  read-create
    STATUS      current
    DESCRIPTION
        "The number of the loopback interface, associated with the specified
        virtual router, whose IP address is used as the source address when
        transmitting IP packets on unnumbered remote access user links.

        For example, if the loopback interface for the associated router was
        configured via the console as 'loopback 2', this object would contain
        the integer value 2.

        A value of -1 indicates the loopback interface is unspecified, e.g.,
        when the IP interface is numbered."
    DEFVAL { -1 }
    ::= { usdIpProfileEntry 11 }

usdIpProfileSetMap OBJECT-TYPE
    SYNTAX      UsdSetMap
    MAX-ACCESS  read-create
    STATUS      current
    DESCRIPTION
        "A bitmap representing which objects in this entry have been explicitly
        configured.  See the definition of the UsdSetMap TEXTUAL-CONVENTION for
        details of use.

        The INDEX object(s) and this object are excluded from representation
        (i.e. their bits are never set).

        When a SET request does not explicitly configure UsdSetMap, bits in
        UsdSetMap are set as a side-effect of configuring other profile
        attributes in the same entry.

        If, however, a SET request explicitly configures UsdSetMap, the
        explicitly configured value overrides 1) any previous bit settings, and
        2) any simultaneous 'side-effect' settings that would otherwise occur.

        Once set, bits can only be cleared by explicitly configuring UsdSetMap."
    ::= { usdIpProfileEntry 12 }

usdIpProfileSrcAddrValidEnable OBJECT-TYPE
    SYNTAX      UsdEnable
    MAX-ACCESS  read-create
    STATUS      current
    DESCRIPTION
        "Enable/disable whether source addresses in received IP packets are
        validated. Validation is performed by looking up the source IP address
        in the routing database and determining whether the packet arrived on
        the expected interface; if not, the packet is discarded."
    DEFVAL { disable }
    ::= { usdIpProfileEntry 13 }


-- ++++++++++++++++++++++++++++++++++++++++++++++++++++++++++++++++++++++
-- Notification control objects
-- ++++++++++++++++++++++++++++++++++++++++++++++++++++++++++++++++++++++

-- No notifications are defined in this MIB. Placeholder follows.

-- usdIpProfileTrapControl      OBJECT IDENTIFIER ::= { usdIpProfileMIB 2 }



-- ++++++++++++++++++++++++++++++++++++++++++++++++++++++++++++++++++++++
-- Notifications
-- ++++++++++++++++++++++++++++++++++++++++++++++++++++++++++++++++++++++

-- No notifications are defined in this MIB. Placeholder follows.

-- The following two OBJECT IDENTIFIERS are used to define SNMPv2 
-- Notifications that are easily translated into SNMPv1 Traps.

-- usdIpProfileTraps            OBJECT IDENTIFIER ::= { usdIpProfileMIB 3 }
-- usdIpProfileTrapPrefix       OBJECT IDENTIFIER ::= { usdIpProfileTraps 0 }



-- ++++++++++++++++++++++++++++++++++++++++++++++++++++++++++++++++++++++
-- Conformance information
-- ++++++++++++++++++++++++++++++++++++++++++++++++++++++++++++++++++++++

usdIpProfileMIBConformance
             OBJECT IDENTIFIER ::= { usdIpProfileMIB 4 }
usdIpProfileMIBCompliances
             OBJECT IDENTIFIER ::= { usdIpProfileMIBConformance 1 }
usdIpProfileMIBGroups
             OBJECT IDENTIFIER ::= { usdIpProfileMIBConformance 2 }


-- compliance statements

usdIpProfileCompliance MODULE-COMPLIANCE
    STATUS      obsolete
    DESCRIPTION
        "Obsolete compliance statement for systems supporting IP configuration
        profiles.  This statement became obsolete when usdIpProfileLoopback
        replaced usdIpProfileLoopbackIfIndex."
    MODULE  -- this module
    MANDATORY-GROUPS { usdIpProfileGroup }
    ::= { usdIpProfileMIBCompliances 1 }                               -- RX 1.1

usdIpProfileCompliance1 MODULE-COMPLIANCE
    STATUS      obsolete
    DESCRIPTION
        "Obsolete compliance statement for systems supporting IP configuration
        profiles.  This statement became obsolete when usdIpProfileRowStatus was
        deprecate and the usdIpProfileSetMap and usdIpProfileSrcAddrValidEnable
        objects were added."
    MODULE  -- this module
    MANDATORY-GROUPS { usdIpProfileGroup1 }
    ::= { usdIpProfileMIBCompliances 2 }                               -- RX 2.0

usdIpProfileCompliance2 MODULE-COMPLIANCE
    STATUS      current
    DESCRIPTION
        "The compliance statement for systems supporting IP configuration
        profiles, incorporating UsdSetMap."
    MODULE  -- this module
    MANDATORY-GROUPS { usdIpProfileGroup2 }
    ::= { usdIpProfileMIBCompliances 3 }                               -- RX 3.0


-- units of conformance

usdIpProfileGroup OBJECT-GROUP
    OBJECTS {
        usdIpProfileRowStatus,
        usdIpProfileRouterName,
        usdIpProfileIpAddr,
        usdIpProfileIpMask,
        usdIpProfileDirectedBcastEnable,
        usdIpProfileIcmpRedirectEnable,
        usdIpProfileAccessRoute,
        usdIpProfileMtu,
        usdIpProfileLoopbackIfIndex
    }
    STATUS      obsolete
    DESCRIPTION
        "An obsolete collection of objects providing management of IP Profile
        functionality in a Unisphere product.  This group became obsolete when
        usdIpProfileLoopback replaced usdIpProfileLoopbackIfIndex."
    ::= { usdIpProfileMIBGroups 1 }

usdIpProfileGroup1 OBJECT-GROUP
    OBJECTS {
        usdIpProfileRowStatus,
        usdIpProfileRouterName,
        usdIpProfileIpAddr,
        usdIpProfileIpMask,
        usdIpProfileDirectedBcastEnable,
        usdIpProfileIcmpRedirectEnable,
        usdIpProfileAccessRoute,
        usdIpProfileMtu,
        usdIpProfileLoopback
    }
    STATUS      obsolete
    DESCRIPTION
        "An obsolete collection of objects providing management of IP Profile
        functionality in a Unisphere product.  This group became obsolete when
        usdIpProfileRowStatus was deprecate and the usdIpProfileSetMap and
        usdIpProfileSrcAddrValidEnable objects were added."
    ::= { usdIpProfileMIBGroups 2 }

usdIpProfileGroup2 OBJECT-GROUP
    OBJECTS {
        usdIpProfileRouterName,
        usdIpProfileIpAddr,
        usdIpProfileIpMask,
        usdIpProfileDirectedBcastEnable,
        usdIpProfileIcmpRedirectEnable,
        usdIpProfileAccessRoute,
        usdIpProfileMtu,
        usdIpProfileLoopback,
        usdIpProfileSetMap,
        usdIpProfileSrcAddrValidEnable
    }
    STATUS      current
    DESCRIPTION
        "The basic collection of objects providing management of IP Profile
        functionality in a Unisphere product."
    ::= { usdIpProfileMIBGroups 3 }

usdIpProfileDeprecatedGroup  OBJECT-GROUP
    OBJECTS {
        usdIpProfileRowStatus }
    STATUS      deprecated
    DESCRIPTION
        "Deprecated object providing management of IP Profile functionality in a
        Juniper product.  This group has been deprecated but may still be
        supported on some implementations."
    ::= { usdIpProfileMIBGroups 4 }

END
