-- *****************************************************************************
-- Unisphere-Data-RIP-CONF
--
-- SNMP Agent Capabilities definitions for the RIPv2 MIB.
--
-- Copyright (c) 2001 Unisphere Networks, Inc.  All rights reserved.
-- *****************************************************************************

Unisphere-Data-RIP-CONF DEFINITIONS ::= BEGIN

IMPORTS
    MODULE-IDENTITY
        FROM SNMPv2-SMI
    AGENT-CAPABILITIES
        FROM SNMPv2-CONF
    usDataAgents
        FROM Unisphere-Data-Agents
    rip2GlobalGroup,
    rip2IfStatGroup,
    rip2IfConfGroup,
    rip2PeerGroup
        FROM RIPv2-MIB;

usdRipAgent MODULE-IDENTITY
    LAST-UPDATED "200103291813Z"  -- 29-Mar-01 01:13 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the RIP component of the SNMP
        agent in the Unisphere Routing Switch family of products."
    -- Revision History
    REVISION    "200103291813Z"  -- 29-Mar-01 01:13 PM EST  - RX 3.2
    DESCRIPTION
        "The initial release of this management information module."
    ::= { usDataAgents 36 }

usdRipAgentV1 AGENT-CAPABILITIES
    PRODUCT-RELEASE
        "Version 1 of the RIP component of the Unisphere Routing Switch SNMP
        agent.  This version of the RIP component is supported in the Unisphere
        RX 1.0 and subsequent system releases."
    STATUS      current
    DESCRIPTION
        "The MIB supported by the SNMP agent for the RIP application in the
        Unisphere Routing Switch."

    SUPPORTS        RIPv2-MIB
        INCLUDES  { rip2GlobalGroup,
                    rip2IfStatGroup,
                    rip2IfConfGroup,
                    rip2PeerGroup }

    ::= { usdRipAgent 1 }

END
