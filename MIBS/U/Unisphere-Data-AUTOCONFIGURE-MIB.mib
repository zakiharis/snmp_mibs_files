-- *****************************************************************
-- Unisphere-Data-AUTOCONFIGURE-MIB
--
-- Unisphere Networks Inc. Enterprise MIB
-- Auto-Configuration MIB
--
-- Copyright (c) 2000 Unisphere Networks, Incorporated.
-- All Rights Reserved.
-- *****************************************************************

Unisphere-Data-AUTOCONFIGURE-MIB DEFINITIONS ::= BEGIN

IMPORTS
    MODULE-IDENTITY, OBJECT-TYPE
        FROM SNMPv2-SMI
    TEXTUAL-CONVENTION
        FROM SNMPv2-TC
    MODULE-COMPLIANCE, OBJECT-GROUP
        FROM SNMPv2-CONF
    InterfaceIndex
        FROM IF-MIB
    usDataMibs
        FROM Unisphere-Data-MIBs
    UsdEnable
        FROM Unisphere-Data-TC;

usdAutoConfMIB MODULE-IDENTITY
    LAST-UPDATED "200211190000Z" -- 19-Nov-02
    ORGANIZATION "Unisphere Networks Inc."
    CONTACT-INFO
        "       Unisphere Networks, Inc.
        Postal: 10 Technology Park Drive
                Westford MA  01886
                USA
        Tel:    +1 978 589 5800
        Email:  mib@UnisphereNetworks.com"
    DESCRIPTION
        "The Auto-Configuration MIB for the Unisphere Networks Inc.
        enterprise."
    -- Revision History
    REVISION      "200211180000Z" --  19-Nov-02
    DESCRIPTION
        "Added bridgedEthernet(19) to UsdAutoConfEncaps."
    REVISION      "200011160000Z" --  16-Nov-00
    DESCRIPTION
        "Initial version of this MIB module."
    ::= { usDataMibs 48 }


-- ++++++++++++++++++++++++++++++++++++++++++++++++++++++++++++++++++++++
-- Textual conventions
-- ++++++++++++++++++++++++++++++++++++++++++++++++++++++++++++++++++++++

UsdAutoConfEncaps ::= TEXTUAL-CONVENTION
    STATUS      current
    DESCRIPTION
        "Encapsulated protocol type."
    SYNTAX      INTEGER {
                    ip(0),
                    ppp(1),
                    pppoe(17),
                    bridgedEthernet(19)
                }

-- ++++++++++++++++++++++++++++++++++++++++++++++++++++++++++++++++++++++
-- Managed object groups
-- ++++++++++++++++++++++++++++++++++++++++++++++++++++++++++++++++++++++

usdAutoConfObjects        OBJECT IDENTIFIER ::= {usdAutoConfMIB 1}

-- Functional groups

usdAutoConf               OBJECT IDENTIFIER ::= {usdAutoConfObjects 1}

-- ++++++++++++++++++++++++++++++++++++++++++++++++++++++++++++++++++++++
-- Managed objects
-- ++++++++++++++++++++++++++++++++++++++++++++++++++++++++++++++++++++++

--
-- Enable/disable autoconfiguration for incoming data encapsulations.
--
usdAutoConfTable OBJECT-TYPE
    SYNTAX      SEQUENCE OF UsdAutoConfEntry
    MAX-ACCESS  not-accessible
    STATUS      current
    DESCRIPTION
        "Configures recognition of incoming data encapsulation types that
        trigger autoconfiguration on an interface."
    ::= { usdAutoConf 1 }

usdAutoConfEntry OBJECT-TYPE
    SYNTAX      UsdAutoConfEntry
    MAX-ACCESS  not-accessible
    STATUS      current
    DESCRIPTION
        "Configures recognition of an incoming data encapsulation type that
        triggers autoconfiguration on an interface."
    INDEX { usdAutoConfIfIndex, usdAutoConfEncaps }
    ::= { usdAutoConfTable 1 }

UsdAutoConfEntry ::= SEQUENCE {
    usdAutoConfIfIndex         InterfaceIndex,
    usdAutoConfEncaps          UsdAutoConfEncaps,
    usdAutoConfEnable          UsdEnable
}

usdAutoConfIfIndex OBJECT-TYPE
    SYNTAX      InterfaceIndex
    MAX-ACCESS  not-accessible
    STATUS      current
    DESCRIPTION
        "The ifIndex of the interface to which the autoconfiguration information
        in this entry applies."
    ::= { usdAutoConfEntry 1 }

usdAutoConfEncaps OBJECT-TYPE
    SYNTAX      UsdAutoConfEncaps
    MAX-ACCESS  not-accessible
    STATUS      current
    DESCRIPTION
        "The encapsulated protocol type to which the autconfiguration
        information in this entry applies."
    ::= { usdAutoConfEntry 2 }

usdAutoConfEnable OBJECT-TYPE
    SYNTAX      UsdEnable
    MAX-ACCESS  read-write
    STATUS      current
    DESCRIPTION
        "When enabled, permits autoconfiguration of the specified interface when
        the specified encapsulation is recognized in an incoming data frame."
    ::= { usdAutoConfEntry 3 }

-- ++++++++++++++++++++++++++++++++++++++++++++++++++++++++++++++++++++++
-- Conformance information
-- ++++++++++++++++++++++++++++++++++++++++++++++++++++++++++++++++++++++

usdAutoConfMIBConformance
             OBJECT IDENTIFIER ::= { usdAutoConfMIB 4 }
usdAutoConfMIBCompliances
             OBJECT IDENTIFIER ::= { usdAutoConfMIBConformance 1 }
usdAutoConfMIBGroups
             OBJECT IDENTIFIER ::= { usdAutoConfMIBConformance 2 }

-- compliance statements

usdAutoConfCompliance MODULE-COMPLIANCE
    STATUS      current
    DESCRIPTION
        "The compliance statement for systems supporting enabling of
        autoconfiguration operation."
    MODULE  -- this module
        MANDATORY-GROUPS { usdAutoConfGroup }
    ::= { usdAutoConfMIBCompliances 1 }

-- units of conformance

usdAutoConfGroup OBJECT-GROUP
    OBJECTS {
        usdAutoConfEnable
    }
    STATUS      current
    DESCRIPTION
        "The basic collection of objects providing management of
        autoconfiguration enabling in a Unisphere product."
    ::= { usdAutoConfMIBGroups 1 }

END
