-- *****************************************************************************
-- Unisphere-Data-PPPoE-CONF
--
-- SNMP Agent Capabilities definitions for the PPPoE MIB.
--
-- Copyright (c) 2001, 2002 Unisphere Networks, Inc.
-- Copyright (c) 2002 Juniper Networks, Inc.
--   All rights reserved.
-- *****************************************************************************

Unisphere-Data-PPPoE-CONF DEFINITIONS ::= BEGIN

IMPORTS
    MODULE-IDENTITY
        FROM SNMPv2-SMI
    AGENT-CAPABILITIES
        FROM SNMPv2-CONF
    usDataAgents
        FROM Unisphere-Data-Agents
    usdPPPoEGroup2, usdPPPoESubIfGroup2, usdPPPoESummaryGroup, usdPPPoEGroup3,
    usdPPPoEGroup4
        FROM Unisphere-Data-PPPOE-MIB;

usdPppoeAgent MODULE-IDENTITY
    LAST-UPDATED "200208191514Z"  -- 19-Aug-02 11:14 AM EDT
    ORGANIZATION "Juniper Networks, Inc."
    CONTACT-INFO
        "       Juniper Networks, Inc.
        Postal: 10 Technology Park Drive
                Westford, MA 01886
                USA
        Tel:    +1 978 589 5800
        E-mail: mib@UnisphereNetworks.com"
    DESCRIPTION
        "The agent capabilities definitions for the point-to-point protocol over
        Ethernet (PPPoE) component of the SNMP agent in the Unisphere Data
        Routing Switch family of products."
    -- Revision History
    REVISION    "200208191514Z"  -- 19-Aug-02 11:14 AM EDT  - RX 4.0
    DESCRIPTION
        "Added PADI flag support."
    REVISION    "200106191427Z"  -- 14-May-02 06:38 PM EST  - RX 3.2.3
    DESCRIPTION
        "Added AC-NAME and duplicate MAC address indicator objects."
    REVISION    "200104021921Z"  -- 02-Apr-01 03:21 PM EDT  - RX 3.2
    DESCRIPTION
        "The initial release of this management information module."
    ::= { usDataAgents 33 }


usdPppoeAgentV1 AGENT-CAPABILITIES
    PRODUCT-RELEASE
        "Version 1 of the PPPoE component of the Unisphere Routing Switch SNMP
        agent.  This version of the PPPoE component was supported in the
        Unisphere RX 3.0 thru 3.2.2 system releases."
    STATUS      obsolete
    DESCRIPTION
        "The MIB supported by the SNMP agent for the PPPoE application in the
        Unisphere Routing Switch.  These capabilities became obsolete when
        AC-NAME and duplicate MAC address indicator objects were added."
    SUPPORTS    Unisphere-Data-PPPOE-MIB
        INCLUDES  {
            usdPPPoEGroup2,
            usdPPPoESubIfGroup2,
            usdPPPoESummaryGroup }
    ::= { usdPppoeAgent 1 }

usdPppoeAgentV2 AGENT-CAPABILITIES
    PRODUCT-RELEASE
        "Version 2 of the PPPoE component of the Unisphere Routing Switch SNMP
        agent.  This version of the PPPoE component was supported in the
        Unisphere RX 3.2.3 through 3.x system releases."
    STATUS      obsolete
    DESCRIPTION
        "The MIB supported by the SNMP agent for the PPPoE application in the
        Unisphere Routing Switch.  These capabilities became obsolete when PADI
        flag support was added."
    SUPPORTS    Unisphere-Data-PPPOE-MIB
        INCLUDES  {
            usdPPPoEGroup3,
            usdPPPoESubIfGroup2,
            usdPPPoESummaryGroup }
    ::= { usdPppoeAgent 2 }

usdPppoeAgentV3 AGENT-CAPABILITIES
    PRODUCT-RELEASE
        "Version 3 of the PPPoE component of the Unisphere Routing Switch SNMP
        agent.  This version of the PPPoE component is supported in the
        Unisphere RX 4.0 and subsequent system releases."
    STATUS      current
    DESCRIPTION
        "The MIB supported by the SNMP agent for the PPPoE application in the
        Unisphere Routing Switch."
    SUPPORTS    Unisphere-Data-PPPOE-MIB
        INCLUDES  {
            usdPPPoEGroup4,
            usdPPPoESubIfGroup2,
            usdPPPoESummaryGroup }
    ::= { usdPppoeAgent 3 }

END
