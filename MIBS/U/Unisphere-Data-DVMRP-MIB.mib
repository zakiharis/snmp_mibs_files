-- *****************************************************************************
-- Unisphere-Data-DVMRP-MIB
--
-- Unisphere Networks Inc. Enterprise MIB
-- DVMRP MIB
--
-- Copyright (c) 2001 Unisphere Networks, Inc.  All Rights Reserved.
-- *****************************************************************************

Unisphere-Data-DVMRP-MIB DEFINITIONS ::= BEGIN

IMPORTS
    MODULE-IDENTITY, OBJECT-TYPE, Integer32, Unsigned32, NOTIFICATION-TYPE,
    IpAddress, TimeTicks
        FROM SNMPv2-SMI
    DisplayString, RowStatus
        FROM SNMPv2-TC
    MODULE-COMPLIANCE, OBJECT-GROUP, NOTIFICATION-GROUP
        FROM SNMPv2-CONF
    InterfaceIndex
        FROM IF-MIB
    uxdDvmrpInterfaceEntry
        FROM DVMRP-STD-MIB-UNI
    usDataMibs
        FROM Unisphere-Data-MIBs;

usdDvmrpMIB MODULE-IDENTITY
    LAST-UPDATED "200111302124Z"  -- 30-Nov-01 04:24 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Enterprise MIB module for management of Unisphere DVMRP routers."
    -- Revision History
    REVISION    "200111302124Z"  -- 30-Nov-01 04:24 PM EST  - RX 3.0
    DESCRIPTION
        "Initial version of this MIB module."
    ::= { usDataMibs 44 } 


-- +++++++++++++++++++++++++++++++++++++++++++++++++++++++++++++++++++++++++++++
-- Managed objects
-- +++++++++++++++++++++++++++++++++++++++++++++++++++++++++++++++++++++++++++++

usdDvmrpMIBObjects OBJECT IDENTIFIER ::= { usdDvmrpMIB 1 }
usdDvmrp           OBJECT IDENTIFIER ::= { usdDvmrpMIBObjects 1 }
usdDvmrpScalar     OBJECT IDENTIFIER ::= { usdDvmrp 1 }

--
-- Unisphere DVMRP scalar objects.
--
usdDvmrpAdminState OBJECT-TYPE
    SYNTAX      INTEGER {
                    disable(0),
                    enable(1)
                }
    MAX-ACCESS  read-write
    STATUS      current
    DESCRIPTION
        "Controls whether usdDvmrp is enabled or not."
    ::= { usdDvmrpScalar 1 }

usdDvmrpMcastAdminState OBJECT-TYPE
    SYNTAX      INTEGER {
                    disable(0),
                    enable(1)
                }
    MAX-ACCESS  read-only
    STATUS      current
    DESCRIPTION
        "Whether Multicast is enabled or not.  This is settable via the
        multicast component."
    ::= { usdDvmrpScalar 2 }

usdDvmrpRouteHogNotification OBJECT-TYPE
    SYNTAX      Integer32 (0..134217727)
    MAX-ACCESS  read-write
    STATUS      current
    DESCRIPTION
        "The number of routes allowed within a 1 minute interval before a trap
        is issued warning that there may be a route surge going on."
    ::= { usdDvmrpScalar 3 }

usdDvmrpRouteLimit OBJECT-TYPE
    SYNTAX      Integer32 (0..134217727)
    MAX-ACCESS  read-write
    STATUS      current
    DESCRIPTION
        "The limit on the number of routes that may be advertised on a usdDvmrp
        interface."
    ::= { usdDvmrpScalar 4 }

usdDvmrpS32PrunesOnly OBJECT-TYPE
    SYNTAX      INTEGER {
                    disable(0),
                    enable(1)
                }
    MAX-ACCESS  read-only
    STATUS      current
    DESCRIPTION
        "Identifies when Dvmrp is sending prunes and grafts with only a 32 bit
        source masks."
    ::= { usdDvmrpScalar 5 }


--
-- The Unisphere DVMRP Access list Distance Neighbor group.
--
usdDvmrpAclDistNbrTable OBJECT-TYPE
    SYNTAX      SEQUENCE OF UsdDvmrpAclDistNbrEntry
    MAX-ACCESS  not-accessible
    STATUS      current
    DESCRIPTION
        "The (conceptual) table listing the access lists distance for a list of
        neighbors."
    ::= { usdDvmrp 2 }

usdDvmrpAclDistNbrEntry OBJECT-TYPE
    SYNTAX      UsdDvmrpAclDistNbrEntry
    MAX-ACCESS  not-accessible
    STATUS      current
    DESCRIPTION
        "An entry (conceptual row) in the usdDvmrpAclDistNbrTable." 
    INDEX     { usdDvmrpAclDistNbrIfIndex,
                usdDvmrpAclDistNbrAclListName }
    ::= { usdDvmrpAclDistNbrTable 1 }

UsdDvmrpAclDistNbrEntry ::= SEQUENCE {
    usdDvmrpAclDistNbrIfIndex              InterfaceIndex,
    usdDvmrpAclDistNbrAclListName          DisplayString,
    usdDvmrpAclDistNbrDistance             Integer32,
    usdDvmrpAclDistNbrNbrListName          DisplayString,
    usdDvmrpAclDistNbrStatus               RowStatus
}

usdDvmrpAclDistNbrIfIndex OBJECT-TYPE
    SYNTAX      InterfaceIndex
    MAX-ACCESS  not-accessible
    STATUS      current
    DESCRIPTION
        "The ifIndex value of the interface for which DVMRP is enabled."
    ::= { usdDvmrpAclDistNbrEntry 1 }

usdDvmrpAclDistNbrAclListName OBJECT-TYPE
    SYNTAX      DisplayString (SIZE(1..80))
    MAX-ACCESS  not-accessible
    STATUS      current
    DESCRIPTION
        "The name of the access list to be used in the filter."
    ::= { usdDvmrpAclDistNbrEntry 2 }

usdDvmrpAclDistNbrDistance  OBJECT-TYPE
    SYNTAX      Integer32 (0..255)
    MAX-ACCESS  read-create
    STATUS      current
    DESCRIPTION
        "The administritive distance metric that will be used"
    DEFVAL    { 1 } 
    ::= { usdDvmrpAclDistNbrEntry 3 }

usdDvmrpAclDistNbrNbrListName OBJECT-TYPE
    SYNTAX      DisplayString(SIZE(1..80))
    MAX-ACCESS  read-create
    STATUS      current
    DESCRIPTION
        "This is the access list of nbrs for this accept-filter to be applied,
        this field must be supplied when the row is created"
    ::= { usdDvmrpAclDistNbrEntry 4 }

usdDvmrpAclDistNbrStatus OBJECT-TYPE
    SYNTAX      RowStatus
    MAX-ACCESS  read-create
    STATUS      current
    DESCRIPTION
        "The status of this entry."
    ::= { usdDvmrpAclDistNbrEntry 5 }


--
-- The Unisphere DVMRP Local Address table.
-- This is used to retrive all of the addresses configured
-- on a DVMRP interface.
--
usdDvmrpLocalAddrTable OBJECT-TYPE
    SYNTAX      SEQUENCE OF UsdDvmrpLocalAddrTableEntry
    MAX-ACCESS  not-accessible
    STATUS      current
    DESCRIPTION
        "The (conceptual) table listing the local addresses.  This is used to
        retrive all of the addresses configured on a DVMRP interface."
    ::= { usdDvmrp 3 }

usdDvmrpLocalAddrTableEntry OBJECT-TYPE
    SYNTAX      UsdDvmrpLocalAddrTableEntry
    MAX-ACCESS  not-accessible
    STATUS      current
    DESCRIPTION
        "An entry (conceptual row) in the usdDvmrpLocalAddrTable." 
    INDEX     { usdDvmrpLocalAddrIfIndex,
                usdDvmrpLocalAddrAddrOrIfIndex }
    ::= { usdDvmrpLocalAddrTable 1 }

UsdDvmrpLocalAddrTableEntry ::= SEQUENCE {
    usdDvmrpLocalAddrIfIndex            InterfaceIndex,
    usdDvmrpLocalAddrAddrOrIfIndex      Unsigned32,
    usdDvmrpLocalAddrMask               IpAddress
}

usdDvmrpLocalAddrIfIndex OBJECT-TYPE
    SYNTAX      InterfaceIndex
    MAX-ACCESS  not-accessible
    STATUS      current
    DESCRIPTION
        "The ifIndex value of the interface for which DVMRP is enabled."
    ::= { usdDvmrpLocalAddrTableEntry 1 }

usdDvmrpLocalAddrAddrOrIfIndex OBJECT-TYPE
    SYNTAX      Unsigned32
    MAX-ACCESS  not-accessible
    STATUS      current
    DESCRIPTION
        "For unnumbered interfaces, this takes on the value of the ifIndex.  For
        numbered interfaces, this is the address of one of the addresses
        associated with the interface."
    ::= { usdDvmrpLocalAddrTableEntry 2 }

usdDvmrpLocalAddrMask OBJECT-TYPE
    SYNTAX      IpAddress
    MAX-ACCESS  read-only
    STATUS      current
    DESCRIPTION
        "The IP Address mask associated with this entry."
    ::= { usdDvmrpLocalAddrTableEntry 3 }


--
-- The Unisphere DVMRP Summary Address table.
-- This is used to retrive all of the summary address configured
-- on a DVMRP interface.
--
usdDvmrpSummaryAddrTable OBJECT-TYPE
    SYNTAX      SEQUENCE OF UsdDvmrpSummaryAddrTableEntry
    MAX-ACCESS  not-accessible
    STATUS      current
    DESCRIPTION
        "The (conceptual) table listing the DVMRP summary addresses.  This is
        used to retrive all of the summary address configured on a DVMRP
        interface."
    ::= { usdDvmrp 4 }

usdDvmrpSummaryAddrTableEntry OBJECT-TYPE
    SYNTAX      UsdDvmrpSummaryAddrTableEntry
    MAX-ACCESS  not-accessible
    STATUS      current
    DESCRIPTION
        "An entry (conceptual row) in the usdDvmrpSummaryAddrTable." 
    INDEX     { usdDvmrpSummaryAddrIfIndex,
                usdDvmrpSummaryAddrAddress,
                usdDvmrpSummaryAddrMask }
    ::= { usdDvmrpSummaryAddrTable 1 }

UsdDvmrpSummaryAddrTableEntry ::= SEQUENCE {
    usdDvmrpSummaryAddrIfIndex          InterfaceIndex,
    usdDvmrpSummaryAddrAddress          IpAddress,
    usdDvmrpSummaryAddrMask             IpAddress,
    usdDvmrpSummaryAddrCost             Integer32,
    usdDvmrpSummaryAddrStatus           RowStatus
}

usdDvmrpSummaryAddrIfIndex OBJECT-TYPE
    SYNTAX      InterfaceIndex
    MAX-ACCESS  not-accessible
    STATUS      current
    DESCRIPTION
        "The ifIndex value of the interface for which DVMRP is enabled."
    ::= { usdDvmrpSummaryAddrTableEntry 1 }

usdDvmrpSummaryAddrAddress OBJECT-TYPE
    SYNTAX      IpAddress
    MAX-ACCESS  not-accessible
    STATUS      current
    DESCRIPTION
        "This is the summary address that will be created."
    ::= { usdDvmrpSummaryAddrTableEntry 2 }

usdDvmrpSummaryAddrMask OBJECT-TYPE
    SYNTAX      IpAddress
    MAX-ACCESS  not-accessible
    STATUS      current
    DESCRIPTION
        "The mask of the summary address to be created."
    ::= { usdDvmrpSummaryAddrTableEntry 3 }

usdDvmrpSummaryAddrCost  OBJECT-TYPE
    SYNTAX      Integer32 (1..32)
    MAX-ACCESS  read-create
    STATUS      current
    DESCRIPTION
        "The administritive distance metric used to actually calculate distance
        vectors."
    DEFVAL    { 1 } 
    ::= { usdDvmrpSummaryAddrTableEntry 4 }

usdDvmrpSummaryAddrStatus OBJECT-TYPE
    SYNTAX      RowStatus
    MAX-ACCESS  read-create
    STATUS      current
    DESCRIPTION
        "The status of this entry."
    ::= { usdDvmrpSummaryAddrTableEntry 5 }


--
-- The Unisphere DVMRP Interface Table.
--
usdDvmrpInterfaceTable OBJECT-TYPE
    SYNTAX      SEQUENCE OF UsdDvmrpInterfaceEntry
    MAX-ACCESS  not-accessible
    STATUS      current
    DESCRIPTION
        "The (conceptual) table listing the router's multicast-capable
        interfaces.  This table augments the DvmrpInterfaceTable."
    ::= { usdDvmrp 5 }

usdDvmrpInterfaceEntry OBJECT-TYPE
    SYNTAX      UsdDvmrpInterfaceEntry
    MAX-ACCESS  not-accessible
    STATUS      current
    DESCRIPTION
        "An entry (conceptual row) in the usdDvmrpInterfaceTable.  This row
        extends ipMRouteInterfaceEntry in the IP Multicast MIB, where the
        threshold object resides."
    AUGMENTS  { uxdDvmrpInterfaceEntry }
    ::= { usdDvmrpInterfaceTable 1 }

UsdDvmrpInterfaceEntry ::= SEQUENCE {
    usdDvmrpInterfaceAutoSummary           INTEGER,
    usdDvmrpInterfaceMetricOffsetOut       Integer32,
    usdDvmrpInterfaceMetricOffsetIn        Integer32,
    usdDvmrpInterfaceAdminState            INTEGER
}

usdDvmrpInterfaceAutoSummary OBJECT-TYPE
    SYNTAX      INTEGER {
                    disable(0),
                    enable(1)
                }
    MAX-ACCESS  read-create
    STATUS      current
    DESCRIPTION
        "Enables or disable auto-summarization on this interface."
    ::= { usdDvmrpInterfaceEntry 3 }

usdDvmrpInterfaceMetricOffsetOut OBJECT-TYPE
    SYNTAX      Integer32 (0..31)
    MAX-ACCESS  read-create
    STATUS      current
    DESCRIPTION
        "The distance metric for this interface which is used to calculate
        outbound distance vectors."
    DEFVAL    { 0 }
    ::= { usdDvmrpInterfaceEntry 4 }

usdDvmrpInterfaceMetricOffsetIn OBJECT-TYPE
    SYNTAX      Integer32 (0..31)
    MAX-ACCESS  read-create
    STATUS      current
    DESCRIPTION
        "The distance metric for this interface which is used to calculate
        inbound distance vectors."
    DEFVAL    { 1 }
    ::= { usdDvmrpInterfaceEntry 5 }

usdDvmrpInterfaceAdminState OBJECT-TYPE
    SYNTAX      INTEGER {
                    disable(0),
                    enable(1)
                }
    MAX-ACCESS  read-create
    STATUS      current
    DESCRIPTION
        "Controls whether DVMRP is enabled or not."
    ::= { usdDvmrpInterfaceEntry 6 }


--
-- The Unisphere DVMRP Prune Table
--
usdDvmrpPruneTable OBJECT-TYPE
    SYNTAX      SEQUENCE OF UsdDvmrpPruneEntry
    MAX-ACCESS  not-accessible
    STATUS      current
    DESCRIPTION
        "The (conceptual) table listing the router's upstream prune state."
    ::= { usdDvmrp 6 }

usdDvmrpPruneEntry OBJECT-TYPE
    SYNTAX      UsdDvmrpPruneEntry
    MAX-ACCESS  not-accessible
    STATUS      current
    DESCRIPTION
        "An entry (conceptual row) in the usdDvmrpPruneTable."
    INDEX     { usdDvmrpPruneGroup,
                usdDvmrpPruneSource,
                usdDvmrpPruneSourceMask }
    ::= { usdDvmrpPruneTable 1 }

UsdDvmrpPruneEntry ::= SEQUENCE {
    usdDvmrpPruneGroup              IpAddress,
    usdDvmrpPruneSource             IpAddress,
    usdDvmrpPruneSourceMask         IpAddress,
    usdDvmrpPruneIIFIfIndex         InterfaceIndex,
    usdDvmrpPruneUpTime             TimeTicks
}

usdDvmrpPruneGroup OBJECT-TYPE
    SYNTAX      IpAddress
    MAX-ACCESS  not-accessible
    STATUS      current
    DESCRIPTION
        "The group address which has been pruned."
    ::= { usdDvmrpPruneEntry 1 }

usdDvmrpPruneSource OBJECT-TYPE
    SYNTAX      IpAddress
    MAX-ACCESS  not-accessible
    STATUS      current
    DESCRIPTION
        "The address of the source or source network which has been pruned."
    ::= { usdDvmrpPruneEntry 2 }

usdDvmrpPruneSourceMask OBJECT-TYPE
    SYNTAX      IpAddress
    MAX-ACCESS  not-accessible
    STATUS      current
    DESCRIPTION
        "The address of the source or source network which has been pruned.  The
        mask must either be all 1's, or else usdDvmrpPruneSource and
        usdDvmrpPruneSourceMask must match usdDvmrpRouteSource and
        usdDvmrpRouteSourceMask for some entry in the usdDvmrpRouteTable."
    ::= { usdDvmrpPruneEntry 3 }

usdDvmrpPruneIIFIfIndex OBJECT-TYPE
    SYNTAX      InterfaceIndex
    MAX-ACCESS  read-only
    STATUS      current
    DESCRIPTION
        "The ifIndex of the upstream interface for this source group entry."
    ::= { usdDvmrpPruneEntry 4 }

usdDvmrpPruneUpTime OBJECT-TYPE
    SYNTAX      TimeTicks
    MAX-ACCESS  read-only
    STATUS      current
    DESCRIPTION
        "This is the amount of time that this prune has remained valid."
    ::= { usdDvmrpPruneEntry 5 }


--
-- The Unisphere DVMRP source group OIF table
--
usdDvmrpSrcGrpOifTable OBJECT-TYPE
    SYNTAX      SEQUENCE OF UsdDvmrpSrcGrpOifEntry
    MAX-ACCESS  not-accessible
    STATUS      current
    DESCRIPTION
        "The (conceptual) OIFs for particular source group entries."
    ::= { usdDvmrp 7 }

usdDvmrpSrcGrpOifEntry OBJECT-TYPE
    SYNTAX      UsdDvmrpSrcGrpOifEntry
    MAX-ACCESS  not-accessible
    STATUS      current
    DESCRIPTION
        "An entry (conceptual row) in the usdDvmrpSrcGrpOifTable."
    INDEX     { usdDvmrpSrcGrpOifGroup,
                usdDvmrpSrcGrpOifSource,
                usdDvmrpSrcGrpOifSourceMask,
                usdDvmrpSrcGrpOifOIFIfIndex }
    ::= { usdDvmrpSrcGrpOifTable 1 }

UsdDvmrpSrcGrpOifEntry ::= SEQUENCE {
    usdDvmrpSrcGrpOifGroup              IpAddress,
    usdDvmrpSrcGrpOifSource             IpAddress,
    usdDvmrpSrcGrpOifSourceMask         IpAddress,
    usdDvmrpSrcGrpOifOIFIfIndex         InterfaceIndex,
    usdDvmrpSrcGrpOifOIFPruned          INTEGER,
    usdDvmrpSrcGrpOifOIFDnTTL           TimeTicks    
}

usdDvmrpSrcGrpOifGroup OBJECT-TYPE
    SYNTAX      IpAddress
    MAX-ACCESS  not-accessible
    STATUS      current
    DESCRIPTION
        "The group address which has been pruned."
    ::= { usdDvmrpSrcGrpOifEntry 1 }

usdDvmrpSrcGrpOifSource OBJECT-TYPE
    SYNTAX      IpAddress
    MAX-ACCESS  not-accessible
    STATUS      current
    DESCRIPTION
        "The address of the source or source network which has been pruned."
    ::= { usdDvmrpSrcGrpOifEntry 2 }

usdDvmrpSrcGrpOifSourceMask OBJECT-TYPE
    SYNTAX      IpAddress
    MAX-ACCESS  not-accessible
    STATUS      current
    DESCRIPTION
        "The address of the source or source network which has been pruned.  The
        mask must either be all 1's, or else usdDvmrpPruneSource and
        usdDvmrpPruneSourceMask must match usdDvmrpRouteSource and
        usdDvmrpRouteSourceMask for some entry in the usdDvmrpRouteTable."
    ::= { usdDvmrpSrcGrpOifEntry 3 }

usdDvmrpSrcGrpOifOIFIfIndex OBJECT-TYPE
    SYNTAX      InterfaceIndex
    MAX-ACCESS  not-accessible
    STATUS      current
    DESCRIPTION
        "The ifIndex of one of the downstream interfaces for this source group
        entry."
    ::= { usdDvmrpSrcGrpOifEntry 4 }

usdDvmrpSrcGrpOifOIFPruned OBJECT-TYPE
    SYNTAX      INTEGER {
                    false(0),
                    true(1)
                }
    MAX-ACCESS  read-only
    STATUS      current
    DESCRIPTION
        "If true this oif has been pruned."
    ::= { usdDvmrpSrcGrpOifEntry 5 }

usdDvmrpSrcGrpOifOIFDnTTL OBJECT-TYPE
    SYNTAX      TimeTicks
    MAX-ACCESS  read-only
    STATUS      current
    DESCRIPTION
        "The timeout for this OIF.  If usdDvmrpSrcGrpOifOIFPruned is false then
        this is undefined."
    ::= { usdDvmrpSrcGrpOifEntry 6 }


-- +++++++++++++++++++++++++++++++++++++++++++++++++++++++++++++++++++++++++++++
-- Notifications
-- +++++++++++++++++++++++++++++++++++++++++++++++++++++++++++++++++++++++++++++

usdDvmrpTraps OBJECT IDENTIFIER ::= { usdDvmrp 0 }

usdDvmrpRouteHogNotificationTrap NOTIFICATION-TYPE
    STATUS      current
    DESCRIPTION
        "This is an indication that the route hog notification limit has been
        exceeded during the past minute.  It may mean that a route surge is
        going on."
   ::= { usdDvmrpTraps 1 }


-- ++++++++++++++++++++++++++++++++++++++++++++++++++++++++++++++++++++++
-- Conformance information
-- ++++++++++++++++++++++++++++++++++++++++++++++++++++++++++++++++++++++

usdDvmrpConformance OBJECT IDENTIFIER ::= { usdDvmrpMIB 4 }
usdDvmrpCompliances OBJECT IDENTIFIER ::= { usdDvmrpConformance 1 }
usdDvmrpGroups      OBJECT IDENTIFIER ::= { usdDvmrpConformance 2 }

-- compliance statements

usdDvmrpCompliance MODULE-COMPLIANCE
    STATUS      current
    DESCRIPTION
        "The compliance statement for entities which implement the Unisphere
        DVMRP MIB."
    MODULE   -- this module
        MANDATORY-GROUPS {
            usdDvmrpBaseGroup,
            usdDvmrpAclDistNbrGroup,
            usdDvmrpInterfaceGroup,
            usdDvmrpSourceGroup }
    ::= { usdDvmrpCompliances 1 }                                      -- RX 3.0


--
-- units of conformance
--
usdDvmrpBaseGroup OBJECT-GROUP
    OBJECTS {
        usdDvmrpAdminState,
        usdDvmrpMcastAdminState,
        usdDvmrpRouteHogNotification,
        usdDvmrpRouteLimit,
        usdDvmrpS32PrunesOnly }
    STATUS      current
    DESCRIPTION
        "A collection of objects providing basic management of DVMRP in a
        Unisphere product."
    ::= { usdDvmrpGroups 1 }

usdDvmrpAclDistNbrGroup OBJECT-GROUP
    OBJECTS {
        usdDvmrpAclDistNbrDistance,
        usdDvmrpAclDistNbrNbrListName,
        usdDvmrpAclDistNbrStatus }
    STATUS      current
    DESCRIPTION
        "A collection of objects providing management of DVMRP access list
        distance neighbors in a Unisphere product."
    ::= { usdDvmrpGroups 2 }

usdDvmrpInterfaceGroup OBJECT-GROUP
    OBJECTS {
        usdDvmrpLocalAddrMask,

        usdDvmrpSummaryAddrCost,
        usdDvmrpSummaryAddrStatus,

        usdDvmrpInterfaceAutoSummary,
        usdDvmrpInterfaceMetricOffsetOut,
        usdDvmrpInterfaceMetricOffsetIn,
        usdDvmrpInterfaceAdminState }
    STATUS      current
    DESCRIPTION
        "A collection of objects providing management of a DVMRP interface in a
        Unisphere product."
    ::= { usdDvmrpGroups 3 }

usdDvmrpSourceGroup OBJECT-GROUP
    OBJECTS {
        usdDvmrpPruneIIFIfIndex,
        usdDvmrpPruneUpTime,

        usdDvmrpSrcGrpOifOIFPruned,
        usdDvmrpSrcGrpOifOIFDnTTL }
    STATUS      current
    DESCRIPTION
        "A collection of objects providing management of a DVMRP source group in
        a Unisphere product."
    ::= { usdDvmrpGroups 4 }

usdDvmrpNotificationGroup NOTIFICATION-GROUP
    NOTIFICATIONS {
        usdDvmrpRouteHogNotificationTrap }
    STATUS      current
    DESCRIPTION
        "A notification for signaling important DVMRP events."
    ::= { usdDvmrpGroups 8 }

END
