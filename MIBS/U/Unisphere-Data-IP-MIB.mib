-- *****************************************************************************
-- Unisphere-Data-IP-MIB
--
-- Unisphere Networks Inc. Enterprise MIB
-- Extensions for IP Protocol Management
--
-- Copyright (c) 1998, 1999 Redstone Communications, Incorporated.
-- Copyright (c) 1999, 2002 Unisphere Networks, Incorporated.
-- All Rights Reserved.
-- *****************************************************************************

Unisphere-Data-IP-MIB DEFINITIONS ::= BEGIN

IMPORTS
    MODULE-IDENTITY, OBJECT-TYPE, Integer32, Unsigned32, IpAddress, Counter64
        FROM SNMPv2-SMI
    RowStatus
        FROM SNMPv2-TC
    MODULE-COMPLIANCE, OBJECT-GROUP
        FROM SNMPv2-CONF
    InterfaceIndex, InterfaceIndexOrZero
        FROM IF-MIB
    ipCidrRouteEntry
        FROM IP-FORWARD-MIB
    usDataMibs
        FROM Unisphere-Data-MIBs
    UsdEnable, UsdIpAddrLessIf, UsdNextIfIndex
        FROM Unisphere-Data-TC;

usdIpMIB  MODULE-IDENTITY
    LAST-UPDATED "200204031404Z"  -- 03-Apr-02 09:04 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The IP Protocol MIB for the Unisphere Networks Inc. enterprise."
    -- Revision History
    REVISION    "200204031404Z"  -- 03-Apr-02 09:04 AM EST  - RX 4.0
    DESCRIPTION
        "Obsoleted the following objects with the introduction of QoS:
            usdIpIfStatsInForwardedPackets
            usdIpIfStatsInForwardedOctets
            usdIpIfStatsOutRequestedPackets
            usdIpIfStatsOutRequesteOctets
            usdIpIfStatsGreenOutSchedDropPackets
            usdIpIfStatsYellowOutSchedDropPackets
            usdIpIfStatsRedOutSchedDropOctets
            usdIpIfStatsGreenOutSchedDropOctets
            usdIpIfStatsYellowOutSchedDropOctets
            usdIpIfStatsRedOutSchedDropOctet "
    REVISION    "200107051400Z"  -- 05-Jul-01 10:00 AM EDT  - RX 3.2
    DESCRIPTION
        "Added the usdIpIfAssocTable."
    REVISION    "200106181911Z"  -- 18-Jun-01 03:11 PM EDT  - RX 3.0
    DESCRIPTION
        "o In usdIpIfTable, added the following:
                usdIpIfSAValidation
                usdIpIfCreationType
                usdIpIfProfileId
                usdIpIfAlwaysUp
                usdIpIfLoopback
                usdIpIfLoopbackUid
                usdIpIfDebounceTime
                usdIpIfForwarding
                usdIpIfForceFragmentation
                usdIpIfSharesLowerUid
                usdIpIfFilterOptions
                usdIpIfName
                usdIpIfArpTimeout
                usdIpIfAdminSpeed
                usdIpIfMultipathMode
                usdIpIfSharedNhAddr
                usdIpIfSharedNhRouterId
                usdIpIfPrimaryIpAddress
                usdIpIfPrimaryIpMask
                usdIpIfOperDebounceTime
         o In usdIpAddrTable, added usdIpAdEntIsSecondary
         o In usdIpAddrTable, deprecated usdIpAdEntIgmpEnable
         o Added following scalars:
             usdIpDebounceTime
             usdIpRouterId
             usdIpSourceRoutingAdminStatus
             usdIpVpnIdOui
             usdIpVpnIdIndex
         o In usdIpIfStatsTable, added:
             usdIpIfStatsGreenOutSchedDropPackets
             usdIpIfStatsYellowOutSchedDropPackets
             usdIpIfStatsRedOutSchedDropPackets
             usdIpIfStatsGreenOutSchedDropOctets
             usdIpIfStatsYellowOutSchedDropOctets
             usdIpIfStatsRedOutSchedDropOctets
         o Changed the type of usdIpRouteStaticNextHop to UsdIpAddrLessIf to
           support setting static routes next hop values to unnumbered IP
           interfaces.  This type is a Unisphere TC, which can transparently
           support the original IpAddress type, so existing clients are not
           negatively affected by this change."
    REVISION    "200007310000Z"  -- 31-Jul-00               - RX 2.2
    DESCRIPTION
        "o Added extended IP interface statistics."
    REVISION      "9911090000Z"  --  9-Nov-99               - RX 1.3
    DESCRIPTION
        "o In usdIpIfTable, added null(5) enumeration value for usdIpIfType.
         o Added usdIpIfTypeId object."
    REVISION      "9909160000Z"  -- 16-Sep-99               - RX 1.1
    DESCRIPTION
        "o In usdIpAddrTable, added usdIpAdEntUnnumLoopbackIfIndex,
           usdIpAdEntIrdpEnable, usdIpAdEntAccessRouteEnable,
           usdIpAdEntAccessRouteHost.
         o In usdIpRouteStaticTable, changed Tos to Preference, and added Tag.
         o Added usdIpCidrRouteTable (proprietary extensions to standard
           ipCidrRouteTable)."
    REVISION      "9811190000Z"  -- 19-Nov-98               - RX 1.0
    DESCRIPTION
        "Initial version of this MIB module."
    ::= { usDataMibs 12 }


-- +++++++++++++++++++++++++++++++++++++++++++++++++++++++++++++++++++++++++++++
-- Textual conventions
-- +++++++++++++++++++++++++++++++++++++++++++++++++++++++++++++++++++++++++++++
-- No textual conventions are defined in this MIB.


-- +++++++++++++++++++++++++++++++++++++++++++++++++++++++++++++++++++++++++++++
-- Managed objects
-- +++++++++++++++++++++++++++++++++++++++++++++++++++++++++++++++++++++++++++++
usdIpObjects     OBJECT IDENTIFIER ::= { usdIpMIB 1 }

usdIpInterface   OBJECT IDENTIFIER ::= { usdIpObjects 1 }
usdIpAddress     OBJECT IDENTIFIER ::= { usdIpObjects 2 }
usdIpRoute       OBJECT IDENTIFIER ::= { usdIpObjects 3 }
usdIpGlobals     OBJECT IDENTIFIER ::= { usdIpObjects 4 }


-- +++++++++++++++++++++++++++++++++++++++++++++++++++++++++++++++++++++++++++++
-- IP Global attributes
-- +++++++++++++++++++++++++++++++++++++++++++++++++++++++++++++++++++++++++++++
usdIpDebounceTime  OBJECT-TYPE
    SYNTAX      Integer32 (0..60000)
    UNITS       "milliseconds"
    MAX-ACCESS  read-write
    STATUS      current
    DESCRIPTION
        "The time in milliseconds that an event has to be in the same state
        before being reported."
    DEFVAL    { 0 }
    ::= { usdIpGlobals 1 }

usdIpRouterId  OBJECT-TYPE
    SYNTAX      IpAddress
    MAX-ACCESS  read-write
    STATUS      current
    DESCRIPTION
        "The router-id that this IP router will use to identify itself."
    ::= { usdIpGlobals 2 }

usdIpSourceRoutingAdminStatus  OBJECT-TYPE
    SYNTAX      UsdEnable
    MAX-ACCESS  read-write
    STATUS      current
    DESCRIPTION
        "The administrative setting for source routing."
    ::= { usdIpGlobals 3 }

usdIpVpnIdOui  OBJECT-TYPE
    SYNTAX      INTEGER (0..16777215)
    MAX-ACCESS  read-write
    STATUS      current
    DESCRIPTION
        "The OUI portion of the VPN identifier.  This object must be set
        coincident with the index portion of the VpnId (usdIpVpnIdIndex),
        otherwise the set will fail."
    ::= { usdIpGlobals 4 }

usdIpVpnIdIndex  OBJECT-TYPE
    SYNTAX      IpAddress
    MAX-ACCESS  read-write
    STATUS      current
    DESCRIPTION
        "The index portion of the VPN identifier.  This object must be set
         coincident with the OUI portion of the VpnId (usdIpVpnOui), otherwise
         the set will fail."
    ::= { usdIpGlobals 5 }


-- +++++++++++++++++++++++++++++++++++++++++++++++++++++++++++++++++++++++++++++
-- IP Interface attributes
-- +++++++++++++++++++++++++++++++++++++++++++++++++++++++++++++++++++++++++++++
--
-- IfIndex selection for creating new IP interfaces
--
usdIpNextIfIndex OBJECT-TYPE
    SYNTAX      UsdNextIfIndex
    MAX-ACCESS  read-only
    STATUS      current
    DESCRIPTION
        "Coordinate ifIndex value allocation for entries in usdIpIfTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously.  "
    ::= { usdIpInterface 1 }


--
-- The IP Interface Table
--
usdIpIfTable OBJECT-TYPE
    SYNTAX      SEQUENCE OF UsdIpIfEntry
    MAX-ACCESS  not-accessible
    STATUS      current
    DESCRIPTION
        "This table contains entries for IP interfaces present in the system."
    ::= { usdIpInterface 2 }

usdIpIfEntry OBJECT-TYPE
    SYNTAX      UsdIpIfEntry
    MAX-ACCESS  not-accessible
    STATUS      current
    DESCRIPTION
        "Each entry describes the characteristics of an IP interface.
        Creating/deleting entries in this table causes corresponding entries for
        be created/deleted in ifTable/ifXTable/usdIfTable."
    INDEX     { usdIpIfIndex }
    ::= { usdIpIfTable 1 }

UsdIpIfEntry ::= SEQUENCE {
    usdIpIfIndex                InterfaceIndex,
    usdIpIfRowStatus            RowStatus,
    usdIpIfLowerIfIndex         InterfaceIndexOrZero,
    usdIpIfType                 INTEGER,
    usdIpIfTypeId               Unsigned32,
    usdIpIfSAValidationEnable   UsdEnable,
    usdIpIfCreationType         INTEGER,
    usdIpIfProfileId            Unsigned32,
    usdIpIfAlwaysUp             UsdEnable,
    usdIpIfLoopback             UsdEnable,
    usdIpIfLoopbackUid          InterfaceIndexOrZero,
    usdIpIfDebounceTime         Integer32,
    usdIpIfForwarding           UsdEnable,
    usdIpIfForceFragmentation   UsdEnable,
    usdIpIfSharesLowerUid       UsdEnable,
    usdIpIfFilterOptions        Unsigned32,
    usdIpIfName                 OCTET STRING,
    usdIpIfArpTimeout           Unsigned32,
    usdIpIfAdminSpeed           Unsigned32,
    usdIpIfMultipathMode        INTEGER,
    usdIpIfSharedNhAddr         IpAddress,
    usdIpIfSharedNhRouterId     Unsigned32,
    usdIpIfPrimaryIpAddress     IpAddress,
    usdIpIfPrimaryIpMask        IpAddress,
    usdIpIfOperDebounceTime     Integer32 }

usdIpIfIndex OBJECT-TYPE
    SYNTAX      InterfaceIndex
    MAX-ACCESS  not-accessible
    STATUS      current
    DESCRIPTION
        "The ifIndex of the IP interface.  When creating entries in this table,
        suitable values for this object are determined by reading
        usdIpNextIfIndex."
    ::= { usdIpIfEntry 1 }

usdIpIfRowStatus OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdIpIfRowStatus
            usdIpIfLowerIfIndex

        In addition, when creating an entry the following conditions must hold:

            A value for usdIpIfIndex must have been determined previously,
            typically by reading usdIpNextIfIndex.

            The interface identified by a nonzero usdIpIfLowerIfIndex must exist.

            If usdIpIfType is configured to be 'loopback' or 'null',
            usdIpIfLowerIfIndex must be set to zero.

            The selected value of usdIpIfType must be compatible with the
            underlying media interface identified by usdIpIfLowerIfIndex.

        Once created, the following objects may not be modified:
            usdIpIfLowerIfIndex
            usdIpIfType
            usdIpIfTypeId

        A corresponding entry in ifTable/ifXTable/usdIfTable is created/destroyed
        as a result of creating/destroying an entry in this table."
    ::= { usdIpIfEntry 2 }

usdIpIfLowerIfIndex OBJECT-TYPE
    SYNTAX      InterfaceIndexOrZero
    MAX-ACCESS  read-create
    STATUS      current
    DESCRIPTION
        "The ifIndex of a media interface over which this IP interface is to be
        layered.  A value of zero is used when usdIpIfType is specified to be
        loopback(4) or null(5)."
    ::= { usdIpIfEntry 3 }

usdIpIfType OBJECT-TYPE
    SYNTAX      INTEGER {
                    other(0),
                    broadcast(1),
                    pointToPoint(2),
                    nbma(3),
                    loopback(4),
                    null(5) }
    MAX-ACCESS  read-create
    STATUS      current
    DESCRIPTION
        "The type of network interface."
    DEFVAL    { pointToPoint }
    ::= { usdIpIfEntry 4 }

usdIpIfTypeId OBJECT-TYPE
    SYNTAX      Unsigned32
    MAX-ACCESS  read-create
    STATUS      current
    DESCRIPTION
        "A numerical distinguisher relevant for the loopback and null IP
        interface types.
            loopback    Must be unique for all IP interfaces of this type.
            null        Must be unique for all IP interfaces of this type.
                        (FOR IMPLEMENTATIONS THAT SUPPORT ONE AND ONLY ONE NULL
                        INTERFACE, THE VALUE ZERO MUST BE USED.)

        For all other IP interface types, this object is not relevant, reports a
        value of zero when read, and must be given a value of zero if explicitly
        configured during creation."
    DEFVAL    { 0 }
    ::= { usdIpIfEntry 5 }

usdIpIfSAValidationEnable OBJECT-TYPE
    SYNTAX      UsdEnable
    MAX-ACCESS  read-create
    STATUS      current
    DESCRIPTION
        "Enable/disable source address validation on this IP network interface."
    DEFVAL    { disable }
    ::= { usdIpIfEntry 6 }

usdIpIfCreationType OBJECT-TYPE
    SYNTAX      INTEGER {
                    static(1),
                    dynamic(2) }
    MAX-ACCESS  read-only
    STATUS      current
    DESCRIPTION
        "Specify if the interface was created due to static configuration or due
        to some dynamic event.  Dynamic interfaces are not stored in NVS."
    ::= { usdIpIfEntry 7 }

usdIpIfProfileId OBJECT-TYPE
    SYNTAX      Unsigned32
    MAX-ACCESS  read-only
    STATUS      current
    DESCRIPTION
        "Identified the profile used when creating a dynamic interface."
    DEFVAL    { 0 }
    ::= { usdIpIfEntry 8 }

usdIpIfAlwaysUp OBJECT-TYPE
    SYNTAX      UsdEnable
    MAX-ACCESS  read-create
    STATUS      current
    DESCRIPTION
        "When enabled, the interface is determined to be up regardless of the
        state of any lower layer interfaces."
    DEFVAL    { disable }
    ::= { usdIpIfEntry 9 }

usdIpIfLoopback OBJECT-TYPE
    SYNTAX      UsdEnable
    MAX-ACCESS  read-create
    STATUS      current
    DESCRIPTION
        "Indicates whether the interface is a loopback type interface."
    DEFVAL    { disable }
    ::= { usdIpIfEntry 10 }

usdIpIfLoopbackUid OBJECT-TYPE
    SYNTAX      InterfaceIndexOrZero
    MAX-ACCESS  read-create
    STATUS      current
    DESCRIPTION
        "Specify the interface index of a loopback interface whose IP address
        should be used when sourcing traffic on this interface.  Useful for
        unnumbered interfaces."
    DEFVAL    { 0 }
    ::= { usdIpIfEntry 11 }

usdIpIfDebounceTime OBJECT-TYPE
    SYNTAX      Integer32 (0..60000)
    UNITS       "milliseconds"
    MAX-ACCESS  read-create
    STATUS      current
    DESCRIPTION
        "Specifies the time in milliseconds that a layer 2 interface must remain
        in a state before it is conveyed to the IP layer.  Useful for interfaces
        that experience brief outages that should not constitute a route flap.
        A value of 0 indicates that the feature is disabled."
    DEFVAL    { 0 }
    ::= { usdIpIfEntry 12 }

usdIpIfForwarding OBJECT-TYPE
    SYNTAX      UsdEnable
    MAX-ACCESS  read-create
    STATUS      current
    DESCRIPTION
        "Enable/disable the forwarding of IP traffic to/from this interface.
        This is currently only applicable to the out-of-band management port."
    DEFVAL    { enable }
    ::= { usdIpIfEntry 13 }

usdIpIfForceFragmentation OBJECT-TYPE
    SYNTAX      UsdEnable
    MAX-ACCESS  read-create
    STATUS      current
    DESCRIPTION
        "Force the fragmentation of all IP packets greater than the interface
        MTU even if the DF bit is set."
    DEFVAL    { disable }
    ::= { usdIpIfEntry 14 }

usdIpIfSharesLowerUid OBJECT-TYPE
    SYNTAX      UsdEnable
    MAX-ACCESS  read-only
    STATUS      current
    DESCRIPTION
        "Identifies the interface as sharing a lower interface with another
        interface vs owning it outright."
    ::= { usdIpIfEntry 15 }

usdIpIfFilterOptions OBJECT-TYPE
    SYNTAX      Unsigned32
    MAX-ACCESS  read-create
    STATUS      current
    DESCRIPTION
        "Bit mask to configure the interface to filter packets with IP header
        options.  Currently, either no bits or all bits may be set."
    DEFVAL    { 0 }
    ::= { usdIpIfEntry 16 }

usdIpIfName OBJECT-TYPE
    SYNTAX      OCTET STRING (SIZE(0..255))
    MAX-ACCESS  read-create
    STATUS      current
    DESCRIPTION
        "Specify the IP interface discriminator for an IP interface not attached
        to a layer 2 interface with a specific location."
    DEFVAL    { ''H }
    ::= { usdIpIfEntry 17 }

usdIpIfArpTimeout OBJECT-TYPE
    SYNTAX      Unsigned32
    MAX-ACCESS  read-create
    STATUS      current
    DESCRIPTION
        "Specify the ARP timeout for this interface in seconds."
    DEFVAL    { 21600 }
    ::= { usdIpIfEntry 18 }


usdIpIfAdminSpeed OBJECT-TYPE
    SYNTAX      Unsigned32
    MAX-ACCESS  read-create
    STATUS      current
    DESCRIPTION
        "Set an administrative speed for the interface that overrides the speed
        learned from the lower layer.  A value of 0 indicates no speed is
        specified."
    DEFVAL    { 0 }
    ::= { usdIpIfEntry 19 }

usdIpIfMultipathMode OBJECT-TYPE
    SYNTAX      INTEGER {
                    hashed(1),
                    roundRobin(2) }
    MAX-ACCESS  read-create
    STATUS      current
    DESCRIPTION
        "Configure the mode this interface should use when forwarding equal-cost
        multipath traffic."
    DEFVAL    { hashed }
    ::= { usdIpIfEntry 20 }

usdIpIfSharedNhAddr OBJECT-TYPE
    SYNTAX      IpAddress
    MAX-ACCESS  read-create
    STATUS      current
    DESCRIPTION
        "The IP address of either a direct or indirect next-hop toward which
        this shared interface should point."
    DEFVAL    { 0 }
    ::= { usdIpIfEntry 21 }

usdIpIfSharedNhRouterId OBJECT-TYPE
    SYNTAX      Unsigned32
    MAX-ACCESS  read-create
    STATUS      current
    DESCRIPTION
        "The identifier for the domain of a virtual router in which the
        usdIpIfSharedNhAddr should be resolved."
    DEFVAL    { 0 }
    ::= { usdIpIfEntry 22 }

usdIpIfPrimaryIpAddress OBJECT-TYPE
    SYNTAX      IpAddress
    MAX-ACCESS  read-only
    STATUS      current
    DESCRIPTION
        "The IP address of the primary IP network on an interface."
    ::= { usdIpIfEntry 23 }

usdIpIfPrimaryIpMask OBJECT-TYPE
    SYNTAX      IpAddress
    MAX-ACCESS  read-only
    STATUS      current
    DESCRIPTION
        "The IP address mask of the primary IP network on an interface."
    ::= { usdIpIfEntry 24 }

usdIpIfOperDebounceTime OBJECT-TYPE
    SYNTAX      Integer32 (0..60000)
    UNITS       "milliseconds"
    MAX-ACCESS  read-only
    STATUS      current
    DESCRIPTION
        "Indicates the operational time in milliseconds that a layer2 interface
        must remain in a state before it is conveyed to the IP layer.  Useful
        for interfaces that experience brief outages that should not constitute
        a route flap.  A value of 0 indicates that the feature is disabled."
    ::= { usdIpIfEntry 25 }


--
-- The IP Interface Statistics Table
--

usdIpIfStatsTable OBJECT-TYPE
    SYNTAX      SEQUENCE OF UsdIpIfStatsEntry
    MAX-ACCESS  not-accessible
    STATUS      current
    DESCRIPTION
        "This table contains entries for IP interfaces present in the system."
    ::= { usdIpInterface 3 }

usdIpIfStatsEntry OBJECT-TYPE
    SYNTAX      UsdIpIfStatsEntry
    MAX-ACCESS  not-accessible
    STATUS      current
    DESCRIPTION
        "Each entry contains statistics for an IP interface."
    INDEX     { usdIpIfStatsIndex }
    ::= { usdIpIfStatsTable 1 }

UsdIpIfStatsEntry ::= SEQUENCE {
    usdIpIfStatsIndex                       InterfaceIndex,
    usdIpIfStatsInPackets                   Counter64,
    usdIpIfStatsInOctets                    Counter64,
    usdIpIfStatsInPoliciedPackets           Counter64,
    usdIpIfStatsInPoliciedOctets            Counter64,
    usdIpIfStatsInErrorPackets              Counter64,
    usdIpIfStatsInSpoofedPackets            Counter64,
    usdIpIfStatsInForwardedPackets          Counter64,
    usdIpIfStatsInForwardedOctets           Counter64,
    usdIpIfStatsOutForwardedPackets         Counter64,
    usdIpIfStatsOutForwardedOctets          Counter64,
    usdIpIfStatsOutSchedDropPackets         Counter64,
    usdIpIfStatsOutSchedDropOctets          Counter64,
    usdIpIfStatsOutRequestedPackets         Counter64,
    usdIpIfStatsOutRequestedOctets          Counter64,
    usdIpIfStatsOutPoliciedPackets          Counter64,
    usdIpIfStatsOutPoliciedOctets           Counter64,
    usdIpIfStatsGreenOutSchedDropPackets    Counter64,
    usdIpIfStatsYellowOutSchedDropPackets   Counter64,
    usdIpIfStatsRedOutSchedDropPackets      Counter64,
    usdIpIfStatsGreenOutSchedDropOctets     Counter64,
    usdIpIfStatsYellowOutSchedDropOctets    Counter64,
    usdIpIfStatsRedOutSchedDropOctets       Counter64 }

usdIpIfStatsIndex OBJECT-TYPE
    SYNTAX      InterfaceIndex
    MAX-ACCESS  not-accessible
    STATUS      current
    DESCRIPTION
        "The ifIndex of the IP interface."
    ::= { usdIpIfStatsEntry 1 }

usdIpIfStatsInPackets OBJECT-TYPE
    SYNTAX      Counter64
    MAX-ACCESS  read-only
    STATUS      current
    DESCRIPTION
        "The number of packets received on this interface."
    ::= { usdIpIfStatsEntry 2 }

usdIpIfStatsInOctets OBJECT-TYPE
    SYNTAX      Counter64
    MAX-ACCESS  read-only
    STATUS      current
    DESCRIPTION
        "The number of octets received on this interface."
    ::= { usdIpIfStatsEntry 3 }

usdIpIfStatsInPoliciedPackets OBJECT-TYPE
    SYNTAX      Counter64
    MAX-ACCESS  read-only
    STATUS      current
    DESCRIPTION
        "The number of packets dropped due to rate limiters attached to this
        interface."
    ::= { usdIpIfStatsEntry 4 }

usdIpIfStatsInPoliciedOctets OBJECT-TYPE
    SYNTAX      Counter64
    MAX-ACCESS  read-only
    STATUS      current
    DESCRIPTION
        "The number of octets dropped due to rate limiters attached to this
        interface."
    ::= { usdIpIfStatsEntry 5 }

usdIpIfStatsInErrorPackets OBJECT-TYPE
    SYNTAX      Counter64
    MAX-ACCESS  read-only
    STATUS      current
    DESCRIPTION
        "The number of packets received with errors on this interface."
    ::= { usdIpIfStatsEntry 6 }

usdIpIfStatsInSpoofedPackets OBJECT-TYPE
    SYNTAX      Counter64
    MAX-ACCESS  read-only
    STATUS      current
    DESCRIPTION
        "The number of packets received on this interface with destination
        unknown."
    ::= { usdIpIfStatsEntry 7 }

usdIpIfStatsInForwardedPackets OBJECT-TYPE
    SYNTAX      Counter64
    MAX-ACCESS  read-only
    STATUS      obsolete
    DESCRIPTION
        "The number of packets received on this interface that were forwarded
        by any interface in the system."
    ::= { usdIpIfStatsEntry 8 }

usdIpIfStatsInForwardedOctets OBJECT-TYPE
    SYNTAX      Counter64
    MAX-ACCESS  read-only
    STATUS      obsolete
    DESCRIPTION
        "The number of octets received on this interface that were forwarded by
        any interface in the system."
    ::= { usdIpIfStatsEntry 9 }

usdIpIfStatsOutForwardedPackets OBJECT-TYPE
    SYNTAX      Counter64
    MAX-ACCESS  read-only
    STATUS      current
    DESCRIPTION
        "The number of packets forwarded by this interface."
    ::= { usdIpIfStatsEntry 10 }

usdIpIfStatsOutForwardedOctets OBJECT-TYPE
    SYNTAX      Counter64
    MAX-ACCESS  read-only
    STATUS      current
    DESCRIPTION
        "The number of octets forwarded by this interface."
    ::= { usdIpIfStatsEntry 11 }

usdIpIfStatsOutSchedDropPackets OBJECT-TYPE
    SYNTAX      Counter64
    MAX-ACCESS  read-only
    STATUS      current
    DESCRIPTION
        "The number of packets dropped at this interface due to output queue
        congestion."
    ::= { usdIpIfStatsEntry 12 }

usdIpIfStatsOutSchedDropOctets OBJECT-TYPE
    SYNTAX      Counter64
    MAX-ACCESS  read-only
    STATUS      current
    DESCRIPTION
        "The number of octets dropped at this interface due to output queue
        congestion."
    ::= { usdIpIfStatsEntry 13 }

usdIpIfStatsOutRequestedPackets OBJECT-TYPE
    SYNTAX      Counter64
    MAX-ACCESS  read-only
    STATUS      obsolete
    DESCRIPTION
        "The number of packets requested for transmission at this interface."
    ::= { usdIpIfStatsEntry 14 }

usdIpIfStatsOutRequestedOctets OBJECT-TYPE
    SYNTAX      Counter64
    MAX-ACCESS  read-only
    STATUS      obsolete
    DESCRIPTION
        "The number of octets requested for transmission at this interface."
    ::= { usdIpIfStatsEntry 15 }

usdIpIfStatsOutPoliciedPackets OBJECT-TYPE
    SYNTAX      Counter64
    MAX-ACCESS  read-only
    STATUS      current
    DESCRIPTION
        "The number of packets dropped due to rate limiters attached to this
        interface."
    ::= { usdIpIfStatsEntry 16 }

usdIpIfStatsOutPoliciedOctets OBJECT-TYPE
    SYNTAX      Counter64
    MAX-ACCESS  read-only
    STATUS      current
    DESCRIPTION
        "The number of octets dropped due to rate limiters attached to this
        interface."
    ::= { usdIpIfStatsEntry 17 }

usdIpIfStatsGreenOutSchedDropPackets OBJECT-TYPE
    SYNTAX      Counter64
    MAX-ACCESS  read-only
    STATUS      deprecated
    DESCRIPTION
        "The number of packets dropped at this interface due to output queue
        congestion in the green output queue.  The green output queue has lowest
        drop probability."
    ::= { usdIpIfStatsEntry 18 }

usdIpIfStatsYellowOutSchedDropPackets OBJECT-TYPE
    SYNTAX      Counter64
    MAX-ACCESS  read-only
    STATUS      deprecated
    DESCRIPTION
        "The number of packets dropped at this interface due to output queue
        congestion in the yellow output queue.  The yellow output queue has
        medium level drop probability."
    ::= { usdIpIfStatsEntry 19 }

usdIpIfStatsRedOutSchedDropPackets OBJECT-TYPE
    SYNTAX      Counter64
    MAX-ACCESS  read-only
    STATUS      deprecated
    DESCRIPTION
        "The number of packets dropped at this interface due to output queue
        congestion in the red output queue.  The red output queue has highest
        level drop probability."
    ::= { usdIpIfStatsEntry 20 }

usdIpIfStatsGreenOutSchedDropOctets OBJECT-TYPE
    SYNTAX      Counter64
    MAX-ACCESS  read-only
    STATUS      deprecated
    DESCRIPTION
        "The number of octets dropped at this interface due to output queue
        congestion in the green output queue.  The green output queue has the
        lowest drop probability."
    ::= { usdIpIfStatsEntry 21 }

usdIpIfStatsYellowOutSchedDropOctets OBJECT-TYPE
    SYNTAX      Counter64
    MAX-ACCESS  read-only
    STATUS      deprecated
    DESCRIPTION
        "The number of octets dropped at this interface due to output queue
        congestion in the yellow output queue.  The yellow output queue has the
        medium drop probability."
    ::= { usdIpIfStatsEntry 22 }

usdIpIfStatsRedOutSchedDropOctets OBJECT-TYPE
    SYNTAX      Counter64
    MAX-ACCESS  read-only
    STATUS      deprecated
    DESCRIPTION
        "The number of octets dropped at this interface due to output queue
        congestion in the red output queue.  The red output queue has the
        highest drop probability."
    ::= { usdIpIfStatsEntry 23 }


--
-- The IP Interface Association Table
--
usdIpIfAssocTable OBJECT-TYPE
    SYNTAX      SEQUENCE OF UsdIpIfAssocEntry
    MAX-ACCESS  not-accessible
    STATUS      current
    DESCRIPTION
        "This table contains entries of interfaces present in the system."
    ::= { usdIpInterface 4 }

usdIpIfAssocEntry OBJECT-TYPE
    SYNTAX      UsdIpIfAssocEntry
    MAX-ACCESS  not-accessible
    STATUS      current
    DESCRIPTION
        "Each entry in this table returns the ifIndex of the IP interface
        associated with the lower layer ifIndex supplied as the index to this
        table.

        The purpose of this table is to translate L2 interfaces to corresponding
        L3 interfaces for billing applications.  Since interesting billing
        related statistics are kept at L3, it is often useful to know the L2-L3
        relationship.  Note that this table is not confined to L2-L3
        relationships.  Any interface sublayer can be used to access this table
        to determine the relationship with the L3 interface."
    INDEX   { usdIpIfAssocLowerIfIndex }
    ::= { usdIpIfAssocTable 1 }

UsdIpIfAssocEntry ::= SEQUENCE {
    usdIpIfAssocLowerIfIndex    InterfaceIndex,
    usdIpIfAssocIpIfIndex       InterfaceIndexOrZero }

usdIpIfAssocLowerIfIndex OBJECT-TYPE
    SYNTAX      InterfaceIndex
    MAX-ACCESS  not-accessible
    STATUS      current
    DESCRIPTION
        "The ifIndex of the lower layer interface."
    ::= { usdIpIfAssocEntry 1 }

usdIpIfAssocIpIfIndex OBJECT-TYPE
    SYNTAX     InterfaceIndexOrZero
    MAX-ACCESS read-only
    STATUS     current
    DESCRIPTION
        "The ifIndex of the IP interface associated with the lower layer
        usdIpIfAssocLowerIfIndex.  In cases where there is not a 1 to 1
        relationship between lower layer and higher layer IP interface, a zero
        value usdIpIfAssocIpIfIndex is returned; this includes the case where an
        IP interface has not yet been configued at the top of the interface
        column.

        An example usage of this table:

        Assume a user needs to know the ifIndex relationship for all interfaces
        with the L3 IP interface.

        Then starting at the bottom of the stack below, the ATM and AAL5's
        ifIndex would be used to access the table.  The agent will return 0 for
        each of these cases because multiple customer's traffic is demultiplexed
        at these levels.

         IP_1
         PPP        IP_2
         ATM1483_1  ATM1483_2
           \         /
              AAL5
              ATM

        If the ATM1483_1 ifIndex is used to access this table, then the value of
        usdIpIfAssocLowerIfIndex will be set to the ifIndex of IP_1.  Similarily,
        if the ATM1483_2 ifIndex is used to access this table, the
        usdIpifAssocLowerIfIndex will set to the ifIndex of IP_2."
    ::= { usdIpIfAssocEntry 2 }


-- +++++++++++++++++++++++++++++++++++++++++++++++++++++++++++++++++++++++++++++
-- IP Address attributes
-- +++++++++++++++++++++++++++++++++++++++++++++++++++++++++++++++++++++++++++++
--
-- IP globals
--
usdIpAddrGlobals  OBJECT IDENTIFIER ::= { usdIpAddress 1 }

usdIpArpTimeout OBJECT-TYPE
    SYNTAX      Integer32 (1..60)
    UNITS       "seconds"
    MAX-ACCESS  read-write
    STATUS      current
    DESCRIPTION
        "Timeout, in seconds, for ARP requests issued by this entity."
    ::= { usdIpAddrGlobals 1 }

--
-- IP Address management
--
usdIpAddrTable OBJECT-TYPE
    SYNTAX      SEQUENCE OF UsdIpAddrEntry
    MAX-ACCESS  not-accessible
    STATUS      current
    DESCRIPTION
        "IP addressing information for this entity's IP network interfaces.
        Representation of both numbered and unnumbered IP interfaces is
        supported."
    ::= { usdIpAddress 2 }

usdIpAddrEntry OBJECT-TYPE
    SYNTAX      UsdIpAddrEntry
    MAX-ACCESS  not-accessible
    STATUS      current
    DESCRIPTION
        "IP addressing information for one of this entity's IP network
        interfaces.  This interface could be either numbered or unnumbered.

        The following objects correspond to (read-only) counterparts in the
        IP-MIB ipAddrTable:
            usdIpAdEntAddr
            usdIpAdEntIfIndex
            usdIpAdEntNetMask
            usdIpAdEntBcastAddr
            usdIpAdEntReasmMaxSize "
    INDEX     { usdIpAdEntAddr }
    ::= { usdIpAddrTable 1 }

UsdIpAddrEntry ::= SEQUENCE {
    usdIpAdEntAddr                  UsdIpAddrLessIf,
    usdIpAdEntIfIndex               InterfaceIndex,
    usdIpAdEntNetMask               IpAddress,
    usdIpAdEntBcastAddr             Integer32,
    usdIpAdEntReasmMaxSize          Integer32,
    usdIpAdEntRowStatus             RowStatus,
    usdIpAdEntAdminStatus           UsdEnable,
    usdIpAdEntArpRspEnable          UsdEnable,
    usdIpAdEntProxyArpRspEnable     UsdEnable,
    usdIpAdEntIgmpEnable            UsdEnable,
    usdIpAdEntDirectedBcastEnable   UsdEnable,
    usdIpAdEntIcmpRedirectEnable    UsdEnable,
    usdIpAdEntIcmpMaskReplyEnable   UsdEnable,
    usdIpAdEntIcmpUnreachEnable     UsdEnable,
    usdIpAdEntMtu                   Integer32,
    usdIpAdEntUnnumLoopbackIfIndex  InterfaceIndexOrZero,
    usdIpAdEntIrdpEnable            UsdEnable,
    usdIpAdEntAccessRouteEnable     UsdEnable,
    usdIpAdEntAccessRouteHost       IpAddress,
    usdIpAdEntIsSecondary           UsdEnable }

usdIpAdEntAddr OBJECT-TYPE
    SYNTAX      UsdIpAddrLessIf
    MAX-ACCESS  not-accessible
    STATUS      current
    DESCRIPTION
        "The IP address for a numbered IP network interface, if this object's
        value has the form 'a.b.c.d', where 'a' is nonzero; or, the ifIndex
        (interpreting the low 24 bits of this value as an integer) of an
        unnumbered ('address-less') IP interface, if this object's value has the
        form '0.b.c.d'."
    ::= { usdIpAddrEntry 1 }

usdIpAdEntIfIndex OBJECT-TYPE
    SYNTAX      InterfaceIndex
    MAX-ACCESS  read-create
    STATUS      current
    DESCRIPTION
        "The ifIndex of the network interface to which this entry's IP
        addressing mode pertains."
    ::= { usdIpAddrEntry 2 }

usdIpAdEntNetMask OBJECT-TYPE
    SYNTAX      IpAddress
    MAX-ACCESS  read-create
    STATUS      current
    DESCRIPTION
        "The IP subnet mask associated with the IP address of this entry.  The
        network and host bit fields of the mask are filled with 1's and 0's,
        respectively.

        If this entry represents an unnumbered IP interface, this object should
        have a value of all ones."
    DEFVAL    { 'ffffffff'H }
    ::= { usdIpAddrEntry 3 }

usdIpAdEntBcastAddr OBJECT-TYPE
    SYNTAX      Integer32 (0..1)
    MAX-ACCESS  read-only
    STATUS      current
    DESCRIPTION
        "The value of the least-significant bit in the IP broadcast address used
        for sending datagrams on the IP network interface associated with this
        entry.  For example, when the Internet standard all-ones broadcast
        address is used, the value will be 1.  This value applies to both the
        subnet and network broadcasts addresses used by the entity on this
        interface."
    ::= { usdIpAddrEntry 4 }

usdIpAdEntReasmMaxSize OBJECT-TYPE
    SYNTAX      Integer32 (0..65535)
    MAX-ACCESS  read-only
    STATUS      current
    DESCRIPTION
        "The size of the largest IP datagram which this entity can re-assemble
        from incoming IP fragmented datagrams received on this interface."
    ::= { usdIpAddrEntry 5 }

usdIpAdEntRowStatus OBJECT-TYPE
    SYNTAX      RowStatus
    MAX-ACCESS  read-create
    STATUS      current
    DESCRIPTION
        "Controls the creation/deletion of entries in this table according to
        the RowStatus textual convention, constrained to support the following
        values only:
            createAndGo
            destroy

        To create entries for both numbered and unnumbered IP interfaces, the
        following entry objects MUST be explicitly configured:
            usdIpAdEntRowStatus
            usdIpAdEntIfIndex

        To create an entry for a numbered IP interface, the following conditions
        must also hold:
            <none>

        To create an entry for an unnumbered IP interface, the following
        conditions must also hold:

            usdIpAdEntUnnumLoopbackIfIndex must be configured with a nonzero
            ifIndex value of an IP loopback interface."
    ::= { usdIpAddrEntry 6 }

usdIpAdEntAdminStatus OBJECT-TYPE
    SYNTAX      UsdEnable
    MAX-ACCESS  read-create
    STATUS      current
    DESCRIPTION
        "Enable/disable operation of IP on this IP network interface."
    DEFVAL    { enable }
    ::= { usdIpAddrEntry 7 }

usdIpAdEntArpRspEnable OBJECT-TYPE
    SYNTAX      UsdEnable
    MAX-ACCESS  read-create
    STATUS      current
    DESCRIPTION
        "Enable/disable ARP response on this IP network interface."
    DEFVAL    { enable }
    ::= { usdIpAddrEntry 8 }

usdIpAdEntProxyArpRspEnable OBJECT-TYPE
    SYNTAX      UsdEnable
    MAX-ACCESS  read-create
    STATUS      current
    DESCRIPTION
        "Enable/disable proxy ARP response on this IP network interface."
    DEFVAL    { disable }
    ::= { usdIpAddrEntry 9 }

usdIpAdEntIgmpEnable OBJECT-TYPE
    SYNTAX      UsdEnable
    MAX-ACCESS  read-create
    STATUS      deprecated
    DESCRIPTION
        "Enable/disable IGMP operation on this IP network interface."
    DEFVAL    { disable }
    ::= { usdIpAddrEntry 10 }

usdIpAdEntDirectedBcastEnable OBJECT-TYPE
    SYNTAX      UsdEnable
    MAX-ACCESS  read-create
    STATUS      current
    DESCRIPTION
        "Enable/disable forwarding of directed broadcasts on this IP network
        interface."
    DEFVAL    { disable }
    ::= { usdIpAddrEntry 11 }

usdIpAdEntIcmpRedirectEnable OBJECT-TYPE
    SYNTAX      UsdEnable
    MAX-ACCESS  read-create
    STATUS      current
    DESCRIPTION
        "Enable/disable transmission of ICMP Redirect messages on this IP
        network interface."
    DEFVAL    { disable }
    ::= { usdIpAddrEntry 12 }

usdIpAdEntIcmpMaskReplyEnable OBJECT-TYPE
    SYNTAX      UsdEnable
    MAX-ACCESS  read-create
    STATUS      current
    DESCRIPTION
        "Enable/disable transmission of ICMP Mask Reply messages on this IP
        network interface."
    DEFVAL    { disable }
    ::= { usdIpAddrEntry 13 }

usdIpAdEntIcmpUnreachEnable OBJECT-TYPE
    SYNTAX      UsdEnable
    MAX-ACCESS  read-create
    STATUS      current
    DESCRIPTION
        "Enable/disable transmission of ICMP Unreachable messages on this IP
        network interface."
    DEFVAL    { disable }
    ::= { usdIpAddrEntry 14 }

usdIpAdEntMtu OBJECT-TYPE
    SYNTAX      Integer32 (0..65535)
    MAX-ACCESS  read-create
    STATUS      current
    DESCRIPTION
        "The configured MTU size for this IP network interface.  If set to zero,
        the default MTU size, as determined by the underlying network media, is
        used."
    ::= { usdIpAddrEntry 15 }

usdIpAdEntUnnumLoopbackIfIndex OBJECT-TYPE
    SYNTAX      InterfaceIndexOrZero
    MAX-ACCESS  read-create
    STATUS      current
    DESCRIPTION
        "For unnumbered interfaces, the ifIndex of the IP loopback interface
        whose IP address is used as the source IP address for IP packets
        transmitted on the unnumbered network.

        For numbered interfaces, this object has a value of zero."
    DEFVAL    { 0 }
    ::= { usdIpAddrEntry 16 }

usdIpAdEntIrdpEnable OBJECT-TYPE
    SYNTAX      UsdEnable
    MAX-ACCESS  read-create
    STATUS      current
    DESCRIPTION
        "Controls whether ICMP Router Discovery Protocol operation is permitted
        to be sent on this network."
    DEFVAL    { enable }
    ::= { usdIpAddrEntry 17 }

usdIpAdEntAccessRouteEnable OBJECT-TYPE
    SYNTAX      UsdEnable
    MAX-ACCESS  read-create
    STATUS      current
    DESCRIPTION
        "If enabled, then establishment/loss of a point-to-point network
        connection causes a host route for the remote host to be created/deleted
        automatically."
    DEFVAL    { disable }
    ::= { usdIpAddrEntry 18 }

usdIpAdEntAccessRouteHost OBJECT-TYPE
    SYNTAX      IpAddress
    MAX-ACCESS  read-only
    STATUS      current
    DESCRIPTION
        "If an access route has been established, the IP address of the remote
        host is reported by this object; otherwise, this object contains the
        value 0.0.0.0."
    ::= { usdIpAddrEntry 19 }

usdIpAdEntIsSecondary OBJECT-TYPE
    SYNTAX      UsdEnable
    MAX-ACCESS  read-create
    STATUS      current
    DESCRIPTION
        "If enabled, then the IP address corresponding to this entry is a
        secondary address.  If disabled, then the IP address corresponding to
        this entry is te primary address."
    DEFVAL    { disable }
    ::= { usdIpAddrEntry 20 }


-- +++++++++++++++++++++++++++++++++++++++++++++++++++++++++++++++++++++++++++++
-- IP Route
-- +++++++++++++++++++++++++++++++++++++++++++++++++++++++++++++++++++++++++++++
--
-- Route Globals
--
usdIpRouteGlobals  OBJECT IDENTIFIER ::= { usdIpRoute 1 }

usdIpRouteLimit OBJECT-TYPE
    SYNTAX      Integer32
    MAX-ACCESS  read-write
    STATUS      current
    DESCRIPTION
        "Maximum number of IP routes maintained by this entity.

        Setting a value lower than the current number of routes prevents
        additional routes from being learned or configured, but does not cause
        existing excess routes to be deleted to enforce the new limit."
    ::= { usdIpRouteGlobals 1 }


--
-- Static Route Table
--
usdIpRouteStaticTable OBJECT-TYPE
    SYNTAX      SEQUENCE OF UsdIpRouteStaticEntry
    MAX-ACCESS  not-accessible
    STATUS      current
    DESCRIPTION
        "Table of static routes configured on this entity.

        The object definitions and indexing for this table are chosen to closely
        align with the IP-FORWARD-MIB's ipCidrRouteTable.

        This  table serves three purposes:
        1. Provide the means for configuring static routes.
        2. Provide an efficient view of static routes (otherwise they must be
           observed by traversing the entire routing table).
        3. Provide view of static routes configured on network interfaces that
           are currently inactive.  (In this implementation, static routes
           configured on inactive interfaces are not visible in the routing
           table.)"
    ::= { usdIpRoute 2 }

usdIpRouteStaticEntry OBJECT-TYPE
    SYNTAX      UsdIpRouteStaticEntry
    MAX-ACCESS  not-accessible
    STATUS      current
    DESCRIPTION
        "A static route."
    INDEX     { usdIpRouteStaticDest,
                usdIpRouteStaticMask,
                usdIpRouteStaticPref,
                usdIpRouteStaticNextHop }
    ::= { usdIpRouteStaticTable 1 }

UsdIpRouteStaticEntry ::= SEQUENCE {
    usdIpRouteStaticDest        IpAddress,
    usdIpRouteStaticMask        IpAddress,
    usdIpRouteStaticPref        Integer32,
    usdIpRouteStaticNextHop     UsdIpAddrLessIf,
    usdIpRouteStaticRowStatus   RowStatus,
    usdIpRouteStaticIfIndex     Integer32,
    usdIpRouteStaticStatus      INTEGER,
    usdIpRouteStaticNextHopAS   Integer32,
    usdIpRouteStaticMetric      Integer32,
    usdIpRouteStaticTag         Unsigned32 }

usdIpRouteStaticDest OBJECT-TYPE
    SYNTAX      IpAddress
    MAX-ACCESS  read-only
    STATUS      current
    DESCRIPTION
        "The destination IP address of this route.

        This object may not take a Multicast (Class D) address value.

        Any assignment (implicit or otherwise) of an instance of this object to
        a value x must be rejected if the bitwise logical-AND of x with the
        value of the corresponding instance of the usdIpRouteStaticMask object is
        not equal to x."
    ::= { usdIpRouteStaticEntry 1 }

usdIpRouteStaticMask OBJECT-TYPE
    SYNTAX      IpAddress
    MAX-ACCESS  read-only
    STATUS      current
    DESCRIPTION
        "Indicate the mask to be logical-ANDed with the destination address
        before being compared to the value in the usdIpRouteStaticDest field.
        For those systems that do not support arbitrary subnet masks, an agent
        constructs the value of the usdIpRouteStaticMask by reference to the IP
        Address Class.

        Any assignment (implicit or otherwise) of an instance of this object to
        a value x must be rejected if the bitwise logical-AND of x with the
        value of the corresponding instance of the usdIpRouteStaticDest object is
        not equal to usdIpRouteStaticDest."
    ::= { usdIpRouteStaticEntry 2 }

-- The following convention is included for specification
-- of TOS Field contents.  At this time, the Host Requirements
-- and the Router Requirements documents disagree on the width
-- of the TOS field.  This mapping describes the Router
-- Requirements mapping, and leaves room to widen the TOS field
-- without impact to fielded systems.

usdIpRouteStaticPref OBJECT-TYPE
    SYNTAX      Integer32 (0..255)
    MAX-ACCESS  read-only
    STATUS      current
    DESCRIPTION
        "The preference of this static route.  Higher values correspond to
        higher preference.  A static route with preference of zero will never be
        installed as an active route."
    ::= { usdIpRouteStaticEntry 3 }

usdIpRouteStaticNextHop OBJECT-TYPE
    SYNTAX      UsdIpAddrLessIf
    MAX-ACCESS  read-only
    STATUS      current
    DESCRIPTION
        "The address of the next hop toward the destination."
    ::= { usdIpRouteStaticEntry 4 }

usdIpRouteStaticRowStatus OBJECT-TYPE
    SYNTAX      RowStatus
    MAX-ACCESS  read-create
    STATUS      current
    DESCRIPTION
        "The row status variable, used according to row installation and removal
        conventions."
    ::= { usdIpRouteStaticEntry 5 }

usdIpRouteStaticIfIndex OBJECT-TYPE
    SYNTAX      Integer32
    MAX-ACCESS  read-create
    STATUS      current
    DESCRIPTION
        "The ifIndex value which identifies the local interface through which
        the next hop of this route should be reached.  A value of zero means the
        router should automatically determine the interface through which the
        specified next-hop address is reached.

        An implementation may disallow non-zero values from being configured."
    DEFVAL    { 0 }
    ::= { usdIpRouteStaticEntry 6 }

usdIpRouteStaticStatus OBJECT-TYPE
    SYNTAX      INTEGER {
                    active(0),
                    inactive(1),
                    incomplete(2) }
    MAX-ACCESS  read-only
    STATUS      current
    DESCRIPTION
        "The operational status of this static route.

        active(0) indicates this route is currently being used to reach the
        specified destination.

        inactive(1) indicates this route is considered valid, but currently is
        superseded by another routing table entry for the destination, having a
        higher preference value.

        incomplete(2) indicates this route entry contains information that is
        incomplete, or is inconsistent with other system configuration (for
        example, the interface specified in usdIpRouteStaticIfIndex does not
        exist)."
    ::= { usdIpRouteStaticEntry 7 }

usdIpRouteStaticNextHopAS OBJECT-TYPE
    SYNTAX      Integer32
    MAX-ACCESS  read-create
    STATUS      current
    DESCRIPTION
        "The Autonomous System Number of the Next Hop.  The semantics of this
        object are determined by the routing-protocol specified in the route's
        ipCidrRouteProto value.  When this object is unknown or not relevant its
        value should be set to zero."
    DEFVAL    { 0 }
    ::= { usdIpRouteStaticEntry 8 }

usdIpRouteStaticMetric OBJECT-TYPE
    SYNTAX      Integer32
    MAX-ACCESS  read-create
    STATUS      current
    DESCRIPTION
        "The primary routing metric for this route.  The semantics of this
        metric are determined by the routing-protocol specified in the route's
        ipCidrRouteProto value.  If this metric is not used, its value should be
        set to -1."
    DEFVAL    { -1 }
    ::= { usdIpRouteStaticEntry 9 }

usdIpRouteStaticTag OBJECT-TYPE
    SYNTAX      Unsigned32
    MAX-ACCESS  read-create
    STATUS      current
    DESCRIPTION
        "A tag value for this static route."
    DEFVAL    { 0 }
    ::= { usdIpRouteStaticEntry 10 }

--
-- Extensions to IP CIDR Route Table
--
usdIpCidrRouteTable OBJECT-TYPE
    SYNTAX      SEQUENCE OF UsdIpCidrRouteEntry
    MAX-ACCESS  not-accessible
    STATUS      current
    DESCRIPTION
        "Table of routes active on this entity.  This table is an augmentation
        of the IP-FORWARD-MIB's ipCidrRouteTable."
    ::= { usdIpRoute 3 }

usdIpCidrRouteEntry OBJECT-TYPE
    SYNTAX      UsdIpCidrRouteEntry
    MAX-ACCESS  not-accessible
    STATUS      current
    DESCRIPTION
        "Additional attributes of an active route."
    AUGMENTS  { ipCidrRouteEntry }
    ::= { usdIpCidrRouteTable 1 }

UsdIpCidrRouteEntry ::= SEQUENCE {
    usdIpCidrRoutePref  Integer32,
    usdIpCidrRouteArea  IpAddress,
    usdIpCidrRouteTag   Unsigned32 }

usdIpCidrRoutePref OBJECT-TYPE
    SYNTAX      Integer32 (0..255)
    MAX-ACCESS  read-only
    STATUS      current
    DESCRIPTION
        "The preference of this route.  Higher values correspond to higher
        preference."
    ::= { usdIpCidrRouteEntry 1 }

usdIpCidrRouteArea OBJECT-TYPE
    SYNTAX      IpAddress
    MAX-ACCESS  read-only
    STATUS      current
    DESCRIPTION
        "The Area to which this route pertains.  A value of 0.0.0.0 indicates no
        area is identified."
    ::= { usdIpCidrRouteEntry 2 }

usdIpCidrRouteTag OBJECT-TYPE
    SYNTAX      Unsigned32
    MAX-ACCESS  read-only
    STATUS      current
    DESCRIPTION
        "A tag value for this route."
    ::= { usdIpCidrRouteEntry 3 }


-- +++++++++++++++++++++++++++++++++++++++++++++++++++++++++++++++++++++++++++++
-- Notification control
-- +++++++++++++++++++++++++++++++++++++++++++++++++++++++++++++++++++++++++++++
-- No notifications are defined in this MIB.  Placeholder follows.
-- usdIpTrapEnables OBJECT IDENTIFIER ::= { usdIpMIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- The following two OBJECT IDENTIFIERS are used to define SNMPv2
-- Notifications that are easily translated into SNMPv1 Traps.
-- usdIpTraps       OBJECT IDENTIFIER ::= { usdIpMIB 3 }
-- usdIpTrapPrefix  OBJECT IDENTIFIER ::= { usdIpTraps 0 }


-- +++++++++++++++++++++++++++++++++++++++++++++++++++++++++++++++++++++++++++++
-- Conformance information
-- +++++++++++++++++++++++++++++++++++++++++++++++++++++++++++++++++++++++++++++
usdIpConformance     OBJECT IDENTIFIER ::= { usdIpMIB 4 }
usdIpCompliances     OBJECT IDENTIFIER ::= { usdIpConformance 1 }
usdIpGroups          OBJECT IDENTIFIER ::= { usdIpConformance 2 }

--
-- compliance statements
--
usdIpCompliance MODULE-COMPLIANCE
    STATUS      obsolete
    DESCRIPTION
        "Obsolete compliance statement for entities which implement the
        Unisphere IP MIB.  This statement became obsolete when the IP interface
        and IP address groups changed and the global objects were added."
    MODULE   -- this module
        MANDATORY-GROUPS {
            usdIpInterfaceGroup,
            usdIpAddressGroup,
            usdIpRouteGroup }
    ::= { usdIpCompliances 1 }                                         -- RX 2.2

usdIpCompliance2 MODULE-COMPLIANCE
    STATUS      obsolete
    DESCRIPTION
        "Obsolete compliance statement for entities which implement the
        Unisphere IP MIB.  This statement became obsolete when the
        usdIpIfAssocTable was added."
    MODULE   -- this module
        MANDATORY-GROUPS {
            usdIpInterfaceGroup2,
            usdIpAddressGroup2,
            usdIpRouteGroup,
            usdIpGlobalGroup }
    ::= { usdIpCompliances 2 }                                         -- RX 3.0

usdIpCompliance3 MODULE-COMPLIANCE
    STATUS      obsolete
    DESCRIPTION
        "Obsolete compliance statement for entities which implement the
        Unisphere IP MIB.  This statement became obsolete when the QoS related
        objects were obsoleted."
    MODULE   -- this module
        MANDATORY-GROUPS {
            usdIpInterfaceGroup3,
            usdIpAddressGroup2,
            usdIpRouteGroup,
            usdIpGlobalGroup }
    ::= { usdIpCompliances 3 }                                         -- RX 3.2

usdIpCompliance4 MODULE-COMPLIANCE
    STATUS      current
    DESCRIPTION
        "The compliance statement for entities which implement the Unisphere IP
        MIB."
    MODULE   -- this module
        MANDATORY-GROUPS {
            usdIpInterfaceGroup4,
            usdIpAddressGroup2,
            usdIpRouteGroup,
            usdIpGlobalGroup }
    ::= { usdIpCompliances 4 }                                         -- RX 4.0

--
-- units of conformance
--
usdIpInterfaceGroup OBJECT-GROUP
    OBJECTS {
        usdIpNextIfIndex,

        usdIpIfRowStatus,
        usdIpIfLowerIfIndex,
        usdIpIfType,
        usdIpIfTypeId,

        usdIpIfStatsInPackets,
        usdIpIfStatsInOctets,
        usdIpIfStatsInPoliciedPackets,
        usdIpIfStatsInPoliciedOctets,
        usdIpIfStatsInErrorPackets,
        usdIpIfStatsInSpoofedPackets,
        usdIpIfStatsInForwardedPackets,
        usdIpIfStatsInForwardedOctets,
        usdIpIfStatsOutForwardedPackets,
        usdIpIfStatsOutForwardedOctets,
        usdIpIfStatsOutSchedDropPackets,
        usdIpIfStatsOutSchedDropOctets,
        usdIpIfStatsOutRequestedPackets,
        usdIpIfStatsOutRequestedOctets,
        usdIpIfStatsOutPoliciedPackets,
        usdIpIfStatsOutPoliciedOctets }
    STATUS      obsolete
    DESCRIPTION
        "Obsolete collection of objects for managing IP interface capabilities
        in a Unisphere product.  This group became obsolete when new objects
        were added to the usdIpIfTable and the usdIpIfStatsTable."
    ::= { usdIpGroups 1 }

usdIpAddressGroup OBJECT-GROUP
    OBJECTS {
        usdIpArpTimeout,

        usdIpAdEntRowStatus,
        usdIpAdEntIfIndex,
        usdIpAdEntNetMask,
        usdIpAdEntAdminStatus,
        usdIpAdEntArpRspEnable,
        usdIpAdEntProxyArpRspEnable,
        usdIpAdEntIgmpEnable,
        usdIpAdEntDirectedBcastEnable,
        usdIpAdEntIcmpRedirectEnable,
        usdIpAdEntIcmpMaskReplyEnable,
        usdIpAdEntIcmpUnreachEnable,
        usdIpAdEntMtu,
        usdIpAdEntUnnumLoopbackIfIndex,
        usdIpAdEntIrdpEnable,
        usdIpAdEntAccessRouteEnable,
        usdIpAdEntAccessRouteHost }
    STATUS      obsolete
    DESCRIPTION
        "Obsolete collection of objects for managing IP address capabilities in
        a Unisphere product.  This group became obsolete when
        usdIpAdEntIgmpEnable was deprecated and usdIpAdEntIsSecondary was added."
    ::= { usdIpGroups 2 }

usdIpRouteGroup OBJECT-GROUP
    OBJECTS {
        usdIpRouteLimit,

        usdIpRouteStaticDest,
        usdIpRouteStaticMask,
        usdIpRouteStaticPref,
        usdIpRouteStaticNextHop,
        usdIpRouteStaticRowStatus,
        usdIpRouteStaticIfIndex,
        usdIpRouteStaticStatus,
        usdIpRouteStaticNextHopAS,
        usdIpRouteStaticMetric,
        usdIpRouteStaticTag,

        usdIpCidrRoutePref,
        usdIpCidrRouteArea,
        usdIpCidrRouteTag }
    STATUS      current
    DESCRIPTION
        "A collection of objects for managing IP routing capabilities in a
        Unisphere product."
    ::= { usdIpGroups 3 }

usdIpGlobalGroup OBJECT-GROUP
    OBJECTS {
        usdIpDebounceTime,
        usdIpRouterId,
        usdIpSourceRoutingAdminStatus,
        usdIpVpnIdOui,
        usdIpVpnIdIndex }
    STATUS      current
    DESCRIPTION
        "A collection of IP global objects for managing instances of IP in a
        Unisphere product."
    ::= { usdIpGroups 4 }

usdIpInterfaceGroup2 OBJECT-GROUP
    OBJECTS {
        usdIpNextIfIndex,

        usdIpIfRowStatus,
        usdIpIfLowerIfIndex,
        usdIpIfType,
        usdIpIfTypeId,
        usdIpIfSAValidationEnable,
        usdIpIfCreationType,
        usdIpIfProfileId,
        usdIpIfAlwaysUp,
        usdIpIfLoopback,
        usdIpIfLoopbackUid,
        usdIpIfDebounceTime,
        usdIpIfForwarding,
        usdIpIfForceFragmentation,
        usdIpIfSharesLowerUid,
        usdIpIfFilterOptions,
        usdIpIfName,
        usdIpIfArpTimeout,
        usdIpIfAdminSpeed,
        usdIpIfMultipathMode,
        usdIpIfSharedNhAddr,
        usdIpIfSharedNhRouterId,
        usdIpIfPrimaryIpAddress,
        usdIpIfPrimaryIpMask,
        usdIpIfOperDebounceTime,

        usdIpIfStatsInPackets,
        usdIpIfStatsInOctets,
        usdIpIfStatsInPoliciedPackets,
        usdIpIfStatsInPoliciedOctets,
        usdIpIfStatsInErrorPackets,
        usdIpIfStatsInSpoofedPackets,
        usdIpIfStatsInForwardedPackets,
        usdIpIfStatsInForwardedOctets,
        usdIpIfStatsOutForwardedPackets,
        usdIpIfStatsOutForwardedOctets,
        usdIpIfStatsOutSchedDropPackets,
        usdIpIfStatsOutSchedDropOctets,
        usdIpIfStatsOutRequestedPackets,
        usdIpIfStatsOutRequestedOctets,
        usdIpIfStatsOutPoliciedPackets,
        usdIpIfStatsOutPoliciedOctets,
        usdIpIfStatsGreenOutSchedDropPackets,
        usdIpIfStatsYellowOutSchedDropPackets,
        usdIpIfStatsRedOutSchedDropPackets,
        usdIpIfStatsGreenOutSchedDropOctets,
        usdIpIfStatsYellowOutSchedDropOctets,
        usdIpIfStatsRedOutSchedDropOctets }
    STATUS      obsolete
    DESCRIPTION
        "Obsolete collection of objects for managing IP interface capabilities
        in a Unisphere product.  This group became obsolete when the
        usdIpIfAssocTable was added."
    ::= { usdIpGroups 5 }

usdIpAddressGroup2 OBJECT-GROUP
    OBJECTS {
        usdIpArpTimeout,

        usdIpAdEntRowStatus,
        usdIpAdEntIfIndex,
        usdIpAdEntNetMask,
        usdIpAdEntBcastAddr,
        usdIpAdEntReasmMaxSize,
        usdIpAdEntAdminStatus,
        usdIpAdEntArpRspEnable,
        usdIpAdEntProxyArpRspEnable,
        usdIpAdEntDirectedBcastEnable,
        usdIpAdEntIcmpRedirectEnable,
        usdIpAdEntIcmpMaskReplyEnable,
        usdIpAdEntIcmpUnreachEnable,
        usdIpAdEntMtu,
        usdIpAdEntUnnumLoopbackIfIndex,
        usdIpAdEntIrdpEnable,
        usdIpAdEntAccessRouteEnable,
        usdIpAdEntAccessRouteHost,
        usdIpAdEntIsSecondary }
    STATUS      current
    DESCRIPTION
        "A collection of objects for managing IP address capabilities in a
        Unisphere product."
    ::= { usdIpGroups 6 }

usdIpInterfaceGroup3 OBJECT-GROUP
    OBJECTS {
        usdIpNextIfIndex,

        usdIpIfRowStatus,
        usdIpIfLowerIfIndex,
        usdIpIfType,
        usdIpIfTypeId,
        usdIpIfSAValidationEnable,
        usdIpIfCreationType,
        usdIpIfProfileId,
        usdIpIfAlwaysUp,
        usdIpIfLoopback,
        usdIpIfLoopbackUid,
        usdIpIfDebounceTime,
        usdIpIfForwarding,
        usdIpIfForceFragmentation,
        usdIpIfSharesLowerUid,
        usdIpIfFilterOptions,
        usdIpIfName,
        usdIpIfArpTimeout,
        usdIpIfAdminSpeed,
        usdIpIfMultipathMode,
        usdIpIfSharedNhAddr,
        usdIpIfSharedNhRouterId,
        usdIpIfPrimaryIpAddress,
        usdIpIfPrimaryIpMask,
        usdIpIfOperDebounceTime,

        usdIpIfStatsInPackets,
        usdIpIfStatsInOctets,
        usdIpIfStatsInPoliciedPackets,
        usdIpIfStatsInPoliciedOctets,
        usdIpIfStatsInErrorPackets,
        usdIpIfStatsInSpoofedPackets,
        usdIpIfStatsInForwardedPackets,
        usdIpIfStatsInForwardedOctets,
        usdIpIfStatsOutForwardedPackets,
        usdIpIfStatsOutForwardedOctets,
        usdIpIfStatsOutSchedDropPackets,
        usdIpIfStatsOutSchedDropOctets,
        usdIpIfStatsOutRequestedPackets,
        usdIpIfStatsOutRequestedOctets,
        usdIpIfStatsOutPoliciedPackets,
        usdIpIfStatsOutPoliciedOctets,
        usdIpIfStatsGreenOutSchedDropPackets,
        usdIpIfStatsYellowOutSchedDropPackets,
        usdIpIfStatsRedOutSchedDropPackets,
        usdIpIfStatsGreenOutSchedDropOctets,
        usdIpIfStatsYellowOutSchedDropOctets,
        usdIpIfStatsRedOutSchedDropOctets,

        usdIpIfAssocIpIfIndex }
    STATUS      obsolete
    DESCRIPTION
        "Obsolete collection of objects for managing IP interface capabilities
        in a Unisphere product.  This group became obsolete when the QoS related
        objects were obsoleted."
    ::= { usdIpGroups 7 }

usdIpInterfaceGroup4 OBJECT-GROUP
    OBJECTS {
        usdIpNextIfIndex,

        usdIpIfRowStatus,
        usdIpIfLowerIfIndex,
        usdIpIfType,
        usdIpIfTypeId,
        usdIpIfSAValidationEnable,
        usdIpIfCreationType,
        usdIpIfProfileId,
        usdIpIfAlwaysUp,
        usdIpIfLoopback,
        usdIpIfLoopbackUid,
        usdIpIfDebounceTime,
        usdIpIfForwarding,
        usdIpIfForceFragmentation,
        usdIpIfSharesLowerUid,
        usdIpIfFilterOptions,
        usdIpIfName,
        usdIpIfArpTimeout,
        usdIpIfAdminSpeed,
        usdIpIfMultipathMode,
        usdIpIfSharedNhAddr,
        usdIpIfSharedNhRouterId,
        usdIpIfPrimaryIpAddress,
        usdIpIfPrimaryIpMask,
        usdIpIfOperDebounceTime,

        usdIpIfStatsInPackets,
        usdIpIfStatsInOctets,
        usdIpIfStatsInPoliciedPackets,
        usdIpIfStatsInPoliciedOctets,
        usdIpIfStatsInErrorPackets,
        usdIpIfStatsInSpoofedPackets,
        usdIpIfStatsOutForwardedPackets,
        usdIpIfStatsOutForwardedOctets,
        usdIpIfStatsOutSchedDropPackets,
        usdIpIfStatsOutSchedDropOctets,
        usdIpIfStatsOutPoliciedPackets,
        usdIpIfStatsOutPoliciedOctets,

        usdIpIfAssocIpIfIndex }
    STATUS      current
    DESCRIPTION
        "A collection of objects for managing IP interface capabilities in a
        Unisphere product."
    ::= { usdIpGroups 8 }
END
