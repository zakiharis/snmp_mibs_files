-- *****************************************************************************
-- Unisphere-Data-L2F-CONF
--
-- SNMP Agent Capabilities definitions for the Layer 2 Forwarding (L2F) MIB.
--
-- Copyright (c) 2001 Unisphere Networks, Inc.  All rights reserved.
-- *****************************************************************************

Unisphere-Data-L2F-CONF DEFINITIONS ::= BEGIN

IMPORTS
    MODULE-IDENTITY
        FROM SNMPv2-SMI
    AGENT-CAPABILITIES
        FROM SNMPv2-CONF
    usDataAgents
        FROM Unisphere-Data-Agents
    usdL2fConfigGroup,
    usdL2fStatusGroup,
    usdL2fStatGroup,
    usdL2fMapGroup
        FROM Unisphere-Data-L2F-MIB;

usdL2fAgent MODULE-IDENTITY
    LAST-UPDATED "200104131337Z"  -- 13-Apr-01 09:37 AM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the layer 2 forwarding protocol
        (L2F) component of the SNMP agent in the Unisphere Routing Switch
        family of products."
    -- Revision History
    REVISION    "200104131337Z"  -- 13-Apr-01 09:37 AM EDT  - RX 3.2
    DESCRIPTION
        "The initial release of this management information module."
    ::= { usDataAgents 49 }

usdL2fAgentV1 AGENT-CAPABILITIES
    PRODUCT-RELEASE
        "Version 1 of the L2F component of the Unisphere Routing Switch SNMP
        agent.  This version of the L2F component is supported in the Unisphere
        RX 3.2 and subsequent system releases."
    STATUS      current
    DESCRIPTION
        "The MIB supported by the SNMP agent for the L2F application in the
        Unisphere Routing Switch."

    SUPPORTS        Unisphere-Data-L2F-MIB
        INCLUDES  { usdL2fConfigGroup,
                    usdL2fStatusGroup,
                    usdL2fStatGroup,
                    usdL2fMapGroup }

    ::= { usdL2fAgent 1 }

END
