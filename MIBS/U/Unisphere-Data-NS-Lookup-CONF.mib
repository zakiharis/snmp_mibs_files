-- *****************************************************************************
-- Unisphere-Data-NS-Lookup-CONF
--
-- SNMP Agent Capabilities definitions for the NS Lookup MIB.
--
-- Copyright (c) 2001 Unisphere Networks, Inc.  All rights reserved.
-- *****************************************************************************

Unisphere-Data-NS-Lookup-CONF DEFINITIONS ::= BEGIN

IMPORTS
    MODULE-IDENTITY
        FROM SNMPv2-SMI
    AGENT-CAPABILITIES
        FROM SNMPv2-CONF
    usDataAgents
        FROM Unisphere-Data-Agents
    lookupGroup
        FROM DISMAN-NSLOOKUP-MIB;

usdNsLookupAgent MODULE-IDENTITY
    LAST-UPDATED "200103282222Z"  -- 28-Mar-01 05:22 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the remote name server (NS)
        lookup component of the SNMP agent in the Unisphere Routing Switch
        family of products."
    -- Revision History
    REVISION    "200103282222Z"  -- 28-Mar-01 05:22 PM EST  - RX 3.2
    DESCRIPTION
        "The initial release of this management information module."
    ::= { usDataAgents 27 }

usdNsLookupAgentV1 AGENT-CAPABILITIES
    PRODUCT-RELEASE
        "Version 1 of the NS Lookup component of the Unisphere Routing Switch
        SNMP agent.  This version of the NS Lookup component is supported in
        the Unisphere RX 3.0 and subsequent system releases."
    STATUS      current
    DESCRIPTION
        "The MIB supported by the SNMP agent for the NS Lookup application in
        the Unisphere Routing Switch."

    SUPPORTS        DISMAN-NSLOOKUP-MIB
        INCLUDES  { lookupGroup }

    ::= { usdNsLookupAgent 1 }

END
