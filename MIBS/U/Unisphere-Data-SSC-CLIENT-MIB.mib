-- *****************************************************************************
-- Unisphere-Data-SSC-CLIENT-MIB
--
-- Unisphere Networks Enterprise MIB
-- Service Selection Center (SSC) Client
--
-- Copyright (c) 2000, 2002 Unisphere Networks, Inc.  All Rights Reserved.
-- *****************************************************************************

Unisphere-Data-SSC-CLIENT-MIB DEFINITIONS ::= BEGIN

IMPORTS
    MODULE-IDENTITY, OBJECT-TYPE, Integer32, IpAddress, Counter32
        FROM SNMPv2-SMI
    DisplayString
        FROM SNMPv2-TC
    MODULE-COMPLIANCE, OBJECT-GROUP
        FROM SNMPv2-CONF
    UsdName
        FROM Unisphere-Data-TC
    usDataMibs
        FROM Unisphere-Data-MIBs;

usdSscClientMIB  MODULE-IDENTITY
    LAST-UPDATED "200201142015Z"  -- 14-Jan-02 03:15 PM EST
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The Service Selection Center (SSC) Client MIB for the Unisphere
        Networks enterprise."
    -- Revision History
    REVISION    "200201142015Z"  -- 14-Jan-02 03:15 PM EST  - RX 4.0
    DESCRIPTION
        "Added version number, local address and transport router name objects."
    REVISION    "200101232130Z"  -- 23-Jan-01 04:30 PM EST  - RX 3.1
    DESCRIPTION
        "Added DHCP-LS, Web and SSC support."
    REVISION    "200002172310Z"  -- 17-Feb-00  6:10 PM EST  - RX 2.0
    DESCRIPTION
        "Initial version of this MIB module."
    ::= { usDataMibs 36 }


-- +++++++++++++++++++++++++++++++++++++++++++++++++++++++++++++++++++++++++++++
-- Managed objects
-- +++++++++++++++++++++++++++++++++++++++++++++++++++++++++++++++++++++++++++++

--
--  This MIB contains definitions needed for the SSC Client
--  component support for the SSC.
--

usdSscClientObjects      OBJECT IDENTIFIER ::= { usdSscClientMIB 1 }

usdSscClientCfg          OBJECT IDENTIFIER ::= { usdSscClientObjects 1 }
usdSscClientStatus       OBJECT IDENTIFIER ::= { usdSscClientObjects 2 }
usdSscClientStatistics   OBJECT IDENTIFIER ::= { usdSscClientObjects 3 }

--
-- Configuration scalars
--
usdSscClientCfgScalars   OBJECT IDENTIFIER ::= { usdSscClientCfg 1 }

usdSscClientServerSwitchoverTimeout  OBJECT-TYPE
    SYNTAX      Integer32 (5..300)
    UNITS       "seconds"
    MAX-ACCESS  read-write
    STATUS      current
    DESCRIPTION
        "The server switchover timeout in seconds.  The SSC Client begins with
        the primary server and proceeds rotationally to secondary, tertiary,
        primary, etc. as timeouts occur."
    ::= { usdSscClientCfgScalars 1 }

usdSscClientPrimaryAddress  OBJECT-TYPE
    SYNTAX      IpAddress
    MAX-ACCESS  read-write
    STATUS      current
    DESCRIPTION
        "The IP address of the primary SSC server.  A value of 0.0.0.0 indicates
        the server address is unconfigured."
    ::= { usdSscClientCfgScalars 2 }

usdSscClientPrimaryPort  OBJECT-TYPE
    SYNTAX      Integer32 (0..65535)
    MAX-ACCESS  read-write
    STATUS      current
    DESCRIPTION
        "The TCP port number for the primary SSC server.  A value of zero
        indicates the port is unconfigured."
    ::= { usdSscClientCfgScalars 3 }

usdSscClientSecondaryAddress  OBJECT-TYPE
    SYNTAX      IpAddress
    MAX-ACCESS  read-write
    STATUS      current
    DESCRIPTION
        "The IP address of the secondary SSC server.  A value of 0.0.0.0
        indicates the server address is unconfigured."
    ::= { usdSscClientCfgScalars 4 }

usdSscClientSecondaryPort  OBJECT-TYPE
    SYNTAX      Integer32 (0..65535)
    MAX-ACCESS  read-write
    STATUS      current
    DESCRIPTION
        "The TCP port number of the secondary SSC server.  A value of zero
        indicates the port is unconfigured."
    ::= { usdSscClientCfgScalars 5 }

usdSscClientTertiaryAddress  OBJECT-TYPE
    SYNTAX      IpAddress
    MAX-ACCESS  read-write
    STATUS      current
    DESCRIPTION
        "The IP address of the tertiary SSC server.  A value of 0.0.0.0
        indicates the server address is unconfigured."
    ::= { usdSscClientCfgScalars 6 }

usdSscClientTertiaryPort  OBJECT-TYPE
    SYNTAX      Integer32 (0..65535)
    MAX-ACCESS  read-write
    STATUS      current
    DESCRIPTION
        "The TCP port number of the tertiary SSC server.  A value of zero
        indicates the port is unconfigured."
    ::= { usdSscClientCfgScalars 7 }

usdSscClientLocalAddress  OBJECT-TYPE
    SYNTAX      IpAddress
    MAX-ACCESS  read-write
    STATUS      current
    DESCRIPTION
        "The local IP address binding of the server connection.  A value of
        0.0.0.0 indicates the local address is unconfigured."
    ::= { usdSscClientCfgScalars 8 }

usdSscClientTransportRouterName  OBJECT-TYPE
    SYNTAX      UsdName
    MAX-ACCESS  read-write
    STATUS      current
    DESCRIPTION
        "The name of the router to be used as the transport for the server
        connection."
    ::= { usdSscClientCfgScalars 9 }

--
-- Status objects
--
usdSscClientStatusScalars    OBJECT IDENTIFIER ::= { usdSscClientStatus 1 }

usdSscClientConnectionState  OBJECT-TYPE
    SYNTAX      INTEGER {
                    disconnected(0),
                    trying(1),
                    connected(2) }
    MAX-ACCESS  read-only
    STATUS      current
    DESCRIPTION
        "The connection state of the SSC Client:
            disconnected    Not connected to a SSC server.
            trying          Attempting a connection to a server.
            connected       Connected to a server.

        When this object has the value 'connected', the active server address
        and TCP port are reported in usdSscClientActiveAddress and
        usdSscClientActivePort, respectively."
    ::= { usdSscClientStatusScalars 1 }

usdSscClientActiveAddress  OBJECT-TYPE
    SYNTAX      IpAddress
    MAX-ACCESS  read-only
    STATUS      current
    DESCRIPTION
        "The IP address of the SSC server currently in use.  A value of 0.0.0.0
        indicates no server is in use."
    ::= { usdSscClientStatusScalars 2 }

usdSscClientActivePort  OBJECT-TYPE
    SYNTAX      Integer32 (0..65535)
    MAX-ACCESS  read-only
    STATUS      current
    DESCRIPTION
        "The TCP port number for the SSC server currently in use.  A value of
        zero indicates no server is in use."
    ::= { usdSscClientStatusScalars 3 }

usdSscClientVersion  OBJECT-TYPE
    SYNTAX      DisplayString (SIZE(0..16))
    MAX-ACCESS  read-only
    STATUS      current
    DESCRIPTION
        "The version number for the SSC server currently in use."
    ::= { usdSscClientStatusScalars 4 }

--
-- Statistics Objects
--
usdSscClientStatisticsScalars OBJECT IDENTIFIER ::= { usdSscClientStatistics 1 }

usdSscClientPolicyCommandsReceived  OBJECT-TYPE
    SYNTAX      Counter32
    MAX-ACCESS  read-only
    STATUS      current
    DESCRIPTION
        "The number of policy command packets received from the SSC."
    ::= { usdSscClientStatisticsScalars 1 }

usdSscClientPolicyCommandsListReceived  OBJECT-TYPE
    SYNTAX      Counter32
    MAX-ACCESS  read-only
    STATUS      current
    DESCRIPTION
        "The number of policy command packets received from the SSC with subtype
        LIST."
    ::= { usdSscClientStatisticsScalars 2 }

usdSscClientPolicyCommandsAcctReceived  OBJECT-TYPE
    SYNTAX      Counter32
    MAX-ACCESS  read-only
    STATUS      current
    DESCRIPTION
        "The number of policy command packets received from the SSC with subtype
        ACCOUTING."
    ::= { usdSscClientStatisticsScalars 3 }

usdSscClientBadPolicyCommandsReceived  OBJECT-TYPE
    SYNTAX      Counter32
    MAX-ACCESS  read-only
    STATUS      current
    DESCRIPTION
        "The number of policy command packets received from the SSC that
        included rules that were in error."
    ::= { usdSscClientStatisticsScalars 4 }

usdSscClientErrorPolicyCommandsReceived  OBJECT-TYPE
    SYNTAX      Counter32
    MAX-ACCESS  read-only
    STATUS      current
    DESCRIPTION
        "The number of policy command packets received from the SSC indicating
        an error from the SSC."
    ::= { usdSscClientStatisticsScalars 5 }

usdSscClientPolicyReportsSent  OBJECT-TYPE
    SYNTAX      Counter32
    MAX-ACCESS  read-only
    STATUS      current
    DESCRIPTION
        "The number of policy report packets sent to the SSC."
    ::= { usdSscClientStatisticsScalars 6 }

usdSscClientConnectionOpenRequests  OBJECT-TYPE
    SYNTAX      Counter32
    MAX-ACCESS  read-only
    STATUS      current
    DESCRIPTION
        "The number of connection open requests sent to the SSC."
    ::= { usdSscClientStatisticsScalars 7 }

usdSscClientConnectionOpenCompletes  OBJECT-TYPE
    SYNTAX      Counter32
    MAX-ACCESS  read-only
    STATUS      current
    DESCRIPTION
        "The number of connections to the SSC that open successfully."
    ::= { usdSscClientStatisticsScalars 8 }

usdSscClientConnectionClosedSent  OBJECT-TYPE
    SYNTAX      Counter32
    MAX-ACCESS  read-only
    STATUS      current
    DESCRIPTION
        "The number of connection close indications that were sent to the SSC."
    ::= { usdSscClientStatisticsScalars 9 }

usdSscClientConnectionClosedRemotely  OBJECT-TYPE
    SYNTAX      Counter32
    MAX-ACCESS  read-only
    STATUS      current
    DESCRIPTION
        "The number of connection close indications that were received from the
        SSC."
    ::= { usdSscClientStatisticsScalars 10 }

usdSscClientCreateInterfacesSent  OBJECT-TYPE
    SYNTAX      Counter32
    MAX-ACCESS  read-only
    STATUS      current
    DESCRIPTION
        "The number of interface creation indications that were sent to the SSC.
        This indicates the transition of an interface to an UP state."
    ::= { usdSscClientStatisticsScalars 11 }

usdSscClientDeleteInterfacesSent  OBJECT-TYPE
    SYNTAX      Counter32
    MAX-ACCESS  read-only
    STATUS      current
    DESCRIPTION
        "The number of delete interface indications that were sent to the SSC.
        This indicates the transition of an interface to an DOWN state."
    ::= { usdSscClientStatisticsScalars 12 }

usdSscClientActiveIpInterfaces  OBJECT-TYPE
    SYNTAX      Counter32
    MAX-ACCESS  read-only
    STATUS      current
    DESCRIPTION
        "The number of currently active IP interfaces that the SSC Client is
        aware of."
    ::= { usdSscClientStatisticsScalars 13 }

usdSscClientIpInterfaceTransitions  OBJECT-TYPE
    SYNTAX      Counter32
    MAX-ACCESS  read-only
    STATUS      current
    DESCRIPTION
        "The number of IP interface transitions that have been tracked by the
        SSC Client."
    ::= { usdSscClientStatisticsScalars 14 }

usdSscClientSynchronizesReceived  OBJECT-TYPE
    SYNTAX      Counter32
    MAX-ACCESS  read-only
    STATUS      current
    DESCRIPTION
        "The number of synchronization requests received from the SSC."
    ::= { usdSscClientStatisticsScalars 15 }

usdSscClientSynchronizeCompletesSent  OBJECT-TYPE
    SYNTAX      Counter32
    MAX-ACCESS  read-only
    STATUS      current
    DESCRIPTION
        "The number of synchronization complete packets sent to the SSC."
    ::= { usdSscClientStatisticsScalars 16 }

usdSscClientInternalErrors  OBJECT-TYPE
    SYNTAX      Counter32
    MAX-ACCESS  read-only
    STATUS      current
    DESCRIPTION
        "The number of internal errors tracked by the SSC Client."
    ::= { usdSscClientStatisticsScalars 17 }

usdSscClientCommunicationErrors  OBJECT-TYPE
    SYNTAX      Counter32
    MAX-ACCESS  read-only
    STATUS      current
    DESCRIPTION
        "The number of lower layer communication errors tracked by the SSC
        Client."
    ::= { usdSscClientStatisticsScalars 18 }

usdSscClientTokensSeen  OBJECT-TYPE
    SYNTAX      Counter32
    MAX-ACCESS  read-only
    STATUS      current
    DESCRIPTION
        "The number of tokens seen by the SSC client."
    ::= { usdSscClientStatisticsScalars 19 }

usdSscClientActiveTokens  OBJECT-TYPE
    SYNTAX      Counter32
    MAX-ACCESS  read-only
    STATUS      current
    DESCRIPTION
        "The number of tokens that the SSC client is currently aware of."
    ::= { usdSscClientStatisticsScalars 20 }

usdSscClientTokenTransitions  OBJECT-TYPE
    SYNTAX      Counter32
    MAX-ACCESS  read-only
    STATUS      current
    DESCRIPTION
        "The number of tokens transitions that have occurred."
    ::= { usdSscClientStatisticsScalars 21 }

usdSscClientCreateTokensSent  OBJECT-TYPE
    SYNTAX      Counter32
    MAX-ACCESS  read-only
    STATUS      current
    DESCRIPTION
        "The number of token creation indications that were sent to the SSC.
        This indicates the transition of a token to an UP state."
    ::= { usdSscClientStatisticsScalars 22 }

usdSscClientDeleteTokensSent  OBJECT-TYPE
    SYNTAX      Counter32
    MAX-ACCESS  read-only
    STATUS      current
    DESCRIPTION
        "The number of delete token indications that were sent to the SSC.  This
        indicates the transition of a token to an DOWN state."
    ::= { usdSscClientStatisticsScalars 23 }

usdSscClientActiveAddresses  OBJECT-TYPE
    SYNTAX      Counter32
    MAX-ACCESS  read-only
    STATUS      current
    DESCRIPTION
        "The number of addresses that the SSC client is currently aware of."
    ::= { usdSscClientStatisticsScalars 24 }

usdSscClientAddressTransitions  OBJECT-TYPE
    SYNTAX      Counter32
    MAX-ACCESS  read-only
    STATUS      current
    DESCRIPTION
        "The number of address transitions that have occurred."
    ::= { usdSscClientStatisticsScalars 25 }

usdSscClientCreateAddressesSent  OBJECT-TYPE
    SYNTAX      Counter32
    MAX-ACCESS  read-only
    STATUS      current
    DESCRIPTION
        "The number of address creation indications that were sent to the SSC.
        This indicates the transition of an address to an UP state."
    ::= { usdSscClientStatisticsScalars 26 }

usdSscClientDeleteAddressesSent  OBJECT-TYPE
    SYNTAX      Counter32
    MAX-ACCESS  read-only
    STATUS      current
    DESCRIPTION
        "The number of delete address indications that were sent to the SSC.
        This indicates the transition of an address to an DOWN state."
    ::= { usdSscClientStatisticsScalars 27 }

usdSscClientAuthenticationSuccesses  OBJECT-TYPE
    SYNTAX      Counter32
    MAX-ACCESS  read-only
    STATUS      current
    DESCRIPTION
        "The number of tokens which were authenticated successfully."
    ::= { usdSscClientStatisticsScalars 28 }

usdSscClientAuthenticationFailures  OBJECT-TYPE
    SYNTAX      Counter32
    MAX-ACCESS  read-only
    STATUS      current
    DESCRIPTION
        "The number of tokens which were not authenticated successfully."
    ::= { usdSscClientStatisticsScalars 29 }


-- ++++++++++++++++++++++++++++++++++++++++++++++++++++++++++++++++++++++
-- Notification control objects
-- ++++++++++++++++++++++++++++++++++++++++++++++++++++++++++++++++++++++

-- No notifications are defined in this MIB. Placeholder follows.
-- usdSscClientTrapControl      OBJECT IDENTIFIER ::= { usdSscClientMIB 2 }

-- ++++++++++++++++++++++++++++++++++++++++++++++++++++++++++++++++++++++
-- Notifications
-- ++++++++++++++++++++++++++++++++++++++++++++++++++++++++++++++++++++++

-- No notifications are defined in this MIB. Placeholder follows.
-- The following two OBJECT IDENTIFIERS are used to define SNMPv2
-- Notifications that are easily translated into SNMPv1 Traps.
-- usdSscClientTraps            OBJECT IDENTIFIER ::= { usdSscClientMIB 3 }
-- usdSscClientTrapPrefix       OBJECT IDENTIFIER ::= { usdSscClientTraps 0 }


-- ++++++++++++++++++++++++++++++++++++++++++++++++++++++++++++++++++++++
-- Conformance information
-- ++++++++++++++++++++++++++++++++++++++++++++++++++++++++++++++++++++++

usdSscClientMIBConformance  OBJECT IDENTIFIER
    ::= { usdSscClientMIB 4 }
usdSscClientMIBCompliances  OBJECT IDENTIFIER
    ::= { usdSscClientMIBConformance 1 }
usdSscClientMIBGroups       OBJECT IDENTIFIER
    ::= { usdSscClientMIBConformance 2 }

-- compliance statements

usdSscClientAuthCompliance MODULE-COMPLIANCE
    STATUS      obsolete
    DESCRIPTION
        "Obsolete compliance statement for authentication clients implementing
        the Unisphere SSC Client MIB authentication functionality.  This
        statement became obsolete when DHCP-LS, Web and SSC support objects were
        added."
    MODULE   -- this module
        MANDATORY-GROUPS {
            usdSscClientGroup }
    ::= { usdSscClientMIBCompliances 1 }                               -- RX 2.0

usdSscClientAuthCompliance2 MODULE-COMPLIANCE
    STATUS      obsolete
    DESCRIPTION
        "Obsolete compliance statement for authentication clients implementing
        the Unisphere SSC Client MIB authentication functionality.  This
        statement became obsolete when the version number, local address
        and transport router name objects were added."
    MODULE   -- this module
        MANDATORY-GROUPS {
            usdSscClientGroup2 }
    ::= { usdSscClientMIBCompliances 2 }                               -- RX 3.1

usdSscClientAuthCompliance3 MODULE-COMPLIANCE
    STATUS      current
    DESCRIPTION
        "The compliance statement for clients implementing the Unisphere SSC
        Client MIB functionality."
    MODULE   -- this module
        MANDATORY-GROUPS {
            usdSscClientGroup3 }
    ::= { usdSscClientMIBCompliances 3 }                               -- RX 4.0

-- units of conformance

usdSscClientGroup OBJECT-GROUP
    OBJECTS {
        usdSscClientServerSwitchoverTimeout,
        usdSscClientPrimaryAddress,
        usdSscClientPrimaryPort,
        usdSscClientSecondaryAddress,
        usdSscClientSecondaryPort,
        usdSscClientTertiaryAddress,
        usdSscClientTertiaryPort,
        usdSscClientActiveAddress,
        usdSscClientConnectionState,
        usdSscClientActivePort,
        usdSscClientPolicyCommandsReceived,
        usdSscClientPolicyCommandsListReceived,
        usdSscClientPolicyCommandsAcctReceived,
        usdSscClientBadPolicyCommandsReceived,
        usdSscClientErrorPolicyCommandsReceived,
        usdSscClientPolicyReportsSent,
        usdSscClientConnectionOpenRequests,
        usdSscClientConnectionOpenCompletes,
        usdSscClientConnectionClosedSent,
        usdSscClientConnectionClosedRemotely,
        usdSscClientCreateInterfacesSent,
        usdSscClientDeleteInterfacesSent,
        usdSscClientActiveIpInterfaces,
        usdSscClientIpInterfaceTransitions,
        usdSscClientSynchronizesReceived,
        usdSscClientSynchronizeCompletesSent,
        usdSscClientInternalErrors,
        usdSscClientCommunicationErrors }
    STATUS      obsolete
    DESCRIPTION
        "Obsolete collection of objects providing management of SSC Clients.
        This group became obsolete when DHCP-LS, Web and SSC support objects
        were added."
    ::= { usdSscClientMIBGroups 1 }                                    -- RX 2.0

usdSscClientGroup2 OBJECT-GROUP
    OBJECTS {
        usdSscClientServerSwitchoverTimeout,
        usdSscClientPrimaryAddress,
        usdSscClientPrimaryPort,
        usdSscClientSecondaryAddress,
        usdSscClientSecondaryPort,
        usdSscClientTertiaryAddress,
        usdSscClientTertiaryPort,
        usdSscClientActiveAddress,
        usdSscClientConnectionState,
        usdSscClientActivePort,
        usdSscClientPolicyCommandsReceived,
        usdSscClientPolicyCommandsListReceived,
        usdSscClientPolicyCommandsAcctReceived,
        usdSscClientBadPolicyCommandsReceived,
        usdSscClientErrorPolicyCommandsReceived,
        usdSscClientPolicyReportsSent,
        usdSscClientConnectionOpenRequests,
        usdSscClientConnectionOpenCompletes,
        usdSscClientConnectionClosedSent,
        usdSscClientConnectionClosedRemotely,
        usdSscClientCreateInterfacesSent,
        usdSscClientDeleteInterfacesSent,
        usdSscClientActiveIpInterfaces,
        usdSscClientIpInterfaceTransitions,
        usdSscClientSynchronizesReceived,
        usdSscClientSynchronizeCompletesSent,
        usdSscClientInternalErrors,
        usdSscClientCommunicationErrors,
        usdSscClientTokensSeen,
        usdSscClientActiveTokens,
        usdSscClientTokenTransitions,
        usdSscClientCreateTokensSent,
        usdSscClientDeleteTokensSent,
        usdSscClientActiveAddresses,
        usdSscClientAddressTransitions,
        usdSscClientCreateAddressesSent,
        usdSscClientDeleteAddressesSent,
        usdSscClientAuthenticationSuccesses,
        usdSscClientAuthenticationFailures }
    STATUS      obsolete
    DESCRIPTION
        "Obsolete basic collection of objects providing management of SSC
        Clients.  This group became obsolete when version number, local address
        and transport router name objects were added."
    ::= { usdSscClientMIBGroups 2 }                                    -- RX 3.1

usdSscClientGroup3 OBJECT-GROUP
    OBJECTS {
        usdSscClientServerSwitchoverTimeout,
        usdSscClientPrimaryAddress,
        usdSscClientPrimaryPort,
        usdSscClientSecondaryAddress,
        usdSscClientSecondaryPort,
        usdSscClientTertiaryAddress,
        usdSscClientTertiaryPort,
        usdSscClientLocalAddress,
        usdSscClientTransportRouterName,
        usdSscClientActiveAddress,
        usdSscClientConnectionState,
        usdSscClientActivePort,
        usdSscClientVersion,
        usdSscClientPolicyCommandsReceived,
        usdSscClientPolicyCommandsListReceived,
        usdSscClientPolicyCommandsAcctReceived,
        usdSscClientBadPolicyCommandsReceived,
        usdSscClientErrorPolicyCommandsReceived,
        usdSscClientPolicyReportsSent,
        usdSscClientConnectionOpenRequests,
        usdSscClientConnectionOpenCompletes,
        usdSscClientConnectionClosedSent,
        usdSscClientConnectionClosedRemotely,
        usdSscClientCreateInterfacesSent,
        usdSscClientDeleteInterfacesSent,
        usdSscClientActiveIpInterfaces,
        usdSscClientIpInterfaceTransitions,
        usdSscClientSynchronizesReceived,
        usdSscClientSynchronizeCompletesSent,
        usdSscClientInternalErrors,
        usdSscClientCommunicationErrors,
        usdSscClientTokensSeen,
        usdSscClientActiveTokens,
        usdSscClientTokenTransitions,
        usdSscClientCreateTokensSent,
        usdSscClientDeleteTokensSent,
        usdSscClientActiveAddresses,
        usdSscClientAddressTransitions,
        usdSscClientCreateAddressesSent,
        usdSscClientDeleteAddressesSent,
        usdSscClientAuthenticationSuccesses,
        usdSscClientAuthenticationFailures }
    STATUS      current
    DESCRIPTION
        "The basic collection of objects providing management of SSC Clients."
    ::= { usdSscClientMIBGroups 3 }                                    -- RX 4.0

END
