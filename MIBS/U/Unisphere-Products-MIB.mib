-- *****************************************************************************
-- Unisphere Networks Enterprise Product MIB
--
-- Copyright (c) 1999, 2001 Unisphere Networks, Inc.  All rights reserved.
-- *****************************************************************************

Unisphere-Products-MIB DEFINITIONS ::= BEGIN

IMPORTS
    MODULE-IDENTITY
        FROM SNMPv2-SMI
    unisphere
        FROM Unisphere-SMI;

usProducts MODULE-IDENTITY
    LAST-UPDATED "200112071536Z"  -- 07-Dec-01 10:36 AM EST
    ORGANIZATION "Unisphere Networks, Inc."
    CONTACT-INFO
        "       Unisphere Networks, Inc.
                Customer Service
        Postal: 10 Technology Park Drive
                Westford, MA  01886
                USA
        Tel:    +1 978 589 5800
        E-mail: info@UnisphereNetworks.com"
    DESCRIPTION
        "The sysObjectID registry for Unisphere Networks products.  This is the
        top-level registry for object identifiers for SNMP managed products that
        are manufactured or distibuted by Unisphere Networks."
    -- Revision History
    REVISION    "200112071536Z"  -- 07-Dec-01 10:36 AM EST
    DESCRIPTION
        "Added nodes for the ERX-1440, ERX-705 and SSX-1440 products."
    REVISION    "200110151829Z"  -- 15-Oct-01 02:29 PM EDT
    DESCRIPTION
        "Change the name of the MRX family."
    REVISION    "200103011527Z"  -- 01-Mar-01 10:27 AM EST
    DESCRIPTION
        "Added nodes for Marconi products."
    REVISION    "200005240000Z"  -- 24-May-2000
    DESCRIPTION
        "Added nodes for UMC System Manamagent"
    REVISION    "9912131936Z"    -- 13-Dec-99 2:36 PM EST
    DESCRIPTION
        "Changed the MRX family definitions.  Added MODULE-IDENTITY."
    REVISION    "9911160000Z"    -- 16-Nov-99
    DESCRIPTION
        "Added Service Ready Switch 3000."
    REVISION    "9909280000Z"    -- 28-Sep-99
    DESCRIPTION
        "The initial release of this information module."
    ::= { unisphere 1 }


-- *****************************************************************************
-- Top-level Unisphere Product OBJECT IDENTIFIER assignments.
-- *****************************************************************************

    productFamilies
        OBJECT IDENTIFIER ::= { usProducts 1 }

    unisphereProductFamilies
        OBJECT IDENTIFIER ::= { productFamilies 1 }

-- *****************************************************************************
-- Unisphere Edge Routing Switch (ERX) product family.
-- *****************************************************************************

    usErx
        OBJECT IDENTIFIER ::= { unisphereProductFamilies 1 }

-- ERX-1400
    usEdgeRoutingSwitch1400
        OBJECT IDENTIFIER ::= { usErx 1 }
-- ERX-700
    usEdgeRoutingSwitch700
        OBJECT IDENTIFIER ::= { usErx 2 }
-- ERX-1440
    usEdgeRoutingSwitch1440
        OBJECT IDENTIFIER ::= { usErx 3 }
-- ERX-705
    usEdgeRoutingSwitch705
        OBJECT IDENTIFIER ::= { usErx 4 }


-- *****************************************************************************
-- Unisphere MRX Routing Switch product family.
-- *****************************************************************************

    usMrx
        OBJECT IDENTIFIER ::= { unisphereProductFamilies 2 }

-- MRX-16000
    usMrxRoutingSwitch16000
        OBJECT IDENTIFIER ::= { usMrx 1 }
-- MRX-32000
    usMrxRoutingSwitch32000
        OBJECT IDENTIFIER ::= { usMrx 2 }


-- *****************************************************************************
-- Unisphere Service Mediation Switch product family.
-- *****************************************************************************

    usSmx
        OBJECT IDENTIFIER ::= { unisphereProductFamilies 3 }

-- SMX-2100
    usServiceMediationSwitch2100
        OBJECT IDENTIFIER ::= { usSmx 1 }


-- *****************************************************************************
-- Unisphere Service Ready Switch product family.
-- *****************************************************************************

    usSrx
        OBJECT IDENTIFIER ::= { unisphereProductFamilies 4 }

-- SRX-3000
    usServiceReadySwitch3000
        OBJECT IDENTIFIER ::= { usSrx 1 }


-- *****************************************************************************
-- Unisphere Management Center product family.
-- *****************************************************************************

    usUmc
        OBJECT IDENTIFIER ::= { unisphereProductFamilies 5 }

-- UMC System Management
    usUmcSystemManagement
        OBJECT IDENTIFIER ::= { usUmc 1 }


-- *****************************************************************************
-- OEM'd versions of Unisphere Networks product families/products are rooted
-- under the oemProductFamilies node.
-- *****************************************************************************

    oemProductFamilies
        OBJECT IDENTIFIER ::= { productFamilies 2 }

-- *****************************************************************************
-- Marconi versions of Unisphere Networks product families/products are rooted
-- under the oemProductFamilies node.
-- *****************************************************************************

    marconiProductFamilies
        OBJECT IDENTIFIER ::= { oemProductFamilies 1 }

    usSsx
        OBJECT IDENTIFIER ::= { marconiProductFamilies 1 }

-- SSX-1400
    usSsx1400
        OBJECT IDENTIFIER ::= { usSsx 1 }
-- SSX-700
    usSsx700
        OBJECT IDENTIFIER ::= { usSsx 2 }
-- SSX-1440
    usSsx1440
        OBJECT IDENTIFIER ::= { usSsx 3 }

END
