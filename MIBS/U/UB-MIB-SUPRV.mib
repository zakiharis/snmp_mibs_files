UB-MIB-SUPRV { iso org(3) dod(6) internet(1) 4 1 75 }

DEFINITIONS ::= BEGIN

	IMPORTS
		Counter, IpAddress
			FROM RFC1065-SMI
 		OBJECT-TYPE, enterprises, Counter, TimeTicks
 			FROM RFC1155-SMI
		DisplayString, ifIndex
  			FROM RFC1158-MIB
		PhysAddress
			FROM RFC1213-MIB;

  ubNode              OBJECT IDENTIFIER ::= { enterprises 75 }
  ubEquip             OBJECT IDENTIFIER ::= { ubNode 1 }
  ubTrapAttrs         OBJECT IDENTIFIER ::= { ubNode 3 }
  ubSystem            OBJECT IDENTIFIER ::= { ubNode 4 }
  ubSuprv             OBJECT IDENTIFIER ::= { ubEquip 1 }
  hub                 OBJECT IDENTIFIER ::= { ubSuprv 1 }
  card                OBJECT IDENTIFIER ::= { ubSuprv 2 }
  port                OBJECT IDENTIFIER ::= { ubSuprv 3 }
  ubSecurity          OBJECT IDENTIFIER ::= { ubSystem 1 }

-- This is version 4.4 of the UB Access/One Supervisor MIB.
-- See the document, UB Access/One Supervisor MIB, that specifies which 
-- groups of this MIB that each Access/One product supports.

  hubId OBJECT-TYPE
      SYNTAX   PhysAddress 
      ACCESS   read-only
      STATUS   mandatory
      DESCRIPTION
          " HUB ENCLOSURE Group The address of the hub enclosure in MAC address format.  This is the supervisor's MAC address."
      ::= { hub 1 }

  hubType OBJECT-TYPE
      SYNTAX   INTEGER  {
         oneSlot-ASE1000(1),    --.'ASE-1000'
         twoSlot-ASE2000(3),    --.'ASE-2000'
         fiveSlot-ASE3000(5),   --.'ASE-3000'
         elevenSlot-ASE7000(11) --.'ASE-7000'
      }
      ACCESS   read-only
      STATUS   mandatory
      DESCRIPTION
          " The type of enclosure; the number of slots in the enclosure."
      ::= { hub 2 }

  hubName OBJECT-TYPE
      SYNTAX   DisplayString 
      ACCESS   read-only
      STATUS   mandatory
      DESCRIPTION
          " The name of the Access/One enclosure."
      ::= { hub 3 }

  hubSerNumber OBJECT-TYPE
      SYNTAX   DisplayString 
      ACCESS   read-only
      STATUS   mandatory
      DESCRIPTION
          " The serial number of the hub."
      ::= { hub 4 }

  hubIPAddr OBJECT-TYPE
      SYNTAX   IpAddress 
      ACCESS   read-only
      STATUS   mandatory
      DESCRIPTION
          " The IP address used to communicate with the SNMP agent in the Supervisor."
      ::= { hub 5 }

  hubPowerSupplyStatus OBJECT-TYPE
      SYNTAX   INTEGER  {
         notApplicable(1),      --.Not Applicable
         normalPower(2),        --.NORMAL: normal power and both (for a fault tolerant power supply) power supplies are operative.
         acPowerAbnormal(3),    --.AC POWER FAIL: ac power abnormal
         highTemp(4),           --.PS HI TEMP: the temperature of the unit is too high
         onePsModuleFailed(5)   --.ONE MODULE FAILED: normal dc power is being supplied, but one power supply module has failed (for a unit having fault tolerant power supplies).
      }
      ACCESS   read-only
      STATUS   mandatory
      DESCRIPTION
          " The power supply status."
      ::= { hub 6 }

  hubTempStatus OBJECT-TYPE
      SYNTAX   INTEGER  {
         notApplicable(1),      --.Not Applicable
         abnormalTemperature(2),--.ABNORMAL
         normalTemperature(3)   --.NORMAL
      }
      ACCESS   read-only
      STATUS   mandatory
      DESCRIPTION
          " Indicates whether the temperature of at least one card in the enclosure is out of range."
      ::= { hub 7 }

  hubPollTime OBJECT-TYPE
      SYNTAX   INTEGER  {
         notApplicable(1),      --.
         no-polling-requested(2), --.
         oneHalfSec(3),         --. OV.5 secs.
         oneSec(4),             --. OV1.0 secs.
         onePt5secs(5),         --. OV1.5 secs.
         twoSecs(6),            --. OV2.0 secs.
         twoPt5secs(7),         --. OV2.5 secs.
         threeSecs(8),          --. OV3.0 secs.
         threePt5secs(9),       --. OV3.5 secs.
         fourSecs(10),          --. OV4.0 secs.
         fourPt5secs(11),       --. OV4.5 secs.
         fiveSecs(12)           --. OV5.0 secs.
      }
      ACCESS   read-only
      STATUS   mandatory
      DESCRIPTION
          " The time in tenths of seconds between polls of hub cards by the supervisor."
      ::= { hub 8 }

  hubResetAction OBJECT-TYPE
      SYNTAX   INTEGER  {
         not-requested(2),      --.'Not Requested'
         resetAllCards(3),      --.'Reset All Except Supervisor'
         forceLoad(5)           --.'Load Zero Slot Enclosure'
      }
      ACCESS   read-write
      STATUS   mandatory
      DESCRIPTION
          " When this internet-object is SET to a value of requested, resetAllCards, or forceLoad,  the hub resets (according to the specific request), and after resetting locally sets the value of this internet-object to not-requested.  Initially its value is not-requested."
      ::= { hub 9 }

  hubAFS OBJECT-TYPE
      SYNTAX   INTEGER  {
         notApplicable(1),      --.
         normalAirflow(2),      --.NORMAL AIRFLOW
         abnormalAirflow(3)     --.AIRFLOW ABNORMAL
      }
      ACCESS   read-only
      STATUS   mandatory
      DESCRIPTION
          " Indicates whether airflow inside the enclosure is normal.  This applies only to enclosures with an Air Flow Sensor (AFS) installed and a supervisor capable of detecting the signal from this sensor (currently only the ASM-710 and ASM-760)."
      ::= { hub 10 }

  ensupStaticNetConfig OBJECT-TYPE
      SYNTAX   INTEGER  {
         netAndSupDirect(2),    --.'Netcard+Supervisor Direct': Supervisor uses its Net Interface, all other cards use Net Card.
         supOnly(3),            --.'Supervisor': All cards use Supervisor's Net Interface.
         netOnly(4),            --.'Netcard': All cards use Net Card.
         supElseBridge(5)       --.'Supervisor or Eth-.3 Bridge': All cards use ETHERNET BUS interface to .3 bridge; if the bridge is down, then use the supervisor.
      }
      ACCESS   read-only
      STATUS   mandatory
      DESCRIPTION
          " CARD Group ensup:	Ethernet Supervisor The configured status of the interface between the net module(s) and the backbone."
      ::= { card 1 }

  ensupDynamicNetStatus OBJECT-TYPE
      SYNTAX   INTEGER  {
         notApplicable(1),      --.'Not Applicable'
         netAndSupDirect(2),    --.'Super. using direct path, other using external Netcard'
         supOnly(3),            --.'All modules using Supervisor's Net Interface'
         netOnly(4),            --.'All modules using external Netcard'
         bridgeOnly(5),         --.'All modules using Eth. backplane to .3 Bridge'
         netOrSupLoopback(6)    --. Interface to the backbone(supervisor or net card) is in loopback mode.
      }
      ACCESS   read-only
      STATUS   mandatory
      DESCRIPTION
          " The dynamically changed configuration status of the interface between the net module(s) and the backbone."
      ::= { card 2 }

  ensupNetBridgeSlot OBJECT-TYPE
      SYNTAX   INTEGER  {
         notApplicable(1),      --.
         slot-1(2),             --.
         slot-2(3),             --.
         slot-3(4),             --.
         slot-4(5),             --.
         slot-5(6),             --.
         slot-6(7),             --.
         slot-7(8),             --.
         slot-8(9),             --.
         slot-9(10),            --.
         slot-10(11),           --.
         slot-11(12)            --.
      }
      ACCESS   read-only
      STATUS   mandatory
      DESCRIPTION
          " The relative group (slot) containing a local bridge by which the modules access the backbone (relevant only if the value of ensupStaticNetConfig is 'sup-bridge')."
      ::= { card 3 }

  ensupCarrierCounter OBJECT-TYPE
      SYNTAX   Counter 
      ACCESS   read-only
      STATUS   mandatory
      DESCRIPTION
          " The number of times that carrier sense was on when sampled every 2 ms (used in conjunction with a1gUpTime)."
      ::= { card 4 }

  ensupNetUtilization OBJECT-TYPE
      SYNTAX   DisplayString 
      ACCESS   read-only
      STATUS   mandatory
      DESCRIPTION
          " The percentage of time that carrier sense was on; the percentage is expressed to the nearest tenth (as XXX.X%)."
      ::= { card 5 }

  ensupNetUtilThreshold OBJECT-TYPE
      SYNTAX   INTEGER 
      ACCESS   read-only
      STATUS   mandatory
      DESCRIPTION
          " The threshold for ensupNetUtilization (sends a trap when exceeded).Percentage utilization to the nearest whole integer."
      ::= { card 6 }

  a1gTable OBJECT-TYPE
      SYNTAX   SEQUENCE OF A1gEntry
      ACCESS   not-accessible
      STATUS   mandatory
      DESCRIPTION
          "a1g: 	Access/1 Group TABLE Row selection: the card's relative position in the enclosure, starting at 1."
      ::= { card 7 }

  a1gEntry OBJECT-TYPE
      SYNTAX   A1gEntry 
      ACCESS   not-accessible
      STATUS   mandatory
      DESCRIPTION
          ""
      INDEX {   a1gSlotId }
      ::= { a1gTable 1 }

	A1gEntry ::= SEQUENCE {
		a1gSlotId			INTEGER,
		a1gPorts			INTEGER,
		a1gOperStatus			INTEGER,
		a1gTempStatus			INTEGER,
		a1gEthBusAdmAction		INTEGER,
		a1gEthBusMgmtStatus		INTEGER,
		a1gNetMgmtBusOperStatus		INTEGER,
		a1gProductType			INTEGER,
		a1gUpTime			TimeTicks,
		a1gResets			Counter,
		a1gResetAction			INTEGER
	}
  a1gSlotId OBJECT-TYPE
      SYNTAX   INTEGER 
      ACCESS   read-only
      STATUS   mandatory
      DESCRIPTION
          " The card's relative position in the enclosure, starting at 1."
      ::= { a1gEntry 1 }

  a1gPorts OBJECT-TYPE
      SYNTAX   INTEGER 
      ACCESS   read-only
      STATUS   mandatory
      DESCRIPTION
          " The number of ports on a card."
      ::= { a1gEntry 2 }

  a1gOperStatus OBJECT-TYPE
      SYNTAX   INTEGER  {
         notApplicable(1),      --.'Unknown'
         initializing(2),       --.'Initialization':initializing
         powerOnDiagnostics(3), --.'Running Power On Diagnostics': power on diagnostics
         debugMode(4),          --.'Module In Debug Mode': module is in debug mode
         onlineDiagnostics(5),  --.'Module running diagnostics': online diagnostics in progress
         moduleFault(6),        --.'Fault': Module faulty
         netBooting(7),         --.'Network Booting': boot requested
         netLoading(8),         --.'Network Downloading': downloading from NMC
         cbLoading(9),          --.'Control Bus Loading': Supervisor is loading configuration data using the control bus interface.
         up(10),                --.'Up': intelligent module up
         standby(11),           --.'Standby'
         softwareDisabled(12),  --.'Software Disabled'
         reset(13),             --.'Module Reset'
         inactive(14),          --.'Concentrator Inactive'
         active(15),            --.'Concentrator Active': non-intelligent concentrator active
         notResponding(16)      --.'Module not responding to supervisor polls'
      }
      ACCESS   read-only
      STATUS   mandatory
      DESCRIPTION
          "states the module goes through when doing power-on diagnostics."
      ::= { a1gEntry 3 }

  a1gTempStatus OBJECT-TYPE
      SYNTAX   INTEGER  {
         notApplicable(1),      --.
         abnormalTemperature(2),--.ABNORMAL
         normalTemperature(3)   --.NORMAL
      }
      ACCESS   read-only
      STATUS   mandatory
      DESCRIPTION
          " An indication whether the card's temperature is too high."
      ::= { a1gEntry 4 }

  a1gEthBusAdmAction OBJECT-TYPE
      SYNTAX   INTEGER  {
         notApplicable(1),      --.'Not Applicable'
         unlock(2),             --.administratively unlock
         lock(3)                --. administratively lock
      }
      ACCESS   read-write
      STATUS   mandatory
      DESCRIPTION
          " The administrative status of a module's Ethernet Bus interface (action). For an ASM320, if a1gEthBusMgmtStatus == lockedByJumper, then values of this attribute cannot be set."
      ::= { a1gEntry 5 }

  a1gEthBusMgmtStatus OBJECT-TYPE
      SYNTAX   INTEGER  {
         notApplicable(1),      --.'Not Applicable'
         unlocked(2),           --. Ethernet Bus interface unlocked and enabled.
         locked(3),             --.module locked and either enabled or disabled.
         notResponding(4),      --. module not responding to supervisor polls and unlocked.
         autosegmented(5),      --. Ethernet Bus autosegmented and unlocked.
         hardwareFault(6),      --.'FAULTY': hardware fault and unlocked.
         lockedByJumper(7)      --.'LOCKED BY JUMPER': applies to ASM320 only.
      }
      ACCESS   read-only
      STATUS   mandatory
      DESCRIPTION
          " The management status of a module's Ethernet bus interface."
      ::= { a1gEntry 6 }

  a1gNetMgmtBusOperStatus OBJECT-TYPE
      SYNTAX   INTEGER  {
         notApplicable(1),      --.'Not Applicable'
         enabled(2),            --. management interface is enabled.
         notResponding(3)       --. module not responding to supervisor polls on the management interface.
      }
      ACCESS   read-only
      STATUS   mandatory
      DESCRIPTION
          " The operational status of the network management interface from the supervisor to the module (the control bus)."
      ::= { a1gEntry 7 }

  a1gProductType OBJECT-TYPE
      SYNTAX   INTEGER  {
         notApplicable(1),      --.
         suprv-780(2),          --.ASM-780; Supervisor token ring
         suprv-700(3),          --.ASM-700; Supervisor Baseband
         brsuprv-760(4),        --.ASM-760; Supervisor Broadband, Buffered Repeater
         brsuprv-710(5),        --.ASM-710; Supervisor Baseband, Buffered Repeater
         net-500(6),            --.ASM-500; Net Card
         net-550(7),            --.ASM-550; Net Card Broadband
         brnet-560(8),          --.ASM-560; Net Card; Buffered Repeater; Broadband
         brnet-510(9),          --.ASM-510; Net Card; Buffered Repeater
         trc-400(10),           --.ASM-400; Token Ring Concentrator
         ecm-300(11),           --.ASM-300; Ethernet on Twisted Pair Concentrator
         tec-900(12),           --.ASM-900; Thin Ethernet Concentrator
         fec-800(13),           --.ASM-800; Fiber Optic Ethernet Concentrator
         ecm-310(14),           --.ASM-310; Ethernet on Twisted Pair (10BaseT) Concentrator
         async-100(15),         --.ASM-100; Asynchronous Terminal Server, 8 ports
         mtm-7100(16),          --.ASM-7100; MaxTalk - Local Talk router
         m3270(17),             --.ASM-200; 3270 Terminal Server on Ethernet
         lebr-5300(18),         --.ASM-5300; Local EthBus to 802.3 bridge
         ltebr-5500(19),        --.ASM-5500; Local EthBus to 802.5 bridge
         lttbr-5550(20),        --.ASM-5550; Local 802.5 to 802.5 bridge
         t1ebr-6300(21),        --.ASM-6300; T1 to EthBus bridge
         t1tbr-6500(22),        --.ASM-6500; T1 to Token Ring bridge
         lftbr-5560(23),        --.ASM-5560; Local FDDI to Token Ring bridge
         lfebr-5360(24),        --.ASM-5360; Local FDDI to EthBus bridge
         lebr-5340(25),         --.ASM-5340; Local EthBus to 802.3 bridge Broadband
         ecm-320-1(26),         --.ASM-320T; Enhanced Ethernet on TP Concentrator Tier 1
         ecm-320-2(27),         --.ASM-320T; Enhanced Ethernet on TP Concentrator Tier 2
         trc-410-1(28),         --.ASM-410T; 16 Mbit Token Ring Concentrator Tier 1
         trc-410-2(29),         --.ASM-410T; 16 Mbit Token Ring Concentrator Tier 2
         suprv-790(30),         --.ASM-790;  Supervisor 4/16Mbit Token Ring
         ausup-700s(31),        --.ASM-700S; Supervisor AUI for 2-Slot Enclosure
         tpsup-700s(32),        --.ASM-700S; Supervisor EOTP for 2-Slot Enclosure
         suprv-790s16(33),      --.ASM-790S; Supervisor TR 16Mbit for 2-Slot Enclosure
         fosup-700s(34),        --.ASM-700S; Supervisor FOIRL for 2-Slot Enclosure
         suprv-700s(35),        --.ASM-700S; Supervisor, no media for 2-Slot Enclosure
         net-500s(36),          --.ASM-500S; Net Card for 2-Slot Enclosure
         rr-8300(37),           --.ASM-8300; ACC EN QE + Serial Router
         rr-8310(38),           --.ASM-8310; ACC EN QE + EN + Serial Router
         rr-8320(39),           --.ASM-8320; ACC EN QE + 2 Serial Router
         rr-8500(40),           --.ASM-8500; ACC TR 4Mbit + Serial Router
         rr-8510(41),           --.ASM-8510; ACC TR 4 Mbit + EN + Serial Router
         rr-8520(42),           --.ASM-8520; ACC TR 4 Mbit + 2 Serial Router
         fBrR-5361(43),         --.ASM-5361; RISC FDDI Brouter
         eTBrR-5530(44),        --.ASM-5530; RISC TR Brouter
         eBrR-5330(45),         --.ASM-5330; RISC 4 EN Brouter
         suprv-790s4(46)        --.ASM-790S; Supervisor TR 4Mbit for 2-Slot Enclosure
      }
      ACCESS   read-only
      STATUS   mandatory
      DESCRIPTION
          " The product type of an A/1 card."
      ::= { a1gEntry 8 }

  a1gUpTime OBJECT-TYPE
      SYNTAX   TimeTicks 
      ACCESS   read-only
      STATUS   mandatory
      DESCRIPTION
          " The elapsed time since the module started operating."
      ::= { a1gEntry 9 }

  a1gResets OBJECT-TYPE
      SYNTAX   Counter 
      ACCESS   read-only
      STATUS   mandatory
      DESCRIPTION
          " The number of times a module has been reset."
      ::= { a1gEntry 10 }

  a1gResetAction OBJECT-TYPE
      SYNTAX   INTEGER  {
         noResetRequested(1),   --.'No Reset Requested'
         enterDebugMode(2),     --.enter debug mode
         podThenDebug(3),       --.do POD then enter debug mode
         podThenNetdownload(4)  --.do POD then download from NMC
      }
      ACCESS   read-write
      STATUS   mandatory
      DESCRIPTION
          " When this internet-object is SET to one of the request values, the card resets, and after resetting retains the value that was SET.  Initially its value is not-requested."
      ::= { a1gEntry 11 }

  configTable OBJECT-TYPE
      SYNTAX   SEQUENCE OF ConfigEntry
      ACCESS   not-accessible
      STATUS   mandatory
      DESCRIPTION
          " config:	Access/1 Group Configuration TABLE Row selection: the card's relative position in the enclosure, starting at 1."
      ::= { card 8 }

  configEntry OBJECT-TYPE
      SYNTAX   ConfigEntry 
      ACCESS   not-accessible
      STATUS   mandatory
      DESCRIPTION
          ""
      INDEX {   configSlotId }
      ::= { configTable 1 }

	ConfigEntry ::= SEQUENCE {
		configSlotId		INTEGER,
		configFaultActionType	INTEGER,
		configRetries		INTEGER,
		configPowerUpMode	INTEGER
	}
  configSlotId OBJECT-TYPE
      SYNTAX   INTEGER 
      ACCESS   read-only
      STATUS   mandatory
      DESCRIPTION
          " The card's relative position in the enclosure, starting at 1."
      ::= { configEntry 1 }

  configFaultActionType OBJECT-TYPE
      SYNTAX   INTEGER  {
         reset(2),              --.'Reset': supervisor resets the card.
         stayInReset(3),        --.'Reset forever (keep reset line active)':supervisor isolates the card by keeping the reset line active.
         noSupvAction(4)        --.'No Action': card takes whatever action independently of the supervisor
      }
      ACCESS   read-only
      STATUS   mandatory
      DESCRIPTION
          " The action to be taken by the Supervisor following a fault on a card."
      ::= { configEntry 2 }

  configRetries OBJECT-TYPE
      SYNTAX   INTEGER 
      ACCESS   read-only
      STATUS   mandatory
      DESCRIPTION
          " The maximum number of times a reset is attempted when configFaultAction is set to reset (no further attempts are made once the reset is successful)."
      ::= { configEntry 3 }

  configPowerUpMode OBJECT-TYPE
      SYNTAX   INTEGER  {
         notApplicable(1),      --.'Not Applicable'
         debug(2),              --.'Enter Debug Immediately'
         podThenDebug(3),       --.'Run power on diagnostics and enter debug'
         podThenNetdownload(4), --.'Run power on diagnostics and request Download'
         pod-CopyUserMem-Run(5),--.Do POD, copy User Durable memory to Active memory, then run.
         pod-CopyDefaults-Run(6)--.Do POD, copy Default Durable memory to User Durable memory and Active memory, and then run.
      }
      ACCESS   read-only
      STATUS   mandatory
      DESCRIPTION
          " The actions taken by the module immediately after power up (pod is Power On Diagnostics)."
      ::= { configEntry 4 }

  a1imTable OBJECT-TYPE
      SYNTAX   SEQUENCE OF A1imEntry
      ACCESS   not-accessible
      STATUS   mandatory
      DESCRIPTION
          " a1im:	Access/1 Intelligent Module TABLE Row selection: the value of the internet-object a1imSlotId, which contains the relative position of a card within an enclosure, starting at 1."
      ::= { card 9 }

  a1imEntry OBJECT-TYPE
      SYNTAX   A1imEntry 
      ACCESS   not-accessible
      STATUS   mandatory
      DESCRIPTION
          ""
      INDEX {   a1imSlotId }
      ::= { a1imTable 1 }

	A1imEntry ::= SEQUENCE {
		a1imSlotId		INTEGER,
		a1imMACAddr		PhysAddress,
		a1imPodDiagnosticMsg	DisplayString,
		a1imModuleFault		INTEGER,
		a1imHaltReason		INTEGER,
		a1imDebugRegisters	OCTET STRING
	}
  a1imSlotId OBJECT-TYPE
      SYNTAX   INTEGER 
      ACCESS   read-only
      STATUS   mandatory
      DESCRIPTION
          " The relative slot position of a card, starting at 1."
      ::= { a1imEntry 1 }

  a1imMACAddr OBJECT-TYPE
      SYNTAX   PhysAddress 
      ACCESS   read-only
      STATUS   mandatory
      DESCRIPTION
          " The module's MAC address (for a bridge, its first network interface).  May be (e.g., for the TRC-410) a unique id chosen from the set of MAC addresses."
      ::= { a1imEntry 2 }

  a1imPodDiagnosticMsg OBJECT-TYPE
      SYNTAX   DisplayString 
      ACCESS   read-only
      STATUS   mandatory
      DESCRIPTION
          " A text message describing a power-on-diagnostic state."
      ::= { a1imEntry 3 }

  a1imModuleFault OBJECT-TYPE
      SYNTAX   INTEGER  {
         notApplicable(1),      --.'Not Applicable'
         noFault(2),            --.'No Fault'
         parityError(3),        --.'Parity Error':
         networkError(4),       --.'Network Error'
         diagosticError(5),     --.'Diagnostic Error'
         operationalError(6)    --.'Operational Error'
      }
      ACCESS   read-only
      STATUS   mandatory
      DESCRIPTION
          " Faults detected by the module."
      ::= { a1imEntry 4 }

  a1imHaltReason OBJECT-TYPE
      SYNTAX   INTEGER  {
         notAvailable(1),       --.
         unexpectedSoftInterrupt(2),    --.'unexpected software interrupt'
         halted(3),             --.'successfully halted by an NMC command'
         singleStepped(4),      --.'successfully single stepped by NMC command'
         breakpoint(5),         --.'normal breakpoint taken after NMC command'
         errorDivideByZero(6),  --.'unexpected divide by zero'
         badSingleStep(7),      --.'unexpected single step'
         nonMaskableInterrupt(8), --.'unrecognized non-maskable interrupt'
         badBreakpoint(9),      --.'unexpected breakpoint taken'
         arithmeticOverflow(10),--.'arithmetic overflow'
         exceededArrayBounds(11), --.'exceeded bounds of an array'
         invalidOpcode(12),     --.'attempt to execute invalid opcode'
         invalidEscapeOpcode(13), --.'attempt to execute invalid esc opcode'
         timer-0Interrupt(14),  --.'unexpected timer 0 interrupt'
         reservedInterrupt(15), --.'unexpected reserved interrupt'
         dma-0Interrupt(16),    --.'unexpected DMA 0 interrupt'
         dma-1Interrupt(17),    --.'unexpected DMA 1 interrupt'
         int-0Interrupt(18),    --.'unexpected INT 0 interrupt'
         int-1Interrupt(19),    --.'unexpected INT 1 interrupt'
         int-2Interrupt(20),    --.'unexpected INT 2 interrupt'
         timer-1Interrupt(21),  --.'unexpected timer 1 interrupt'
         timer-2Interrupt(22),  --.'unexpected timer 2 interrupt'
         parityError(23),       --.'parity error'
         watchDogTimeout(24)    --.'watchdog timeout'
      }
      ACCESS   read-only
      STATUS   mandatory
      DESCRIPTION
          " The last specific halt reason detected by the card."
      ::= { a1imEntry 5 }

  a1imDebugRegisters OBJECT-TYPE
      SYNTAX   OCTET STRING 
      ACCESS   read-only
      STATUS   mandatory
      DESCRIPTION
          " A set of 14 80186 registers used for debugging purposes.  These are CS, IP, FLAG, AX, BX, CX, DX, SP, BP, SI, DI, DS, ES, and SS."
      ::= { a1imEntry 6 }

  tplTable OBJECT-TYPE
      SYNTAX   SEQUENCE OF TplEntry
      ACCESS   not-accessible
      STATUS   mandatory
      DESCRIPTION
          " tpl:	Transport Layer TABLE Row selection: the value of the internet-object tplSlotId, which contains the relative position of a card within an enclosure, starting at 1."
      ::= { card 10 }

  tplEntry OBJECT-TYPE
      SYNTAX   TplEntry 
      ACCESS   not-accessible
      STATUS   mandatory
      DESCRIPTION
          ""
      INDEX {   tplSlotId }
      ::= { tplTable 1 }

	TplEntry ::= SEQUENCE {
		tplSlotId		INTEGER,
		tplIPAddress		IpAddress,
		tplNiuName		DisplayString,
		tplProtocolType		INTEGER,
		tplSuprvPollStatus	INTEGER
	}
  tplSlotId OBJECT-TYPE
      SYNTAX   INTEGER 
      ACCESS   read-only
      STATUS   mandatory
      DESCRIPTION
          " The relative slot position of a card, starting at 1."
      ::= { tplEntry 1 }

  tplIPAddress OBJECT-TYPE
      SYNTAX   IpAddress 
      ACCESS   read-only
      STATUS   mandatory
      DESCRIPTION
          " The card's IP address (only applies to TCP/IP)"
      ::= { tplEntry 2 }

  tplNiuName OBJECT-TYPE
      SYNTAX   DisplayString 
      ACCESS   read-only
      STATUS   mandatory
      DESCRIPTION
          "The card's Niu name (only applies to ISO)"
      ::= { tplEntry 3 }

  tplProtocolType OBJECT-TYPE
      SYNTAX   INTEGER  {
         unknown(1),            --.'Unknown'
         xns(2),                --.'XNS'
         tcpIp(3),              --.'TCP/IP'
         iso(4),                --.'ISO/OSI'
         any(5)                 --.'Protocol independent': can use any of XNS, tcp/ip, or ISO
      }
      ACCESS   read-only
      STATUS   mandatory
      DESCRIPTION
          " The type of transport protocol used by the module."
      ::= { tplEntry 4 }

  tplSuprvPollStatus OBJECT-TYPE
      SYNTAX   INTEGER  {
         notApplicable(1),      --.
         responding(2),         --.'Responding': Supervisor has received a response to its poll over Ethernet.
         notResponding(3),      --.'Not Responding': the module does not communicate over Ethernet.
         pollingSuspended(4),   --.'Polling Suspended': supervisor is not currently polling the module.
         cannotPoll(5)          --.'Cannot Poll': The module uses a different protocol than the supervisor (TCP vs. XNS).
      }
      ACCESS   read-only
      STATUS   mandatory
      DESCRIPTION
          " Indicates whether the module has responded to supervisor polling over Ethernet."
      ::= { tplEntry 5 }

  imenEthBusTable OBJECT-TYPE
      SYNTAX   SEQUENCE OF ImenEthBusEntry
      ACCESS   not-accessible
      STATUS   mandatory
      DESCRIPTION
          " imen:	Intelligent Module Ethernet Datalink TABLE (Ethernet Bus interface) Row selection: the value of the internet-object imenSlotId, which contains the relative position of a card within an enclosure, starting at 1."
      ::= { card 11 }

  imenEthBusEntry OBJECT-TYPE
      SYNTAX   ImenEthBusEntry 
      ACCESS   not-accessible
      STATUS   mandatory
      DESCRIPTION
          ""
      INDEX { imenSlotId }
      ::= { imenEthBusTable 1 }

	ImenEthBusEntry ::= SEQUENCE {
		imenSlotId		INTEGER,
		imenTransmitPkts	Counter,
		imenReceivePkts		Counter,
		imenCRCErrors		Counter,
		imenCollisions		Counter
	}
  imenSlotId OBJECT-TYPE
      SYNTAX   INTEGER 
      ACCESS   read-only
      STATUS   mandatory
      DESCRIPTION
          " The relative position of the card in the enclosure, starting from 1."
      ::= { imenEthBusEntry 1 }

  imenTransmitPkts OBJECT-TYPE
      SYNTAX   Counter 
      ACCESS   read-only
      STATUS   mandatory
      DESCRIPTION
          " The total number of packets transmitted."
      ::= { imenEthBusEntry 2 }

  imenReceivePkts OBJECT-TYPE
      SYNTAX   Counter 
      ACCESS   read-only
      STATUS   mandatory
      DESCRIPTION
          " The total number of packets received."
      ::= { imenEthBusEntry 3 }

  imenCRCErrors OBJECT-TYPE
      SYNTAX   Counter 
      ACCESS   read-only
      STATUS   mandatory
      DESCRIPTION
          " The number of packets received with CRC errors."
      ::= { imenEthBusEntry 4 }

  imenCollisions OBJECT-TYPE
      SYNTAX   Counter 
      ACCESS   read-only
      STATUS   mandatory
      DESCRIPTION
          " The number of packets transmitted with collision detected."
      ::= { imenEthBusEntry 5 }

  brdgTable OBJECT-TYPE
      SYNTAX   SEQUENCE OF BrdgEntry
      ACCESS   not-accessible
      STATUS   mandatory
      DESCRIPTION
          " brdg:	Bridge TABLE Row selection: the value of the internet-object brdgSlotId, which contains the relative position of a card within an enclosure, starting at 1, plus the relative interface, brdgIfId, starting at 1."
      ::= { card 12 }

  brdgEntry OBJECT-TYPE
      SYNTAX   BrdgEntry 
      ACCESS   not-accessible
      STATUS   mandatory
      DESCRIPTION
          ""
      INDEX {   brdgSlotId,  brdgIfId }
      ::= { brdgTable 1 }

	BrdgEntry ::= SEQUENCE {
		brdgSlotId		INTEGER,
		brdgIfId		INTEGER,
		brdgIfType		INTEGER,
		brdgIfFault		INTEGER,
		brdgIfMACAddr		PhysAddress
	}
  brdgSlotId OBJECT-TYPE
      SYNTAX   INTEGER 
      ACCESS   read-only
      STATUS   mandatory
      DESCRIPTION
          " The relative slot (from 1) containing this card."
      ::= { brdgEntry 1 }

  brdgIfId OBJECT-TYPE
      SYNTAX   INTEGER 
      ACCESS   read-only
      STATUS   mandatory
      DESCRIPTION
          " The relative interface (from 1) of this entry (see the appropriate hardware specification to determine which interface is 1, 2, etc.)."
      ::= { brdgEntry 2 }

  brdgIfType OBJECT-TYPE
      SYNTAX   INTEGER  {
         ethernetBus(2),        --.'EthBus'
         baseband802-3(3),      --.'802.3'
         fourMbps802-5(4),      --.'802.5 (4 Mbps)'
         fddi(5),               --.'FDDI'
         t1(6),                 --.'T1'
         broadband802-3(7),     --.'802.3 Broadband'
         sixteenMbps802-5(8)    --.'802.5 (16 Mbps)'
      }
      ACCESS   read-only
      STATUS   mandatory
      DESCRIPTION
          " The type of bridge interface."
      ::= { brdgEntry 3 }

  brdgIfFault OBJECT-TYPE
      SYNTAX   INTEGER  {
         notApplicable(1),      --.'Not Applicable'
         linkDown(2),           --.'Link Down'
         linkUp(3),             --.'Link Up'
         linkLoopbackTest(4)    --.'Link Running Loopback Test'
      }
      ACCESS   read-only
      STATUS   mandatory
      DESCRIPTION
          " Bridge faults (note these are interface specific)."
      ::= { brdgEntry 4 }

  brdgIfMACAddr OBJECT-TYPE
      SYNTAX   PhysAddress 
      ACCESS   read-only
      STATUS   mandatory
      DESCRIPTION
          " The MAC address of the bridge's specific interface"
      ::= { brdgEntry 5 }

  ecTable OBJECT-TYPE
      SYNTAX   SEQUENCE OF EcEntry
      ACCESS   not-accessible
      STATUS   mandatory
      DESCRIPTION
          " ec:	Ethernet Concentrator TABLE Row selection: the value of the internet-object ecSlotId, which contains the relative position of a card within an enclosure, starting at 1."
      ::= { card 13 }

  ecEntry OBJECT-TYPE
      SYNTAX   EcEntry 
      ACCESS   not-accessible
      STATUS   mandatory
      DESCRIPTION
          ""
      INDEX {   ecSlotId }
      ::= { ecTable 1 }

	EcEntry ::= SEQUENCE {
		ecSlotId		INTEGER,
		ecCarrierCounter	Counter,
		ecFanStatus		INTEGER
	}
  ecSlotId OBJECT-TYPE
      SYNTAX   INTEGER 
      ACCESS   read-only
      STATUS   mandatory
      DESCRIPTION
          " The relative slot (from 1) containing this card."
      ::= { ecEntry 1 }

  ecCarrierCounter OBJECT-TYPE
      SYNTAX   Counter 
      ACCESS   read-only
      STATUS   mandatory
      DESCRIPTION
          " The number of times carrier was sensed when sampled every 2 ms."
      ::= { ecEntry 2 }

  ecFanStatus OBJECT-TYPE
      SYNTAX   INTEGER  {
         notApplicable(1),      --.Not Applicable
         normalFan(2),          --.Normal
         abnormalFan(3)         --.Abnormal
      }
      ACCESS   read-only
      STATUS   mandatory
      DESCRIPTION
          " The status of the Temp/Flex mount adaptor fan (on the ASM-800 (fiber EC) only)."
      ::= { ecEntry 3 }

  netTable OBJECT-TYPE
      SYNTAX   SEQUENCE OF NetEntry
      ACCESS   not-accessible
      STATUS   mandatory
      DESCRIPTION
          " net:	NET Card TABLE Row selection: the value of the internet-object netSlotId, which contains the relative position of a card within an enclosure, starting at 1."
      ::= { card 14 }

  netEntry OBJECT-TYPE
      SYNTAX   NetEntry 
      ACCESS   not-accessible
      STATUS   mandatory
      DESCRIPTION
          ""
      INDEX {   netSlotId }
      ::= { netTable 1 }

	NetEntry ::= SEQUENCE {
		netSlotId		INTEGER,
		netBackboneType		INTEGER,
		netFault		INTEGER,
		netBackboneStatus	INTEGER
	}
  netSlotId OBJECT-TYPE
      SYNTAX   INTEGER 
      ACCESS   read-only
      STATUS   mandatory
      DESCRIPTION
          " The relative slot (from 1) containing this card."
      ::= { netEntry 1 }

  netBackboneType OBJECT-TYPE
      SYNTAX   INTEGER  {
         baseband(2),           --.'Base Band'
         broadband(3)           --.'Broad Band'
      }
      ACCESS   read-only
      STATUS   mandatory
      DESCRIPTION
          " The type of backbone to which the NET interface is attached."
      ::= { netEntry 2 }

  netFault OBJECT-TYPE
      SYNTAX   INTEGER  {
         notApplicable(1),      --.
         internalFault(2),      --.'Int FAULT: net interface detects problems...'
         auiBad(3),             --.'Ext FAULT: check cables, xceiver, 12VDC...': external: cables or transceiver are bad
         mdiBad(4),             --.'Ext FAULT: check link to backbone...': external: link to backbone bad
         bufferedRepeaterBad(5),--.'Buffered Repeater Down': Onboard buffered repeater is faulty.
         normal(6)              --.'Normal'
      }
      ACCESS   read-only
      STATUS   mandatory
      DESCRIPTION
          " An interface fault at various points between the module and the attached backbone."
      ::= { netEntry 3 }

  netBackboneStatus OBJECT-TYPE
      SYNTAX   INTEGER  {
         notApplicable(1),      --.'Unknown'
         netOnly(2),            --.'Active': all modules use the net interface to access the backbone
         netAndSupDirect(3),    --.'Direct': the supervisor accesses its own interface to the backbone; all other modules access the backbone via the Net Card
         loopback(4),           --.'Loopback': Any transmissions directed to the backbone are looped back to the sender; this implies that the other (if any) net interface is in the standby state.
         bridgeOnly(5),         --.'Supervisor and other modules use bridge to connect to backbone'
         standby(6)             --.'Standby': there is no communication to the backbone; the card is waiting to takeover communication should the other backbone interface fail.
      }
      ACCESS   read-only
      STATUS   mandatory
      DESCRIPTION
          " Backbone interface status: the status of the interface or interfaces to the backbone."
      ::= { netEntry 4 }

  brnTable OBJECT-TYPE
      SYNTAX   SEQUENCE OF BrnEntry
      ACCESS   not-accessible
      STATUS   mandatory
      DESCRIPTION
          " brn:	Buffer Repeater NET Card TABLE Row selection: the value of the internet-object brnSlotId, which contains the relative position of a card within an enclosure, starting at 1, plus the relative interface, brnIfId (1 or 2)."
      ::= { card 15 }

  brnEntry OBJECT-TYPE
      SYNTAX   BrnEntry 
      ACCESS   not-accessible
      STATUS   mandatory
      DESCRIPTION
          ""
      INDEX {   brnSlotId, brnIfId }
      ::= { brnTable 1 }

	BrnEntry ::= SEQUENCE {
		brnSlotId		INTEGER,
		brnIfId			INTEGER,
		brnIfEthDLCStatus	INTEGER,
		brnCarrierCounter	Counter,
		brnCarrierTimeInterval	TimeTicks,
		brnTransmitPkts		Counter,
		brnReceivePkts		Counter,
		brnCRCErrors		Counter,
		brnCollisions		Counter,
		brnPktsAborted16Colls	Counter,
		brnShortPkts		Counter,
		brnAlignmentErrors	Counter,
		brnOverflows		Counter,
		brnUnderflows		Counter
	}
  brnSlotId OBJECT-TYPE
      SYNTAX   INTEGER 
      ACCESS   read-only
      STATUS   mandatory
      DESCRIPTION
          " The relative slot (from 1) containing this card."
      ::= { brnEntry 1 }

  brnIfId OBJECT-TYPE
      SYNTAX   INTEGER  {
         if-1(1),               --.
         if-ETHBUS(2)           --.
      }
      ACCESS   read-only
      STATUS   mandatory
      DESCRIPTION
          " The relative interface (from 1) containing this card; interface 1 is the Ethernet Bus interface."
      ::= { brnEntry 2 }

  brnIfEthDLCStatus OBJECT-TYPE
      SYNTAX   INTEGER  {
         notApplicable(1),      --.'not applicable': no transmissions yet.
         normal(2),             --.'Normal': no error on the last transmission.
         parityError(3),        --.'Parity Error': Set when the parallel to serial converter detects a parity error in the data.
         collisions-16(4),      --.'16 collisions': Set when the 16th collision for the same packet aborts tranmission.
         collision(5),          --.'Collision': Set when a collision terminates transmission of a packet.
         underflow(6)           --.'Underflow': Set when data to be transmitted is not available to the parallel to serial converter before it is empty.
      }
      ACCESS   read-only
      STATUS   mandatory
      DESCRIPTION
          " The Ethernet Data Link Control status of the last transmission to the segment attached to the buffered repeater net card."
      ::= { brnEntry 3 }

  brnCarrierCounter OBJECT-TYPE
      SYNTAX   Counter 
      ACCESS   read-only
      STATUS   mandatory
      DESCRIPTION
          " The number of times carrier was sensed when sampled every 1 ms."
      ::= { brnEntry 4 }

  brnCarrierTimeInterval OBJECT-TYPE
      SYNTAX   TimeTicks 
      ACCESS   read-only
      STATUS   mandatory
      DESCRIPTION
          " The time interval over which brnCarrierCounter counts."
      ::= { brnEntry 5 }

  brnTransmitPkts OBJECT-TYPE
      SYNTAX   Counter 
      ACCESS   read-only
      STATUS   mandatory
      DESCRIPTION
          " The total number of packets transmitted."
      ::= { brnEntry 6 }

  brnReceivePkts OBJECT-TYPE
      SYNTAX   Counter 
      ACCESS   read-only
      STATUS   mandatory
      DESCRIPTION
          " The total number of packets received."
      ::= { brnEntry 7 }

  brnCRCErrors OBJECT-TYPE
      SYNTAX   Counter 
      ACCESS   read-only
      STATUS   mandatory
      DESCRIPTION
          " The number of packets received with CRC errors."
      ::= { brnEntry 8 }

  brnCollisions OBJECT-TYPE
      SYNTAX   Counter 
      ACCESS   read-only
      STATUS   mandatory
      DESCRIPTION
          " The number of collisions detected."
      ::= { brnEntry 9 }

  brnPktsAborted16Colls OBJECT-TYPE
      SYNTAX   Counter 
      ACCESS   read-only
      STATUS   mandatory
      DESCRIPTION
          " The number of packets aborted because of 16 consecutive collisions detected."
      ::= { brnEntry 10 }

  brnShortPkts OBJECT-TYPE
      SYNTAX   Counter 
      ACCESS   read-only
      STATUS   mandatory
      DESCRIPTION
          " The total number of short packets received."
      ::= { brnEntry 11 }

  brnAlignmentErrors OBJECT-TYPE
      SYNTAX   Counter 
      ACCESS   read-only
      STATUS   mandatory
      DESCRIPTION
          " The total number of packets received with alignment errors: the number of frames received that are not an integral number of octets and do not pass the FCS check."
      ::= { brnEntry 12 }

  brnOverflows OBJECT-TYPE
      SYNTAX   Counter 
      ACCESS   read-only
      STATUS   mandatory
      DESCRIPTION
          " The number of packets received that had to be discarded due to errors in bit frequency resulting in overflow."
      ::= { brnEntry 13 }

  brnUnderflows OBJECT-TYPE
      SYNTAX   Counter 
      ACCESS   read-only
      STATUS   mandatory
      DESCRIPTION
          " The number of packets received that had to be discarded due to errors in bit frequency resulting in underflow."
      ::= { brnEntry 14 }

  tr16cTable OBJECT-TYPE
      SYNTAX   SEQUENCE OF Tr16cEntry
      ACCESS   not-accessible
      STATUS   mandatory
      DESCRIPTION
          " tr16c:  Token Ring Concentrator Card TABLE Row selection: the value of the internet-object tr16cSlotId, which contains the relative position of a card within an enclosure, starting at 1."
      ::= { card 16 }

  tr16cEntry OBJECT-TYPE
      SYNTAX   Tr16cEntry 
      ACCESS   not-accessible
      STATUS   mandatory
      DESCRIPTION
          ""
      INDEX {   tr16cSlotId }
      ::= { tr16cTable 1 }

	Tr16cEntry ::= SEQUENCE {
		tr16cSlotId			INTEGER,
		tr16cTier			INTEGER,
		tr16cOperState			INTEGER,
		tr16cRingNumber			INTEGER,
		tr16cManufacturerID		OCTET STRING,
		tr16cManufacturerProductID	DisplayString,
		tr16cManufProductVers		OCTET STRING,
		tr16cActiveMonitorPortNumber	INTEGER,
		tr16cRingSpeed			INTEGER,
		tr16cLLCFrames			Counter,
		tr16cMACFrames			Counter,
		tr16cOctets			Counter,
		tr16cMulticastFrames		Counter,
		tr16cBroadcastFrames		Counter,
		tr16cFrameCheckSequences	Counter,
		tr16cAutoPartitionEnableTimer	TimeTicks,
		tr16cAutoPartitionHoldTimer	TimeTicks,
		tr16cAutoPartitionRetries	INTEGER,
		tr16cLLCSamples			Counter,
		tr16cMACSamples			Counter,
		tr16cUpTimeMS			Counter,
		tr16cResetDurableUserAttrs	INTEGER
	}
  tr16cSlotId OBJECT-TYPE
      SYNTAX   INTEGER 
      ACCESS   read-only
      STATUS   mandatory
      DESCRIPTION
          "The relative slot number, starting at 1, of the concentrator."
      ::= { tr16cEntry 1 }

  tr16cTier OBJECT-TYPE
      SYNTAX   INTEGER  {
         tier-1(1),             --. 'TIER 1'
         tier-2(2),             --. 'TIER 2'
         tier-3(3)              --. 'TIER 3'
      }
      ACCESS   read-only
      STATUS   mandatory
      DESCRIPTION
          "17,32	RelayID Indicates the management level of functionality (tier) of this concentrator."
      ::= { tr16cEntry 2 }

  tr16cOperState OBJECT-TYPE
      SYNTAX   INTEGER  {
         notApplicable(1),      --.
         normal(2),             --. The ring is operational.
         beaconDetectInProgress(3)  --. The ring is operational but busy with the beacon detect process.
      }
      ACCESS   read-only
      STATUS   mandatory
      DESCRIPTION
          " The operational state of the ring."
      ::= { tr16cEntry 3 }

  tr16cRingNumber OBJECT-TYPE
      SYNTAX   INTEGER 
      ACCESS   read-only
      STATUS   mandatory
      DESCRIPTION
          " The ring number assigned when configuring a bridge."
      ::= { tr16cEntry 4 }

  tr16cManufacturerID OBJECT-TYPE
      SYNTAX   OCTET STRING 
      ACCESS   read-only
      STATUS   mandatory
      DESCRIPTION
          " The Organization Unique Identifier as defined in IEEE 802.1A, Overview and Architecture.  This is the first 24 bits of UB's MAC address identifying UB uniquely worldwide and is a constant equal to 00DD00 in hexadecimal."
      ::= { tr16cEntry 5 }

  tr16cManufacturerProductID OBJECT-TYPE
      SYNTAX   DisplayString 
      ACCESS   read-only
      STATUS   mandatory
      DESCRIPTION
          " A string of ASCII characters  representing the concentrator's product identifier (i.e., a name identifying an enumeration of a1gProductType).  Some examples are 'trc-410-1' and 'trc-410-2'."
      ::= { tr16cEntry 6 }

  tr16cManufProductVers OBJECT-TYPE
      SYNTAX   OCTET STRING 
      ACCESS   read-only
      STATUS   mandatory
      DESCRIPTION
          " A string that is unique for a specific manufacturerProductID that identifies a concentrators's hardware and firmware  versions.   The two octets are non-negative integers with values from 0 through 255.  If a version does not apply then the version number is zero.  One is the first applicable version number.  The first octet is the hardware version and the second is the firmware version. "
      ::= { tr16cEntry 7 }

  tr16cActiveMonitorPortNumber OBJECT-TYPE
      SYNTAX   INTEGER 
      ACCESS   read-only
      STATUS   mandatory
      DESCRIPTION
          " The relative port number of the active monitor for this ring.  Its value is 0 if the active monitor is not attached to any port on this concentrator."
      ::= { tr16cEntry 8 }

  tr16cRingSpeed OBJECT-TYPE
      SYNTAX   INTEGER  {
         notApplicable(1),      --.'not applicable'
         fourMbps(2),           --.'four Mbps'
         sixteenMbps(3)         --.'sixteen Mbps'
      }
      ACCESS   read-only
      STATUS   mandatory
      DESCRIPTION
          "17	RingSpeed The current concentrator operating speed of either 4 or 16 Mbps.  Note that each concentrator in a ring must be configured with the same value of this attribute."
      ::= { tr16cEntry 9 }

  tr16cLLCFrames OBJECT-TYPE
      SYNTAX   Counter 
      ACCESS   read-only
      STATUS   mandatory
      DESCRIPTION
          "26	TotalLLCFramesThe total number of transmitted frames that are not MAC level management frames."
      ::= { tr16cEntry 10 }

  tr16cMACFrames OBJECT-TYPE
      SYNTAX   Counter 
      ACCESS   read-only
      STATUS   mandatory
      DESCRIPTION
          "26	TotalMACFramesThe total number of transmitted frames that are MAC level management frames."
      ::= { tr16cEntry 11 }

  tr16cOctets OBJECT-TYPE
      SYNTAX   Counter 
      ACCESS   read-only
      STATUS   mandatory
      DESCRIPTION
          "26	TotalOctetsThe total number of octets transmitted."
      ::= { tr16cEntry 12 }

  tr16cMulticastFrames OBJECT-TYPE
      SYNTAX   Counter 
      ACCESS   read-only
      STATUS   mandatory
      DESCRIPTION
          "26	TotalMulticastFramesThe total number of frames with a destination address that is either a Functional Group Address or a Group Address."
      ::= { tr16cEntry 13 }

  tr16cBroadcastFrames OBJECT-TYPE
      SYNTAX   Counter 
      ACCESS   read-only
      STATUS   mandatory
      DESCRIPTION
          "26	TotalBroadcastFramesThe total number of frames with a destination address that is a Broadcast Address."
      ::= { tr16cEntry 14 }

  tr16cFrameCheckSequences OBJECT-TYPE
      SYNTAX   Counter 
      ACCESS   read-only
      STATUS   mandatory
      DESCRIPTION
          "26,27	TotalFrameCheckSequenceThe total number of packets with an FCS error."
      ::= { tr16cEntry 15 }

  tr16cAutoPartitionEnableTimer OBJECT-TYPE
      SYNTAX   TimeTicks 
      ACCESS   read-write
      STATUS   mandatory
      DESCRIPTION
          "25	AutoPartitionEnableTimer	*a Indicates the period of time to wait until re-enabling a 'beacon detected' port. the default value is 0 seconds"
      ::= { tr16cEntry 16 }

  tr16cAutoPartitionHoldTimer OBJECT-TYPE
      SYNTAX   TimeTicks 
      ACCESS   read-write
      STATUS   mandatory
      DESCRIPTION
          "25	AutoPartitionHoldTimer	*a Indicates the amount of time to wait until starting the beacon detect process.  The default value is 0 seconds."
      ::= { tr16cEntry 17 }

  tr16cAutoPartitionRetries OBJECT-TYPE
      SYNTAX   INTEGER 
      ACCESS   read-write
      STATUS   mandatory
      DESCRIPTION
          "25	AutoPartitionThreshold	*a Indicates the number of times a port can be temporarily locked by the beacon detect process prior to being permanently locked. The default value is 3."
      ::= { tr16cEntry 18 }

  tr16cLLCSamples OBJECT-TYPE
      SYNTAX   Counter 
      ACCESS   read-only
      STATUS   mandatory
      DESCRIPTION
          "26,27	BandwidthUtilizationA count of the number of times that an LLC packet was present when sampling every millisecond."
      ::= { tr16cEntry 19 }

  tr16cMACSamples OBJECT-TYPE
      SYNTAX   Counter 
      ACCESS   read-only
      STATUS   mandatory
      DESCRIPTION
          "26,27	BandwidthUtilizationA count of the number of times that a MAC frame was present when sampling every millisecond."
      ::= { tr16cEntry 20 }

  tr16cUpTimeMS OBJECT-TYPE
      SYNTAX   Counter 
      ACCESS   read-only
      STATUS   mandatory
      DESCRIPTION
          "26,27	BandwidthUtilization The elapsed time in milliseconds since the concentrator started operating."
      ::= { tr16cEntry 21 }

  tr16cResetDurableUserAttrs OBJECT-TYPE
      SYNTAX   INTEGER  {
         resetComplete(1),      --. 'Complete' :reset complete or never requested
         setToDefaults(2)       --. reset user durable attributes to their default values
      }
      ACCESS   read-write
      STATUS   mandatory
      DESCRIPTION
          " A request to copy the default values stored in durable memory to the User Durable attributes also in durable memory.  The User attributes affected are tr16cRingSpeed, tr16p1AllowInsert, tr16p1ForceInsert, tr16cAutoPartitionEnableTimer, tr16cAutoPartitionHoldTimer, and tr16cAutoPartitionRetries."
      ::= { tr16cEntry 22 }

  tr16reTable OBJECT-TYPE
      SYNTAX   SEQUENCE OF Tr16reEntry
      ACCESS   not-accessible
      STATUS   mandatory
      DESCRIPTION
          " tr16re:  Token Ring Concentrator Ring Error TABLE Row selection: the value of the internet-object tr16cSlotId, which contains the relative position of a card within an enclosure, starting at 1. Contains ring error monitor non-isolating errors."
      ::= { card 17 }

  tr16reEntry OBJECT-TYPE
      SYNTAX   Tr16reEntry 
      ACCESS   not-accessible
      STATUS   mandatory
      DESCRIPTION
          ""
      INDEX {   tr16reSlotId }
      ::= { tr16reTable 1 }

	Tr16reEntry ::= SEQUENCE {
		tr16reSlotId			INTEGER,
		tr16reLostFrames		Counter,
		tr16reRcvCongestionErrors	Counter,
		tr16reFrequencyErrors		Counter,
		tr16reFrameCopyErrors		Counter,
		tr16reTokenErrors		Counter
	}
  tr16reSlotId OBJECT-TYPE
      SYNTAX   INTEGER 
      ACCESS   read-only
      STATUS   mandatory
      DESCRIPTION
          " The relative slot in the hub enclosure, starting at 1."
      ::= { tr16reEntry 1 }

  tr16reLostFrames OBJECT-TYPE
      SYNTAX   Counter 
      ACCESS   read-only
      STATUS   mandatory
      DESCRIPTION
          " Non-isolating lost frames."
      ::= { tr16reEntry 2 }

  tr16reRcvCongestionErrors OBJECT-TYPE
      SYNTAX   Counter 
      ACCESS   read-only
      STATUS   mandatory
      DESCRIPTION
          " Non-isolating congestion on receive errors."
      ::= { tr16reEntry 3 }

  tr16reFrequencyErrors OBJECT-TYPE
      SYNTAX   Counter 
      ACCESS   read-only
      STATUS   mandatory
      DESCRIPTION
          " Non-isolating frequency errors."
      ::= { tr16reEntry 4 }

  tr16reFrameCopyErrors OBJECT-TYPE
      SYNTAX   Counter 
      ACCESS   read-only
      STATUS   mandatory
      DESCRIPTION
          " Non-isolating frame copy errors."
      ::= { tr16reEntry 5 }

  tr16reTokenErrors OBJECT-TYPE
      SYNTAX   Counter 
      ACCESS   read-only
      STATUS   mandatory
      DESCRIPTION
          " Non-isolating token errors."
      ::= { tr16reEntry 6 }

  ecpTable OBJECT-TYPE
      SYNTAX   SEQUENCE OF EcpEntry
      ACCESS   not-accessible
      STATUS   mandatory
      DESCRIPTION
          " PORT Group ecp:	Ethernet Port TABLE Row selection: the value of the internet-object ecpSlotId, which contains the relative position of a card within an enclosure, starting at 1, plus a relative port identifier, starting at 1."
      ::= { port 1 }

  ecpEntry OBJECT-TYPE
      SYNTAX   EcpEntry 
      ACCESS   not-accessible
      STATUS   mandatory
      DESCRIPTION
          ""
      INDEX {   ecpSlotId, ecpPortId }
      ::= { ecpTable 1 }

	EcpEntry ::= SEQUENCE {
		ecpSlotId		INTEGER,
		ecpPortId		INTEGER,
		ecpMgmtStatus		INTEGER,
		ecpAdmAction		INTEGER,
		ecpCarrierCounter	Counter
	}
  ecpSlotId OBJECT-TYPE
      SYNTAX   INTEGER 
      ACCESS   read-only
      STATUS   mandatory
      DESCRIPTION
          " The relative slot (from 1) containing the card."
      ::= { ecpEntry 1 }

  ecpPortId OBJECT-TYPE
      SYNTAX   INTEGER 
      ACCESS   read-only
      STATUS   mandatory
      DESCRIPTION
          " The relative port (from 1) on the card."
      ::= { ecpEntry 2 }

  ecpMgmtStatus OBJECT-TYPE
      SYNTAX   INTEGER  {
         notApplicable(1),      --.Not Applicable
         enabled(2),            --.Port enabled and unlocked.
         lockedByNMC(3),        --.Port  locked and could be operationally either enabled or disabled.
         autosegmented(4),      --.Port disabled: auto segmented by concentrator
         faultyLockedBySuprv(5),--.Port locked: error detected by supervisor
         lowLight(6)            --.Low Light: ethernet on fiber only
      }
      ACCESS   read-only
      STATUS   mandatory
      DESCRIPTION
          " The management status of an Ethernet port."
      ::= { ecpEntry 3 }

  ecpAdmAction OBJECT-TYPE
      SYNTAX   INTEGER  {
         notApplicable(1),      --.
         unlocked(2),           --. administratively unlocked: when a port is unlocked, any of the values of ecpMgmtStatus can apply.
         locked(3)              --. administratively locked.
      }
      ACCESS   read-write
      STATUS   mandatory
      DESCRIPTION
          " The administrative status of an Ethernet port."
      ::= { ecpEntry 4 }

  ecpCarrierCounter OBJECT-TYPE
      SYNTAX   Counter 
      ACCESS   read-only
      STATUS   mandatory
      DESCRIPTION
          " The number of times carrier was sensed on the port when sampled every 2 ms."
      ::= { ecpEntry 5 }

  ecfpTable OBJECT-TYPE
      SYNTAX   SEQUENCE OF EcfpEntry
      ACCESS   not-accessible
      STATUS   mandatory
      DESCRIPTION
          " ecfp:	Ethernet Concentrator Fiber Port TABLE Row selection: the value of the internet-object ecfpSlotId, which contains the relative position of a card within an enclosure, starting at 1, plus the  relative port identifier, ecfpPortId, starting at 1."
      ::= { port 2 }

  ecfpEntry OBJECT-TYPE
      SYNTAX   EcfpEntry 
      ACCESS   not-accessible
      STATUS   mandatory
      DESCRIPTION
          ""
      INDEX {   ecfpSlotId, ecfpPortId }
      ::= { ecfpTable 1 }

	EcfpEntry ::= SEQUENCE {
		ecfpSlotId	INTEGER,
		ecfpPortId	INTEGER,
		ecfpMACAddr	PhysAddress,
		ecfpTxIdleTime	TimeTicks
	}
  ecfpSlotId OBJECT-TYPE
      SYNTAX   INTEGER 
      ACCESS   read-only
      STATUS   mandatory
      DESCRIPTION
          " The relative slot (from 1) containing the card."
      ::= { ecfpEntry 1 }

  ecfpPortId OBJECT-TYPE
      SYNTAX   INTEGER 
      ACCESS   read-only
      STATUS   mandatory
      DESCRIPTION
          " The relative port (from 1) on the card."
      ::= { ecfpEntry 2 }

  ecfpMACAddr OBJECT-TYPE
      SYNTAX   PhysAddress 
      ACCESS   read-only
      STATUS   mandatory
      DESCRIPTION
          " The latest source MAC address from packets received from the MAC side of the AUI"
      ::= { ecfpEntry 3 }

  ecfpTxIdleTime OBJECT-TYPE
      SYNTAX   TimeTicks 
      ACCESS   read-only
      STATUS   mandatory
      DESCRIPTION
          " The elapsed time since the last packet was transmitted."
      ::= { ecfpEntry 4 }

  ec10btpTable OBJECT-TYPE
      SYNTAX   SEQUENCE OF Ec10btpEntry
      ACCESS   not-accessible
      STATUS   mandatory
      DESCRIPTION
          " ec10btp:	Ethernet Concentrator 10BaseT Port TABLE Row selection: the value of the internet-object ec10btpSlotId, which contains the relative position of a card within an enclosure, starting at 1, plus the  relative port identifier, ec10btpPortId, starting at 1."
      ::= { port 3 }

  ec10btpEntry OBJECT-TYPE
      SYNTAX   Ec10btpEntry 
      ACCESS   not-accessible
      STATUS   mandatory
      DESCRIPTION
          ""
      INDEX {   ec10btpSlotId, ec10btpPortId }
      ::= { ec10btpTable 1 }

	Ec10btpEntry ::= SEQUENCE {
		ec10btpSlotId		INTEGER,
		ec10btpPortId		INTEGER,
		ec10btpLinkTestStatus	INTEGER,
		ec10btpLinkTestAction	INTEGER
	}
  ec10btpSlotId OBJECT-TYPE
      SYNTAX   INTEGER 
      ACCESS   read-only
      STATUS   mandatory
      DESCRIPTION
          " The relative slot (from 1) containing the card."
      ::= { ec10btpEntry 1 }

  ec10btpPortId OBJECT-TYPE
      SYNTAX   INTEGER 
      ACCESS   read-only
      STATUS   mandatory
      DESCRIPTION
          " The relative port (from 1) on the card."
      ::= { ec10btpEntry 2 }

  ec10btpLinkTestStatus OBJECT-TYPE
      SYNTAX   INTEGER  {
         testLocked(2),         --.10BaseT Link integrity test Administratively locked
         testFailed(3),         --.10BaseT Link integrity test failed
         testPassed(4)          --.10BaseT Link integrity test passed
      }
      ACCESS   read-only
      STATUS   mandatory
      DESCRIPTION
          " The result of the link integrity test."
      ::= { ec10btpEntry 3 }

  ec10btpLinkTestAction OBJECT-TYPE
      SYNTAX   INTEGER  {
         unlockIntegrityTest(2),--.Unlock the 10BaseT Link integrity test  
         lockIntegrityTest(3)   --.Lock the 10BaseT Link integrity test
      }
      ACCESS   read-write
      STATUS   mandatory
      DESCRIPTION
          "A request to unlock the link integrity test (which is a continuous test)."
      ::= { ec10btpEntry 4 }

  trcpTable OBJECT-TYPE
      SYNTAX   SEQUENCE OF TrcpEntry
      ACCESS   not-accessible
      STATUS   mandatory
      DESCRIPTION
          " trcp:	Token Ring Concentrator Port TABLE Row selection: the value of the internet-object trcpSlotId, which contains the relative position of a card within an enclosure, starting at 1, plus a relative port identifier starting at 1."
      ::= { port 4 }

  trcpEntry OBJECT-TYPE
      SYNTAX   TrcpEntry 
      ACCESS   not-accessible
      STATUS   mandatory
      DESCRIPTION
          ""
      INDEX {   trcpSlotId, trcpPortId }
      ::= { trcpTable 1 }

	TrcpEntry ::= SEQUENCE {
		trcpSlotId		INTEGER,
		trcpPortId		INTEGER,
		trcpAdmAction		INTEGER,
		trcpOperStatus		INTEGER
	}
  trcpSlotId OBJECT-TYPE
      SYNTAX   INTEGER 
      ACCESS   read-only
      STATUS   mandatory
      DESCRIPTION
          " The relative slot (from 1) containing the card."
      ::= { trcpEntry 1 }

  trcpPortId OBJECT-TYPE
      SYNTAX   INTEGER  {
         rs1(1),                --.ring station port 1
         rs2(2),                --.
         rs3(3),                --.
         rs4(4),                --.
         rs5(5),                --.
         rs6(6),                --.
         rs7(7),                --.
         rs8(8),                --.
         rs9(9),                --.
         rs10(10),              --.
         rs11(11),              --.
         rs12(12),              --.
         rs13(13),              --.
         rs14(14),              --.
         rs15(15),              --.
         rs16(16),              --.
         rs17(17),              --.
         rs18(18),              --.
         rs19(19),              --.
         rs20(20),              --.
         in(21),                --.
         out(22)                --.
      }
      ACCESS   read-only
      STATUS   mandatory
      DESCRIPTION
          " The relative port (from 1) on the card."
      ::= { trcpEntry 2 }

  trcpAdmAction OBJECT-TYPE
      SYNTAX   INTEGER  {
         notApplicable(1),      --.
         unlock(2),             --.administratively unlock the port
         lock(3)                --.administratively lock the port (bypass it)
      }
      ACCESS   read-write
      STATUS   mandatory
      DESCRIPTION
          " The administrative status of a token ring port.  It reflects only administrative status."
      ::= { trcpEntry 3 }

  trcpOperStatus OBJECT-TYPE
      SYNTAX   INTEGER  {
         stationInserted(2),    --.Station Inserted
         selfBypass(3),         --.Port Bypassed
         portError(4)           --.Port Error
      }
      ACCESS   read-only
      STATUS   mandatory
      DESCRIPTION
          " The operational status of a token ring port."
      ::= { trcpEntry 4 }

  tr16p1Table OBJECT-TYPE
      SYNTAX   SEQUENCE OF Tr16p1Entry
      ACCESS   not-accessible
      STATUS   mandatory
      DESCRIPTION
          " tr16p1:	Token Ring Concentrator Port Tier 1 TABLE Row selection: the value of the internet-object tr16p1SlotId, which contains the relative position of a card within an enclosure, starting at 1 plus the value of tr16p1PortId, which contains the relative position of a port within a card, starting at 1."
      ::= { port 5 }

  tr16p1Entry OBJECT-TYPE
      SYNTAX   Tr16p1Entry 
      ACCESS   not-accessible
      STATUS   mandatory
      DESCRIPTION
          ""
      INDEX {   tr16p1SlotId, tr16p1PortId }
      ::= { tr16p1Table 1 }

	Tr16p1Entry ::= SEQUENCE {
		tr16p1SlotId			INTEGER,
		tr16p1PortId			INTEGER,
		tr16p1InsertionState		INTEGER,
		tr16p1AllowInsert		INTEGER,
		tr16p1ForceInsert		INTEGER,
		tr16p1PhantomState		INTEGER
	}
  tr16p1SlotId OBJECT-TYPE
      SYNTAX   INTEGER 
      ACCESS   read-only
      STATUS   mandatory
      DESCRIPTION
          " The relative position (starting at 1) of the concentrator's slot within the enclosure."
      ::= { tr16p1Entry 1 }

  tr16p1PortId OBJECT-TYPE
      SYNTAX   INTEGER  {
         rs1(1),                --.
         rs2(2),                --.
         rs3(3),                --.
         rs4(4),                --.
         rs5(5),                --.
         rs6(6),                --.
         rs7(7),                --.
         rs8(8),                --.
         rs9(9),                --.
         rs10(10),              --.
         rs11(11),              --.
         rs12(12),              --.
         in(13),                --.
         out(14)                --.
      }
      ACCESS   read-only
      STATUS   mandatory
      DESCRIPTION
          " The relative port on the card starting at 1.  Ports 1-12 are ring station ports, 13 is the expansion in port, and 14 is the expansion out port."
      ::= { tr16p1Entry 2 }

  tr16p1InsertionState OBJECT-TYPE
      SYNTAX   INTEGER  {
         notApplicable(1),      --.'not applicable'
         inserted(2),           --.'INSERTED'
         bypassed(3)            --.'BYPASSED'
      }
      ACCESS   read-only
      STATUS   mandatory
      DESCRIPTION
          " The end result of tr16p1AllowInsert, tr16p1ForceInsert, and tr16p1PhantomState, i.e., inserted means tr16p1ForceInsert | tr16p1AllowInsert & tr16p1PhantomState, where tr16p1ForceInsert is true if requested, tr16p1AllowInsert is true if requested, and tr16p1PhantomState is true if phantomPresent."
      ::= { tr16p1Entry 3 }

  tr16p1AllowInsert OBJECT-TYPE
      SYNTAX   INTEGER  {
         notApplicable(1),      --.'not applicable'
         insertionNotAllowed(2),--.request to not allow insertion
         insertionAllowed(3)    --.request to allow insertion
      }
      ACCESS   read-write
      STATUS   mandatory
      DESCRIPTION
          "19	RingStationPortAction	*aAn action that allows an RS port to insert onto its ring if both phantom voltages are present (tr16p1PhantomState is phantomPresent).20	ExpansionInPortAction	*aWhen not allowed, this bypass forces a 'loop-back' to occur on the XI port, and does not allow concentrators to insert onto their rings.21	ExpansionOutPortAction	*aWhen not allowed this bypass forces a 'loop-back' to occur on the XO port so that an attached ASM400 or ASM410 is not inserted when phantom voltage is detected."
      ::= { tr16p1Entry 4 }

  tr16p1ForceInsert OBJECT-TYPE
      SYNTAX   INTEGER  {
         notApplicable(1),      --.'not applicable'
         noForcedInsertion(2),  --.forced insertion rescinded
         forcedInsertion(3)     --.forced insertion requested
      }
      ACCESS   read-write
      STATUS   mandatory
      DESCRIPTION
          "19	RingStationPortInsert	*aWhen forcedInsertion, forces an RS port to insert onto its ring regardless of whether phantom voltage or other conditions are detected.   This is used to support passive devices, such as the IBM MSAU, in order to support the Satellite expansion capability.19	ExpansionInPortInsert	*aWhen set, inserts the XI port onto the ring regardless of whether phantom voltage is present.21	ExpansionOutPortInsert	*aForces XI port to insert on the network."
      ::= { tr16p1Entry 5 }

  tr16p1PhantomState OBJECT-TYPE
      SYNTAX   INTEGER  {
         notApplicable(1),      --.'not applicable'
         phantomVoltagePresent(2),  --. both phantom voltages are on
         phantomVoltageAbsent(3), --. both phantom voltages are off
         wiringFault(4)         --. phantom voltages not both on or off: indicates a wiring fault
      }
      ACCESS   read-only
      STATUS   mandatory
      DESCRIPTION
          "19	ExpansionInPhantomDetect Indicates the XI port detects phantom voltage being provided.20	ExpansionOutPhantomLoadDetect	The status of the phantom voltage provided by the XO port (XO->XI or XO->RS (satellite))."
      ::= { tr16p1Entry 6 }

  tr16p2Table OBJECT-TYPE
      SYNTAX   SEQUENCE OF Tr16p2Entry
      ACCESS   not-accessible
      STATUS   mandatory
      DESCRIPTION
          " tr16p2:	Token Ring Concentrator Port Tiers 2,3 TABLE Row selection: the value of the internet-object tr16p2SlotId, which contains the relative position of a card within an enclosure, starting at 1 plus the value of tr16p2PortId, which contains the relative position of a port within a card, starting at 1."
      ::= { port 6 }

  tr16p2Entry OBJECT-TYPE
      SYNTAX   Tr16p2Entry 
      ACCESS   not-accessible
      STATUS   mandatory
      DESCRIPTION
          ""
      INDEX {   tr16p2SlotId, tr16p2PortId }
      ::= { tr16p2Table 1 }

	Tr16p2Entry ::= SEQUENCE {
		tr16p2SlotId			INTEGER,
		tr16p2PortId			INTEGER,
		tr16p2OperState			INTEGER,
		tr16p2BeaconDetects		Counter,
		tr16p2LastSourceAddress		PhysAddress,
		tr16p2LLCFramesTransmitted	Counter,
		tr16p2LLCFramesReceived		Counter,
		tr16p2MACFramesTransmitted	Counter,
		tr16p2MACFramesReceived		Counter,
		tr16p2OctetsTransmitted		Counter,
		tr16p2OctetsReceived		Counter,
		tr16p2MulticastsTransmitted	Counter,
		tr16p2BroadcastsTransmitted	Counter,
		tr16p2FCSErrorsTransmitted	Counter,
		tr16p2FCSErrorsReceived		Counter,
		tr16p2LastSourceAddressUptime	TimeTicks
	}
  tr16p2SlotId OBJECT-TYPE
      SYNTAX   INTEGER 
      ACCESS   read-only
      STATUS   mandatory
      DESCRIPTION
          " The relative position (starting at 1) of the concentrator's slot within the enclosure."
      ::= { tr16p2Entry 1 }

  tr16p2PortId OBJECT-TYPE
      SYNTAX   INTEGER  {
         rs1(1),                --.
         rs2(2),                --.
         rs3(3),                --.
         rs4(4),                --.
         rs5(5),                --.
         rs6(6),                --.
         rs7(7),                --.
         rs8(8),                --.
         rs9(9),                --.
         rs10(10),              --.
         rs11(11),              --.
         rs12(12),              --.
         in(13),                --.
         out(14)                --.
      }
      ACCESS   read-only
      STATUS   mandatory
      DESCRIPTION
          " The relative port on the card starting at 1.  Ports 1-12 are ring station ports, 13 is the expansion in port, and 14 is the expansion out port."
      ::= { tr16p2Entry 2 }

  tr16p2OperState OBJECT-TYPE
      SYNTAX   INTEGER  {
         notApplicable(1),      --.not applicable
         portOperational(2),    --.unlock
         autoPartitioned(3)     --.beaconing port bypassed
      }
      ACCESS   read-only
      STATUS   mandatory
      DESCRIPTION
          "25	RingStationAutoPartitionState25	RingExpansionInPartitionState25	ExpansionOutAutoPartitionState Indicates whether a hard failure has occurred on a port, been detected through the beaconing procedure, and the offending port subsequently bypassed in the ring."
      ::= { tr16p2Entry 3 }

  tr16p2BeaconDetects OBJECT-TYPE
      SYNTAX   Counter 
      ACCESS   read-only
      STATUS   mandatory
      DESCRIPTION
          "25	RingStationAutoPartitionCount25	ExpansionInAutoPartitionCount25	ExpansionOutAutoPartitionCount Indicates the number of beacon detects that have resulted in this port being partitioned (removed from its ring)."
      ::= { tr16p2Entry 4 }

  tr16p2LastSourceAddress OBJECT-TYPE
      SYNTAX   PhysAddress 
      ACCESS   read-only
      STATUS   mandatory
      DESCRIPTION
          "23,27 	RingStationLastSourceAddress23,27  ExpansionInLastSourceAddress23,27 	ExpansionOutLastSourceAddress Address of previously attached node."
      ::= { tr16p2Entry 5 }

  tr16p2LLCFramesTransmitted OBJECT-TYPE
      SYNTAX   Counter 
      ACCESS   read-only
      STATUS   mandatory
      DESCRIPTION
          " 27	RingStationLLCFramesTransmitted 27	ExpansionInLLCFramesTransmitted 27	ExpansionOutLLCFramesTransmitted Total number of non-MAC Management packets transmitted."
      ::= { tr16p2Entry 6 }

  tr16p2LLCFramesReceived OBJECT-TYPE
      SYNTAX   Counter 
      ACCESS   read-only
      STATUS   mandatory
      DESCRIPTION
          " 27	RingStationLLCFramesReceived 27	ExpansionInLLCFramesReceived 27	ExpansionOutLLCFramesReceived Total number of non-MAC Management packets received."
      ::= { tr16p2Entry 7 }

  tr16p2MACFramesTransmitted OBJECT-TYPE
      SYNTAX   Counter 
      ACCESS   read-only
      STATUS   mandatory
      DESCRIPTION
          "27	RingStationMACFramesTransmitted27	ExpansionInMACFramesTransmitted27	ExpansionOutMACFramesTransmitted Total number of MAC Management packets transmitted."
      ::= { tr16p2Entry 8 }

  tr16p2MACFramesReceived OBJECT-TYPE
      SYNTAX   Counter 
      ACCESS   read-only
      STATUS   mandatory
      DESCRIPTION
          "27	RingStationMACFramesReceived27	ExpansionInMACFramesReceived27	ExpansionOutMACFramesReceived Total number of MAC Management packets received."
      ::= { tr16p2Entry 9 }

  tr16p2OctetsTransmitted OBJECT-TYPE
      SYNTAX   Counter 
      ACCESS   read-only
      STATUS   mandatory
      DESCRIPTION
          "27	RingStationOctetsTransmitted27	ExpansionInOctetsTransmitted27	ExpansionOutOctetsTransmitted Total number of LLC Information octets transmitted."
      ::= { tr16p2Entry 10 }

  tr16p2OctetsReceived OBJECT-TYPE
      SYNTAX   Counter 
      ACCESS   read-only
      STATUS   mandatory
      DESCRIPTION
          "27	RingStationOctetsReceived27	ExpansionInOctetsReceived27	ExpansionOutOctetsReceived Total number of LLC Information Field octets received."
      ::= { tr16p2Entry 11 }

  tr16p2MulticastsTransmitted OBJECT-TYPE
      SYNTAX   Counter 
      ACCESS   read-only
      STATUS   mandatory
      DESCRIPTION
          " 28	RingStationMulticastTransmitted 28	ExpansionInMulticastTransmitted 28	ExpansionOutMulticastTransmitted Total number of Multicast packets transmitted."
      ::= { tr16p2Entry 12 }

  tr16p2BroadcastsTransmitted OBJECT-TYPE
      SYNTAX   Counter 
      ACCESS   read-only
      STATUS   mandatory
      DESCRIPTION
          "28	RingStationBroadcastTransmitted28	ExpansionOutBroadcastTransmitted28	ExpansionInBroadcastTransmitted Total number of Broadcast packets transmitted."
      ::= { tr16p2Entry 13 }

  tr16p2FCSErrorsTransmitted OBJECT-TYPE
      SYNTAX   Counter 
      ACCESS   read-only
      STATUS   mandatory
      DESCRIPTION
          "28	RingStationFCSErrorsTransmitted28	ExpansionInFCSErrorsTransmitted28	ExpansionOutFCSErrorsTransmitted Total number of packets transmitted with an FCS error."
      ::= { tr16p2Entry 14 }

  tr16p2FCSErrorsReceived OBJECT-TYPE
      SYNTAX   Counter 
      ACCESS   read-only
      STATUS   mandatory
      DESCRIPTION
          "28	RingStationFCSErrorsReceived28	ExpansionInFCSErrorsReceived28	ExpansionOutFCSErrorsReceived Total number of packets received with an FCS error."
      ::= { tr16p2Entry 15 }

  tr16p2LastSourceAddressUptime OBJECT-TYPE
      SYNTAX   TimeTicks 
      ACCESS   read-only
      STATUS   mandatory
      DESCRIPTION
          " Time since the value of tr16p2LastSourceAddress last changed."
      ::= { tr16p2Entry 16 }

  tr16p3Table OBJECT-TYPE
      SYNTAX   SEQUENCE OF Tr16p3Entry
      ACCESS   not-accessible
      STATUS   mandatory
      DESCRIPTION
          " tr16p3:	Token Ring Concentrator Port Tiers 2,3 TABLE Row selection: the value of the internet-object tr16p3SlotId, which contains the relative position of a card within an enclosure, starting at 1 plus the value of tr16p3PortId, which contains the relative position of a port within a card, starting at 1."
      ::= { port 7 }

  tr16p3Entry OBJECT-TYPE
      SYNTAX   Tr16p3Entry 
      ACCESS   not-accessible
      STATUS   mandatory
      DESCRIPTION
          ""
      INDEX {   tr16p3SlotId, tr16p3PortId }
      ::= { tr16p3Table 1 }

	Tr16p3Entry ::= SEQUENCE {
		tr16p3SlotId				INTEGER,
		tr16p3PortId				INTEGER,
		tr16p3LineErrors			Counter,
		tr16p3InternalErrors			Counter,
		tr16p3Burst5Errors			Counter,
		tr16p3AcErrors				Counter,
		tr16p3AbortDelimiters			Counter
	}
  tr16p3SlotId OBJECT-TYPE
      SYNTAX   INTEGER 
      ACCESS   read-only
      STATUS   mandatory
      DESCRIPTION
          " The relative position (starting at 1) of the concentrator's slot within the enclosure."
      ::= { tr16p3Entry 1 }

  tr16p3PortId OBJECT-TYPE
      SYNTAX   INTEGER  {
         rs1(1),                --.
         rs2(2),                --.
         rs3(3),                --.
         rs4(4),                --.
         rs5(5),                --.
         rs6(6),                --.
         rs7(7),                --.
         rs8(8),                --.
         rs9(9),                --.
         rs10(10),              --.
         rs11(11),              --.
         rs12(12),              --.
         in(13),                --.
         out(14)                --.
      }
      ACCESS   read-only
      STATUS   mandatory
      DESCRIPTION
          " The relative port on the card starting at 1.  Ports 1-12 are ring station ports, 13 is the expansion in port, and 14 is the expansion out port."
      ::= { tr16p3Entry 2 }

  tr16p3LineErrors OBJECT-TYPE
      SYNTAX   Counter 
      ACCESS   read-only
      STATUS   mandatory
      DESCRIPTION
          " Isolating line errors."
      ::= { tr16p3Entry 3 }

  tr16p3InternalErrors OBJECT-TYPE
      SYNTAX   Counter 
      ACCESS   read-only
      STATUS   mandatory
      DESCRIPTION
          " Isolating internal errors."
      ::= { tr16p3Entry 4 }

  tr16p3Burst5Errors OBJECT-TYPE
      SYNTAX   Counter 
      ACCESS   read-only
      STATUS   mandatory
      DESCRIPTION
          " Isolating burst 5 errors."
      ::= { tr16p3Entry 5 }

  tr16p3AcErrors OBJECT-TYPE
      SYNTAX   Counter 
      ACCESS   read-only
      STATUS   mandatory
      DESCRIPTION
          " Isolating AC errors."
      ::= { tr16p3Entry 6 }

  tr16p3AbortDelimiters OBJECT-TYPE
      SYNTAX   Counter 
      ACCESS   read-only
      STATUS   mandatory
      DESCRIPTION
          " Isolating abort delimiters."
      ::= { tr16p3Entry 7 }

  trapInstanceId OBJECT-TYPE
      SYNTAX   INTEGER 
      ACCESS   not-accessible
      STATUS   mandatory
      DESCRIPTION
          " TRAP Group:  The attributes that may appear in the variable-bindings list of the Trap-PDU. An instance identifier that uniquely identifies an occurrence of a trap.  Note that if multiple Trap-PDUs are sent to reflect the occurrence of the same trap, each contains the same value of the trapInstanceId."
      ::= { ubTrapAttrs 1 }

  trapSlotId OBJECT-TYPE
      SYNTAX   INTEGER 
      ACCESS   not-accessible
      STATUS   optional
      DESCRIPTION
          " trapSource (consists of the following):The attributes required to define the source of the trap.  For example, when a port is unlocked, the slot identifier and port identifier define the source of the trap.  The product type is also included in case the enterprise field in the trap-PDU does not completely distinguish the characteristics of the source. The relative slot (from 1) containing the card that the trap is about."
      ::= { ubTrapAttrs 2 }

  trapProductType OBJECT-TYPE
      SYNTAX   INTEGER 
      ACCESS   not-accessible
      STATUS   mandatory
      DESCRIPTION
          " The product type of the Access/One card that the trap is about.See a1gProductType for specific values."
      ::= { ubTrapAttrs 3 }

  trapPortID OBJECT-TYPE
      SYNTAX   INTEGER 
      ACCESS   not-accessible
      STATUS   optional
      DESCRIPTION
          " The relative port (from 1) that the trap is about."
      ::= { ubTrapAttrs 4 }

  trapPortCount OBJECT-TYPE
      SYNTAX   INTEGER 
      ACCESS   not-accessible
      STATUS   optional
      DESCRIPTION
          " The number of ports on a concentrator."
      ::= { ubTrapAttrs 15 }

  trapPortMask OBJECT-TYPE
      SYNTAX   OCTET STRING 
      ACCESS   not-accessible
      STATUS   optional
      DESCRIPTION
          " A mask indicating the status of ports on the concentrator."
      ::= { ubTrapAttrs 16 }

  trpsbTable OBJECT-TYPE
      SYNTAX   SEQUENCE OF TrpsbEntry
      ACCESS   not-accessible
      STATUS   mandatory
      DESCRIPTION
          " TRAP SUBSCRIPTION Group Trap Subscription TABLE Row selection: the value of the internet-object trpsbIpAddress identifies a row corresponding to a valid member of an agent's community. This table contains 5 entries."
      ::= { ubSecurity 2 }

  trpsbEntry OBJECT-TYPE
      SYNTAX   TrpsbEntry 
      ACCESS   not-accessible
      STATUS   mandatory
      DESCRIPTION
          ""
      INDEX {   trpsbIpAddress }
      ::= { trpsbTable 1 }

	TrpsbEntry ::= SEQUENCE {
		trpsbIpAddress		IpAddress,
		trpsbCommunity		OCTET STRING,
		trpsbActions		INTEGER
	}
  trpsbIpAddress OBJECT-TYPE
      SYNTAX   IpAddress 
      ACCESS   read-write
      STATUS   mandatory
      DESCRIPTION
          " The IP address of a manager subscribing to traps."
      ::= { trpsbEntry 1 }

  trpsbCommunity OBJECT-TYPE
      SYNTAX   OCTET STRING 
      ACCESS   read-write
      STATUS   mandatory
      DESCRIPTION
          " The community string identifying a manager subscribing to traps."
      ::= { trpsbEntry 2 }

  trpsbActions OBJECT-TYPE
      SYNTAX   INTEGER  {
         notApplicable(1),      --.
         subscribeToTraps(2),   --.add: A manager's request to subscribe to traps.
         subscriptionToTrapsCancelled(3)        --.delete: A manager's request to cancel its subscription to traps.
      }
      ACCESS   write-only
      STATUS   mandatory
      DESCRIPTION
          " Actions on a manager's trap subscription."
      ::= { trpsbEntry 3 }


--7.   SUPPORTED TRAPS
--When the generic-trap value in a Trap-PDU is enterpriseSpecific(6), the specific-trap field contains a UB-defined integer that is unique relative to the enterprise object identifier in the Trap_PDU.  This integer identifies the specific type of UB trap that has occurred.
-- Note that some of the objects in the VARIABLES lists are contained in the special Trap Group.
--The Access/One Supervisor supports the following specific traps:

moduleInserted TRAP-TYPE
ENTERPRISE 	ubNode
VARIABLES		{ trapInstanceId, trapProductType, trapSlotId, trapPortID, trapPortCount, trapPortMask }
DESCRIPTION
"A card was inserted in the Access/One chassis."
	::= 1
moduleRemoved TRAP-TYPE
ENTERPRISE 	ubNode
VARIABLES		{ trapInstanceId, trapSlotId, trapProductType, trapPortID, trapPortCount, trapPortMask }
DESCRIPTION
"A card was removed from the Access/One chassis."
	::= 2
moduleFaulty TRAP-TYPE
ENTERPRISE 	ubNode	VARIABLES		{ trapInstanceId, trapSlotId, trapProductType, trapPortID, trapPortCount, trapPortMask }
DESCRIPTION
"A card has become faulty: its state changed to a1gOperStatus (moduleFault(6))."
	::= 3
moduleDown TRAP-TYPE
ENTERPRISE 	ubNode
VARIABLES		{ trapInstanceId, trapSlotId, trapProductType, trapPortID, trapPortCount, trapPortMask }
DESCRIPTION
"A card has not responded to a supervisor poll: its state changed to a1gEthBusMgmtStatus(notResponding(4))."
	::= 4

moduleReset TRAP-TYPE
ENTERPRISE 	ubNode
VARIABLES		{ trapInstanceId, trapSlotId, trapProductType, trapPortID, trapPortCount, trapPortMask }
DESCRIPTION
"A card has been reset: its state changed to a1gOperStatus (reset(13))."
	::= 5
moduleDebug TRAP-TYPE
ENTERPRISE 	ubNode
VARIABLES		{ trapInstanceId, trapSlotId, trapProductType, trapPortID, trapPortCount, trapPortMask }
DESCRIPTION
"A card has put into debug mode: its state changed to a1gOperStatus (debugMode(4))."
	::= 6
moduleHighTemperature TRAP-TYPE
ENTERPRISE 	ubNode
VARIABLES		{ trapInstanceId, trapSlotId, trapProductType, trapPortID, trapPortCount, trapPortMask }
DESCRIPTION
"The card's temperature has become too high: its state changed to a1gTempStatus(abnormal(2))."
	::= 7
ethBusUnlocked TRAP-TYPE
ENTERPRISE 	ubNode
VARIABLES		{ trapInstanceId, trapSlotId, trapProductType, trapPortID, trapPortCount, trapPortMask }
DESCRIPTION
"The interface to the Ethernet bus has been unlocked: its state changed to a1gEthBusAdmAction(unlock(2))."
	::= 8

ethBusLocked TRAP-TYPE
ENTERPRISE 	ubNode
VARIABLES		{ trapInstanceId, trapSlotId, trapProductType, trapPortID, trapPortCount, trapPortMask }
DESCRIPTION
"The interface to the Ethernet bus has been locked: its state changed to a1gEthBusAdmAction(lock(3))."
	::= 9
moduleNetIfEnabled TRAP-TYPE
ENTERPRISE 	ubNode
VARIABLES		{ trapInstanceId, trapSlotId, trapProductType, trapPortID, trapPortCount, trapPortMask }
DESCRIPTION
"The status of the interface to the backbone has changed so that all modules (with the possible exception of the supervisor - when it is in direct mode)  access the backbone through the card's net interface: a state change to netBackboneStatus(active(2)) has occurred."
	::= 16
moduleNetIfDisabled TRAP-TYPE
ENTERPRISE 	ubNode
VARIABLES		{ trapInstanceId, trapSlotId, trapProductType, trapPortID, trapPortCount, trapPortMask }
DESCRIPTION	"The status of the interface to the backbone has changed so that there is no communication backbone through the card's net interface: a state change to netBackboneStatus(standby(6)) has occurred"
	::= 17
moduleNetIfLoopBack TRAP-TYPE
ENTERPRISE 	ubNode
VARIABLES		{ trapInstanceId, trapSlotId, trapProductType, trapPortID, trapPortCount, trapPortMask }
DESCRIPTION
"The status of the interface to the backbone has changed so that this card's net interface loops back traffic directed to the backbone, while the other (possible) net interface's status becomes standby: a state change to netBackboneStatus(loopback(4)) has occurred."
	::= 18
moduleNetIfInternalError TRAP-TYPE
ENTERPRISE 	ubNode
VARIABLES		{ trapInstanceId, trapSlotId, trapProductType, trapPortID, trapPortCount, trapPortMask }
DESCRIPTION
"An internal error at the net interface has been detected: its state changed to netFault(internal(2))."
	::= 19
moduleNetIfExternalError TRAP-TYPE
ENTERPRISE 	ubNode
VARIABLES		{ trapInstanceId, trapSlotId, trapProductType, trapPortID, trapPortCount, trapPortMask }
DESCRIPTION
"An external error at the net interface has been detected: its state changed to either netFault(auiBad(3)) or netFault(mdiBad(4))."
	::= 20
moduleParityError TRAP-TYPE
ENTERPRISE 	ubNode
VARIABLES		{ trapInstanceId, trapSlotId, trapProductType, trapPortID, trapPortCount, trapPortMask }
DESCRIPTION
"An intelligent module has detected a parity error: its status has changed to a1imModuleFault (parityErr(3))."
	::= 21
moduleFanBad TRAP-TYPE
ENTERPRISE 	ubNode
VARIABLES		{ trapInstanceId, trapSlotId, trapProductType, trapPortID, trapPortCount, trapPortMask }
DESCRIPTION
"The fan on the module is defective: its status has changed to ecFanStatus(abnormal(3))."
	::= 22

beaconDetected TRAP-TYPE
ENTERPRISE 	ubNode
VARIABLES		{ trapInstanceId, trapSlotId, trapProductType, trapPortID, trapPortCount, trapPortMask }
DESCRIPTION
"The ring containing this card has begun the beacon detect process: its status has changed to tr16cOperState(beaconDetectInProgress(4))."
	::= 23
moduleTemperatureNormal TRAP-TYPE
ENTERPRISE 	ubNode
VARIABLES		{ trapInstanceId, trapSlotId, trapProductType, trapPortID, trapPortCount, trapPortMask }
DESCRIPTION
"The card's temperature has returned to normal: its state changed from a1gTempStatus(abnormal(2)) to a1gTempStatus(normal(3))."
	::= 24
portUnlocked TRAP-TYPE
ENTERPRISE 	ubNode
VARIABLES		{ trapInstanceId, trapSlotId, trapProductType, trapPortID, trapPortCount, trapPortMask }
DESCRIPTION
"One or more of the concentrator's ports have been unlocked."
	::= 32
portLocked TRAP-TYPE
ENTERPRISE 	ubNode
VARIABLES		{ trapInstanceId, trapSlotId, trapProductType, trapPortID, trapPortCount, trapPortMask }
DESCRIPTION
"One or more of the concentrator's ports have been locked."
	::= 33
portAutoSegmented TRAP-TYPE
ENTERPRISE 	ubNode
VARIABLES		{ trapInstanceId, trapSlotId, trapProductType, trapPortID, trapPortCount, trapPortMask }
DESCRIPTION
"One or more of the concentrator's ports have been auto-segmented by the hardware because of a fault."
	::= 34

portFault TRAP-TYPE
ENTERPRISE 	ubNode
VARIABLES		{ trapInstanceId, trapSlotId, trapProductType, trapPortID, trapPortCount, trapPortMask }
DESCRIPTION
"One or more of the concentrator's ports have been segmented by the supervisor because of a fault."
	::= 35
portForced TRAP-TYPE
ENTERPRISE 	ubNode
VARIABLES		{ trapInstanceId, trapSlotId, trapProductType, trapPortID, trapPortCount, trapPortMask }
DESCRIPTION
"One or more of the concentrator's ports have been forced to allow passive devices to enter the ring."
	::= 36
portNotForced TRAP-TYPE
ENTERPRISE 	ubNode
VARIABLES		{ trapInstanceId, trapSlotId, trapProductType, trapPortID, trapPortCount, trapPortMask }
DESCRIPTION
"One or more of the concentrator's ports are no longer being forced to allow passive devices to enter the ring."
	::= 37
portLobeFault TRAP-TYPE
ENTERPRISE 	ubNode
VARIABLES		{ trapInstanceId, trapSlotId, trapProductType, trapPortID, trapPortCount, trapPortMask }
DESCRIPTION
"One or more of the concentrator's ports are experiencing a lobe fault.  The concentrator experiences voltage(either positive or negative) in only one of the phantom pair wires."
	::= 38

portLobeFaultCleared TRAP-TYPE
ENTERPRISE 	ubNode
VARIABLES		{ trapInstanceId, trapSlotId, trapProductType }
DESCRIPTION
"One or more of the concentrator's ports are no longer experiencing a lobe fault."
	::= 39
portLinkTestUnlocked TRAP-TYPE
ENTERPRISE 	ubNode
VARIABLES		{ trapInstanceId, trapSlotId, trapProductType, trapPortID, trapPortCount, trapPortMask }
DESCRIPTION
"The link test on one or more of the concentrator's ports has been unlocked."
	::= 40
portLinkTestLocked TRAP-TYPE
ENTERPRISE 	ubNode
VARIABLES		{ trapInstanceId, trapSlotId, trapProductType, trapPortID, trapPortCount, trapPortMask }
DESCRIPTION
"The link test on one or more of the concentrator's ports has been locked."
	::= 41
badPowerSupply TRAP-TYPE
ENTERPRISE 	ubNode
VARIABLES		{ trapInstanceId, trapSlotId, trapProductType, trapPortID, trapPortCount, trapPortMask }
DESCRIPTION
"At least one power module has lost its AC power. : its state changed to hubPowerSupplyStatus(acPowerAbnormal(3))."
	::= 48
powerSupplyHiTemp TRAP-TYPE
ENTERPRISE 	ubNode
VARIABLES		{ trapInstanceId, trapSlotId, trapProductType, trapPortID, trapPortCount, trapPortMask }
DESCRIPTION
"The temperature of the power supply has become too high: its state changed to hubPowerSupplyStatus(highTemp(4))."
	::= 49
networkIfError TRAP-TYPE
ENTERPRISE 	ubNode
VARIABLES		{ trapInstanceId, trapSlotId, trapProductType, trapPortID, trapPortCount, trapPortMask }
DESCRIPTION
"One or more of the interfaces to the network backbone are experiencing faults: its state changed to ensupDynamicNetStatus(netOrSupLoopback(6))."
	::= 50
networkIfOK TRAP-TYPE
ENTERPRISE 	ubNode
VARIABLES		{ trapInstanceId, trapSlotId, trapProductType, trapPortID, trapPortCount, trapPortMask }
DESCRIPTION
"The interface to the backbone network has changed (recovered) by using a redundant connection.  The state of the interface to the backbone network changed to one of ensupDynamicNetStatus(netAndSupDirect(2) | supOnly(3) | netOnly(4) | bridgeOnly(5))."
	::= 51
tempBad TRAP-TYPE
ENTERPRISE 	ubNode
DESCRIPTION
"The temperature in the enclosure has been reported by an enclosure temperature sensor to be out of range(possible enclosure fan failure) or the temperature of at least one card in the enclosure is out of range: the hub's state changed to hubTempStatus(abnormal(2))."
	::= 52
tempOK TRAP-TYPE
ENTERPRISE 	ubNode
VARIABLES		{ trapInstanceId, trapSlotId, trapProductType, trapPortID, trapPortCount, trapPortMask }
DESCRIPTION
"The temperature of all cards in the enclosure is now in the proper range or the enclosure temperature has returned to the proper range: the hub's state changed to: hubTempStatus(normal(3))"
	::= 53
fTPSBad TRAP-TYPE
ENTERPRISE 	ubNode
VARIABLES		{ trapInstanceId, trapSlotId, trapProductType, trapPortID, trapPortCount, trapPortMask }
DESCRIPTION
"One or both (for a fault tolerant power supply) dc power supplies have failed.  The power supply's state has changed to: hubPowerSupplyStatus(onePsModuleFailed(5))."
	::= 54
netUtilThreshold TRAP-TYPE
ENTERPRISE 	ubNode
VARIABLES		{ trapInstanceId, trapSlotId, trapProductType, trapPortID, trapPortCount, trapPortMask }
DESCRIPTION
"The network utilization has been exceeded: ensupNetUtilization exceeded ensupNetUtilThreshold."
	::= 55
enclosureFanBad TRAP-TYPE
ENTERPRISE 	ubNode
VARIABLES		{ trapInstanceId, trapSlotId, trapProductType, trapPortID, trapPortCount, trapPortMask }
DESCRIPTION
"The enclosure has an airflow problem (probably a defective fan): the state of hubAFS has changed to abnormal(3)."
	::= 56
servicePortLogin TRAP-TYPE
ENTERPRISE 	ubNode
VARIABLES		{ trapInstanceId, trapSlotId, trapProductType, trapPortID, trapPortCount, trapPortMask }
DESCRIPTION
"The interpreter on the netcard has detected a login command on the service port."
	::= 64

servicePortLogout TRAP-TYPE
ENTERPRISE 	ubNode
VARIABLES		{ trapInstanceId, trapSlotId, trapProductType, trapPortID, trapPortCount, trapPortMask }
DESCRIPTION
"The interpreter on the netcard has detected a logout command on the service port."
	::= 65

END
