USR-CHASSIS-MIB DEFINITIONS ::= BEGIN
	IMPORTS
        OBJECT-TYPE, MODULE-IDENTITY, Counter32, Integer32
                  FROM SNMPv2-SMI
        DateAndTime
                  FROM SNMPv2-TC
        DisplayString, common, UsrConfigStatus
                  FROM USR-DEFINITIONS-MIB;
    usrChassis MODULE-IDENTITY
         LAST-UPDATED "200205051700Z"
         ORGANIZATION "CommWorks Corporation, a 3Com Company"
         CONTACT-INFO "Customer Support"
         DESCRIPTION
                 "The commWorks enterprise defined MIB objects
                   for the card chassis."
--       REVISION "200205051700Z"
--       DESCRIPTION "Converted to SNMPv2"
         ::= { common 41 }
	usrChassisConfigFileName OBJECT-TYPE
		SYNTAX      DisplayString
		MAX-ACCESS  read-only
		STATUS      current
		DESCRIPTION		
		  "The name of a ConfigFile to read/write permanent
		   database records. If the value of this object is an
           empty string, then the NMBA process uses the
           default name `@file://Chassis.cfg'. "
	::= { usrChassis 1 }
	usrChassisCFMStatusFlag  OBJECT-TYPE
	 	SYNTAX	    UsrConfigStatus
		MAX-ACCESS  read-write
		STATUS      current
		DESCRIPTION
		  "Setting the value of this object to `save' causes the values
		   of the ChassisSlotTable to be written out to the
           current config file, which is stored in the 
           usrChassisConfigFileName object. While the new
           ConfigFile is being written, the NMBA process
		   will set the value of this flag to `saving''. Any
		   attempts to set the value while it is not `normal'
		   (i.e. the file is currently being written to the
		   ConfigFile) while result in a badValue error being
		   returned. Setting the value to `normal' will result in no
		   action."
	::= { usrChassis 2 }
	usrChassisChassisAwareness  OBJECT-TYPE
		SYNTAX   INTEGER {
			enabled(1),
			disabled(2)
			}
		MAX-ACCESS  read-write
		STATUS      current
		DESCRIPTION
		  "The value of this object determines if
		   chassis awareness messages from the NMC are to be
           handled or not.  If this object is set to `enabled' 
           then when a chassis awareness message is received, 
           the information contained within the message is used 
           to update the chassis configuration. If this object 
           is set to `disabled' any chassis awareness messages 
           received from the NMC are ignored, and the configuration
           of the chassis must be set statically through SNMP sets,
           or CLI commands. To be able to SET this object
           usrChassisDSA must be 'enabled'."            
	        --CONFIGURABLE
	::= { usrChassis 3 }
	usrChassisSlotTable	OBJECT-TYPE
		SYNTAX SEQUENCE OF UsrChassisSlotEntry
		MAX-ACCESS not-accessible
		STATUS current
		DESCRIPTION
                  "A table containing one row per slot in the chassis.  Each
		   row describes the characteristics of the slot"
	::= { usrChassis 4 }
	usrChassisSlotEntry OBJECT-TYPE
         SYNTAX      UsrChassisSlotEntry
         MAX-ACCESS  not-accessible
         STATUS      current
         DESCRIPTION
            ""
         INDEX   { usrChassisSlot}
	::= { usrChassisSlotTable 1 }
	UsrChassisSlotEntry ::=
         SEQUENCE {
         usrChassisSlot
            Integer32,
         usrChassisOwner
            INTEGER,
         usrChassisCardType
            INTEGER,
         usrChassisNumPorts
            Integer32,
         usrChassisDescription
            DisplayString,
	     usrChassisType
  	        INTEGER,
         usrChassisConsole
            INTEGER
         }
	usrChassisSlot OBJECT-TYPE
         SYNTAX  Integer32
	 MAX-ACCESS  not-accessible
         STATUS  current
         DESCRIPTION
            "The slot number of this row."
	::= { usrChassisSlotEntry 1 }
	usrChassisOwner OBJECT-TYPE
		SYNTAX   INTEGER {
			no(1),
			yes(2),
			assigned(3)
			}
         MAX-ACCESS   read-write
         STATUS   current
         DESCRIPTION
            "An indication if this slot's card has this Gateway card assigned
             as the owning gateway"
         --CONFIGURABLE
         ::= { usrChassisSlotEntry 2 }
	usrChassisCardType OBJECT-TYPE
		SYNTAX   INTEGER {
			empty(1),
			unknown(2),
			quadV32Modem(3),
			dualT1E1(4),
			genericQuadIModem(5),
			hdmsimulator(6),
			trGatewayNAC(7),
			x25GatewayNAC(8),
			dualV34ModemNAC(9),
			quadV32DigitalTerboModemNAC(10),
			quadV32AnalogTerboModemNAC(11),
			quadV32DigAnlTerboModemNAC(12),
			quadV34DigModemNAC(13),
			quadV34AnlModemNAC(14),
			quadV34DigAnlModemNAC(15),
			singleT1NAC(16),
			ethernetGatewayNAC(17),
			accessServer(18),
			i486TrGatewayNAC(19),
			i486EthernetGatewayNAC(20),
			genericQuadModem(21),
			dualRS232NAC(22),
			i486X25GatewayNAC(23),
			i486DXAPINAC(24),
			applicationServerNAC(25),
			iSDNGatewayNAC(26),
			iSDNpriT1NAC(27),
			clkedNetMgtCard(28),
			modemPoolManagementNAC(29),
			modemPoolNetserverNAC(30),
			modemPoolV34ModemNAC(31),
			modemPoolISDNNAC(32),
			nTServerNAC(33),
			quadV34DigitalG2NAC(34),
			quadV34AnalogG2NAC(35),
			quadV34DigAnlgG2NAC(36),
			nETServerFrameRelayNAC(37),
			nETServerTokenRingNAC(38),
			x2524ChannelNAC(39),
			highDensityModem(41),
			wirelessGatewayNAC(42),
			ciscoAS51NAC(43),
			enhancedAccessServer(44),
			enhancedISDNGatewayNAC(45),
			hdm24ChannelNAC(46),
			hdm30ChannelNAC(47),
			riscNetserverNAC(48),
            dualP6NAC(49),
            p5NMC(50),
            ss7iHapiCard(51),
            ds3jhdmt1NAC(52),
            jhdme1NAC(53),
            harc2CARD(54)
			}
         MAX-ACCESS   read-write
         STATUS   current
         DESCRIPTION
            "The ID of the card that is resident in this slot of
             the chassis."
         --CONFIGURABLE
         ::= { usrChassisSlotEntry 3 }
	usrChassisNumPorts OBJECT-TYPE
         SYNTAX  Integer32
         MAX-ACCESS  read-write
         STATUS  current
         DESCRIPTION
            "The number ports that are enabled on the card in this 
             chassis slot. This value will be determined when the the
	     card type for this slot is set, or when a chassis
             awareness message arrives updating this slot.  If the
             card type is empty, the number of ports is set to zero."
         --CONFIGURABLE
	::= { usrChassisSlotEntry 4 }
	usrChassisDescription OBJECT-TYPE
         SYNTAX  DisplayString (SIZE(0..32))
         MAX-ACCESS  read-only
         STATUS  current
         DESCRIPTION
            "A string that describes the type of card in this chassis 
    		   slot."
	::= { usrChassisSlotEntry 5 }
	usrChassisType OBJECT-TYPE
		SYNTAX   INTEGER {
			static(1),
			dynamic(2)
			}
         MAX-ACCESS   read-write
         STATUS   current
         DESCRIPTION
            "An indicator that tells if this slot's (row's) data was
             created statically by configuration, or dynamically by
             the receipt of chassis awareness information from the
             NMC.  Only static entries are saved to the configuration
             file.  Dynamic entries are saved as static entries with 
             an empty card type. If dynamic information is learned
             it replaces the information in a static entry.  A dynamic
             entry cannot be changed through the CLI or an SNMP set."
         ::= { usrChassisSlotEntry 6 }
    usrChassisConsole OBJECT-TYPE
        SYNTAX   INTEGER {
            no(1),
            yes(2)
            }
         MAX-ACCESS   read-write
         STATUS   current
         DESCRIPTION
            "An indicator that tells if this slot supports a packet
         bus based console."
    DEFVAL { no }
         --CONFIGURABLE
         ::= { usrChassisSlotEntry 7 }
	usrChassisDSA  OBJECT-TYPE
		SYNTAX   INTEGER {
			enabled(1),
			disabled(2)
			}
		MAX-ACCESS  read-write
		STATUS      current
		DESCRIPTION
		  "The value of this object determines if
		   the card is participating in the
		   dynamic slot assignment algorithm.
		   The default is disabled."
	        --CONFIGURABLE
	::= { usrChassis 5 }
	usrChassisDSAQueryReq  OBJECT-TYPE
		SYNTAX      Counter32
		MAX-ACCESS  read-only
		STATUS      current
		DESCRIPTION
		  "The number of DSA query requests from NMC seen by this card"
	::= { usrChassis 6 }
	usrChassisDSAQueryRsp  OBJECT-TYPE
		SYNTAX      Counter32
		MAX-ACCESS  read-only
		STATUS      current
		DESCRIPTION
		  "The number of DSA query responses sent by this card to NMC"
	::= { usrChassis 7 }
	usrChassisDSAServiceReq  OBJECT-TYPE
		SYNTAX      Counter32
		MAX-ACCESS  read-only
		STATUS      current
		DESCRIPTION
		  "The number of DSA service requests issued to this card"
	::= { usrChassis 8 }
	usrChassisDSAServiceAssignments  OBJECT-TYPE
		SYNTAX      Counter32
		MAX-ACCESS  read-only
		STATUS      current
		DESCRIPTION
		  "The number of DSA assignments performed by this card"
	::= { usrChassis 9 }
	usrChassisDSATraps  OBJECT-TYPE
		SYNTAX      Counter32
		MAX-ACCESS  read-only
		STATUS      current
		DESCRIPTION
		  "The number of DSA traps issued"
	::= { usrChassis 10 }
	usrChassisDSAInvalidRX  OBJECT-TYPE
		SYNTAX      Counter32
		MAX-ACCESS  read-only
		STATUS      current
		DESCRIPTION
		  "The number invalid DSA packets received"
	::= { usrChassis 11 }
    usrChassisWhenLastNMCQuery    OBJECT-TYPE
		SYNTAX		DateAndTime
		MAX-ACCESS  read-only
		STATUS		current
		DESCRIPTION
			"Time when the last NMC query packet was received"
	::= { usrChassis 12 }
	usrChassisDSARebalancing  OBJECT-TYPE
		SYNTAX   INTEGER {
			enabled(1),
			disabled(2)
			}
		MAX-ACCESS  read-write
		STATUS      current
		DESCRIPTION
		  "The value of this object determines if
		   the card allows slot rebalancing when
		   participating in the dynamic slot assignment algorithm.
		   The default is enabled."
	        --CONFIGURABLE
	::= { usrChassis 13 }
	usrNMCSnmpForwarding  OBJECT-TYPE
		SYNTAX   INTEGER {
			enabled(1),
			disabled(2)
			}
		MAX-ACCESS  read-write
		STATUS      current
		DESCRIPTION
		  "The value of this object determines if Hiper will
		   accept SNMP forwarded messages from the NMC over NM bus.
                   or CLI commands."
	        --CONFIGURABLE
	::= { usrChassis 14 }
END         -- End usrChassis MIB definitions
-- ************************************************************************
