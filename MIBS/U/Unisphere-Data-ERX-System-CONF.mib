-- *****************************************************************************
-- Unisphere-Data-ERX-System-CONF
--
-- SNMP Agent Capabilities definitions for the Edge Routing Switch System MIBs.
--
-- Copyright (c) 2001, 2002 Unisphere Networks, Inc.  All rights reserved.
-- *****************************************************************************

Unisphere-Data-ERX-System-CONF DEFINITIONS ::= BEGIN

IMPORTS
    MODULE-IDENTITY
        FROM SNMPv2-SMI
    AGENT-CAPABILITIES
        FROM SNMPv2-CONF
    usdSystemAgents
        FROM Unisphere-Data-Agents
    usdERXSysGroup, usdERXSysNotifyGroup, usdERXSysGeneralGroup,
    usdERXSysFabricGroup, usdERXSysNvsGroup, usdERXSysSlotGroup,
    usdERXSysPortGroup, usdERXSysPowerGroup, usdERXSysTemperatureGroup,
    usdERXSysSubsystemGroup, usdERXSysTimingGroup, usdERXSysGeneralGroup2,
    usdERXSysNotifyGroup2, usdERXSysTemperatureGroup2, usdERXSysNotifyGroup3
        FROM Unisphere-Data-ERX-System-MIB;

usdErxSystemAgent MODULE-IDENTITY
    LAST-UPDATED "200204012232Z"  -- 01-Apr-02 05:32 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Edge Routing Switch (ERX)
        System component of the SNMP agent in the Unisphere ERX family of
        products."
    -- Revision History
    REVISION    "200204012232Z"  -- 01-Apr-02 05:32 PM EST  - RX 3.3
    DESCRIPTION
        "Added thermal protection support."
    REVISION    "200104131303Z"  -- 13-Apr-01 09:03 AM EDT  - RX 3.2
    DESCRIPTION
        "The initial release of this management information module."
    ::= { usdSystemAgents 1 }


usdErxSystemAgentV1 AGENT-CAPABILITIES
    PRODUCT-RELEASE
        "Version 1 of the ERX System component of the Unisphere Edge Routing
        Switch SNMP agent.  This version of the ERX System component was
        supported in the Unisphere RX 1.3 system release."
    STATUS      obsolete
    DESCRIPTION
        "The MIB supported by the SNMP agent for the ERX (platform-specific)
        System application in the Unisphere Edge Routing Switch.  These
        capabilities became obsolete when new slot information objects were
        added."
    SUPPORTS    Unisphere-Data-ERX-System-MIB
        INCLUDES  {
            usdERXSysGroup,
            usdERXSysNotifyGroup }
    ::= { usdErxSystemAgent 1 }

usdErxSystemAgentV2 AGENT-CAPABILITIES
    PRODUCT-RELEASE
        "Version 2 of the ERX System component of the Unisphere Edge Routing
        Switch SNMP agent.  This version of the ERX System component was
        supported in the Unisphere RX 2.x system releases."
    STATUS      obsolete
    DESCRIPTION
        "The MIB supported by the SNMP agent for the ERX (platform-specific)
        System application in the Unisphere Edge Routing Switch.  These
        capabilities became obsolete when the timing group was added."
    SUPPORTS    Unisphere-Data-ERX-System-MIB
        INCLUDES  {
            usdERXSysGeneralGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup }
    ::= { usdErxSystemAgent 2 }

usdErxSystemAgentV3 AGENT-CAPABILITIES
    PRODUCT-RELEASE
        "Version 3 of the ERX System component of the Unisphere Edge Routing
        Switch SNMP agent.  This version of the ERX System component was
        supported in the Unisphere RX 3.0 system release."
    STATUS      obsolete
    DESCRIPTION
        "The MIB supported by the SNMP agent for the ERX (platform-specific)
        System application in the Unisphere Edge Routing Switch.  These
        capabilities became obsolete when memory management objects and
        notifications were added."
    SUPPORTS    Unisphere-Data-ERX-System-MIB
        INCLUDES  {
            usdERXSysGeneralGroup,
            usdERXSysTimingGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup }
    ::= { usdErxSystemAgent 3 }

usdErxSystemAgentV4 AGENT-CAPABILITIES
    PRODUCT-RELEASE
        "Version 4 of the ERX System component of the Unisphere Edge Routing
        Switch SNMP agent.  This version of the ERX System component was
        supported in the Unisphere RX 3.2 system release."
    STATUS      obsolete
    DESCRIPTION
        "The MIB supported by the SNMP agent for the ERX (platform-specific)
        System application in the Unisphere Edge Routing Switch.  These
        capabilities became obsolete when thermal protection support was added."
    SUPPORTS    Unisphere-Data-ERX-System-MIB
        INCLUDES  {
            usdERXSysGeneralGroup2,
            usdERXSysTimingGroup,
            usdERXSysFabricGroup,
            usdERXSysNvsGroup,
            usdERXSysSlotGroup,
            usdERXSysPortGroup,
            usdERXSysPowerGroup,
            usdERXSysTemperatureGroup,
            usdERXSysSubsystemGroup,
            usdERXSysNotifyGroup2 }
    ::= { usdErxSystemAgent 4 }

usdErxSystemAgentV5 AGENT-CAPABILITIES
    PRODUCT-RELEASE
        "Version 5 of the ERX System component of the Unisphere Edge Routing
        Switch SNMP agent.  This version of the ERX System component is
        supported in the Unisphere RX 3.3 and subsequent system releases."
    STATUS      current
    DESCRIPTION
        "The MIB supported by the SNMP agent for the ERX (platform-specific)
        System application in the Unisphere Edge Routing Switch."
    SUPPORTS    Unisphere-Data-ERX-System-MIB
        INCLUDES  {
            usdERXSysGeneralGroup2,
            usdERXSysTimingGroup,
            usdERXSysFabricGroup,
            usdERXSysNvsGroup,
            usdERXSysSlotGroup,
            usdERXSysPortGroup,
            usdERXSysPowerGroup,
            usdERXSysTemperatureGroup2,
            usdERXSysSubsystemGroup,
            usdERXSysNotifyGroup3 }
    ::= { usdErxSystemAgent 5 }

END
