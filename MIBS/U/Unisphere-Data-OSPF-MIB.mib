-- *****************************************************************************
-- Unisphere-Data-OSPF-MIB
--
-- Unisphere Networks Inc. Enterprise MIB
-- Extensions for OSPF Protocol Management
--
-- Copyright (c) 1999 Redstone Communications, Incorporated.
-- Copyright (c) 1999, 2002 Unisphere Networks, Incorporated.
-- All Rights Reserved.
-- *****************************************************************************

Unisphere-Data-OSPF-MIB DEFINITIONS ::= BEGIN

IMPORTS
    MODULE-IDENTITY, OBJECT-TYPE, Integer32, Unsigned32, Counter32, IpAddress
        FROM SNMPv2-SMI
    TruthValue, RowStatus
        FROM SNMPv2-TC
    MODULE-COMPLIANCE, OBJECT-GROUP
        FROM SNMPv2-CONF
    InterfaceIndex
        FROM IF-MIB
    ospfAreaEntry, ospfIfEntry, ospfIfIpAddress, ospfAddressLessIf,
    ospfVirtIfEntry, ospfNbrEntry
        FROM OSPF-MIB
    usDataMibs
        FROM Unisphere-Data-MIBs;

usdOspfMIB  MODULE-IDENTITY
    LAST-UPDATED "200204052120Z"  -- 05-Apr-02 04:20 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The OSPF Protocol MIB for the Unisphere Networks Inc. enterprise."
    -- Revision History
    REVISION    "200204052120Z"  -- 05-Apr-02 04:20 PM EST  - RX 4.0
    DESCRIPTION
        "Added usdOspfVpnRouteTag, usdOspfDomainId, usdOspfAreaTeCapable and
        usdOspfMplsTeRtrIdIfIndex objects."
    REVISION    "200005230000Z"  -- 23-May-00               - RX 2.0
    DESCRIPTION
        "Key revisions include:
         o Corrected description for usdOspfProcessId.
         o Added usdOspfNetworkRangeTable.
         o Added usdOspfOperState."
    REVISION      "9909280000Z"  -- 28-Sep-99               - RX 1.0
    DESCRIPTION
        "Initial version of this MIB module."
    ::= { usDataMibs 14 }


-- ++++++++++++++++++++++++++++++++++++++++++++++++++++++++++++++++++++++
-- Managed objects
-- ++++++++++++++++++++++++++++++++++++++++++++++++++++++++++++++++++++++
usdOspfObjects       OBJECT IDENTIFIER ::= { usdOspfMIB 1 }


-- +++++++++++++++++++++++++++++++++++++++++++++++++++++++++++++++++++++++++++++
-- OSPF General Group attributes (scalars)
-- +++++++++++++++++++++++++++++++++++++++++++++++++++++++++++++++++++++++++++++
usdOspfGeneralGroup  OBJECT IDENTIFIER ::= { usdOspfObjects 1 }

usdOspfProcessId OBJECT-TYPE
    SYNTAX      Integer32 (0..65535)
    MAX-ACCESS  read-write
    STATUS      current
    DESCRIPTION
        "An identifier having special semantics when set.

        When this object's value is zero, OSPF is disabled and cannot be
        configured.  Setting this object to a nonzero value enables OSPF
        operation and permits further OSPF configuration to be performed.

        Once set to a nonzero value, this object cannot be modified."
    ::= { usdOspfGeneralGroup 1 }

usdOspfMaxPathSplits OBJECT-TYPE
    SYNTAX      Integer32 (1..16)
    MAX-ACCESS  read-write
    STATUS      current
    DESCRIPTION
        "The maximum number of equal-cost routes that will be maintained by the
        OSPF protocol.

        A change in this value will be taken into account at the next
        shortest-path-first recalculation."
    ::= { usdOspfGeneralGroup 2 }

usdOspfSpfHoldInterval OBJECT-TYPE
    SYNTAX      Integer32 (1..5)
    UNITS       "seconds"
    MAX-ACCESS  read-write
    STATUS      current
    DESCRIPTION
        "The minimum amount of time that must elapse between shortest-path-first
        recalculations.

        Reducing this value can cause an immediate SPF recalulation if the new
        value is less than the current value of usdOspfSpfHoldTimeRemaining and
        other SPF-inducing protocol events have occurred."
    ::= { usdOspfGeneralGroup 3 }

usdOspfNumActiveAreas OBJECT-TYPE
    SYNTAX       Counter32
    MAX-ACCESS   read-only
    STATUS       current
    DESCRIPTION
        "The number of active areas."
    ::= { usdOspfGeneralGroup 4 }

usdOspfSpfTime OBJECT-TYPE
    SYNTAX       Counter32
    MAX-ACCESS   read-only
    STATUS       current
    DESCRIPTION
        "The SPF schedule delay."
    ::= { usdOspfGeneralGroup 5 }

usdOspfRefBw OBJECT-TYPE
    SYNTAX       Unsigned32 (1..4294967295)
    UNITS        "bits per second"
    MAX-ACCESS   read-write
    STATUS       current
    DESCRIPTION
        "The reference bandwith, in bits per second.  This object is used when
        OSPF automatic interface cost calculation is used."
    DEFVAL     { 100 }
    ::= { usdOspfGeneralGroup 6 }

usdOspfAutoVlink OBJECT-TYPE
    SYNTAX       TruthValue
    MAX-ACCESS   read-write
    STATUS       current
    DESCRIPTION
        "Set this object to true(1) in order to have virtual links automatically
        configured."
    ::= { usdOspfGeneralGroup 7 }

usdOspfIntraDistance OBJECT-TYPE
    SYNTAX       Integer32 (1..255)
    MAX-ACCESS   read-write
    STATUS       current
    DESCRIPTION
        "Default distance for intra-area routes."
    ::= { usdOspfGeneralGroup 8 }

usdOspfInterDistance OBJECT-TYPE
    SYNTAX       Integer32 (1..255)
    MAX-ACCESS   read-write
    STATUS       current
    DESCRIPTION
        "Default distance for inter-area routes."
    ::= { usdOspfGeneralGroup 9 }

usdOspfExtDistance OBJECT-TYPE
    SYNTAX       Integer32 (1..255)
    MAX-ACCESS   read-write
    STATUS       current
    DESCRIPTION
        "Default distance for external type 5 and type 7 routes."
    ::= { usdOspfGeneralGroup 10 }

usdOspfHelloPktsRcv OBJECT-TYPE
    SYNTAX       Counter32
    MAX-ACCESS   read-only
    STATUS       current
    DESCRIPTION
        "Number of hello packets received."
    ::= { usdOspfGeneralGroup 11 }

usdOspfDDPktsRcv OBJECT-TYPE
    SYNTAX       Counter32
    MAX-ACCESS   read-only
    STATUS       current
    DESCRIPTION
        "Number of database description packets received."
    ::= { usdOspfGeneralGroup 12 }

usdOspfLsrPktsRcv OBJECT-TYPE
    SYNTAX       Counter32
    MAX-ACCESS   read-only
    STATUS       current
    DESCRIPTION
        "Number of link state request packets received."
    ::= { usdOspfGeneralGroup 13 }

usdOspfLsuPktsRcv OBJECT-TYPE
    SYNTAX       Counter32
    MAX-ACCESS   read-only
    STATUS       current
    DESCRIPTION
        "Number of link state update packets received."
    ::= { usdOspfGeneralGroup 14 }

usdOspfLsAckPktsRcv OBJECT-TYPE
    SYNTAX       Counter32
    MAX-ACCESS   read-only
    STATUS       current
    DESCRIPTION
        "Number of link state ACK packets received."
    ::= { usdOspfGeneralGroup 15 }

usdOspfTotalRcv OBJECT-TYPE
    SYNTAX       Counter32
    MAX-ACCESS   read-only
    STATUS       current
    DESCRIPTION
        "Number of OSPF packets received."
    ::= { usdOspfGeneralGroup 16 }

usdOspfLsaDiscardCnt OBJECT-TYPE
    SYNTAX       Counter32
    MAX-ACCESS   read-only
    STATUS       current
    DESCRIPTION
        "Number of LSA packets discarded."
    ::= { usdOspfGeneralGroup 17 }

usdOspfHelloPktsSent OBJECT-TYPE
    SYNTAX       Counter32
    MAX-ACCESS   read-only
    STATUS       current
    DESCRIPTION
        "Number of hello packets sent."
    ::= { usdOspfGeneralGroup 18 }

usdOspfDDPktsSent OBJECT-TYPE
    SYNTAX       Counter32
    MAX-ACCESS   read-only
    STATUS       current
    DESCRIPTION
        "Number of database description packets sent."
    ::= { usdOspfGeneralGroup 19 }

usdOspfLsrPktsSent OBJECT-TYPE
    SYNTAX       Counter32
    MAX-ACCESS   read-only
    STATUS       current
    DESCRIPTION
        "Number of link state request packets sent."
    ::= { usdOspfGeneralGroup 20 }

usdOspfLsuPktsSent OBJECT-TYPE
    SYNTAX       Counter32
    MAX-ACCESS   read-only
    STATUS       current
    DESCRIPTION
        "Number of link state update packets sent."
    ::= { usdOspfGeneralGroup 21 }

usdOspfLsAckPktsSent OBJECT-TYPE
    SYNTAX       Counter32
    MAX-ACCESS   read-only
    STATUS       current
    DESCRIPTION
        "Number of link state ACK packets sent."
    ::= { usdOspfGeneralGroup 22 }

usdOspfErrPktsSent OBJECT-TYPE
    SYNTAX       Counter32
    MAX-ACCESS   read-only
    STATUS       current
    DESCRIPTION
        "Number of packets dropped."
    ::= { usdOspfGeneralGroup 23 }

usdOspfTotalSent OBJECT-TYPE
    SYNTAX       Counter32
    MAX-ACCESS   read-only
    STATUS       current
    DESCRIPTION
        "Number of OSPF packets sent."
    ::= { usdOspfGeneralGroup 24 }

usdOspfCsumErrPkts OBJECT-TYPE
    SYNTAX       Counter32
    MAX-ACCESS   read-only
    STATUS       current
    DESCRIPTION
        "Number of packets received with a checksum error."
    ::= { usdOspfGeneralGroup 25 }

usdOspfAllocFailNbr OBJECT-TYPE
    SYNTAX       Counter32
    MAX-ACCESS   read-only
    STATUS       current
    DESCRIPTION
        "Number of neighbor allocation failures."
    ::= { usdOspfGeneralGroup 26 }

usdOspfAllocFailLsa OBJECT-TYPE
    SYNTAX       Counter32
    MAX-ACCESS   read-only
    STATUS       current
    DESCRIPTION
        "Number of LSA allocation failures."
    ::= { usdOspfGeneralGroup 27 }

usdOspfAllocFailLsd OBJECT-TYPE
    SYNTAX       Counter32
    MAX-ACCESS   read-only
    STATUS       current
    DESCRIPTION
        "Number of LSA HDR allocation failures."
    ::= { usdOspfGeneralGroup 28 }

usdOspfAllocFailDbRequest OBJECT-TYPE
    SYNTAX       Counter32
    MAX-ACCESS   read-only
    STATUS       current
    DESCRIPTION
        "Number of database request allocation failures."
    ::= { usdOspfGeneralGroup 29 }

usdOspfAllocFailRtx OBJECT-TYPE
    SYNTAX       Counter32
    MAX-ACCESS   read-only
    STATUS       current
    DESCRIPTION
        "Number of RTX allocation failures."
    ::= { usdOspfGeneralGroup 30 }

usdOspfAllocFailAck OBJECT-TYPE
    SYNTAX       Counter32
    MAX-ACCESS   read-only
    STATUS       current
    DESCRIPTION
        "Number of LS ACK allocation failures."
    ::= { usdOspfGeneralGroup 31 }

usdOspfAllocFailDbPkt OBJECT-TYPE
    SYNTAX       Counter32
    MAX-ACCESS   read-only
    STATUS       current
    DESCRIPTION
        "Number of DD packet allocation failures."
    ::= { usdOspfGeneralGroup 32 }

usdOspfAllocFailCirc OBJECT-TYPE
    SYNTAX       Counter32
    MAX-ACCESS   read-only
    STATUS       current
    DESCRIPTION
        "Number of OSPF interface allocation failures."
    ::= { usdOspfGeneralGroup 33 }

usdOspfAllocFailPkt OBJECT-TYPE
    SYNTAX       Counter32
    MAX-ACCESS   read-only
    STATUS       current
    DESCRIPTION
        "Number of OSPF general packet allocation failures."
    ::= { usdOspfGeneralGroup 34 }

usdOspfOperState OBJECT-TYPE
    SYNTAX       TruthValue
    MAX-ACCESS   read-only
    STATUS       current
    DESCRIPTION
        "A flag to note whether this router is operational."
    ::= { usdOspfGeneralGroup 35 }

usdOspfVpnRouteTag OBJECT-TYPE
    SYNTAX       Unsigned32 (0..4294967295)
    MAX-ACCESS   read-write
    STATUS       current
    DESCRIPTION
        "VPN route tag value."
    ::= { usdOspfGeneralGroup 36 }

usdOspfDomainId OBJECT-TYPE
    SYNTAX       Unsigned32 (0..4294967295)
    MAX-ACCESS   read-write
    STATUS       current
    DESCRIPTION
        "OSPF domain ID."
    ::= { usdOspfGeneralGroup 37 }

usdOspfMplsTeRtrIdIfIndex OBJECT-TYPE
    SYNTAX       InterfaceIndex
    MAX-ACCESS   read-write
    STATUS       current
    DESCRIPTION
        "Configure the stable router interface id to designate it as TE
        capable."
    ::= { usdOspfGeneralGroup 38 }


-- +++++++++++++++++++++++++++++++++++++++++++++++++++++++++++++++++++++++++++++
-- OSPF Area attributes
-- +++++++++++++++++++++++++++++++++++++++++++++++++++++++++++++++++++++++++++++
--
--  OSPF Area Table
--
usdOspfAreaTable OBJECT-TYPE
    SYNTAX      SEQUENCE OF UsdOspfAreaEntry
    MAX-ACCESS  not-accessible
    STATUS      current
    DESCRIPTION
        "The Unisphere OSPF area table describes the OSPF-specific
        characteristics of areas."
    ::= { usdOspfObjects 2 }

usdOspfAreaEntry OBJECT-TYPE
    SYNTAX      UsdOspfAreaEntry
    MAX-ACCESS  not-accessible
    STATUS      current
    DESCRIPTION
        "The OSPF area entry describes OSPF-specific characteristics of one
        area."
    AUGMENTS  { ospfAreaEntry }
    ::= { usdOspfAreaTable 1 }

UsdOspfAreaEntry ::= SEQUENCE {
    usdOspfAreaType         INTEGER,
    usdOspfAreaTeCapable    TruthValue }

usdOspfAreaType OBJECT-TYPE
    SYNTAX      INTEGER {
                    transitArea(1),
                    stubArea(2),
                    nssaArea(3) }
    MAX-ACCESS  read-only
    STATUS      current
    DESCRIPTION
        "The type of this area."
    ::= { usdOspfAreaEntry 1 }

usdOspfAreaTeCapable OBJECT-TYPE
    SYNTAX       TruthValue
    MAX-ACCESS   read-write
    STATUS       current
    DESCRIPTION
        "Configure the specified area TE capable to flood the TE information."
    ::= { usdOspfAreaEntry 2 }


-- +++++++++++++++++++++++++++++++++++++++++++++++++++++++++++++++++++++++++++++
-- OSPF Interface attributes
-- +++++++++++++++++++++++++++++++++++++++++++++++++++++++++++++++++++++++++++++
--
--  OSPF Interface Table
--
usdOspfIfTable OBJECT-TYPE
    SYNTAX      SEQUENCE OF UsdOspfIfEntry
    MAX-ACCESS  not-accessible
    STATUS      current
    DESCRIPTION
        "The Unisphere OSPF interface table describes the OSPF-specific
        characteristics of interfaces."
    ::= { usdOspfObjects 7 }

usdOspfIfEntry OBJECT-TYPE
    SYNTAX      UsdOspfIfEntry
    MAX-ACCESS  not-accessible
    STATUS      current
    DESCRIPTION
        "The OSPF interface entry describes OSPF-specific characteristics of one
        interface."
    AUGMENTS  { ospfIfEntry }
    ::= { usdOspfIfTable 1 }

UsdOspfIfEntry ::= SEQUENCE {
    usdOspfIfCost           Integer32,
    usdOspfIfMask           IpAddress,
    usdOspfIfPassiveFlag    INTEGER,
    usdOspfIfNbrCount       Counter32,
    usdOspfIfAdjNbrCount    Counter32,
    usdOspfIfMd5AuthKey     OCTET STRING,
    usdOspfIfMd5AuthKeyId   Integer32 }

usdOspfIfCost OBJECT-TYPE
    SYNTAX      Integer32 (1..65535)
    MAX-ACCESS  read-create
    STATUS      current
    DESCRIPTION
        "The cost value for this interface."
    DEFVAL    { 10 }
    ::= { usdOspfIfEntry 1 }

usdOspfIfMask OBJECT-TYPE
    SYNTAX      IpAddress
    MAX-ACCESS  read-create
    STATUS      current
    DESCRIPTION
        "The mask used to derive the network range of this interface."
    ::= { usdOspfIfEntry 2 }

usdOspfIfPassiveFlag OBJECT-TYPE
    SYNTAX      INTEGER {
                    disabled(0),
                    enabled(1) }
    MAX-ACCESS  read-create
    STATUS      current
    DESCRIPTION
        "Flag to indicate whether routing updates should be suppressed on this
        interface.  To actively perform routing updates, set this object to
        disabled(0)."
    ::= { usdOspfIfEntry 3 }

usdOspfIfNbrCount OBJECT-TYPE
    SYNTAX      Counter32
    MAX-ACCESS  read-only
    STATUS      current
    DESCRIPTION
        "Number of OSPF neighbors from this interface."
    ::= { usdOspfIfEntry 4 }

usdOspfIfAdjNbrCount OBJECT-TYPE
    SYNTAX      Counter32
    MAX-ACCESS  read-only
    STATUS      current
    DESCRIPTION
        "Number of OSPF adjacent neighbors from this interface."
    ::= { usdOspfIfEntry 5 }

usdOspfIfMd5AuthKey OBJECT-TYPE
    SYNTAX      OCTET STRING (SIZE(0..16))
    MAX-ACCESS  read-create
    STATUS      current
    DESCRIPTION
        "The MD5 authentication key.  When setting this object, the
        usdOspfIfMd5AuthKeyId must be specified on the same PDU.  For simple
        text authentication type, use ospfIfAuthKey.  Setting this object will
        have the side effect of adding or updating the correspondent entry in
        usdOspfMd5IntfKeyTable.  If key given has less than 16 octets, such value
        will be appended with zeros to complete 16 octets.  The zeros will
        appended to the right of the given key.  Reading this object always
        results in an OCTET STRING of length zero."
    ::= { usdOspfIfEntry 6 }

usdOspfIfMd5AuthKeyId OBJECT-TYPE
    SYNTAX      Integer32 (1..2147483647)
    MAX-ACCESS  read-create
    STATUS      current
    DESCRIPTION
        "The MD5 authentication key ID.  When setting this object,
        usdOspfIfMd5AuthKey must be specified on the same PDU."
    ::= { usdOspfIfEntry 7 }


-- +++++++++++++++++++++++++++++++++++++++++++++++++++++++++++++++++++++++++++++
-- OSPF Virtual Interface attributes
-- +++++++++++++++++++++++++++++++++++++++++++++++++++++++++++++++++++++++++++++
--
--  OSPF Virtual Interface Table
--
usdOspfVirtIfTable OBJECT-TYPE
    SYNTAX      SEQUENCE OF UsdOspfVirtIfEntry
    MAX-ACCESS  not-accessible
    STATUS      current
    DESCRIPTION
        "The Unisphere OSPF virtual interface table describes the OSPF-specific
        characteristics of virtual interfaces."
    ::= { usdOspfObjects 9 }

usdOspfVirtIfEntry OBJECT-TYPE
    SYNTAX      UsdOspfVirtIfEntry
    MAX-ACCESS  not-accessible
    STATUS      current
    DESCRIPTION
        "The OSPF virtual interface entry describes OSPF-specific
        characteristics of one virtual interface."
    AUGMENTS  { ospfVirtIfEntry }
    ::= { usdOspfVirtIfTable 1 }

UsdOspfVirtIfEntry ::= SEQUENCE {
    usdOspfVirtIfMd5AuthKey     OCTET STRING,
    usdOspfVirtIfMd5AuthKeyId   Integer32 }

usdOspfVirtIfMd5AuthKey OBJECT-TYPE
    SYNTAX      OCTET STRING (SIZE(0..16))
    MAX-ACCESS  read-create
    STATUS      current
    DESCRIPTION
        "The MD5 authentication key.  When setting this object, the
        usdOspfVirtIfMd5AuthKeyId must be specified on the same PDU.  For simple
        text authentication type, use ospfVirtIfAuthKey.  Setting this object
        will have the side effect of adding or updating the correspondent entry
        in usdOspfMd5IntfKeyTable.  If key given has less than 16 octets, such
        value will be appended with zeros to complete 16 octets.  The zeros will
        appended to the right of the given key.  Reading this object always
        results in an OCTET STRING of length zero."
    ::= { usdOspfVirtIfEntry 1 }

usdOspfVirtIfMd5AuthKeyId OBJECT-TYPE
    SYNTAX      Integer32 (1..2147483647)
    MAX-ACCESS  read-create
    STATUS      current
    DESCRIPTION
        "The MD5 authentication key id. When setting this object,
        usdOspfVirtIfMd5AuthKey must be specified on the same psu."
    ::= { usdOspfVirtIfEntry 2 }


-- +++++++++++++++++++++++++++++++++++++++++++++++++++++++++++++++++++++++++++++
-- OSPF Neighbor attributes
-- +++++++++++++++++++++++++++++++++++++++++++++++++++++++++++++++++++++++++++++
--
--  OSPF Neighbor Table
--
usdOspfNbrTable OBJECT-TYPE
    SYNTAX      SEQUENCE OF UsdOspfNbrEntry
    MAX-ACCESS  not-accessible
    STATUS      current
    DESCRIPTION
        "The Unisphere OSPF neighbor table describes the OSPF-specific
        characteristics of neighbors."
    ::= { usdOspfObjects 10 }

usdOspfNbrEntry OBJECT-TYPE
    SYNTAX      UsdOspfNbrEntry
    MAX-ACCESS  not-accessible
    STATUS      current
    DESCRIPTION
        "The OSPF neighbor entry describes OSPF-specific characteristics of one
        neighbor."
    AUGMENTS  { ospfNbrEntry }
    ::= { usdOspfNbrTable 1 }

UsdOspfNbrEntry ::= SEQUENCE {
    usdOspfNbrLocalIpAddr   IpAddress,
    usdOspfNbrDR            IpAddress,
    usdOspfNbrBDR           IpAddress }

usdOspfNbrLocalIpAddr OBJECT-TYPE
    SYNTAX      IpAddress
    MAX-ACCESS  read-only
    STATUS      current
    DESCRIPTION
        "The local IP address on this OSPF circuit."
    ::= { usdOspfNbrEntry 1 }

usdOspfNbrDR OBJECT-TYPE
    SYNTAX      IpAddress
    MAX-ACCESS  read-only
    STATUS      current
    DESCRIPTION
        "The neighbor's idea of designated router."
    ::= { usdOspfNbrEntry 2 }

usdOspfNbrBDR OBJECT-TYPE
    SYNTAX      IpAddress
    MAX-ACCESS  read-only
    STATUS      current
    DESCRIPTION
        "The neighbor's idea of backup designated router."
    ::= { usdOspfNbrEntry 3 }


-- +++++++++++++++++++++++++++++++++++++++++++++++++++++++++++++++++++++++++++++
-- OSPF Summary Import attributes
-- +++++++++++++++++++++++++++++++++++++++++++++++++++++++++++++++++++++++++++++
--
--  OSPF Summary Import Table
--
usdOspfSummImportTable OBJECT-TYPE
    SYNTAX      SEQUENCE OF UsdOspfSummImportEntry
    MAX-ACCESS  not-accessible
    STATUS      current
    DESCRIPTION
        "The Unisphere OSPF summary import table describes the OSPF-specific
        characteristics of network aggregation into the OSPF autonomous system.
        With this table, the load of advertising many external routes can be
        reduced by specifying a range which includes some or all of the external
        routes."
    ::= { usdOspfObjects 15 }

usdOspfSummImportEntry OBJECT-TYPE
    SYNTAX      UsdOspfSummImportEntry
    MAX-ACCESS  not-accessible
    STATUS      current
    DESCRIPTION
        "The OSPF summary import entry describes OSPF-specific characteristics
        of one summary report."
    INDEX     { usdOspfSummAggNet,
                usdOspfSummAggMask }
    ::= { usdOspfSummImportTable 1 }

UsdOspfSummImportEntry ::= SEQUENCE {
    usdOspfSummAggNet       IpAddress,
    usdOspfSummAggMask      IpAddress,
    usdOspfSummAdminStat    INTEGER,
    usdOspfSummRowStatus    RowStatus }

usdOspfSummAggNet OBJECT-TYPE
    SYNTAX      IpAddress
    MAX-ACCESS  read-only
    STATUS      current
    DESCRIPTION
        "The summary address for a range of addresses."
    ::= { usdOspfSummImportEntry 1 }

usdOspfSummAggMask OBJECT-TYPE
    SYNTAX      IpAddress
    MAX-ACCESS  read-only
    STATUS      current
    DESCRIPTION
        "The subnet mask used for the summary route."
    ::= { usdOspfSummImportEntry 2 }

usdOspfSummAdminStat OBJECT-TYPE
    SYNTAX      INTEGER {
                    disabled(0),
                    enabled(1) }
    MAX-ACCESS  read-create
    STATUS      current
    DESCRIPTION
        "The admin status of this summary aggregation."
    ::= { usdOspfSummImportEntry 3 }

usdOspfSummRowStatus OBJECT-TYPE
    SYNTAX      RowStatus
    MAX-ACCESS  read-create
    STATUS      current
    DESCRIPTION
        "This variable displays the status of the entry."
    ::= { usdOspfSummImportEntry 4 }


-- +++++++++++++++++++++++++++++++++++++++++++++++++++++++++++++++++++++++++++++
-- OSPF Interface MD5 Key attributes
-- +++++++++++++++++++++++++++++++++++++++++++++++++++++++++++++++++++++++++++++
--
--  OSPF Interface MD5 Key Table
--
usdOspfMd5IntfTable OBJECT-TYPE
    SYNTAX      SEQUENCE OF UsdOspfMd5IntfEntry
    MAX-ACCESS  not-accessible
    STATUS      current
    DESCRIPTION
        "The Unisphere OSPF interface MD5 key table describes OSPF-specific
        characteristics of the MD5 authentication key for the OSPF interfaces.
        This table is not to be used for the simple password authentication."
    ::= { usdOspfObjects 16 }

usdOspfMd5IntfEntry OBJECT-TYPE
    SYNTAX      UsdOspfMd5IntfEntry
    MAX-ACCESS  not-accessible
    STATUS      current
    DESCRIPTION
        "The OSPF interface MD5 key entry describes OSPF-specific
        characteristics of one MD5 authentication's interface."
    INDEX     { ospfIfIpAddress,
                ospfAddressLessIf,
                usdOspfMd5IntfKeyId }
    ::= { usdOspfMd5IntfTable 1 }

UsdOspfMd5IntfEntry ::= SEQUENCE {
    usdOspfMd5IntfKeyId     Integer32,
    usdOspfMd5IntfKeyActive TruthValue,
    usdOspfMd5IntfAuthKey   OCTET STRING,
    usdOspfMd5IntfRowStatus RowStatus }

usdOspfMd5IntfKeyId OBJECT-TYPE
    SYNTAX      Integer32 (1..2147483647)
    MAX-ACCESS  read-only
    STATUS      current
    DESCRIPTION
        "The OSPF interface this key belongs to."
    ::= { usdOspfMd5IntfEntry 1 }

usdOspfMd5IntfKeyActive OBJECT-TYPE
    SYNTAX      TruthValue
    MAX-ACCESS  read-create
    STATUS      current
    DESCRIPTION
        "Set this object to true(1) in order to have this key active."
    ::= { usdOspfMd5IntfEntry 2 }

usdOspfMd5IntfAuthKey OBJECT-TYPE
    SYNTAX      OCTET STRING (SIZE(0..16))
    MAX-ACCESS  read-create
    STATUS      current
    DESCRIPTION
        "The MD5 authentication key.  If key given has less than 16 octets, such
        value will be appended with zeros to complete 16 octets.  The zeros will
        appended to the right of the given key.  Reading this object always
        results in an OCTET STRING of length zero."
    ::= { usdOspfMd5IntfEntry 3 }

usdOspfMd5IntfRowStatus OBJECT-TYPE
    SYNTAX      RowStatus
    MAX-ACCESS  read-create
    STATUS      current
    DESCRIPTION
        "This variable displays the status of the entry."
    ::= { usdOspfMd5IntfEntry 4 }


-- +++++++++++++++++++++++++++++++++++++++++++++++++++++++++++++++++++++++++++++
-- OSPF Vitural Interface MD5 Key attributes
-- +++++++++++++++++++++++++++++++++++++++++++++++++++++++++++++++++++++++++++++
--
--  OSPF Virual Interface MD5 Key Table
--
usdOspfMd5VirtIntfTable OBJECT-TYPE
    SYNTAX      SEQUENCE OF UsdOspfMd5VirtIntfEntry
    MAX-ACCESS  not-accessible
    STATUS      current
    DESCRIPTION
        "The Unisphere OSPF interface MD5 key table describes OSPF-specific
        characteristics of the MD5 authentication key for the OSPF interfaces.
        This table is not to be used for the simple password authentication."
    ::= { usdOspfObjects 17 }

usdOspfMd5VirtIntfEntry OBJECT-TYPE
    SYNTAX      UsdOspfMd5VirtIntfEntry
    MAX-ACCESS  not-accessible
    STATUS      current
    DESCRIPTION
        "The OSPF Interface MD5  Key entry describes OSPF-specific
        characteristics of one MD5 authentication's interface."
    INDEX     { usdOspfMd5VirtIntfAreaId,
                usdOspfMd5VirtIntfNeighbor,
                usdOspfMd5VirtIntfKeyId }
    ::= { usdOspfMd5VirtIntfTable 1 }

UsdOspfMd5VirtIntfEntry ::= SEQUENCE {
    usdOspfMd5VirtIntfAreaId    IpAddress,
    usdOspfMd5VirtIntfNeighbor  IpAddress,
    usdOspfMd5VirtIntfKeyId     Integer32,
    usdOspfMd5VirtIntfKeyActive TruthValue,
    usdOspfMd5VirtIntfAuthKey   OCTET STRING,
    usdOspfMd5VirtIntfRowStatus RowStatus }

usdOspfMd5VirtIntfAreaId OBJECT-TYPE
    SYNTAX      IpAddress
    MAX-ACCESS  read-only
    STATUS      current
    DESCRIPTION
        "The OSPF area ID this key belongs to."
    ::= { usdOspfMd5VirtIntfEntry 1 }

usdOspfMd5VirtIntfNeighbor OBJECT-TYPE
    SYNTAX      IpAddress
    MAX-ACCESS  read-only
    STATUS      current
    DESCRIPTION
        "The OSPF neightbor this key belongs to."
    ::= { usdOspfMd5VirtIntfEntry 2 }

usdOspfMd5VirtIntfKeyId OBJECT-TYPE
    SYNTAX      Integer32 (1..2147483647)
    MAX-ACCESS  read-only
    STATUS      current
    DESCRIPTION
        "The OSPF virtual interface this key belongs to."
    ::= { usdOspfMd5VirtIntfEntry 3 }

usdOspfMd5VirtIntfKeyActive OBJECT-TYPE
    SYNTAX      TruthValue
    MAX-ACCESS  read-create
    STATUS      current
    DESCRIPTION
        "Set this object to true(1) in order to have this key active."
    ::= { usdOspfMd5VirtIntfEntry 4 }

usdOspfMd5VirtIntfAuthKey OBJECT-TYPE
    SYNTAX      OCTET STRING (SIZE(0..16))
    MAX-ACCESS  read-create
    STATUS      current
    DESCRIPTION
        "The MD5 authentication key.  If key given has less than 16 octets, such
        value will be appended with zeros to complete 16 octets.  The zeros will
        appended to the right of the given key.  Reading this object always
        results in an OCTET STRING of length zero."
    ::= { usdOspfMd5VirtIntfEntry 5 }

usdOspfMd5VirtIntfRowStatus OBJECT-TYPE
    SYNTAX      RowStatus
    MAX-ACCESS  read-create
    STATUS      current
    DESCRIPTION
        "This variable displays the status of the entry."
    ::= { usdOspfMd5VirtIntfEntry 6 }


-- +++++++++++++++++++++++++++++++++++++++++++++++++++++++++++++++++++++++++++++
-- OSPF Network Range attributes
-- +++++++++++++++++++++++++++++++++++++++++++++++++++++++++++++++++++++++++++++
--
--  OSPF Network Range Table
--
usdOspfNetworkRangeTable OBJECT-TYPE
    SYNTAX      SEQUENCE OF UsdOspfNetworkRangeEntry
    MAX-ACCESS  not-accessible
    STATUS      current
    DESCRIPTION
        "The Unisphere OSPF network range table describes the OSPF-specific
        characteristics of network ranges, encompassing one or multiple OSPF
        interfaces."
    ::= { usdOspfObjects 18 }

usdOspfNetworkRangeEntry OBJECT-TYPE
    SYNTAX      UsdOspfNetworkRangeEntry
    MAX-ACCESS  not-accessible
    STATUS      current
    DESCRIPTION
        "The Unisphere OSPF network range entry describes OSPF-specific
        characteristics of one OSPF network range."
    INDEX     { usdOspfNetRangeNet,
                usdOspfNetRangeMask,
                usdOspfNetRangeAreaId }
    ::= { usdOspfNetworkRangeTable 1 }

UsdOspfNetworkRangeEntry ::= SEQUENCE {
    usdOspfNetRangeNet          IpAddress,
    usdOspfNetRangeMask         IpAddress,
    usdOspfNetRangeAreaId       IpAddress,
    usdOspfNetRangeRowStatus    RowStatus }

usdOspfNetRangeNet OBJECT-TYPE
    SYNTAX   IpAddress
    MAX-ACCESS   read-only
    STATUS   current
    DESCRIPTION
        "The network range address."
    ::= {usdOspfNetworkRangeEntry  1 }

usdOspfNetRangeMask OBJECT-TYPE
    SYNTAX      IpAddress
    MAX-ACCESS  read-only
    STATUS      current
    DESCRIPTION
        "The subnet mask used for the network range.  Unlike the mask used under
        the command line interface (CLI), this object is set in the non-inversed
        format (i.e. not a wild-card mask)."
    ::= {usdOspfNetworkRangeEntry  2 }

usdOspfNetRangeAreaId OBJECT-TYPE
    SYNTAX      IpAddress
    MAX-ACCESS  read-only
    STATUS      current
    DESCRIPTION
        "The OSPF area ID this network range belongs to."
    ::= { usdOspfNetworkRangeEntry 3 }

usdOspfNetRangeRowStatus OBJECT-TYPE
    SYNTAX      RowStatus
    MAX-ACCESS  read-create
    STATUS      current
    DESCRIPTION
        "This variable displays the status of the entry."
    ::= { usdOspfNetworkRangeEntry 4 }


-- +++++++++++++++++++++++++++++++++++++++++++++++++++++++++++++++++++++++++++++
-- Notifications control 
-- +++++++++++++++++++++++++++++++++++++++++++++++++++++++++++++++++++++++++++++
-- No notifications are defined in this MIB.  Placeholder follows.
-- usdOspfTrapEnables OBJECT IDENTIFIER ::= { usdOspfMIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- usdOspfTraps       OBJECT IDENTIFIER ::= { usdOspfMIB 19 }
-- usdOspfTrapPrefix  OBJECT IDENTIFIER ::= { usdOspfTraps 0 }


-- +++++++++++++++++++++++++++++++++++++++++++++++++++++++++++++++++++++++++++++
-- Conformance information
-- +++++++++++++++++++++++++++++++++++++++++++++++++++++++++++++++++++++++++++++
usdOspfConformance     OBJECT IDENTIFIER ::= { usdOspfMIB 4 }
usdOspfCompliances     OBJECT IDENTIFIER ::= { usdOspfConformance 1 }
usdOspfGroups          OBJECT IDENTIFIER ::= { usdOspfConformance 2 }

--
-- compliance statements
--
usdOspfCompliance MODULE-COMPLIANCE
    STATUS      obsolete
    DESCRIPTION
        "Obsolete compliance statement for entities which implement the
        Unisphere OSPF MIB.  This statement became obsolete when
        usdOspfVpnRouteTag, usdOspfDomainId, usdOspfAreaTeCapable and
        usdOspfMplsTeRtrIdIfIndex were added to the basic group."
    MODULE   -- this module
        MANDATORY-GROUPS {
            usdOspfBasicGroup,
            usdOspfAreaGroup,
            usdOspfIfGroup,
            usdOspfVirtIfGroup,
            usdOspfNbrGroup,
            usdOspfSummImportGroup,
            usdOspfMd5IntfGroup,
            usdOspfMd5VirtIntfGroup,
            usdOspfNetRangeGroup }
    ::= { usdOspfCompliances 1 }                                       -- RX 2.0

usdOspfCompliance2 MODULE-COMPLIANCE
    STATUS      current
    DESCRIPTION
        "The compliance statement for entities which implement the Unisphere
        OSPF MIB."
    MODULE   -- this module
        MANDATORY-GROUPS {
            usdOspfBasicGroup2,
            usdOspfAreaGroup,
            usdOspfIfGroup,
            usdOspfVirtIfGroup,
            usdOspfNbrGroup,
            usdOspfSummImportGroup,
            usdOspfMd5IntfGroup,
            usdOspfMd5VirtIntfGroup,
            usdOspfNetRangeGroup }
    ::= { usdOspfCompliances 2 }                                       -- RX 4.0

--
-- units of conformance
--
usdOspfBasicGroup OBJECT-GROUP
    OBJECTS {
        usdOspfProcessId,
        usdOspfMaxPathSplits,
        usdOspfSpfHoldInterval,
        usdOspfNumActiveAreas,
        usdOspfSpfTime,
        usdOspfRefBw,
        usdOspfAutoVlink,
        usdOspfIntraDistance,
        usdOspfInterDistance,
        usdOspfExtDistance,
        usdOspfHelloPktsRcv,
        usdOspfDDPktsRcv,
        usdOspfLsrPktsRcv,
        usdOspfLsuPktsRcv,
        usdOspfLsAckPktsRcv,
        usdOspfTotalRcv,
        usdOspfLsaDiscardCnt,
        usdOspfHelloPktsSent,
        usdOspfDDPktsSent,
        usdOspfLsrPktsSent,
        usdOspfLsuPktsSent,
        usdOspfLsAckPktsSent,
        usdOspfErrPktsSent,
        usdOspfTotalSent,
        usdOspfCsumErrPkts,
        usdOspfAllocFailNbr,
        usdOspfAllocFailLsa,
        usdOspfAllocFailLsd,
        usdOspfAllocFailDbRequest,
        usdOspfAllocFailRtx,
        usdOspfAllocFailAck,
        usdOspfAllocFailDbPkt,
        usdOspfAllocFailCirc,
        usdOspfAllocFailPkt,
        usdOspfOperState }
    STATUS      obsolete
    DESCRIPTION
        "Obsolete collection of objects for managing general OSPF capabilities
        in a Unisphere product.  This group became obsolete when
        usdOspfVpnRouteTag, usdOspfDomainId, usdOspfAreaTeCapable and
        usdOspfMplsTeRtrIdIfIndex were added."
    ::= { usdOspfGroups 1 }

usdOspfIfGroup OBJECT-GROUP
    OBJECTS {
        usdOspfIfCost,
        usdOspfIfMask,
        usdOspfIfPassiveFlag,
        usdOspfIfNbrCount,
        usdOspfIfAdjNbrCount,
        usdOspfIfMd5AuthKey,
        usdOspfIfMd5AuthKeyId }
    STATUS      current
    DESCRIPTION
        "A collection of objects which augments the standard MIB objects for
        managing OSPF Interface capabilities in a Unisphere product."
    ::= { usdOspfGroups 2 }

usdOspfAreaGroup OBJECT-GROUP
    OBJECTS {
        usdOspfAreaType,
        usdOspfAreaTeCapable }
    STATUS      current
    DESCRIPTION
        "An object which augments the standard MIB objects for managing OSPF
        areas capabilities in a Unisphere product."
    ::= { usdOspfGroups 3 }

usdOspfVirtIfGroup OBJECT-GROUP
    OBJECTS {
        usdOspfVirtIfMd5AuthKey,
        usdOspfVirtIfMd5AuthKeyId }
    STATUS      current
    DESCRIPTION
        "A collection of objects which augments the standard MIB objects for
        managing OSPF virtual interface capabilities in a Unisphere product."
    ::= { usdOspfGroups 4 }

usdOspfNbrGroup OBJECT-GROUP
    OBJECTS {
        usdOspfNbrLocalIpAddr,
        usdOspfNbrDR,
        usdOspfNbrBDR }
    STATUS      current
    DESCRIPTION
        "A collection of objects which augments the standard MIB objects for
        managing OSPF neighbor capabilities in a Unisphere product."
    ::= { usdOspfGroups 5 }

usdOspfSummImportGroup OBJECT-GROUP
    OBJECTS {
        usdOspfSummAggNet,
        usdOspfSummAggMask,
        usdOspfSummAdminStat,
        usdOspfSummRowStatus }
    STATUS      current
    DESCRIPTION
        "A collection of objects for managing OSPF summary report capabilities
        in a Unisphere product."
    ::= { usdOspfGroups 6 }

usdOspfMd5IntfGroup OBJECT-GROUP
    OBJECTS {
        usdOspfMd5IntfKeyId,
        usdOspfMd5IntfKeyActive,
        usdOspfMd5IntfAuthKey,
        usdOspfMd5IntfRowStatus }
    STATUS      current
    DESCRIPTION
        "A collection of objects for managing OSPF MD5 interfaces capabilities
        in a Unisphere product."
    ::= { usdOspfGroups 7 }

usdOspfMd5VirtIntfGroup OBJECT-GROUP
    OBJECTS {
        usdOspfMd5VirtIntfAreaId,
        usdOspfMd5VirtIntfNeighbor,
        usdOspfMd5VirtIntfKeyId,
        usdOspfMd5VirtIntfKeyActive,
        usdOspfMd5VirtIntfAuthKey,
        usdOspfMd5VirtIntfRowStatus }
    STATUS      current
    DESCRIPTION
        "A collection of objects for managing OSPF MD5 virtual interfaces
        capabilities in a Unisphere product."
    ::= { usdOspfGroups 8 }

usdOspfNetRangeGroup OBJECT-GROUP
    OBJECTS {
        usdOspfNetRangeNet,
        usdOspfNetRangeMask,
        usdOspfNetRangeAreaId,
        usdOspfNetRangeRowStatus }
    STATUS      current
    DESCRIPTION
        "A collection of objects for managing OSPF network range capabilities in
        a Unisphere product."
    ::= { usdOspfGroups 9 }

usdOspfBasicGroup2 OBJECT-GROUP
    OBJECTS {
        usdOspfProcessId,
        usdOspfMaxPathSplits,
        usdOspfSpfHoldInterval,
        usdOspfNumActiveAreas,
        usdOspfSpfTime,
        usdOspfRefBw,
        usdOspfAutoVlink,
        usdOspfIntraDistance,
        usdOspfInterDistance,
        usdOspfExtDistance,
        usdOspfHelloPktsRcv,
        usdOspfDDPktsRcv,
        usdOspfLsrPktsRcv,
        usdOspfLsuPktsRcv,
        usdOspfLsAckPktsRcv,
        usdOspfTotalRcv,
        usdOspfLsaDiscardCnt,
        usdOspfHelloPktsSent,
        usdOspfDDPktsSent,
        usdOspfLsrPktsSent,
        usdOspfLsuPktsSent,
        usdOspfLsAckPktsSent,
        usdOspfErrPktsSent,
        usdOspfTotalSent,
        usdOspfCsumErrPkts,
        usdOspfAllocFailNbr,
        usdOspfAllocFailLsa,
        usdOspfAllocFailLsd,
        usdOspfAllocFailDbRequest,
        usdOspfAllocFailRtx,
        usdOspfAllocFailAck,
        usdOspfAllocFailDbPkt,
        usdOspfAllocFailCirc,
        usdOspfAllocFailPkt,
        usdOspfOperState,
        usdOspfVpnRouteTag,
        usdOspfDomainId,
        usdOspfMplsTeRtrIdIfIndex }
    STATUS      current
    DESCRIPTION
        "A collection of objects for managing general OSPF capabilities in a
        Unisphere product."
    ::= { usdOspfGroups 10 }

END
