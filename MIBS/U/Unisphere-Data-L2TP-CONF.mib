-- *****************************************************************************
-- Unisphere-Data-L2TP-CONF
--
-- SNMP Agent Capabilities definitions for the L2TP MIB.
--
-- Copyright (c) 2001 Unisphere Networks, Inc.  All rights reserved.
-- *****************************************************************************

Unisphere-Data-L2TP-CONF DEFINITIONS ::= BEGIN

IMPORTS
    MODULE-IDENTITY
        FROM SNMPv2-SMI
    AGENT-CAPABILITIES
        FROM SNMPv2-CONF
    usDataAgents
        FROM Unisphere-Data-Agents
    usdL2tpConfigGroup, usdL2tpStatusGroup, usdL2tpStatGroup, usdL2tpMapGroup,
    usdL2tpUdpIpGroup, usdL2tpStatusGroup2, usdL2tpStatGroup2,
    usdL2tpConfigGroup2, usdL2tpConfigGroup3
        FROM Unisphere-Data-L2TP-MIB;

usdL2tpAgent MODULE-IDENTITY
    LAST-UPDATED "200110171603Z"  -- 17-Oct-01 12:03 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the layer 2 tunneling protocol
        (L2TP) component of the SNMP agent in the Unisphere Routing Switch
        family of products."
    -- Revision History
    REVISION    "200110171603Z"  -- 17-Oct-01 12:03 PM EDT  - RX 3.3
    DESCRIPTION
        "New objects were added to the configuration group."
    REVISION    "200110171421Z"  -- 17-Oct-01 10:21 AM EDT  - RX 3.2
    DESCRIPTION
        "The initial release of this management information module."
    ::= { usDataAgents 24 }

usdL2tpAgentV1 AGENT-CAPABILITIES
    PRODUCT-RELEASE
        "Version 1 of the L2TP component of the Unisphere Routing Switch SNMP
        agent.  This version of the L2TP component was supported in the
        Unisphere RX 2.x system releases."
    STATUS      obsolete
    DESCRIPTION
        "The MIB supported by the SNMP agent for the L2TP application in the
        Unisphere Routing Switch.  These capabilities became obsolete when
        rsL2tpTunnelStatusCumEstabTime, rsL2tpSessionStatusCumEstabTime and
        rsL2tpSessionStatPayLostPackets were added, and
        rsL2tpSessionStatusLacTunneledIfIndex replaced
        rsL2tpSessionStatusLacPppIfIndex."
    SUPPORTS    Unisphere-Data-L2TP-MIB
        INCLUDES  {
            usdL2tpConfigGroup,
            usdL2tpStatusGroup,
            usdL2tpStatGroup,
            usdL2tpMapGroup,
            usdL2tpUdpIpGroup }
    ::= { usdL2tpAgent 1 }

usdL2tpAgentV2 AGENT-CAPABILITIES
    PRODUCT-RELEASE
        "Version 2 of the L2TP component of the Unisphere Routing Switch SNMP
        agent.  This version of the L2TP component was supported in the
        Unisphere RX 3.0 and 3.1 system releases."
    STATUS      obsolete
    DESCRIPTION
        "The MIB supported by the SNMP agent for the L2TP application in the
        Unisphere Routing Switch.  These capabilities became obsolete when
        usdL2tpSysConfigReceiveDataSequencingIgnore was added to the
        configuration group."
    SUPPORTS    Unisphere-Data-L2TP-MIB
        INCLUDES  {
            usdL2tpConfigGroup,
            usdL2tpStatusGroup2,
            usdL2tpStatGroup2,
            usdL2tpMapGroup,
            usdL2tpUdpIpGroup }
    ::= { usdL2tpAgent 2 }

usdL2tpAgentV3 AGENT-CAPABILITIES
    PRODUCT-RELEASE
        "Version 3 of the L2TP component of the Unisphere Routing Switch SNMP
        agent.  This version of the L2TP component was supported in the
        Unisphere RX 3.2 system release."
    STATUS      obsolete
    DESCRIPTION
        "The MIB supported by the SNMP agent for the L2TP application in the
        Unisphere Routing Switch.  These capabilities became obsolete when new
        objects were added to the configuration group."
    SUPPORTS    Unisphere-Data-L2TP-MIB
        INCLUDES  {
            usdL2tpConfigGroup2,
            usdL2tpStatusGroup2,
            usdL2tpStatGroup2,
            usdL2tpMapGroup,
            usdL2tpUdpIpGroup }
    ::= { usdL2tpAgent 3 }

usdL2tpAgentV4 AGENT-CAPABILITIES
    PRODUCT-RELEASE
        "Version 4 of the L2TP component of the Unisphere Routing Switch SNMP
        agent.  This version of the L2TP component is supported in the Unisphere
        RX 3.3 and subsequent system releases."
    STATUS      current
    DESCRIPTION
        "The MIB supported by the SNMP agent for the L2TP application in the
        Unisphere Routing Switch."
    SUPPORTS    Unisphere-Data-L2TP-MIB
        INCLUDES  {
            usdL2tpConfigGroup3,
            usdL2tpStatusGroup2,
            usdL2tpStatGroup2,
            usdL2tpMapGroup,
            usdL2tpUdpIpGroup }
    ::= { usdL2tpAgent 4 }

END
