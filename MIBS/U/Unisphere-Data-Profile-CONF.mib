-- *****************************************************************************
-- Unisphere-Data-Profile-CONF
--
-- SNMP Agent Capabilities definitions for the Profile Manager MIB.
--
-- Copyright (c) 2001 Unisphere Networks, Inc.  All rights reserved.
-- *****************************************************************************

Unisphere-Data-Profile-CONF DEFINITIONS ::= BEGIN

IMPORTS
    MODULE-IDENTITY
        FROM SNMPv2-SMI
    AGENT-CAPABILITIES
        FROM SNMPv2-CONF
    usdProfileAgents
        FROM Unisphere-Data-Agents
    usdProfileGroup,
    usdProfileIfGroup
        FROM Unisphere-Data-PROFILE-MIB;

usdProfileManagerAgent MODULE-IDENTITY
    LAST-UPDATED "200103291800Z"  -- 29-Mar-01 01:00 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Profile Manager component of
        the SNMP agent in the Unisphere Routing Switch family of products."
    -- Revision History
    REVISION    "200103291800Z"  -- 29-Mar-01 01:00 PM EST  - RX 3.2
    DESCRIPTION
        "The initial release of this management information module."
    ::= { usdProfileAgents 1 }

usdProfileManagerAgentV1 AGENT-CAPABILITIES
    PRODUCT-RELEASE
        "Version 1 of the Profile Manager component of the Unisphere Routing
        Switch SNMP agent.  This version of the Profile Manager component was
        supported in the Unisphere RX 1.1 thru 1.3 system releases."
    STATUS      obsolete
    DESCRIPTION
        "The MIBs supported by the SNMP agent for the Profile Manager
        application in the Unisphere Routing Switch.  These capabilities became
        obsolete when support was added for assignment of profiles to interface/
        encapsulation pairs."

    SUPPORTS        Unisphere-Data-PROFILE-MIB
        INCLUDES  { usdProfileGroup }

    ::= { usdProfileManagerAgent 1 }

usdProfileManagerAgentV2 AGENT-CAPABILITIES
    PRODUCT-RELEASE
        "Version 2 of the Profile Manager component of the Unisphere Routing
        Switch SNMP agent.  This version of the Profile Manager component is
        supported in the Unisphere RX 2.0 and subsequent system releases."
    STATUS      current
    DESCRIPTION
        "The MIB supported by the SNMP agent for the Profile Manager application
        in the Unisphere Routing Switch."

    SUPPORTS        Unisphere-Data-PROFILE-MIB
        INCLUDES  { usdProfileGroup,
                    usdProfileIfGroup }

    ::= { usdProfileManagerAgent 2 }

END
