-- *****************************************************************************
-- Unisphere-Data-DS1-MIB
--
-- Unisphere Networks Enterprise MIB
--   DS1/E1 MIB
--
-- Copyright (c) 1998, 1999 Redstone Communications, Incorporated.
-- Copyright (c) 1999, 2002 Unisphere Networks, Incorporated.
-- All Rights Reserved.
-- *****************************************************************************

Unisphere-Data-DS1-MIB DEFINITIONS ::= BEGIN

IMPORTS
    MODULE-IDENTITY, OBJECT-TYPE, Integer32
        FROM SNMPv2-SMI
    RowStatus, DisplayString
        FROM SNMPv2-TC
    MODULE-COMPLIANCE, OBJECT-GROUP
        FROM SNMPv2-CONF
    ifIndex, InterfaceIndexOrZero
        FROM IF-MIB
    usDataMibs
        FROM Unisphere-Data-MIBs
    UsdTimeSlotMap, UsdNextIfIndex
        FROM Unisphere-Data-TC;

usdDs1MIB  MODULE-IDENTITY
    LAST-UPDATED "200205131601Z"  -- 13-May-02 12:01 PM EDT
    ORGANIZATION "Unisphere Networks, Inc."
    CONTACT-INFO
        "       Unisphere Networks, Inc.
        Postal: 10 Technology Park Drive
                Westford, MA  01886
                USA
        Tel:    +1 978 589 5800
        Email:  mib@UnisphereNetworks.com"
    DESCRIPTION
        "The DS1/E1 MIB for the Unisphere enterprise.  This MIB contains managed
        objects to supplement those found in RFC1406 DS1/E1 MIB."
    -- Revision History
    REVISION    "200205131601Z"  -- 13-May-02 12:01 PM EDT  - RX 4.0
    DESCRIPTION
        "Added support for FDL."
    REVISION    "200107311825Z"  -- 31-Jul-01 02:25 PM EDT  - RX 3.2
    DESCRIPTION
        "Change access on usdDsx1Ds1ChannelNumber."
    REVISION    "200104041805Z"  -- 04-Apr-01 02:05 PM EDT  - RX 3.0
    DESCRIPTION
        "Added dynamic DS1 interface support."
    REVISION      "9906170000Z"  -- 17-Jun-99               - RX 1.1
    DESCRIPTION
        "Updated version of this MIB module."
    REVISION      "9811130000Z"  -- 13-Nov-98               - RX 1.0
    DESCRIPTION
        "Initial version of this MIB module."
    ::= { usDataMibs 5 }


-- +++++++++++++++++++++++++++++++++++++++++++++++++++++++++++++++++++++++++++++
-- Textual conventions
-- +++++++++++++++++++++++++++++++++++++++++++++++++++++++++++++++++++++++++++++
-- No textual conventions are defined in this MIB


-- +++++++++++++++++++++++++++++++++++++++++++++++++++++++++++++++++++++++++++++
-- Managed objects
-- +++++++++++++++++++++++++++++++++++++++++++++++++++++++++++++++++++++++++++++
usdDs1Objects     OBJECT IDENTIFIER ::= { usdDs1MIB 1 }


-- /////////////////////////////////////////////////////////////////////////////
--
-- DS1 Interfaces
--
-- /////////////////////////////////////////////////////////////////////////////
--
-- The DS1 Configuration Table
--
usdDsx1ConfigTable  OBJECT-TYPE
    SYNTAX      SEQUENCE OF UsdDsx1ConfigEntry
    MAX-ACCESS  not-accessible
    STATUS      current
    DESCRIPTION
        "This table contains entries for DS1/E1 interfaces present in the
        system."
    ::= { usdDs1Objects 1 }

usdDsx1ConfigEntry  OBJECT-TYPE
    SYNTAX      UsdDsx1ConfigEntry
    MAX-ACCESS  not-accessible
    STATUS      current
    DESCRIPTION
        "Each entry describes the characteristics of an DS1/E1 interface."
    INDEX     { ifIndex }
    ::= { usdDsx1ConfigTable 1 }

UsdDsx1ConfigEntry ::= SEQUENCE {
        usdDsx1TimeSlotMap              UsdTimeSlotMap,
        usdDsx1Ds1ChannelNumber         Integer32,
        usdDsx1Capabilities             Integer32,
        usdDsx1Mode                     INTEGER,
        usdDsx1LineBuildOutCapabilities Integer32,
        usdDsx1LineBuildOutType         INTEGER,
        usdDsx1LineAttenuation          INTEGER,
        usdDsx1LineLength               Integer32,
        usdDsx1LowerIfIndex             InterfaceIndexOrZero,
        usdDsx1RowStatus                RowStatus,
        usdDsx1SendCode                 INTEGER,
        usdDsx1YellowAlarm              INTEGER,
        usdDsx1RemoteLoopback           INTEGER,
        usdDsx1FdlCarrier               INTEGER,
        usdDsx1FdlEic                   DisplayString,
        usdDsx1FdlLic                   DisplayString,
        usdDsx1FdlFic                   DisplayString,
        usdDsx1FdlUnit                  DisplayString,
        usdDsx1FdlPfi                   DisplayString,
        usdDsx1FdlPort                  DisplayString,
        usdDsx1FdlGenerator             DisplayString }

usdDsx1TimeSlotMap  OBJECT-TYPE
    SYNTAX      UsdTimeSlotMap
    MAX-ACCESS  read-only
    STATUS      current
    DESCRIPTION
        "A bitmap representing the timeslots on the DS1/E1 interface that have
        been allocated for service.

        For channelized DS1/E1, set bits reflect the union of timeslot
        allocations across all fractional arrangements operating over this
        DS1/E1 interface.

        For unchannelized DS1/E1, all relevant timeslot bits will be set."
    ::= { usdDsx1ConfigEntry 1 }

usdDsx1Ds1ChannelNumber  OBJECT-TYPE
    SYNTAX      Integer32 (0..28)
    MAX-ACCESS  read-create
    STATUS      current
    DESCRIPTION
        "This variable represents the channel number of the DS1/E1 on its parent
        DS3/E3.  A value of 0 indicates this DS1/E1 does not have a parent
        DS3/E3."
    ::= { usdDsx1ConfigEntry 2 }

usdDsx1Capabilities  OBJECT-TYPE
    SYNTAX      Integer32 (0..7)
    MAX-ACCESS  read-only
    STATUS      current
    DESCRIPTION
        "A value which indicates the set of capabilities of the DS1/E1
        interface.

        The value is a sum.  This sum initially takes the value zero.  Then, for
        each capability, C, in the range 1 through 3, that this interface
        supports, 2 raised to (C - 1) is added to the sum.  For example, an
        interface which is only E1 capable would have a value of 2 (2^(2-1)).
        In contrast, an interface which is both T1 and J1 capable would have a
        value of 5 (2^(1-1) + 2^(3-1)).  The values for DS1/E1 interface
        capabilities are as follows:
            capability  function
                1       T1
                2       E1
                3       J1 "
    ::= { usdDsx1ConfigEntry 3 }

usdDsx1Mode  OBJECT-TYPE
    SYNTAX      INTEGER {
                    t1(1),
                    e1(2),
                    j1(3) }
    MAX-ACCESS  read-create
    STATUS      current
    DESCRIPTION
        "This variable represents the DS1/E1 interface mode.  The value of the
        usdDsx1Capabilities object for the DS1/E1 interface indicates the valid
        set of values for this object."
    ::= { usdDsx1ConfigEntry 4 }

usdDsx1LineBuildOutCapabilities  OBJECT-TYPE
    SYNTAX      Integer32 (0..3)
    MAX-ACCESS  read-only
    STATUS      current
    DESCRIPTION
        "A value which indicates the set of line build out capabilities of the
        DS1/E1 interface.

        The value is a sum.  This sum initially takes the value zero.  Then, for
        each line build out capability, C, in the range 1 or 2, that this
        interface supports, 2 raised to (C - 1) is added to the sum.  For
        example, an interface which is only short haul capable would have a
        value of 2 (2^(2-1)).  In contrast, an interface which is both short
        haul and long haul capable would have a value of 3 (2^(1-1) + 2^(2-1)).
        The values for DS1/E1 interface line build out capabilities are as
        follows:
            line build out capability   function
                1                       short haul
                2                       long haul"
    ::= { usdDsx1ConfigEntry 5 }

usdDsx1LineBuildOutType  OBJECT-TYPE
    SYNTAX      INTEGER {
                    shortHaul(1),
                    longHaul(2),
                    notSupported(3) }
    MAX-ACCESS  read-create
    STATUS      current
    DESCRIPTION
        "This variable represents the configured line build out type of the
        DS1/E1 interface.  The value of the usdDsx1LineBuildOutCapabilities
        object for the DS1/E1 interface indicates the valid set of values for
        this object."
    ::= { usdDsx1ConfigEntry 6 }

usdDsx1LineAttenuation  OBJECT-TYPE
    SYNTAX      INTEGER {
                    db0(1),
                    dbMinus7Point5(2),
                    dbMinus15(3),
                    dbMinus22Point5(4),
                    notSupported(5) }
    MAX-ACCESS  read-create
    STATUS      current
    DESCRIPTION
        "This variable represents the configured line attenuation of the DS1/E1
        interface.  Note that the value of this object only takes effect when
        the value of the usdDsx1LineBuildOutType for the DS1/E1 interface is set
        to longHaul(2)."
    ::= { usdDsx1ConfigEntry 7 }

usdDsx1LineLength  OBJECT-TYPE
    SYNTAX      Integer32 (0..64000)
    UNITS       "meters"
    MAX-ACCESS  read-create
    STATUS      current
    DESCRIPTION
        "This variable represents the length of the DS1/E1 line in meters.  Note
        that the value of this object only takes effect when the value of the
        usdDsx1LineBuildOutType for the DS1/E1 interface is set to
        shortHaul(1)."
    ::= { usdDsx1ConfigEntry 8 }

usdDsx1LowerIfIndex  OBJECT-TYPE
    SYNTAX      InterfaceIndexOrZero
    MAX-ACCESS  read-create
    STATUS      current
    DESCRIPTION
        "The ifIndex of the interface over which this Dsx1 interface is to be
        layered.  A value of zero indicates no layering.  An implementation may
        choose to require that a nonzero value be configured at entry creation."
    ::= { usdDsx1ConfigEntry 9 }

usdDsx1RowStatus  OBJECT-TYPE
    SYNTAX      RowStatus
    MAX-ACCESS  read-create
    STATUS      current
    DESCRIPTION
        "Controls creation/deletion of entries in this table according to the
        RowStatus textual convention, constrained to support the following
        values only:
            createAndGo
            destroy

        To create an entry in this table, the following entry objects MUST be
        explicitly configured:
            usdDsx1RowStatus
            usdDsx1LowerIfIndex

        In addition, when creating an entry the following conditions must hold:

            A value for ifIndex must have been determined previously, by reading
            usdDsx1NextIfIndex.

            The interface identified by usdDsx1hLowerIfIndex must exist.

        A corresponding entry in ifTable/ifXTable/usdIfTable is created/destroyed
        as a result of creating/destroying an entry in this table."
    ::= { usdDsx1ConfigEntry 10 }

usdDsx1SendCode  OBJECT-TYPE
    SYNTAX      INTEGER {
                    sendInbandLineCode(1),
                    sendBellcoreLineCode(2),
                    sendBellcoreInbandLineCode(3),
                    sendQRSPattern(4),
                    sendAllZerosPattern(5),
                    sendAllOnesPattern(6),
                    sendAltZeroOnePattern(7),
                    sendTwo11Pattern(8),
                    sendTwo15Pattern(9),
                    sendTwo20Pattern(10),
                    sendTwo23Pattern(11),
                    sendUnfrQRSPattern(12),
                    sendUnfrAllZerosPattern(13),
                    sendUnfrAllOnesPattern(14),
                    sendUnfrAltZeroOnePattern(15),
                    sendUnfrTwo11Pattern(16),
                    sendUnfrTwo15Pattern(17),
                    sendUnfrTwo20Pattern(18),
                    sendUnfrTwo23Pattern(19),
                    otherPattern(20) }
    MAX-ACCESS  read-create
    STATUS      current
    DESCRIPTION
        "This variable indicates what type of code is being sent across the DS1
        interface by the device."
    DEFVAL { otherPattern }
    ::= { usdDsx1ConfigEntry 11 }

usdDsx1YellowAlarm  OBJECT-TYPE
    SYNTAX      INTEGER {
                    generate(1),
                    detect(2),
                    none(4) }
    MAX-ACCESS  read-create
    STATUS      current
    DESCRIPTION
        "This bitmap indicates the yellow alarm settings, and is the sum of the
        capabilities."
    ::= { usdDsx1ConfigEntry 12 }

usdDsx1RemoteLoopback  OBJECT-TYPE
    SYNTAX      INTEGER {
                    disabled(0),
                    enabled(1) }
    MAX-ACCESS  read-create
    STATUS      current
    DESCRIPTION
        "This variable indicates the remote loopback setting."
    DEFVAL    { disabled }
    ::= { usdDsx1ConfigEntry 13 }

usdDsx1FdlCarrier  OBJECT-TYPE
    SYNTAX      INTEGER {
                    disabled(0),
                    enabled(1) }
    MAX-ACCESS  read-create
    STATUS      current
    DESCRIPTION
        "Specifies the interface is used in carrier environment."
    DEFVAL    { disabled }
    ::= { usdDsx1ConfigEntry 14 }

usdDsx1FdlEic  OBJECT-TYPE
    SYNTAX      DisplayString (SIZE(0..10))
    MAX-ACCESS  read-create
    STATUS      current
    DESCRIPTION
        "This is the equipment identification code."
    DEFVAL    { "" }
    ::= { usdDsx1ConfigEntry 15 }

usdDsx1FdlLic  OBJECT-TYPE
    SYNTAX      DisplayString (SIZE(0..11))
    MAX-ACCESS  read-create
    STATUS      current
    DESCRIPTION
        "This is the location identification code."
    DEFVAL    { "" }
    ::= { usdDsx1ConfigEntry 16 }

usdDsx1FdlFic  OBJECT-TYPE
    SYNTAX      DisplayString (SIZE(0..10))
    MAX-ACCESS  read-create
    STATUS      current
    DESCRIPTION
        "This is the frame identification code."
    DEFVAL    { "" }
    ::= { usdDsx1ConfigEntry 17 }

usdDsx1FdlUnit  OBJECT-TYPE
    SYNTAX      DisplayString (SIZE(0..6))
    MAX-ACCESS  read-create
    STATUS      current
    DESCRIPTION
        "This is the unit identification code."
    DEFVAL    { "" }
    ::= { usdDsx1ConfigEntry 18 }

usdDsx1FdlPfi  OBJECT-TYPE
    SYNTAX      DisplayString (SIZE(0..38))
    MAX-ACCESS  read-create
    STATUS      current
    DESCRIPTION
        "This is the facility identification code."
    DEFVAL    { "" }
    ::= { usdDsx1ConfigEntry 19 }

 usdDsx1FdlPort  OBJECT-TYPE
    SYNTAX      DisplayString (SIZE(0..4))
    MAX-ACCESS  read-create
    STATUS      current
    DESCRIPTION
        "This is the equipment port number."
    ::= { usdDsx1ConfigEntry 20 }

usdDsx1FdlGenerator  OBJECT-TYPE
    SYNTAX      DisplayString (SIZE(0..38))
    MAX-ACCESS  read-create
    STATUS      current
    DESCRIPTION
        "This is the generator number."
    ::= { usdDsx1ConfigEntry 21 }

usdDs1NextIfIndex  OBJECT-TYPE
    SYNTAX      UsdNextIfIndex
    MAX-ACCESS  read-only
    STATUS      current
    DESCRIPTION
        "Coordinate ifIndex value allocation for entries in usdDsx1ConfigTable.

        A GET of this object returns the next available ifIndex value to be used
        to create an entry in the associated interface table; or zero, if no
        valid ifIndex value is available.  This object also returns a value of
        zero when it is the lexicographic successor of a varbind presented in an
        SNMP GETNEXT or GETBULK request, for which circumstance it is assumed
        that ifIndex allocation is unintended.

        Successive GETs will typically return different values, thus avoiding
        collisions among cooperating management clients seeking to create table
        entries simultaneously."
    ::= { usdDs1Objects 2 }


-- +++++++++++++++++++++++++++++++++++++++++++++++++++++++++++++++++++++++++++++
-- Notification control objects
-- +++++++++++++++++++++++++++++++++++++++++++++++++++++++++++++++++++++++++++++
-- No notifications are defined in this MIB.  Placeholder follows.
-- usdDs1TrapControl      OBJECT IDENTIFIER ::= { usdDs1MIB 2 }

-- +++++++++++++++++++++++++++++++++++++++++++++++++++++++++++++++++++++++++++++
-- Notifications
-- +++++++++++++++++++++++++++++++++++++++++++++++++++++++++++++++++++++++++++++
-- No notifications are defined in this MIB.  Placeholders follow.
-- The following two OBJECT IDENTIFIERS are used to define SNMPv2
-- Notifications that are easily translated into SNMPv1 Traps.
-- usdDs1Traps            OBJECT IDENTIFIER ::= { usdDs1MIB 3 }
-- usdDs1TrapPrefix       OBJECT IDENTIFIER ::= { usdDs1Traps 0 }


-- +++++++++++++++++++++++++++++++++++++++++++++++++++++++++++++++++++++++++++++
-- Conformance information
-- +++++++++++++++++++++++++++++++++++++++++++++++++++++++++++++++++++++++++++++
usdDs1Conformance OBJECT IDENTIFIER ::= { usdDs1MIB 4 }
usdDs1Compliances OBJECT IDENTIFIER ::= { usdDs1Conformance 1 }
usdDs1Groups      OBJECT IDENTIFIER ::= { usdDs1Conformance 2 }

--
-- compliance statements
--
usdDs1Compliance MODULE-COMPLIANCE
    STATUS      obsolete
    DESCRIPTION
        "Obsolete compliance statement for entities which implement the
        Unisphere DS1/E1 MIB.  This statement became obsolete when new objects
        were added."
    MODULE   -- this module
        MANDATORY-GROUPS {
            usdDs1Group }
    ::= { usdDs1Compliances 1 }                                        -- RX 1.0

usdDs1Compliance1 MODULE-COMPLIANCE
    STATUS      obsolete
    DESCRIPTION
        "Obsolete compliance statement for entities which implement the
        Unisphere DS1/E1 MIB.  This statement became obsolete when dynamic DS1
        interface support was added."
    MODULE   -- this module
        MANDATORY-GROUPS {
            usdDs1Group1 }
    ::= { usdDs1Compliances 2 }                                        -- RX 1.1

usdDs1Compliance2 MODULE-COMPLIANCE
    STATUS      obsolete
    DESCRIPTION
        "Obsolete compliance statement for entities which implement the
        Unisphere DS1/E1 MIB.  This statement became obsolete when FDL support
        was added."
    MODULE   -- this module
        MANDATORY-GROUPS {
            usdDs1Group2 }
    ::= { usdDs1Compliances 3 }                                        -- RX 3.0

usdDs1Compliance3 MODULE-COMPLIANCE
    STATUS      current
    DESCRIPTION
        "The compliance statement for entities which implement the Unisphere
        DS1/E1 MIB."
    MODULE   -- this module
        MANDATORY-GROUPS {
            usdDs1Group3 }
    ::= { usdDs1Compliances 4 }                                        -- RX 4.0

--
-- units of conformance
--
usdDs1Group  OBJECT-GROUP
    OBJECTS {
        usdDsx1TimeSlotMap,
        usdDsx1Ds1ChannelNumber }
    STATUS      obsolete
    DESCRIPTION
        "Obsolete collection of objects providing management of DS1/E1
        interfaces in a Unisphere product.  This group became obsolete when new
        objects where added to the MIB."
    ::= { usdDs1Groups 1 }

usdDs1Group1  OBJECT-GROUP
    OBJECTS {
        usdDsx1TimeSlotMap,
        usdDsx1Ds1ChannelNumber,
        usdDsx1Capabilities,
        usdDsx1Mode,
        usdDsx1LineBuildOutCapabilities,
        usdDsx1LineBuildOutType,
        usdDsx1LineAttenuation,
        usdDsx1LineLength }
    STATUS      obsolete
    DESCRIPTION
        "Obsolete collection of objects providing management of DS1/E1
        interfaces in a Unisphere product.  This group became obsolete when
        dynamic DS1 interface support was added."
    ::= { usdDs1Groups 2 }

usdDs1Group2  OBJECT-GROUP
    OBJECTS {
        usdDsx1TimeSlotMap,
        usdDsx1Ds1ChannelNumber,
        usdDsx1Capabilities,
        usdDsx1Mode,
        usdDsx1LineBuildOutCapabilities,
        usdDsx1LineBuildOutType,
        usdDsx1LineAttenuation,
        usdDsx1LineLength,
        usdDsx1LowerIfIndex,
        usdDsx1RowStatus,

        usdDs1NextIfIndex }
    STATUS      obsolete
    DESCRIPTION
        "Obsolete collection of objects providing management of DS1/E1
        interfaces in a Unisphere product.  This group became obsolete when FDL
        support was added."
    ::= { usdDs1Groups 3 }

usdDs1Group3  OBJECT-GROUP
    OBJECTS {
        usdDsx1TimeSlotMap,
        usdDsx1Ds1ChannelNumber,
        usdDsx1Capabilities,
        usdDsx1Mode,
        usdDsx1LineBuildOutCapabilities,
        usdDsx1LineBuildOutType,
        usdDsx1LineAttenuation,
        usdDsx1LineLength,
        usdDsx1LowerIfIndex,
        usdDsx1RowStatus,
        usdDsx1SendCode,
        usdDsx1YellowAlarm,
        usdDsx1RemoteLoopback,
        usdDsx1FdlCarrier,
        usdDsx1FdlEic,
        usdDsx1FdlLic,
        usdDsx1FdlFic,
        usdDsx1FdlUnit,
        usdDsx1FdlPfi,
        usdDsx1FdlPort,
        usdDsx1FdlGenerator,

        usdDs1NextIfIndex }
    STATUS      current
    DESCRIPTION
        "A collection of objects providing management of DS1/E1 interfaces in a
        Unisphere product."
    ::= { usdDs1Groups 4 }

END
