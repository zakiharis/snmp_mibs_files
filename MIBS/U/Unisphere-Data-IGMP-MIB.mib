-- *****************************************************************************
-- Unisphere-Data-IGMP-MIB
--
-- Unisphere Networks Inc. Enterprise MIB
-- Interfaces MIB
--
-- Copyright (c) 2000 Unisphere Networks, Incorporated.
-- All Rights Reserved.
-- *****************************************************************************

Unisphere-Data-IGMP-MIB DEFINITIONS ::= BEGIN

IMPORTS
    MODULE-IDENTITY, OBJECT-TYPE, Integer32, Counter32, IpAddress
        FROM SNMPv2-SMI

    RowStatus, TEXTUAL-CONVENTION
        FROM SNMPv2-TC

    MODULE-COMPLIANCE, OBJECT-GROUP  
        FROM SNMPv2-CONF

    InterfaceIndex
        FROM IF-MIB

    usDataMibs
        FROM Unisphere-Data-MIBs;


usdIgmpMIB  MODULE-IDENTITY
    LAST-UPDATED "200009261850Z" -- 26-Sep-00 2:50 PM EDT
    ORGANIZATION "Unisphere Networks, Inc."
    CONTACT-INFO
        "       Unisphere Networks, Inc.
        Postal: 10 Technology Park Drive
                Westford MA  01886
                USA
        Tel:    +1 978 589 5800
        Email:  mib@UnisphereNetworks.com"
    DESCRIPTION
        "The IGMP MIB for Unisphere Networks, Inc. enterprise."
    -- Revision History
    REVISION      "200009261850Z" -- 26-Sep-00 2:50 PM EDT
    DESCRIPTION
        "Initial version of this MIB module."
    ::= { usDataMibs 40 }

-- +++++++++++++++++++++++++++++++++++++++++++++++++++++++++++++++++++++++++++++
-- Textual conventions
-- +++++++++++++++++++++++++++++++++++++++++++++++++++++++++++++++++++++++++++++

UsdIgmpProxyGroupState ::= TEXTUAL-CONVENTION
    STATUS          current
    DESCRIPTION     
        "IP multicast group state in respect to the host IGMP (IGMP proxy)
        behavior."
    SYNTAX          INTEGER
        { 
            usdIgmpProxyGroupUnknown (0),
            usdIgmpProxyGroupIdleMember(1),
            usdIgmpProxyGroupDelayingMember(2)
        }

UsdIgmpProxyInterfaceState ::= TEXTUAL-CONVENTION
    STATUS          current
    DESCRIPTION     
        "IGMP proxy Interface state."
    SYNTAX          INTEGER
        {
            usdIgmpProxyInterfaceUnknown(0),
            usdIgmpProxyInterfaceStateV1RouterPresent(1),
            usdIgmpProxyInterfaceStateNonV1RouterPresent(2)
        }


-- +++++++++++++++++++++++++++++++++++++++++++++++++++++++++++++++++++++++++++++
-- Managed objects
-- +++++++++++++++++++++++++++++++++++++++++++++++++++++++++++++++++++++++++++++

usdIgmpMIBObject     OBJECT IDENTIFIER ::= { usdIgmpMIB 1 }
usdIgmpProtocol      OBJECT IDENTIFIER ::= { usdIgmpMIBObject 1 }
usdIgmpProxy         OBJECT IDENTIFIER ::= { usdIgmpMIBObject 2 }

--
-- The IGMP Proxy Interface Table
-- 

usdIgmpProxyInterfaceTable OBJECT-TYPE
    SYNTAX SEQUENCE OF UsdIgmpProxyInterfaceEntry
    MAX-ACCESS  not-accessible
    STATUS      current
    DESCRIPTION
        "The IGMP proxy interface table consists of interface on which the IGMP
        proxy is enabled."
    ::= { usdIgmpProxy 1 }

usdIgmpProxyInterfaceEntry OBJECT-TYPE
    SYNTAX          UsdIgmpProxyInterfaceEntry
    MAX-ACCESS      not-accessible
    STATUS          current
    DESCRIPTION
        "An entry in the usdIgmpProxyInterfaceTable."
    INDEX   { usdIgmpProxyInterfaceIfIndex }
    ::= {usdIgmpProxyInterfaceTable 1 }

UsdIgmpProxyInterfaceEntry ::= SEQUENCE {
    usdIgmpProxyInterfaceIfIndex                     InterfaceIndex,
    usdIgmpProxyInterfaceAddress                     IpAddress,
    usdIgmpProxyInterfaceMask                        IpAddress,
    usdIgmpProxyInterfaceState                       UsdIgmpProxyInterfaceState,
    usdIgmpProxyInterfaceStatus                      RowStatus,
    usdIgmpProxyInterfaceVersion                     Integer32,
    usdIgmpProxyInterfaceV1RoutePresentTimeout       Integer32,
    usdIgmpProxyInterfaceUnsolicitedReportInterval   Integer32,
    usdIgmpProxyInterfaceTotalGroupCount             Counter32,
    usdIgmpProxyInterfaceWrongVersionCount           Counter32,
    usdIgmpProxyInterfaceV1QueryReceiveCount         Counter32,
    usdIgmpProxyInterfaceV2QueryReceiveCount         Counter32,
    usdIgmpProxyInterfaceV1ReportReceiveCount        Counter32,
    usdIgmpProxyInterfaceV2ReportReceiveCount        Counter32,
    usdIgmpProxyInterfaceV1JoinReportCount           Counter32,
    usdIgmpProxyInterfaceV2JoinReportCount           Counter32,
    usdIgmpProxyInterfaceLeaveReportCount            Counter32   
    }

usdIgmpProxyInterfaceIfIndex OBJECT-TYPE
    SYNTAX      InterfaceIndex
    MAX-ACCESS  not-accessible
    STATUS      current
    DESCRIPTION     
        "The ifIndex value of the interface for which the IGMP proxy is
        enabled."
    ::= { usdIgmpProxyInterfaceEntry 1 }

usdIgmpProxyInterfaceAddress OBJECT-TYPE
    SYNTAX      IpAddress
    MAX-ACCESS  read-only
    STATUS      current
    DESCRIPTION
        "The IP address of the interface for which the IGMP proxy is enabled."
    ::= { usdIgmpProxyInterfaceEntry 2 }

usdIgmpProxyInterfaceMask OBJECT-TYPE
    SYNTAX      IpAddress
    MAX-ACCESS  read-only
    STATUS      current
    DESCRIPTION
        "The IP subnet mask of the interface for which the IGMP proxy is
        enabled."
    ::= { usdIgmpProxyInterfaceEntry 3 }

usdIgmpProxyInterfaceState   OBJECT-TYPE
    SYNTAX      UsdIgmpProxyInterfaceState
    MAX-ACCESS  read-only
    STATUS      current
    DESCRIPTION
        "When the IGMP proxy interface has v1 router present timeout running, it
        is in IgmpIntfStateV1RtPresent state.  Otherwise, it is in
        IgmpIntfStateNonV1RtPresent states.  While it is in
        IgmpIntfStateV1RtPresent, it only sends out version 1 group membership
        report(s).  While it is in IgmpIntfStateNonV1RtPresent state, it sends
        out version 2 group membership report(s)."
    ::= { usdIgmpProxyInterfaceEntry 4 }

usdIgmpProxyInterfaceStatus OBJECT-TYPE
    SYNTAX      RowStatus
    MAX-ACCESS  read-create
    STATUS      current
    DESCRIPTION
        "The state of the IGMP proxy interface.  This object follows the
        RowStatus behavior.  The destruction of the the row deletes the IGMP
        proxy inteface."
    ::= { usdIgmpProxyInterfaceEntry 5 }

usdIgmpProxyInterfaceVersion OBJECT-TYPE
    SYNTAX      Integer32
    MAX-ACCESS  read-only
    STATUS      current
    DESCRIPTION
        "The version of IGMP that this IGMP proxy interface is running."
    ::= { usdIgmpProxyInterfaceEntry 6 }

usdIgmpProxyInterfaceV1RoutePresentTimeout OBJECT-TYPE
    SYNTAX      Integer32(0..1000)
    UNITS       "seconds"
    MAX-ACCESS  read-create
    STATUS      current
    DESCRIPTION
        "The IGMP version 1 router present timeout is the time between IGMP
        proxy receives a version 1 query and the time it assumes that there is
        no more IGMP version 1 router IGMP running.  While before the V1 router
        present timeout expires, the IGMP proxy only sends out version 1 group
        membership report.  When it expires, it sends out version 2 group
        membership report."
    DEFVAL {400}
    ::= { usdIgmpProxyInterfaceEntry 7 }

usdIgmpProxyInterfaceUnsolicitedReportInterval OBJECT-TYPE
    SYNTAX      Integer32(0..1000)
    UNITS       "seconds"
    MAX-ACCESS  read-create
    STATUS      current
    DESCRIPTION
        "The unsolicited report interval specifies the time between the two
        initial group membership reports that the IGMP proxy sends."
    DEFVAL {10}
    ::= { usdIgmpProxyInterfaceEntry 8 }

usdIgmpProxyInterfaceTotalGroupCount OBJECT-TYPE
    SYNTAX          Counter32
    MAX-ACCESS      read-only
    STATUS          current
    DESCRIPTION
        "Total number of multicast groups for this upstream interface (interface
        running IGMP proxy)."
    ::= { usdIgmpProxyInterfaceEntry 9 }

usdIgmpProxyInterfaceWrongVersionCount OBJECT-TYPE
    SYNTAX          Counter32
    MAX-ACCESS      read-only
    STATUS          current
    DESCRIPTION
        "Total number of wrong version of IGMP packets received on this
        interface."
    ::= { usdIgmpProxyInterfaceEntry 10 }

usdIgmpProxyInterfaceV1QueryReceiveCount OBJECT-TYPE
    SYNTAX          Counter32
    MAX-ACCESS      read-only
    STATUS          current
    DESCRIPTION
        "Total number of version 1 IGMP queries received on this interface"
    ::= { usdIgmpProxyInterfaceEntry 11 }

usdIgmpProxyInterfaceV2QueryReceiveCount OBJECT-TYPE
    SYNTAX          Counter32
    MAX-ACCESS      read-only
    STATUS          current
    DESCRIPTION
        "Total number of version 2 IGMP queries received on this interface."
    ::= { usdIgmpProxyInterfaceEntry 12 }

usdIgmpProxyInterfaceV1ReportReceiveCount OBJECT-TYPE
    SYNTAX          Counter32
    MAX-ACCESS      read-only
    STATUS          current
    DESCRIPTION
        "Total number of version 1 group membership reports received on this
        interface."
    ::= { usdIgmpProxyInterfaceEntry 13 }

usdIgmpProxyInterfaceV2ReportReceiveCount OBJECT-TYPE
    SYNTAX          Counter32
    MAX-ACCESS      read-only
    STATUS          current
    DESCRIPTION
        "Total number of version 2 group membership reports received on this
        interface."
    ::= { usdIgmpProxyInterfaceEntry 14 }

usdIgmpProxyInterfaceV1JoinReportCount OBJECT-TYPE
    SYNTAX          Counter32
    MAX-ACCESS      read-only
    STATUS          current
    DESCRIPTION
        "Total number of version 1 group membership reports sent on this
        interface."
    ::= { usdIgmpProxyInterfaceEntry 15 }

usdIgmpProxyInterfaceV2JoinReportCount OBJECT-TYPE
    SYNTAX          Counter32
    MAX-ACCESS      read-only
    STATUS          current
    DESCRIPTION
        "Total number of version 2 group membership reports sent on this
        interface."
    ::= { usdIgmpProxyInterfaceEntry 16 }

usdIgmpProxyInterfaceLeaveReportCount OBJECT-TYPE
    SYNTAX          Counter32
    MAX-ACCESS      read-only
    STATUS          current
    DESCRIPTION
        "Total number of group leave reports sent on this interface."
    ::= { usdIgmpProxyInterfaceEntry 17 }

--
-- The IGMP Proxy Cache Table
--

usdIgmpProxyCacheTable OBJECT-TYPE
    SYNTAX          SEQUENCE OF UsdIgmpProxyCacheEntry
    MAX-ACCESS      not-accessible
    STATUS          current
    DESCRIPTION
        "The IP multicast group table.  The table is a union of multicast member
        groups from all its downstream interfaces and for which the IGMP proxy
        send group membership report."
    ::= { usdIgmpProxy 2 }

usdIgmpProxyCacheEntry OBJECT-TYPE   
    SYNTAX          UsdIgmpProxyCacheEntry
    MAX-ACCESS      not-accessible
    STATUS          current
    DESCRIPTION     
        "An entry in the usdIgmpProxyCacheTable."
    INDEX {usdIgmpProxyIfIndex, usdIgmpProxyAddress }
    ::= { usdIgmpProxyCacheTable 1}

UsdIgmpProxyCacheEntry ::= SEQUENCE {
    usdIgmpProxyIfIndex  InterfaceIndex,
    usdIgmpProxyAddress  IpAddress,
    usdIgmpProxyStatus   UsdIgmpProxyGroupState
    }

usdIgmpProxyIfIndex OBJECT-TYPE  
    SYNTAX          InterfaceIndex
    MAX-ACCESS      not-accessible
    STATUS          current
    DESCRIPTION
        "The ifIndex value of the interface for which IGMP proxy is enabled."
    ::= { usdIgmpProxyCacheEntry 1 }

usdIgmpProxyAddress OBJECT-TYPE  
    SYNTAX          IpAddress
    MAX-ACCESS      not-accessible
    STATUS          current
    DESCRIPTION
        "The IP multicast group address that the IGMP proxy sends group
        membership for."
    ::= { usdIgmpProxyCacheEntry 2 }

usdIgmpProxyStatus   OBJECT-TYPE 
    SYNTAX          UsdIgmpProxyGroupState
    MAX-ACCESS      read-only
    STATUS          current
    DESCRIPTION
        "The state of this entry.  When the IGMP proxy has a delay time running
        for this multicast group, the state of this enry is in the
        usdIgmpDelayingMember state.  When the delay time expires, the IGMP proxy
        sends an unsolicited report and the state of this group enters
        usdIgmpDelayMember state."
    ::= { usdIgmpProxyCacheEntry 3 }


-- +++++++++++++++++++++++++++++++++++++++++++++++++++++++++++++++++++++++++++++
-- Notifications
-- +++++++++++++++++++++++++++++++++++++++++++++++++++++++++++++++++++++++++++++

-- No notifications are defined in this MIB.  Placeholders follow.

-- usdIgmpTrapControl      OBJECT IDENTIFIER ::= { usdIgmpMIB 2 }
-- usdIgmpTraps            OBJECT IDENTIFIER ::= { usdIgmpMIB 3 }
-- usdIgmpTrapPrefix       OBJECT IDENTIFIER ::= { usdIgmpTraps 0 }


-- +++++++++++++++++++++++++++++++++++++++++++++++++++++++++++++++++++++++++++++
-- Conformance information
-- +++++++++++++++++++++++++++++++++++++++++++++++++++++++++++++++++++++++++++++

usdIgmpConformance OBJECT IDENTIFIER ::= { usdIgmpMIB 4 }
usdIgmpCompliances OBJECT IDENTIFIER ::= { usdIgmpConformance 1 }
usdIgmpGroups      OBJECT IDENTIFIER ::= { usdIgmpConformance 2 }

-- compliance statements

usdIgmpCompliance MODULE-COMPLIANCE
    STATUS  current
    DESCRIPTION
        "The compliance statement for entities that implement the Unisphere
        IGMP MIB."
    MODULE  -- this module
        MANDATORY-GROUPS {
            usdIgmpProxyInterfaceGroup,
            usdIgmpProxyCacheGroup }
    ::= { usdIgmpCompliances 1 }

-- units of conformance

usdIgmpProxyInterfaceGroup OBJECT-GROUP
    OBJECTS {
        usdIgmpProxyInterfaceAddress,
        usdIgmpProxyInterfaceMask,
        usdIgmpProxyInterfaceState,
        usdIgmpProxyInterfaceStatus,
        usdIgmpProxyInterfaceVersion,
        usdIgmpProxyInterfaceV1RoutePresentTimeout,
        usdIgmpProxyInterfaceUnsolicitedReportInterval,
        usdIgmpProxyInterfaceTotalGroupCount,
        usdIgmpProxyInterfaceWrongVersionCount,
        usdIgmpProxyInterfaceV1QueryReceiveCount,
        usdIgmpProxyInterfaceV2QueryReceiveCount,
        usdIgmpProxyInterfaceV1ReportReceiveCount,
        usdIgmpProxyInterfaceV2ReportReceiveCount,
        usdIgmpProxyInterfaceV1JoinReportCount,
        usdIgmpProxyInterfaceV2JoinReportCount,
        usdIgmpProxyInterfaceLeaveReportCount }
    STATUS  current
    DESCRIPTION
        "A collection of objects providing management of IGMP proxy interfaces
        in a Unisphere product."
    ::= { usdIgmpGroups 1 }

usdIgmpProxyCacheGroup OBJECT-GROUP
    OBJECTS {
        usdIgmpProxyStatus }
    STATUS  current
    DESCRIPTION
        "An object providing management of IGMP proxy caches in a Unisphere
        product."
    ::= { usdIgmpGroups 2 }

END
