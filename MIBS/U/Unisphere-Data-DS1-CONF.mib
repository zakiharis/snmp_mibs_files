-- *****************************************************************************
-- Unisphere-Data-DS1-CONF
--
-- SNMP Agent Capabilities definitions for the DS1 MIBs.
--
-- Copyright (c) 2001 Unisphere Networks, Inc.  All rights reserved.
-- *****************************************************************************

Unisphere-Data-DS1-CONF DEFINITIONS ::= BEGIN

IMPORTS
    MODULE-IDENTITY
        FROM SNMPv2-SMI
    AGENT-CAPABILITIES
        FROM SNMPv2-CONF
    usDataAgents
        FROM Unisphere-Data-Agents
    dsx1ConfigEntry, dsx1CurrentEntry, dsx1IntervalEntry, dsx1TotalEntry,
    dsx1FarEndCurrentEntry, dsx1FarEndIntervalEntry, dsx1FarEndTotalEntry,
    dsx1FracEntry
        FROM RFC1406-MIB
    usdDs1Group, usdDs1Group1, usdDs1Group2, usdDs1Group3
        FROM Unisphere-Data-DS1-MIB;

usdDs1Agent MODULE-IDENTITY
    LAST-UPDATED "200205131634Z"  -- 13-May-02 12:34 PM EDT
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the DS1 component of the SNMP
        agent in the Unisphere Routing Switch family of products."
    -- Revision History
    REVISION    "200205131634Z"  -- 13-May-02 12:34 PM EDT  - RX 4.0
    DESCRIPTION
        "Add far end statistics support.  More configuration objects were added
        to Unisphere-Data-DS1-MIB."
    REVISION    "200103292036Z"  -- 29-Mar-01 03:36 PM EST  - RX 3.2
    DESCRIPTION
        "The initial release of this management information module."
    ::= { usDataAgents 10 }


usdDs1AgentV1  AGENT-CAPABILITIES
    PRODUCT-RELEASE
        "Version 1 of the DS1 component of the Unisphere Routing Switch SNMP
        agent.  This version of the DS1 component was supported in the Unisphere
        RX 1.0 system releases."
    STATUS      obsolete
    DESCRIPTION
        "The MIBs supported by the SNMP agent for the DS1 application in the
        Unisphere Routing Switch.  This version became obsolete when new objects
        were added to the Unisphere-Data-DS1-MIB."
    SUPPORTS    RFC1406-MIB
    --  The RFC1406-MIB is based on SMIv1 and has no conformance groups.
    --  Therefore, we list capabilities by OID subtree "groups".
        INCLUDES  {
            dsx1ConfigEntry,
            dsx1CurrentEntry,
            dsx1IntervalEntry,
            dsx1TotalEntry,
            dsx1FracEntry }
    SUPPORTS    Unisphere-Data-DS1-MIB
        INCLUDES  {
            usdDs1Group }
    ::= { usdDs1Agent 1 }

usdDs1AgentV2  AGENT-CAPABILITIES
    PRODUCT-RELEASE
        "Version 2 of the DS1 component of the Unisphere Routing Switch SNMP
        agent.  This version of the DS1 component was supported in the Unisphere
        RX 1.1 thru RX 2.x system releases."
    STATUS      obsolete
    DESCRIPTION
        "The MIBs supported by the SNMP agent for the DS1 application in the
        Unisphere Routing Switch.  This version became obsolete when dynamic DS1
        interface support was added to the Unisphere-Data-DS1-MIB."
    SUPPORTS    RFC1406-MIB
    --  The RFC1406-MIB is based on SMIv1 and has no conformance groups.
    --  Therefore, we list capabilities by OID subtree "groups".
        INCLUDES  {
            dsx1ConfigEntry,
            dsx1CurrentEntry,
            dsx1IntervalEntry,
            dsx1TotalEntry,
            dsx1FracEntry }
    SUPPORTS    Unisphere-Data-DS1-MIB
        INCLUDES  {
            usdDs1Group1 }
    ::= { usdDs1Agent 2 }

usdDs1AgentV3  AGENT-CAPABILITIES
    PRODUCT-RELEASE
        "Version 3 of the DS1 component of the Unisphere Routing Switch SNMP
        agent.  This version of the DS1 component was supported in the Unisphere
        RX 3.x system releases."
    STATUS      obsolete
    DESCRIPTION
        "The MIBs supported by the SNMP agent for the DS1 application in the
        Unisphere Routing Switch.  This version became obsolete when far end
        statistics support was added and more configuration objects were added
        to the Unisphere-Data-DS1-MIB."
    SUPPORTS    RFC1406-MIB
    --  The RFC1406-MIB is based on SMIv1 and has no conformance groups.
    --  Therefore, we list capabilities by OID subtree "groups".
        INCLUDES  {
            dsx1ConfigEntry,
            dsx1CurrentEntry,
            dsx1IntervalEntry,
            dsx1TotalEntry,
            dsx1FracEntry }
    SUPPORTS    Unisphere-Data-DS1-MIB
        INCLUDES  {
            usdDs1Group2 }
    ::= { usdDs1Agent 3 }

usdDs1AgentV4 AGENT-CAPABILITIES
    PRODUCT-RELEASE
        "Version 4 of the DS1 component of the Unisphere Routing Switch SNMP
        agent.  This version of the DS1 component is supported in the Unisphere
        RX 4.0 and subsequent system releases."
    STATUS      current
    DESCRIPTION
        "The MIBs supported by the SNMP agent for the DS1 application in the
        Unisphere Routing Switch."
    SUPPORTS    RFC1406-MIB
    --  The RFC1406-MIB is based on SMIv1 and has no conformance groups.
    --  Therefore, we list capabilities by OID subtree "groups".
        INCLUDES  {
            dsx1ConfigEntry,
            dsx1CurrentEntry,
            dsx1IntervalEntry,
            dsx1TotalEntry,
            dsx1FarEndCurrentEntry,
            dsx1FarEndIntervalEntry,
            dsx1FarEndTotalEntry,
            dsx1FracEntry }
    SUPPORTS    Unisphere-Data-DS1-MIB
        INCLUDES  {
            usdDs1Group3 }
    ::= { usdDs1Agent 4 }

END
