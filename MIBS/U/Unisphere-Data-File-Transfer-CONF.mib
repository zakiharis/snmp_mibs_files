-- *****************************************************************************
-- Unisphere-Data-File-Transfer-CONF
--
-- SNMP Agent Capabilities definitions for the File Transfer MIBs.
--
-- Copyright (c) 2001 Unisphere Networks, Inc.  All rights reserved.
-- *****************************************************************************

Unisphere-Data-File-Transfer-CONF DEFINITIONS ::= BEGIN

IMPORTS
    MODULE-IDENTITY
        FROM SNMPv2-SMI
    AGENT-CAPABILITIES
        FROM SNMPv2-CONF
    usDataAgents
        FROM Unisphere-Data-Agents
    usdFileXferGroup1,
    usdFileXferGroup2,
    usdFileXferTrapGroup
        FROM Unisphere-Data-FILE-XFER-MIB;

usdFileTransferAgent MODULE-IDENTITY
    LAST-UPDATED "200103281322Z"  -- 28-Mar-01 08:22 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the File Transfer component of
        the SNMP agent in the Unisphere Routing Switch family of products."
    -- Revision History
    REVISION    "200103281322Z"  -- 28-Mar-01 08:22 AM EST  - RX 3.2
    DESCRIPTION
        "The initial release of this management information module."
    ::= { usDataAgents 15 }

usdFileTransferAgentV1 AGENT-CAPABILITIES
    PRODUCT-RELEASE
        "Version 1 of the File Transfer component of the Unisphere Routing
        Switch SNMP agent.  This version of the File Transfer component was
        supported in the Unisphere RX 1.x system releases."
    STATUS      obsolete
    DESCRIPTION
        "The MIB supported by the SNMP agent for the File System application in
        the Unisphere Routing Switch.  These capabilities became obsolete when
        remote user information was removed and router name was added."

    SUPPORTS        Unisphere-Data-FILE-XFER-MIB
        INCLUDES  { usdFileXferGroup1,
                    usdFileXferTrapGroup }

    ::= { usdFileTransferAgent 1 }

usdFileTransferAgentV2 AGENT-CAPABILITIES
    PRODUCT-RELEASE
        "Version 2 of the File Transfer component of the Unisphere Routing
        Switch SNMP agent.  This version of the File Transfer component is
        supported in the Unisphere RX 2.0 and subsequent system releases."
    STATUS      current
    DESCRIPTION
        "The MIB supported by the SNMP agent for the File System application in
        the Unisphere Routing Switch."

    SUPPORTS        Unisphere-Data-FILE-XFER-MIB
        INCLUDES  { usdFileXferGroup2,
                    usdFileXferTrapGroup }

    ::= { usdFileTransferAgent 2 }

END
