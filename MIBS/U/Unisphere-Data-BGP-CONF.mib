-- *****************************************************************************
-- Unisphere-Data-BGP-CONF
--
-- SNMP Agent Capabilities definitions for the BGP MIB.
--
-- Copyright (c) 2001, 2002 Unisphere Networks, Inc.
-- Copyright (c) 2002 Juniper Networks, Inc.
--   All rights reserved.
-- *****************************************************************************

Unisphere-Data-BGP-CONF DEFINITIONS ::= BEGIN

IMPORTS
    MODULE-IDENTITY
        FROM SNMPv2-SMI
    AGENT-CAPABILITIES
        FROM SNMPv2-CONF
    usDataAgents
        FROM Unisphere-Data-Agents
    bgp4MIBGlobalsGroup, bgp4MIBPeerGroup, bgp4MIBRcvdPathAttrGroup,
    bgp4MIBPathAttrGroup, bgp4MIBNotificationGroup, bgp4MIBNewNotificationGroup
        FROM BGP4-MIB
    usdBgpGeneralConfGroup, usdBgpStatisticsConfGroup,
    usdBgpConfederationPeerConfGroup, usdBgpPeerConfGroup,
    usdBgpAfiSafiPeerConfGroup, usdBgpPeerAddressFamilyConfGroup,
    usdBgpPeerGroupConfGroup, usdBgpPeerGroupAddressFamilyConfGroup,
    usdBgpRouteConfGroup, usdBgpNetworkConfGroup, usdBgpAggregateConfGroup,
    usdBgpVrfConfGroup, usdBgpAddressFamilyConfGroup, usdBgpStorageConfGroup,
    usdBgpGeneralConfGroup2, usdBgpNewRouteConfGroup, usdBgpPeerConfGroup2,
    usdBgpPeerGroupConfGroup2, usdBgpVrfConfGroup2, usdBgpGeneralConfGroup3,
    usdBgpStorageConfGroup2, usdBgpPeerConfGroup3,
    usdBgpPeerAddressFamilyConfGroup2, usdBgpPeerGroupConfGroup3,
    usdBgpPeerGroupAddressFamilyConfGroup2, usdBgpNetworkConfGroup2,
    usdBgpAggregateConfGroup2, usdBgpVrfConfGroup3,
    usdBgpAddressFamilyConfGroup2
        FROM Unisphere-Data-BGP-MIB;

usdBgpAgent MODULE-IDENTITY
    LAST-UPDATED "200209041756Z"  -- 04-Sep-02 01:56 PM EDT
    ORGANIZATION "Juniper Networks, Inc."
    CONTACT-INFO
        "       Juniper Networks, Inc.
        Postal: 10 Technology Park Drive
                Westford, MA  01886
                USA
        Tel:    +1 978 589 5800
        E-mail: mib@Juniper.net"
    DESCRIPTION
        "The agent capabilities definitions for the BGP component of the SNMP
        agent in the Unisphere Routing Switch family of products."
    -- Revision History
    REVISION    "200209041756Z"  -- 04-Sep-02 01:56 PM EDT  - RX 4.0
    DESCRIPTION
        "Added support for the BGP4-MIB.
         Added support for BGP internal redistribute.
         Obsoleted rsBgpStorageInitialHistoryRoutePoolSize and
         rsBgpStorageMaxHistoryRoutePoolSize.
         Added the ability to unconfigure BGP attributes from the MIB."
    REVISION    "200203011751Z"  -- 01-Mar-02 12:51 PM EST  - RX 3.5
    DESCRIPTION
        "Added support for adding unicast BGP routes into a multicast view."
    REVISION    "200201231316Z"  -- 23-Jan-02 01:16 PM EST  - RX 3.4
    DESCRIPTION
        "Added support for peer and peer-group local-as."
    REVISION    "200112041609Z"  -- 04-Dec-01 11:09 AM EST  - RX 3.3
    DESCRIPTION
        "Replaced the BGP route congiguration group with new tables containing
        the original route destination as an additional index."
    REVISION    "200112031848Z"  -- 03-Dec-01 01:48 PM EST  - RX 3.2
    DESCRIPTION
        "The initial release of this management information module."
    ::= { usDataAgents 4 }


usdBgpAgentV1 AGENT-CAPABILITIES
    PRODUCT-RELEASE
        "Version 1 of the BGP component of the Unisphere Routing Switch SNMP
        agent.  This version of the BGP component was supported in the Unisphere
        RX 3.0 and 3.1 system releases."
    STATUS      obsolete
    DESCRIPTION
        "The MIB supported by the SNMP agent for the BGP application in the
        Unisphere Routing Switch.  These capabilities became obsolete when a new
        object was added to the general configuration group."
    SUPPORTS    Unisphere-Data-BGP-MIB
        INCLUDES {
            usdBgpGeneralConfGroup,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpRouteConfGroup,
            usdBgpNetworkConfGroup,
            usdBgpAggregateConfGroup,
            usdBgpVrfConfGroup,
            usdBgpAddressFamilyConfGroup,
            usdBgpStorageConfGroup }
    ::= { usdBgpAgent 1 }

usdBgpAgentV2 AGENT-CAPABILITIES
    PRODUCT-RELEASE
        "Version 2 of the BGP component of the Unisphere Routing Switch SNMP
        agent.  This version of the BGP component was supported in the Unisphere
        RX 3.2 system release."
    STATUS      obsolete
    DESCRIPTION
        "The MIB supported by the SNMP agent for the BGP application in the
        Unisphere Routing Switch.  These capabilities became obsolete when the
        BGP route congiguration group was replaced with new tables containing
        the original route destination as an additional index."
    SUPPORTS    Unisphere-Data-BGP-MIB
        INCLUDES {
            usdBgpGeneralConfGroup2,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpRouteConfGroup,
            usdBgpNetworkConfGroup,
            usdBgpAggregateConfGroup,
            usdBgpVrfConfGroup,
            usdBgpAddressFamilyConfGroup,
            usdBgpStorageConfGroup }
    ::= { usdBgpAgent 2 }

usdBgpAgentV3 AGENT-CAPABILITIES
    PRODUCT-RELEASE
        "Version 3 of the BGP component of the Unisphere Routing Switch SNMP
        agent.  This version of the BGP component was supported in the Unisphere
        RX 3.3 system release."
    STATUS      obsolete
    DESCRIPTION
        "The MIB supported by the SNMP agent for the BGP application in the
        Unisphere Routing Switch.  These capabilities became obsolete when the
        peer and peer-group local-as support was added."
    SUPPORTS    Unisphere-Data-BGP-MIB
        INCLUDES {
            usdBgpGeneralConfGroup2,
            usdBgpStatisticsConfGroup,
            usdBgpConfederationPeerConfGroup,
            usdBgpPeerConfGroup,
            usdBgpAfiSafiPeerConfGroup,
            usdBgpPeerAddressFamilyConfGroup,
            usdBgpPeerGroupConfGroup,
            usdBgpPeerGroupAddressFamilyConfGroup,
            usdBgpNewRouteConfGroup,
            usdBgpNetworkConfGroup,
            usdBgpAggregateConfGroup,
            usdBgpVrfConfGroup,
            usdBgpAddressFamilyConfGroup,
            usdBgpStorageConfGroup }
    ::= { usdBgpAgent 3 }

usdBgpAgentV4 AGENT-CAPABILITIES
    PRODUCT-RELEASE
        "Version 4 of the BGP component of the Unisphere Routing Switch SNMP
        agent.  This version of the BGP component was supported in the Unisphere
        RX 3.4 system release."
    STATUS      obsolete
    DESCRIPTION
        "The MIB supported by the SNMP agent for the BGP application in the
        Unisphere Routing Switch.  These capabilities became obsolete when
        support was added for adding unicast BGP routes into a multicast view."
    SUPPORTS    Unisphere-Data-BGP-MIB
        INCLUDES {
            usdBgpGeneralConfGroup2,
            usdBgpStatisticsConfGroup,
            usdBgpConfederationPeerConfGroup,
            usdBgpPeerConfGroup2,
            usdBgpAfiSafiPeerConfGroup,
            usdBgpPeerAddressFamilyConfGroup,
            usdBgpPeerGroupConfGroup2,
            usdBgpPeerGroupAddressFamilyConfGroup,
            usdBgpNewRouteConfGroup,
            usdBgpNetworkConfGroup,
            usdBgpAggregateConfGroup,
            usdBgpVrfConfGroup,
            usdBgpAddressFamilyConfGroup,
            usdBgpStorageConfGroup }
    ::= { usdBgpAgent 4 }

usdBgpAgentV5 AGENT-CAPABILITIES
    PRODUCT-RELEASE
        "Version 5 of the BGP component of the Unisphere Routing Switch SNMP
        agent.  This version of the BGP component was supported in the Unisphere
        RX 3.5 and subseguent 3.x system releases."
    STATUS      obsolete
    DESCRIPTION
        "The MIB supported by the SNMP agent for the BGP application in the
        Unisphere Routing Switch.  These capabilities became obsolete when
        support was added for the standard BGP4-MIB and for BGP internal
        redistribute."
    SUPPORTS    Unisphere-Data-BGP-MIB
        INCLUDES  {
            usdBgpGeneralConfGroup2,
            usdBgpStatisticsConfGroup,
            usdBgpConfederationPeerConfGroup,
            usdBgpPeerConfGroup2,
            usdBgpAfiSafiPeerConfGroup,
            usdBgpPeerAddressFamilyConfGroup,
            usdBgpPeerGroupConfGroup2,
            usdBgpPeerGroupAddressFamilyConfGroup,
            usdBgpNewRouteConfGroup,
            usdBgpNetworkConfGroup,
            usdBgpAggregateConfGroup,
            usdBgpVrfConfGroup2,
            usdBgpAddressFamilyConfGroup,
            usdBgpStorageConfGroup }
    ::= { usdBgpAgent 5 }

usdBgpAgentV6 AGENT-CAPABILITIES
    PRODUCT-RELEASE
        "Version 6 of the BGP component of the Unisphere Routing Switch SNMP
        agent.  This version of the BGP component is supported in the Unisphere
        RX 4.0 and subsequent system releases."
    STATUS      current
    DESCRIPTION
        "The MIB supported by the SNMP agent for the BGP application in the
        Unisphere Routing Switch."
   SUPPORTS     BGP4-MIB
        INCLUDES  {
            bgp4MIBGlobalsGroup,
            bgp4MIBPeerGroup,
            bgp4MIBRcvdPathAttrGroup,
            bgp4MIBPathAttrGroup,
            bgp4MIBNotificationGroup,
            bgp4MIBNewNotificationGroup }
    SUPPORTS    Unisphere-Data-BGP-MIB
        INCLUDES  {
            usdBgpGeneralConfGroup3,
            usdBgpStatisticsConfGroup,
            usdBgpConfederationPeerConfGroup,
            usdBgpPeerConfGroup3,
            usdBgpAfiSafiPeerConfGroup,
            usdBgpPeerAddressFamilyConfGroup2,
            usdBgpPeerGroupConfGroup3,
            usdBgpPeerGroupAddressFamilyConfGroup2,
            usdBgpNewRouteConfGroup,
            usdBgpNetworkConfGroup2,
            usdBgpAggregateConfGroup2,
            usdBgpVrfConfGroup3,
            usdBgpAddressFamilyConfGroup2,
            usdBgpStorageConfGroup2 }
    ::= { usdBgpAgent 6 }

END
