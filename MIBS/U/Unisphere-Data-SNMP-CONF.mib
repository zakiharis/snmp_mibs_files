-- *****************************************************************************
-- Unisphere-Data-SNMP-CONF
--
-- SNMP Agent Capabilities definitions for the SNMP MIBs.
--
-- Copyright (c) 2001 Unisphere Networks, Inc.
-- Copyright (c) 2002 Juniper Networks, Inc.
--   All rights reserved.
-- *****************************************************************************

Unisphere-Data-SNMP-CONF DEFINITIONS ::= BEGIN

IMPORTS
    MODULE-IDENTITY
        FROM SNMPv2-SMI
    AGENT-CAPABILITIES
        FROM SNMPv2-CONF
    usDataAgents
        FROM Unisphere-Data-Agents
    snmpGroup, snmpCommunityGroup, snmpObsoleteGroup, snmpSetGroup, systemGroup,
    sysORLastChange, sysORID, sysORUpTime, sysORDescr,
    snmpBasicNotificationsGroup
        FROM SNMPv2-MIB
    snmpEngineGroup
        FROM SNMP-FRAMEWORK-MIB
    snmpMPDGroup
        FROM SNMP-MPD-MIB
    snmpTargetBasicGroup, snmpTargetAddrTDomain, snmpTargetAddrTAddress,
    snmpTargetAddrTagList, snmpTargetAddrParams, snmpTargetAddrStorageType,
    snmpTargetAddrRowStatus, snmpTargetParamsMPModel,
    snmpTargetParamsSecurityModel, snmpTargetParamsSecurityName,
    snmpTargetParamsSecurityLevel, snmpTargetParamsStorageType,
    snmpTargetParamsRowStatus, snmpTargetResponseGroup, snmpTargetAddrTimeout,
    snmpTargetAddrRetryCount, snmpTargetCommandResponderGroup
        FROM SNMP-TARGET-MIB
    snmpNotifyGroup, snmpNotifyTag, snmpNotifyType, snmpNotifyStorageType,
    snmpNotifyRowStatus, snmpNotifyFilterGroup, snmpNotifyFilterProfileName,
    snmpNotifyFilterProfileStorType, snmpNotifyFilterProfileRowStatus,
    snmpNotifyFilterMask, snmpNotifyFilterType, snmpNotifyFilterStorageType,
    snmpNotifyFilterRowStatus
        FROM SNMP-NOTIFICATION-MIB
    usmMIBBasicGroup
        FROM SNMP-USER-BASED-SM-MIB
    vacmBasicGroup
        FROM SNMP-VIEW-BASED-ACM-MIB
    usdSnmpGroup, usdSnmpGroup2, usdSnmpGroup3, usdSnmpGeneralGroup,
    usdSnmpAccessGroup, usdSnmpTrapGroup, usdSnmpAuthFailGroup,
    usdSnmpGeneralGroup2
        FROM Unisphere-Data-SNMP-MIB;

usdSnmpAgent MODULE-IDENTITY
    LAST-UPDATED "200208141923Z"  -- 14-Aug-02 03:23 PM EDT
    ORGANIZATION "Juniper Networks, Inc."
    CONTACT-INFO
        "       Juniper Networks, Inc.
        Postal: 10 Technology Park Drive
                Westford, MA  01886
                USA
        Tel:    +1 978 589 5800
        E-mail: mib@UnisphereNetworks.com"
    DESCRIPTION
        "The agent capabilities definitions for the SNMP entity component of the
        SNMP agent in the Juniper Routing Switch family of products."
    -- Revision History
    REVISION    "200208141923Z"  -- 14-Aug-02 03:23 PM EDT  - RX 3.4
    DESCRIPTION
        "Added support for proxy enable/disable feature."
    REVISION    "200110161344Z"  -- 16-Oct-01 09:44 AM EDT  - RX 3.3
    DESCRIPTION
        "Added support for the snmpSetGroup.  Added new objects to the
        Unisphere-Data-SNMP-MIB supporting interface compress, trap severities
        and trap severity filtering."
    REVISION    "200104131544Z"  -- 13-Apr-01 11:44 AM EDT  - RX 3.2
    DESCRIPTION
        "The initial release of this management information module."
    ::= { usDataAgents 39 }

usdSnmpAgentV1 AGENT-CAPABILITIES
    PRODUCT-RELEASE
        "Version 1 of the SNMP entity component of the Unisphere Routing Switch
        SNMP agent.  This version of the SNMP entity component was supported in
        the Unisphere RX 1.x system releases."
    STATUS      obsolete
    DESCRIPTION
        "The MIBs supported by the SNMP agent for the SNMP entity application in
        the Unisphere Routing Switch.  These capabilities became obsolete when
        SNMPv3 support, View support, and Named Access List support were added."
    SUPPORTS    SNMPv2-MIB
        INCLUDES  {
            snmpGroup,
            snmpCommunityGroup,
            snmpObsoleteGroup,
            systemGroup,
            snmpBasicNotificationsGroup }
        VARIATION   sysORLastChange
            ACCESS  not-implemented
            DESCRIPTION
                "The system object resource table is not supported."
        VARIATION   sysORID
            ACCESS  not-implemented
            DESCRIPTION
                "The system object resource table is not supported."
        VARIATION   sysORDescr
            ACCESS  not-implemented
            DESCRIPTION
                "The system object resource table is not supported."
        VARIATION   sysORUpTime
            ACCESS  not-implemented
            DESCRIPTION
                "The system object resource table is not supported."
    SUPPORTS    Unisphere-Data-SNMP-MIB
        INCLUDES  {
            usdSnmpGroup,
            usdSnmpAuthFailGroup }
    ::= { usdSnmpAgent 1 }

usdSnmpAgentV2 AGENT-CAPABILITIES
    PRODUCT-RELEASE
        "Version 2 of the SNMP entity component of the Unisphere Routing Switch
        SNMP agent.  This version of the SNMP entity component was supported in
        the Unisphere RX 2.0 thru 2.2 system releases."
    STATUS      obsolete
    DESCRIPTION
        "The MIBs supported by the SNMP agent for the SNMP entity application in
        the Unisphere Routing Switch.  These capabilities became obsolete when
        the usdSnmpInterfaceMode object was added."
    SUPPORTS    SNMPv2-MIB
        INCLUDES  {
            snmpGroup,
            snmpCommunityGroup,
            snmpObsoleteGroup,
            systemGroup,
            snmpBasicNotificationsGroup }
        VARIATION   sysORLastChange
            ACCESS  not-implemented
            DESCRIPTION
                "The system object resource table is not supported."
        VARIATION   sysORID
            ACCESS  not-implemented
            DESCRIPTION
                "The system object resource table is not supported."
        VARIATION   sysORDescr
            ACCESS  not-implemented
            DESCRIPTION
                "The system object resource table is not supported."
        VARIATION   sysORUpTime
            ACCESS  not-implemented
            DESCRIPTION
                "The system object resource table is not supported."
    SUPPORTS    Unisphere-Data-SNMP-MIB
        INCLUDES  {
            usdSnmpGroup2,
            usdSnmpAuthFailGroup }
    SUPPORTS    SNMP-FRAMEWORK-MIB
        INCLUDES  {
            snmpEngineGroup }
    SUPPORTS    SNMP-MPD-MIB
        INCLUDES  {
            snmpMPDGroup }
    SUPPORTS    SNMP-TARGET-MIB
        INCLUDES  {
            snmpTargetBasicGroup,
            snmpTargetResponseGroup,
            snmpTargetCommandResponderGroup }
        VARIATION   snmpTargetAddrTDomain
            ACCESS      read-only
            DESCRIPTION
                "Unable to create or set elements of the snmpTargetAddrTable."
        VARIATION   snmpTargetAddrTAddress
            ACCESS      read-only
            DESCRIPTION
                "Unable to create or set elements of the snmpTargetAddrTable."
        VARIATION   snmpTargetAddrTimeout
            ACCESS      read-only
            DESCRIPTION
                "Unable to create or set elements of the snmpTargetAddrTable."
        VARIATION   snmpTargetAddrRetryCount
            ACCESS      read-only
            DESCRIPTION
                "Unable to create or set elements of the snmpTargetAddrTable."
        VARIATION   snmpTargetAddrTagList
            ACCESS      read-only
            DESCRIPTION
                "Unable to create or set elements of the snmpTargetAddrTable."
        VARIATION   snmpTargetAddrParams
            ACCESS      read-only
            DESCRIPTION
                "Unable to create or set elements of the snmpTargetAddrTable."
        VARIATION   snmpTargetAddrStorageType
            ACCESS      read-only
            DESCRIPTION
                "Unable to create or set elements of the snmpTargetAddrTable."
        VARIATION   snmpTargetAddrRowStatus
            ACCESS      read-only
            DESCRIPTION
                "Unable to create or set elements of the snmpTargetAddrTable."
        VARIATION   snmpTargetParamsMPModel
            ACCESS      read-only
            DESCRIPTION
                "Unable to create or set elements of the snmpTargetParamsTable."
        VARIATION   snmpTargetParamsSecurityModel
            ACCESS      read-only
            DESCRIPTION
                "Unable to create or set elements of the snmpTargetParamsTable."
        VARIATION   snmpTargetParamsSecurityName
            ACCESS      read-only
            DESCRIPTION
                "Unable to create or set elements of the snmpTargetParamsTable."
        VARIATION   snmpTargetParamsSecurityLevel
            ACCESS      read-only
            DESCRIPTION
                "Unable to create or set elements of the snmpTargetParamsTable."
        VARIATION   snmpTargetParamsStorageType
            ACCESS      read-only
            DESCRIPTION
                "Unable to create or set elements of the snmpTargetParamsTable."
        VARIATION   snmpTargetParamsRowStatus
            ACCESS      read-only
            DESCRIPTION
                "Unable to create or set elements of the snmpTargetParamsTable."
    SUPPORTS    SNMP-NOTIFICATION-MIB
        INCLUDES  {
            snmpNotifyGroup,
            snmpNotifyFilterGroup }
        VARIATION   snmpNotifyTag
            ACCESS      read-only
            DESCRIPTION
                "Unable to create or set elements of the snmpNotifyTable."
        VARIATION   snmpNotifyType
            ACCESS      read-only
            DESCRIPTION
                "Unable to create or set elements of the snmpNotifyTable."
        VARIATION   snmpNotifyStorageType
            ACCESS      read-only
            DESCRIPTION
                "Unable to create or set elements of the snmpNotifyTable."
        VARIATION   snmpNotifyRowStatus
            ACCESS      read-only
            DESCRIPTION
                "Unable to create or set elements of the snmpNotifyTable."
        VARIATION   snmpNotifyFilterProfileName
            ACCESS      read-only
            DESCRIPTION
                "Unable to create or set elements of the
                snmpNotifyFilterProfileTable."
        VARIATION   snmpNotifyFilterProfileStorType
            ACCESS      read-only
            DESCRIPTION
                "Unable to create or set elements of the
                snmpNotifyFilterProfileTable."
        VARIATION   snmpNotifyFilterProfileRowStatus
            ACCESS      read-only
            DESCRIPTION
                "Unable to create or set elements of the
                snmpNotifyFilterProfileTable."
        VARIATION   snmpNotifyFilterMask
            ACCESS      read-only
            DESCRIPTION
                "Unable to create or set elements of the snmpNotifyFilterTable."
        VARIATION   snmpNotifyFilterType
            ACCESS      read-only
            DESCRIPTION
                "Unable to create or set elements of the snmpNotifyFilterTable."
        VARIATION   snmpNotifyFilterStorageType
            ACCESS      read-only
            DESCRIPTION
                "Unable to create or set elements of the snmpNotifyFilterTable."
        VARIATION   snmpNotifyFilterRowStatus
            ACCESS      read-only
            DESCRIPTION
                "Unable to create or set elements of the snmpNotifyFilterTable."
    SUPPORTS    SNMP-USER-BASED-SM-MIB
        INCLUDES  {
            usmMIBBasicGroup }
    SUPPORTS    SNMP-VIEW-BASED-ACM-MIB
        INCLUDES  {
            vacmBasicGroup }
    ::= { usdSnmpAgent 2 }

usdSnmpAgentV3 AGENT-CAPABILITIES
    PRODUCT-RELEASE
        "Version 3 of the SNMP entity component of the Unisphere Routing Switch
        SNMP agent.  This version of the SNMP entity component was supported in
        the Unisphere RX 2.3 thru 3.1 system releases."
    STATUS      obsolete
    DESCRIPTION
        "The MIBs supported by the SNMP agent for the SNMP entity application in
        the Unisphere Routing Switch.  These capabilities became obsolete when
        SNMPv2-MIB.sysORTable support was added."
    SUPPORTS    SNMPv2-MIB
        INCLUDES  {
            snmpGroup,
            snmpCommunityGroup,
            snmpObsoleteGroup,
            systemGroup,
            snmpBasicNotificationsGroup }
        VARIATION   sysORLastChange
            ACCESS  not-implemented
            DESCRIPTION
                "The system object resource table is not supported."
        VARIATION   sysORID
            ACCESS  not-implemented
            DESCRIPTION
                "The system object resource table is not supported."
        VARIATION   sysORDescr
            ACCESS  not-implemented
            DESCRIPTION
                "The system object resource table is not supported."
        VARIATION   sysORUpTime
            ACCESS  not-implemented
            DESCRIPTION
                "The system object resource table is not supported."
    SUPPORTS    Unisphere-Data-SNMP-MIB
        INCLUDES  {
            usdSnmpGroup3,
            usdSnmpAuthFailGroup }
    SUPPORTS    SNMP-FRAMEWORK-MIB
        INCLUDES  {
            snmpEngineGroup }
    SUPPORTS    SNMP-MPD-MIB
        INCLUDES  {
            snmpMPDGroup }
    SUPPORTS    SNMP-TARGET-MIB
        INCLUDES  {
            snmpTargetBasicGroup,
            snmpTargetResponseGroup,
            snmpTargetCommandResponderGroup }
        VARIATION   snmpTargetAddrTDomain
            ACCESS      read-only
            DESCRIPTION
                "Unable to create or set elements of the snmpTargetAddrTable."
        VARIATION   snmpTargetAddrTAddress
            ACCESS      read-only
            DESCRIPTION
                "Unable to create or set elements of the snmpTargetAddrTable."
        VARIATION   snmpTargetAddrTimeout
            ACCESS      read-only
            DESCRIPTION
                "Unable to create or set elements of the snmpTargetAddrTable."
        VARIATION   snmpTargetAddrRetryCount
            ACCESS      read-only
            DESCRIPTION
                "Unable to create or set elements of the snmpTargetAddrTable."
        VARIATION   snmpTargetAddrTagList
            ACCESS      read-only
            DESCRIPTION
                "Unable to create or set elements of the snmpTargetAddrTable."
        VARIATION   snmpTargetAddrParams
            ACCESS      read-only
            DESCRIPTION
                "Unable to create or set elements of the snmpTargetAddrTable."
        VARIATION   snmpTargetAddrStorageType
            ACCESS      read-only
            DESCRIPTION
                "Unable to create or set elements of the snmpTargetAddrTable."
        VARIATION   snmpTargetAddrRowStatus
            ACCESS      read-only
            DESCRIPTION
                "Unable to create or set elements of the snmpTargetAddrTable."
        VARIATION   snmpTargetParamsMPModel
            ACCESS      read-only
            DESCRIPTION
                "Unable to create or set elements of the snmpTargetParamsTable."
        VARIATION   snmpTargetParamsSecurityModel
            ACCESS      read-only
            DESCRIPTION
                "Unable to create or set elements of the snmpTargetParamsTable."
        VARIATION   snmpTargetParamsSecurityName
            ACCESS      read-only
            DESCRIPTION
                "Unable to create or set elements of the snmpTargetParamsTable."
        VARIATION   snmpTargetParamsSecurityLevel
            ACCESS      read-only
            DESCRIPTION
                "Unable to create or set elements of the snmpTargetParamsTable."
        VARIATION   snmpTargetParamsStorageType
            ACCESS      read-only
            DESCRIPTION
                "Unable to create or set elements of the snmpTargetParamsTable."
        VARIATION   snmpTargetParamsRowStatus
            ACCESS      read-only
            DESCRIPTION
                "Unable to create or set elements of the snmpTargetParamsTable."
    SUPPORTS    SNMP-NOTIFICATION-MIB
        INCLUDES  {
            snmpNotifyGroup,
            snmpNotifyFilterGroup }
        VARIATION   snmpNotifyTag
            ACCESS      read-only
            DESCRIPTION
                "Unable to create or set elements of the snmpNotifyTable."
        VARIATION   snmpNotifyType
            ACCESS      read-only
            DESCRIPTION
                "Unable to create or set elements of the snmpNotifyTable."
        VARIATION   snmpNotifyStorageType
            ACCESS      read-only
            DESCRIPTION
                "Unable to create or set elements of the snmpNotifyTable."
        VARIATION   snmpNotifyRowStatus
            ACCESS      read-only
            DESCRIPTION
                "Unable to create or set elements of the snmpNotifyTable."
        VARIATION   snmpNotifyFilterProfileName
            ACCESS      read-only
            DESCRIPTION
                "Unable to create or set elements of the
                snmpNotifyFilterProfileTable."
        VARIATION   snmpNotifyFilterProfileStorType
            ACCESS      read-only
            DESCRIPTION
                "Unable to create or set elements of the
                snmpNotifyFilterProfileTable."
        VARIATION   snmpNotifyFilterProfileRowStatus
            ACCESS      read-only
            DESCRIPTION
                "Unable to create or set elements of the
                snmpNotifyFilterProfileTable."
        VARIATION   snmpNotifyFilterMask
            ACCESS      read-only
            DESCRIPTION
                "Unable to create or set elements of the snmpNotifyFilterTable."
        VARIATION   snmpNotifyFilterType
            ACCESS      read-only
            DESCRIPTION
                "Unable to create or set elements of the snmpNotifyFilterTable."
        VARIATION   snmpNotifyFilterStorageType
            ACCESS      read-only
            DESCRIPTION
                "Unable to create or set elements of the snmpNotifyFilterTable."
        VARIATION   snmpNotifyFilterRowStatus
            ACCESS      read-only
            DESCRIPTION
                "Unable to create or set elements of the snmpNotifyFilterTable."
    SUPPORTS    SNMP-USER-BASED-SM-MIB
        INCLUDES  {
            usmMIBBasicGroup }
    SUPPORTS    SNMP-VIEW-BASED-ACM-MIB
        INCLUDES  {
            vacmBasicGroup }
    ::= { usdSnmpAgent 3 }

usdSnmpAgentV4 AGENT-CAPABILITIES
    PRODUCT-RELEASE
        "Version 4 of the SNMP entity component of the Unisphere Routing Switch
        SNMP agent.  This version of the SNMP entity component was supported in
        the Unisphere RX 3.2 system release."
    STATUS      obsolete
    DESCRIPTION
        "The MIBs supported by the SNMP agent for the SNMP entity application in
        the Unisphere Routing Switch.  These capabilities became obsolete when
        SNMPv2-MIB.snmpSetGroup support was added and new Unisphere SNMP MIB
        objects were added supporting interface compress, trap severities and
        trap severity filtering."
    SUPPORTS    SNMPv2-MIB
        INCLUDES  {
            snmpGroup,
            snmpCommunityGroup,
            snmpObsoleteGroup,
            systemGroup,
            snmpBasicNotificationsGroup }
    SUPPORTS    Unisphere-Data-SNMP-MIB
        INCLUDES  {
            usdSnmpGroup3,
            usdSnmpAuthFailGroup }
    SUPPORTS    SNMP-FRAMEWORK-MIB
        INCLUDES  {
            snmpEngineGroup }
    SUPPORTS    SNMP-MPD-MIB
        INCLUDES  {
            snmpMPDGroup }
    SUPPORTS    SNMP-TARGET-MIB
        INCLUDES  {
            snmpTargetBasicGroup,
            snmpTargetResponseGroup,
            snmpTargetCommandResponderGroup }
        VARIATION   snmpTargetAddrTDomain
            ACCESS      read-only
            DESCRIPTION
                "Unable to create or set elements of the snmpTargetAddrTable."
        VARIATION   snmpTargetAddrTAddress
            ACCESS      read-only
            DESCRIPTION
                "Unable to create or set elements of the snmpTargetAddrTable."
        VARIATION   snmpTargetAddrTimeout
            ACCESS      read-only
            DESCRIPTION
                "Unable to create or set elements of the snmpTargetAddrTable."
        VARIATION   snmpTargetAddrRetryCount
            ACCESS      read-only
            DESCRIPTION
                "Unable to create or set elements of the snmpTargetAddrTable."
        VARIATION   snmpTargetAddrTagList
            ACCESS      read-only
            DESCRIPTION
                "Unable to create or set elements of the snmpTargetAddrTable."
        VARIATION   snmpTargetAddrParams
            ACCESS      read-only
            DESCRIPTION
                "Unable to create or set elements of the snmpTargetAddrTable."
        VARIATION   snmpTargetAddrStorageType
            ACCESS      read-only
            DESCRIPTION
                "Unable to create or set elements of the snmpTargetAddrTable."
        VARIATION   snmpTargetAddrRowStatus
            ACCESS      read-only
            DESCRIPTION
                "Unable to create or set elements of the snmpTargetAddrTable."
        VARIATION   snmpTargetParamsMPModel
            ACCESS      read-only
            DESCRIPTION
                "Unable to create or set elements of the snmpTargetParamsTable."
        VARIATION   snmpTargetParamsSecurityModel
            ACCESS      read-only
            DESCRIPTION
                "Unable to create or set elements of the snmpTargetParamsTable."
        VARIATION   snmpTargetParamsSecurityName
            ACCESS      read-only
            DESCRIPTION
                "Unable to create or set elements of the snmpTargetParamsTable."
        VARIATION   snmpTargetParamsSecurityLevel
            ACCESS      read-only
            DESCRIPTION
                "Unable to create or set elements of the snmpTargetParamsTable."
        VARIATION   snmpTargetParamsStorageType
            ACCESS      read-only
            DESCRIPTION
                "Unable to create or set elements of the snmpTargetParamsTable."
        VARIATION   snmpTargetParamsRowStatus
            ACCESS      read-only
            DESCRIPTION
                "Unable to create or set elements of the snmpTargetParamsTable."
    SUPPORTS    SNMP-NOTIFICATION-MIB
        INCLUDES  {
            snmpNotifyGroup,
            snmpNotifyFilterGroup }
        VARIATION   snmpNotifyTag
            ACCESS      read-only
            DESCRIPTION
                "Unable to create or set elements of the snmpNotifyTable."
        VARIATION   snmpNotifyType
            ACCESS      read-only
            DESCRIPTION
                "Unable to create or set elements of the snmpNotifyTable."
        VARIATION   snmpNotifyStorageType
            ACCESS      read-only
            DESCRIPTION
                "Unable to create or set elements of the snmpNotifyTable."
        VARIATION   snmpNotifyRowStatus
            ACCESS      read-only
            DESCRIPTION
                "Unable to create or set elements of the snmpNotifyTable."
        VARIATION   snmpNotifyFilterProfileName
            ACCESS      read-only
            DESCRIPTION
                "Unable to create or set elements of the
                snmpNotifyFilterProfileTable."
        VARIATION   snmpNotifyFilterProfileStorType
            ACCESS      read-only
            DESCRIPTION
                "Unable to create or set elements of the
                snmpNotifyFilterProfileTable."
        VARIATION   snmpNotifyFilterProfileRowStatus
            ACCESS      read-only
            DESCRIPTION
                "Unable to create or set elements of the
                snmpNotifyFilterProfileTable."
        VARIATION   snmpNotifyFilterMask
            ACCESS      read-only
            DESCRIPTION
                "Unable to create or set elements of the snmpNotifyFilterTable."
        VARIATION   snmpNotifyFilterType
            ACCESS      read-only
            DESCRIPTION
                "Unable to create or set elements of the snmpNotifyFilterTable."
        VARIATION   snmpNotifyFilterStorageType
            ACCESS      read-only
            DESCRIPTION
                "Unable to create or set elements of the snmpNotifyFilterTable."
        VARIATION   snmpNotifyFilterRowStatus
            ACCESS      read-only
            DESCRIPTION
                "Unable to create or set elements of the snmpNotifyFilterTable."
    SUPPORTS    SNMP-USER-BASED-SM-MIB
        INCLUDES  {
            usmMIBBasicGroup }
    SUPPORTS    SNMP-VIEW-BASED-ACM-MIB
        INCLUDES  {
            vacmBasicGroup }
    ::= { usdSnmpAgent 4 }

usdSnmpAgentV5 AGENT-CAPABILITIES
    PRODUCT-RELEASE
        "Version 5 of the SNMP entity component of the Unisphere Routing Switch
        SNMP agent.  This version of the SNMP entity component was supported in
        the Unisphere RX 3.3 system releases."
    STATUS      obsolete
    DESCRIPTION
        "The MIBs supported by the SNMP agent for the SNMP entity application in
        the Unisphere Routing Switch.  These capabilities became obsolete when
        support for proxy enable/disable was added."
    SUPPORTS    SNMPv2-MIB
        INCLUDES  {
            snmpGroup,
            snmpCommunityGroup,
            snmpSetGroup,
            snmpObsoleteGroup,
            systemGroup,
            snmpBasicNotificationsGroup }
    SUPPORTS    Unisphere-Data-SNMP-MIB
        INCLUDES  {
            usdSnmpGeneralGroup,
            usdSnmpAccessGroup,
            usdSnmpTrapGroup,
            usdSnmpAuthFailGroup }
    SUPPORTS    SNMP-FRAMEWORK-MIB
        INCLUDES  {
            snmpEngineGroup }
    SUPPORTS    SNMP-MPD-MIB
        INCLUDES  {
            snmpMPDGroup }
    SUPPORTS    SNMP-TARGET-MIB
        INCLUDES  {
            snmpTargetBasicGroup,
            snmpTargetResponseGroup,
            snmpTargetCommandResponderGroup }
        VARIATION   snmpTargetAddrTDomain
            ACCESS      read-only
            DESCRIPTION
                "Unable to create or set elements of the snmpTargetAddrTable."
        VARIATION   snmpTargetAddrTAddress
            ACCESS      read-only
            DESCRIPTION
                "Unable to create or set elements of the snmpTargetAddrTable."
        VARIATION   snmpTargetAddrTimeout
            ACCESS      read-only
            DESCRIPTION
                "Unable to create or set elements of the snmpTargetAddrTable."
        VARIATION   snmpTargetAddrRetryCount
            ACCESS      read-only
            DESCRIPTION
                "Unable to create or set elements of the snmpTargetAddrTable."
        VARIATION   snmpTargetAddrTagList
            ACCESS      read-only
            DESCRIPTION
                "Unable to create or set elements of the snmpTargetAddrTable."
        VARIATION   snmpTargetAddrParams
            ACCESS      read-only
            DESCRIPTION
                "Unable to create or set elements of the snmpTargetAddrTable."
        VARIATION   snmpTargetAddrStorageType
            ACCESS      read-only
            DESCRIPTION
                "Unable to create or set elements of the snmpTargetAddrTable."
        VARIATION   snmpTargetAddrRowStatus
            ACCESS      read-only
            DESCRIPTION
                "Unable to create or set elements of the snmpTargetAddrTable."
        VARIATION   snmpTargetParamsMPModel
            ACCESS      read-only
            DESCRIPTION
                "Unable to create or set elements of the snmpTargetParamsTable."
        VARIATION   snmpTargetParamsSecurityModel
            ACCESS      read-only
            DESCRIPTION
                "Unable to create or set elements of the snmpTargetParamsTable."
        VARIATION   snmpTargetParamsSecurityName
            ACCESS      read-only
            DESCRIPTION
                "Unable to create or set elements of the snmpTargetParamsTable."
        VARIATION   snmpTargetParamsSecurityLevel
            ACCESS      read-only
            DESCRIPTION
                "Unable to create or set elements of the snmpTargetParamsTable."
        VARIATION   snmpTargetParamsStorageType
            ACCESS      read-only
            DESCRIPTION
                "Unable to create or set elements of the snmpTargetParamsTable."
        VARIATION   snmpTargetParamsRowStatus
            ACCESS      read-only
            DESCRIPTION
                "Unable to create or set elements of the snmpTargetParamsTable."
    SUPPORTS    SNMP-NOTIFICATION-MIB
        INCLUDES  {
            snmpNotifyGroup,
            snmpNotifyFilterGroup }
        VARIATION   snmpNotifyTag
            ACCESS      read-only
            DESCRIPTION
                "Unable to create or set elements of the snmpNotifyTable."
        VARIATION   snmpNotifyType
            ACCESS      read-only
            DESCRIPTION
                "Unable to create or set elements of the snmpNotifyTable."
        VARIATION   snmpNotifyStorageType
            ACCESS      read-only
            DESCRIPTION
                "Unable to create or set elements of the snmpNotifyTable."
        VARIATION   snmpNotifyRowStatus
            ACCESS      read-only
            DESCRIPTION
                "Unable to create or set elements of the snmpNotifyTable."
        VARIATION   snmpNotifyFilterProfileName
            ACCESS      read-only
            DESCRIPTION
                "Unable to create or set elements of the
                snmpNotifyFilterProfileTable."
        VARIATION   snmpNotifyFilterProfileStorType
            ACCESS      read-only
            DESCRIPTION
                "Unable to create or set elements of the
                snmpNotifyFilterProfileTable."
        VARIATION   snmpNotifyFilterProfileRowStatus
            ACCESS      read-only
            DESCRIPTION
                "Unable to create or set elements of the
                snmpNotifyFilterProfileTable."
        VARIATION   snmpNotifyFilterMask
            ACCESS      read-only
            DESCRIPTION
                "Unable to create or set elements of the snmpNotifyFilterTable."
        VARIATION   snmpNotifyFilterType
            ACCESS      read-only
            DESCRIPTION
                "Unable to create or set elements of the snmpNotifyFilterTable."
        VARIATION   snmpNotifyFilterStorageType
            ACCESS      read-only
            DESCRIPTION
                "Unable to create or set elements of the snmpNotifyFilterTable."
        VARIATION   snmpNotifyFilterRowStatus
            ACCESS      read-only
            DESCRIPTION
                "Unable to create or set elements of the snmpNotifyFilterTable."
    SUPPORTS    SNMP-USER-BASED-SM-MIB
        INCLUDES  {
            usmMIBBasicGroup }
    SUPPORTS    SNMP-VIEW-BASED-ACM-MIB
        INCLUDES  {
            vacmBasicGroup }
    ::= { usdSnmpAgent 5 }

usdSnmpAgentV6 AGENT-CAPABILITIES
    PRODUCT-RELEASE
        "Version 6 of the SNMP entity component of the Unisphere Routing Switch
        SNMP agent.  This version of the SNMP entity component is supported in
        the Unisphere RX 3.4 and subsequent system releases."
    STATUS      current
    DESCRIPTION
        "The MIBs supported by the SNMP agent for the SNMP entity application in
        the Unisphere Routing Switch."
    SUPPORTS    SNMPv2-MIB
        INCLUDES  {
            snmpGroup,
            snmpCommunityGroup,
            snmpSetGroup,
            snmpObsoleteGroup,
            systemGroup,
            snmpBasicNotificationsGroup }
    SUPPORTS    Unisphere-Data-SNMP-MIB
        INCLUDES  {
            usdSnmpGeneralGroup2,
            usdSnmpAccessGroup,
            usdSnmpTrapGroup,
            usdSnmpAuthFailGroup }
    SUPPORTS    SNMP-FRAMEWORK-MIB
        INCLUDES  {
            snmpEngineGroup }
    SUPPORTS    SNMP-MPD-MIB
        INCLUDES  {
            snmpMPDGroup }
    SUPPORTS    SNMP-TARGET-MIB
        INCLUDES  {
            snmpTargetBasicGroup,
            snmpTargetResponseGroup,
            snmpTargetCommandResponderGroup }
        VARIATION   snmpTargetAddrTDomain
            ACCESS      read-only
            DESCRIPTION
                "Unable to create or set elements of the snmpTargetAddrTable."
        VARIATION   snmpTargetAddrTAddress
            ACCESS      read-only
            DESCRIPTION
                "Unable to create or set elements of the snmpTargetAddrTable."
        VARIATION   snmpTargetAddrTimeout
            ACCESS      read-only
            DESCRIPTION
                "Unable to create or set elements of the snmpTargetAddrTable."
        VARIATION   snmpTargetAddrRetryCount
            ACCESS      read-only
            DESCRIPTION
                "Unable to create or set elements of the snmpTargetAddrTable."
        VARIATION   snmpTargetAddrTagList
            ACCESS      read-only
            DESCRIPTION
                "Unable to create or set elements of the snmpTargetAddrTable."
        VARIATION   snmpTargetAddrParams
            ACCESS      read-only
            DESCRIPTION
                "Unable to create or set elements of the snmpTargetAddrTable."
        VARIATION   snmpTargetAddrStorageType
            ACCESS      read-only
            DESCRIPTION
                "Unable to create or set elements of the snmpTargetAddrTable."
        VARIATION   snmpTargetAddrRowStatus
            ACCESS      read-only
            DESCRIPTION
                "Unable to create or set elements of the snmpTargetAddrTable."
        VARIATION   snmpTargetParamsMPModel
            ACCESS      read-only
            DESCRIPTION
                "Unable to create or set elements of the snmpTargetParamsTable."
        VARIATION   snmpTargetParamsSecurityModel
            ACCESS      read-only
            DESCRIPTION
                "Unable to create or set elements of the snmpTargetParamsTable."
        VARIATION   snmpTargetParamsSecurityName
            ACCESS      read-only
            DESCRIPTION
                "Unable to create or set elements of the snmpTargetParamsTable."
        VARIATION   snmpTargetParamsSecurityLevel
            ACCESS      read-only
            DESCRIPTION
                "Unable to create or set elements of the snmpTargetParamsTable."
        VARIATION   snmpTargetParamsStorageType
            ACCESS      read-only
            DESCRIPTION
                "Unable to create or set elements of the snmpTargetParamsTable."
        VARIATION   snmpTargetParamsRowStatus
            ACCESS      read-only
            DESCRIPTION
                "Unable to create or set elements of the snmpTargetParamsTable."
    SUPPORTS    SNMP-NOTIFICATION-MIB
        INCLUDES  {
            snmpNotifyGroup,
            snmpNotifyFilterGroup }
        VARIATION   snmpNotifyTag
            ACCESS      read-only
            DESCRIPTION
                "Unable to create or set elements of the snmpNotifyTable."
        VARIATION   snmpNotifyType
            ACCESS      read-only
            DESCRIPTION
                "Unable to create or set elements of the snmpNotifyTable."
        VARIATION   snmpNotifyStorageType
            ACCESS      read-only
            DESCRIPTION
                "Unable to create or set elements of the snmpNotifyTable."
        VARIATION   snmpNotifyRowStatus
            ACCESS      read-only
            DESCRIPTION
                "Unable to create or set elements of the snmpNotifyTable."
        VARIATION   snmpNotifyFilterProfileName
            ACCESS      read-only
            DESCRIPTION
                "Unable to create or set elements of the
                snmpNotifyFilterProfileTable."
        VARIATION   snmpNotifyFilterProfileStorType
            ACCESS      read-only
            DESCRIPTION
                "Unable to create or set elements of the
                snmpNotifyFilterProfileTable."
        VARIATION   snmpNotifyFilterProfileRowStatus
            ACCESS      read-only
            DESCRIPTION
                "Unable to create or set elements of the
                snmpNotifyFilterProfileTable."
        VARIATION   snmpNotifyFilterMask
            ACCESS      read-only
            DESCRIPTION
                "Unable to create or set elements of the snmpNotifyFilterTable."
        VARIATION   snmpNotifyFilterType
            ACCESS      read-only
            DESCRIPTION
                "Unable to create or set elements of the snmpNotifyFilterTable."
        VARIATION   snmpNotifyFilterStorageType
            ACCESS      read-only
            DESCRIPTION
                "Unable to create or set elements of the snmpNotifyFilterTable."
        VARIATION   snmpNotifyFilterRowStatus
            ACCESS      read-only
            DESCRIPTION
                "Unable to create or set elements of the snmpNotifyFilterTable."
    SUPPORTS    SNMP-USER-BASED-SM-MIB
        INCLUDES  {
            usmMIBBasicGroup }
    SUPPORTS    SNMP-VIEW-BASED-ACM-MIB
        INCLUDES  {
            vacmBasicGroup }
    ::= { usdSnmpAgent 6 }

END
