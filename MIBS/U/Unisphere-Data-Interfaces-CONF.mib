-- *****************************************************************************
-- Unisphere-Data-Interfaces-CONF
--
-- SNMP Agent Capabilities definitions for the Interfaces MIBs.
--
-- Copyright (c) 2001 Unisphere Networks, Inc.  All rights reserved.
-- *****************************************************************************

Unisphere-Data-Interfaces-CONF DEFINITIONS ::= BEGIN

IMPORTS
    MODULE-IDENTITY
        FROM SNMPv2-SMI
    AGENT-CAPABILITIES
        FROM SNMPv2-CONF
    usDataAgents
        FROM Unisphere-Data-Agents
    ifGeneralInformationGroup,
    ifFixedLengthGroup,
    ifHCFixedLengthGroup,
    ifPacketGroup,
    ifHCPacketGroup,
    ifVHCPacketGroup,
    ifStackGroup2,
    ifCounterDiscontinuityGroup,
    linkUpDownNotificationsGroup,
    ifAlias,
    ifStackStatus
        FROM IF-MIB
    usdIfGroup,
    usdIfInvStackGroup
        FROM Unisphere-Data-IF-MIB;

usdInterfacesAgent MODULE-IDENTITY
    LAST-UPDATED "200104271424Z"  -- 27-Apr-01 10:24 AM EDT
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the Interfaces component of the
        SNMP agent in the Unisphere Routing Switch family of products."
    -- Revision History
    REVISION    "200104271424Z"  -- 27-Apr-01 10:24 AM EDT  - RX 3.2
    DESCRIPTION
        "The initial release of this management information module."
    ::= { usDataAgents 20 }

usdInterfacesAgentV1 AGENT-CAPABILITIES
    PRODUCT-RELEASE
        "Version 1 of the Interfaces component of the Unisphere Routing Switch
        SNMP agent.  This version of the Interfaces component is supported in
        the Unisphere RX 1.0 and subsequent system releases."
    STATUS      current
    DESCRIPTION
        "The MIBs supported by the SNMP agent for the Interfaces application in
        the Unisphere Routing Switch."

    SUPPORTS    IF-MIB
        INCLUDES  {
            ifGeneralInformationGroup,
            ifFixedLengthGroup,
            ifHCFixedLengthGroup,
            ifPacketGroup,
            ifHCPacketGroup,
            ifVHCPacketGroup,
            ifStackGroup2,
            ifCounterDiscontinuityGroup,
            linkUpDownNotificationsGroup }
        VARIATION   ifAlias
            DESCRIPTION
                "This Agent limits the lenght of an alias to 15 octets excect
                for IP interfaces, which may have a lenght of up to 255 octets."
        VARIATION   ifStackStatus
            ACCESS      read-only
            DESCRIPTION
                "The ifStackTable cannot be modified with this Agent."

    SUPPORTS    Unisphere-Data-IF-MIB
        INCLUDES  {
            usdIfGroup,
            usdIfInvStackGroup }

    ::= { usdInterfacesAgent 1 }

END
