-- *****************************************************************************
-- Unisphere-Data-MPLS-CONF
--
-- SNMP Agent Capabilities definitions for the MPLS MIB.
--
-- Copyright (c) 2001 Unisphere Networks, Inc.  All rights reserved.
-- *****************************************************************************

Unisphere-Data-MPLS-CONF DEFINITIONS ::= BEGIN

IMPORTS
    MODULE-IDENTITY
        FROM SNMPv2-SMI
    AGENT-CAPABILITIES
        FROM SNMPv2-CONF
    usDataAgents
        FROM Unisphere-Data-Agents
    usdMplsLsrGlobalConfGroup, usdMplsMajorLayerConfGroup,
    usdMplsMinorLayerConfGroup, usdMplsTunnelProfileConfGroup,
    usdMplsExplicitPathConfGroup
        FROM Unisphere-Data-MPLS-MIB;

usdMplsAgent MODULE-IDENTITY
    LAST-UPDATED "200112052141Z"  -- 05-Dec-01 04:41 PM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the MultiProtocol Label
        Switching (MPLS) component of the SNMP agent in the Unisphere Routing
        Switch family of products."
    -- Revision History
    REVISION    "200112052141Z"  -- 05-Dec-01 04:41 PM EST  - RX 4.0
    DESCRIPTION
        "The initial release of this management information module."
    ::= { usDataAgents 51 }


-- *****************************************************************************
-- MPLS SNMP Agent Capabilities definitions
-- *****************************************************************************

usdMplsAgentV1 AGENT-CAPABILITIES
    PRODUCT-RELEASE
        "Version 1 of the MultiProtocol Label Switching (MPLS) component of the
        Unisphere Routing Switch SNMP agent.  This version of the MPLS component
        is supported in the Unisphere RX 4.0 and subsequent system releases."
    STATUS      current
    DESCRIPTION
        "The MIB supported by the SNMP agent for the MPLS application in the
        Unisphere Routing Switch."
    SUPPORTS    Unisphere-Data-MPLS-MIB
        INCLUDES  {
            usdMplsLsrGlobalConfGroup,
            usdMplsMajorLayerConfGroup,
            usdMplsMinorLayerConfGroup,
            usdMplsTunnelProfileConfGroup,
            usdMplsExplicitPathConfGroup }
    ::= { usdMplsAgent 1 }

END
