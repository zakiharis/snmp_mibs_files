-- *****************************************************************************
-- Unisphere-Data-SNMP-MIB
--
-- Unisphere Networks Inc. Enterprise MIB
-- SNMP MIB
--
-- Copyright (c) 1998, 1999 Redstone Communications, Incorporated.
-- Copyright (c) 1999, 2002 Unisphere Networks, Incorporated.
-- All Rights Reserved.
-- *****************************************************************************

Unisphere-Data-SNMP-MIB DEFINITIONS ::= BEGIN

IMPORTS
    MODULE-IDENTITY, OBJECT-TYPE, Integer32, Counter32, IpAddress
        FROM SNMPv2-SMI
    TEXTUAL-CONVENTION, RowStatus, TruthValue
        FROM SNMPv2-TC
    MODULE-COMPLIANCE, OBJECT-GROUP
        FROM SNMPv2-CONF
    UsdEnable
        FROM Unisphere-Data-TC
    usDataMibs
        FROM Unisphere-Data-MIBs;

usdSnmpMIB  MODULE-IDENTITY
    LAST-UPDATED "200208152018Z"  -- 15-Aug-02 04:18 PM EDT
    ORGANIZATION "Juniper Networks, Inc."
    CONTACT-INFO
        "       Juniper Networks, Inc.
        Postal: 10 Technology Park Drive
                Westford, MA  01886
                USA
        Tel:    +1 978 589 5800
        Email:  mib@UnisphereNetworks.com"
    DESCRIPTION
        "MIB objects for configuring SNMP-based management access into Juniper
        routing switch products."
    -- Revision History
    REVISION    "200208152018Z"  -- 15-Aug-02 04:18 PM EDT  - RX 4.0
    DESCRIPTION
        "Added support for SNMPv3 trap."
    REVISION    "200208141909Z"  -- 14-Aug-02 03:09 PM EDT  - RX 3.4
    DESCRIPTION
        "Added support for proxy enable/disable feature.
         Added support for the VRRP trap catagory."
    REVISION    "200111071709Z"  -- 07-Nov-01 12:09 PM EST  - RX 3.3
    DESCRIPTION
        "Added support for interface compress.
            New textual convention:
                UsdSnmpIntfCompRestrictedMask
            New objects:
                usdSnmpIntfCompCompressed
                usdSnmpIntfCompEnhanced
                usdSnmpIntfCompEnhancedDisplay
                usdSnmpIntfCompRestricted
                usdSnmpIntfCompRestrictedDisplay
            Obsoleted object:
                usdSnmpInterfaceMode
        Added support for trap severities and trap severity filtering at the
        global and host levels.
            New textual convention:
                UsdTrapSeverity
            New objects:
                usdSnmpTrapHostDiscards
                usdSnmpTrapHostSeverityFilter
                usdSnmpTrapTrapSeverity
                usdSnmpTrapGlobalDiscards
                usdSnmpTrapGlobalSeverityFilter"
    REVISION    "200111071500Z"  -- 07-Nov-01 10:00 AM EST  - RX 3.2
    DESCRIPTION
        "Added support for DVMRP and local address pool and ATM ping trap
        categories."
    REVISION    "200105081206Z"  -- 08-May-01 08:06 AM EDT  - RX 3.0
    DESCRIPTION
        "Make it SMIv2 conformant."
    REVISION    "200008020000Z"  --  2-Aug-00               - RX 2.3
    DESCRIPTION
        "Added usdSnmpInterfaceMode."
    REVISION    "200005090000Z"  --  9-May-00               - RX 2.0
    DESCRIPTION
        "Added View support.
         Added Named Access List support."
    REVISION    "9902170000Z"    -- 17-Feb-99               - RX 1.0
    DESCRIPTION
        "Initial version of this MIB module."
    ::= { usDataMibs 16 }

-- ++++++++++++++++++++++++++++++++++++++++++++++++++++++++++++++++++++++
-- Textual conventions
-- ++++++++++++++++++++++++++++++++++++++++++++++++++++++++++++++++++++++

UsdSnmpCommunityName ::= TEXTUAL-CONVENTION
    DISPLAY-HINT "31a"
    STATUS      current
    DESCRIPTION
        "An SNMP community name.  Represents textual information taken from the
        NVT ASCII character set.

        The character repertoire of the string is restricted to printable,
        non-whitespace characters."
    REFERENCE
        "RFC 854: NVT ASCII character set.  See SNMPv2-TC.DisplayString
        DESCRIPTION for a summary."
    SYNTAX      OCTET STRING (SIZE(1..31))

UsdSnmpAccessListName ::= TEXTUAL-CONVENTION
    DISPLAY-HINT "31a"
    STATUS      current
    DESCRIPTION
        "An IP Access List name.  Represents textual information taken from the
        NVT ASCII character set.

        The character repertoire of the string is restricted to printable,
        non-whitespace characters."
    REFERENCE
        "RFC 854: NVT ASCII character set.  See SNMPv2-TC.DisplayString
        DESCRIPTION for a summary."
    SYNTAX      OCTET STRING (SIZE(0..31))

UsdSnmpTrapMask ::= TEXTUAL-CONVENTION
    STATUS      current
    DESCRIPTION
        "This octet string is interpreted as a bit mask, in which each bit
        corresponds to a category of SNMP trap.

        Bit definitions are as follows, where bit 31 is the most significant bit
        of the first octet, and bit 0 is the least significant bit of the fourth
        octet:

        Bit     Category
        -----   -----------------------------------------------
         0      SNMP standard coldStart/warmStart/authenticationFailure traps
         1      Standard linkUp/linkDown traps
         2      Platform inventory traps
         3      Environment (power, temperature, fan and memory) traps
         4      Accounting (bulk statistics) traps
         5      File transfer status trap
         6      BGP traps
         7      Log configuration traps
         8      CLI security alert trap
         9      Ping traps
        10      OSPF traps
        11      TraceRoute traps
        12      Standard DVMRP traps
        13      Proprietary DVMRP trap
        14      Local address pool traps
        15      ATM ping traps
        16      VRRP traps
        17-31   Undefined."
    SYNTAX      OCTET STRING (SIZE(4))

UsdTrapSeverity ::= TEXTUAL-CONVENTION
    STATUS      current
    DESCRIPTION
        "The set of trap severity values:"
    SYNTAX      INTEGER {
                    trapEmergency(0),     -- system is unusable
                    trapAlert(1),         -- action must be taken immediately
                    trapCritical(2),      -- critical conditions
                    trapError(3),         -- error conditions
                    trapWarning(4),       -- warning conditions
                    trapNotice(5),        -- normal but significant condition
                    trapInformational(6), -- informational messages
                    trapDebug(7)          -- debug-level messages
                }

UsdSnmpIntfCompRestrictedMask ::= TEXTUAL-CONVENTION
    STATUS      current
    DESCRIPTION
        "This octet string is interpreted as a bit mask, in which each bit
        corresponds to an interface restriction.

        The DESCRIPTION clause of a MIB object having this SYNTAX should specify
        the semantics of bit values '1' and '0'.

        Bit definitions are as follows, where bit 31 is the most significant bit
        of the first octet, and bit 0 is the least significant bit of the fourth
        octet:

        Bit     interface restriction
        -----   -----------------------------------------------
         0      ifAdminStatus Down
         1-31   Undefined."
    SYNTAX      OCTET STRING (SIZE(4))

-- ++++++++++++++++++++++++++++++++++++++++++++++++++++++++++++++++++++++
-- MIB Structure
-- ++++++++++++++++++++++++++++++++++++++++++++++++++++++++++++++++++++++

usdSnmpObjects       OBJECT IDENTIFIER ::= { usdSnmpMIB 1 }
usdSnmpConformance   OBJECT IDENTIFIER ::= { usdSnmpMIB 2 }

-- ++++++++++++++++++++++++++++++++++++++++++++++++++++++++++++++++++++++
-- Managed objects
-- ++++++++++++++++++++++++++++++++++++++++++++++++++++++++++++++++++++++

--
-- Object Groups
--
usdSnmpGeneral           OBJECT IDENTIFIER ::= { usdSnmpObjects 1 }
usdSnmpInterfaceCompress OBJECT IDENTIFIER ::= { usdSnmpGeneral 3 }
usdSnmpCommunity         OBJECT IDENTIFIER ::= { usdSnmpObjects 2 }
usdSnmpTrap              OBJECT IDENTIFIER ::= { usdSnmpObjects 3 }
usdSnmpAuthFailId        OBJECT IDENTIFIER ::= { usdSnmpObjects 4 }


--
-- General objects
--
usdSnmpMaxPduSize OBJECT-TYPE
    SYNTAX      Integer32 (484..8192)
    MAX-ACCESS  read-write
    STATUS      current
    DESCRIPTION
        "The maximum sized SNMP PDU, in bytes, that this agent is capable of
        handling.  The default is 1500 bytes.  The possibility of IP
        fragmentation should be considered when setting this object to large
        values."
    ::= { usdSnmpGeneral 1 }

usdSnmpInterfaceMode OBJECT-TYPE
    SYNTAX      INTEGER {
                    usdSnmpInterfaceModeVerbose(1),
                    usdSnmpInterfaceModeCompress(2),
                    usdSnmpInterfaceModeEnhanced(3)
                }
    MAX-ACCESS  read-write
    STATUS      obsolete
    DESCRIPTION
        "The interface table mode for the SNMP agent(s) associated with this
        system.
         usdSnmpInterfaceModeVerbose(1)  - the standard ifTable, ifXTable and
                                          ifStackTable contain entries for
                                          every standard and proprietary
                                          interface type supported by this
                                          system.

         usdSnmpInterfaceModeCompress(2) - the standard ifTable, ifXTable and
                                          ifStackTable contain a subset of
                                          interface types.  Certain interface
                                          types like HDLC and IP and others
                                          are excluded from the standard tables
                                          but are manageable from proprietary
                                          MIBs.

         usdSnmpInterfaceModeEnhanced(3) - the standard ifTable, ifXTable and
                                          ifStackTable contain a subset of
                                          interface types.  Enhanced mode cannot
                                          by configured at this time via SNMP.
                                          Attempts to set this value will fail.
         "
    ::= { usdSnmpGeneral 2 }

usdSnmpProxyStatus  OBJECT-TYPE
    SYNTAX      UsdEnable
    MAX-ACCESS  read-write
    STATUS      current
    DESCRIPTION
        "Enable/disable SNMP proxy between virtual routers."
    DEFVAL    { enable }
    ::= { usdSnmpGeneral 4 }

usdSnmpIntfCompCompressed OBJECT-TYPE
    SYNTAX      TruthValue
    MAX-ACCESS  read-write
    STATUS      current
    DESCRIPTION
        "true(1)   - the standard ifTable, ifXTable and ifStackTable contain a
                     subset of interface types.  Certain interface types like
                     HDLC and IP and others are excluded from the standard
                     tables but are manageable from proprietary MIBs.

         false(2)  - the standard ifTable, ifXTable and ifStackTable contain
                     entries for every standard and proprietary interface type
                     supported by this system.
         "
    DEFVAL    { false }
    ::= { usdSnmpInterfaceCompress 1 }

usdSnmpIntfCompEnhanced OBJECT-TYPE
    SYNTAX      OCTET STRING (SIZE(5..16))
    MAX-ACCESS  read-write
    STATUS      current
    DESCRIPTION
        "This object governs which interface types are visable to SNMP
        management clients that use the standard ifTable, ifXTable and
        ifStackTable.  The object is a variable length octet string that is
        interpreted as a bit mask.  Each bit respresents a specific Unisphere
        interface type that can be included or excluded in the standard
        interface tables.

        For each bit position in each octet of the string, a '1' or '0'
        indicates the corresponding interface type is either removed
        (compressed) from the standard interface MIB tables, or included
        respectively.

        Individual bit definitions follow the UsdIfType convention defined in the
        Unisphere-Data-IF-MIB.  For example, ip(0) and ppp(1) correspond to bit
        definitions 0 and 1 respectively.

        In each octet, bit 0 is least significant, bit 7 most significant."
    REFERENCE
        "rstc.mi2 - Unisphere-Data-IF-MIB.UsdIfType"
    ::= { usdSnmpInterfaceCompress 2 }

usdSnmpIntfCompEnhancedDisplay OBJECT-TYPE
    SYNTAX      OCTET STRING (SIZE(1..1000))
    MAX-ACCESS  read-only
    STATUS      current
    DESCRIPTION
        "This object displays the excluded interface types in human readable
        form.  Three dots (...) at the end of display string indicates that the
        output has been truncated.  "
    ::= { usdSnmpInterfaceCompress 3 }

usdSnmpIntfCompRestricted OBJECT-TYPE
    SYNTAX      UsdSnmpIntfCompRestrictedMask
    MAX-ACCESS  read-write
    STATUS      current
    DESCRIPTION
        "This object governs which interface instances appear to SNMP management
        clients that use the standard ifTable, ifXTable and ifStackTable.  The
        control is based on a set of interface restrictions defined by
        UsdSnmpInterfaceModeRestrictedMask.

        For each bit position in each octet of the string, a '1' or '0' controls
        whether an interface instance that matches the restriction is removed or
        included in the standard interface MIB tables.  For example, setting the
        value of this object to 1 will remove all interface instances with an
        ifAdminStatus(2).

        In each octet, bit 0 is least significant, bit 7 most significant."
    ::= { usdSnmpInterfaceCompress 4 }

usdSnmpIntfCompRestrictedDisplay OBJECT-TYPE
    SYNTAX      OCTET STRING (SIZE(1..100))
    MAX-ACCESS  read-only
    STATUS      current
    DESCRIPTION
        "This object displays the restrictions in human readable form.  Three
        dots (...) at the end of display string indicates that the output has
        been truncated."
    ::= { usdSnmpInterfaceCompress 5 }


--
-- SNMP Community Objects
--
usdSnmpCommunityTable OBJECT-TYPE
    SYNTAX      SEQUENCE OF UsdSnmpCommunityEntry
    MAX-ACCESS  not-accessible
    STATUS      current
    DESCRIPTION
        "Table of SNMP management clients.

        Authentic SNMP clients are identified by a combination community name
        and IP address.

        Upon receipt of an SNMP request, this table is scanned for a matching
        community name.  If an entry containing a matching community name is
        found, the entry's IP access list, if nonzero, is used to validate the
        source IP address received in the request; else, if the IP access list
        number in the matching entry is zero, the source IP address is accepted.

        Finally, the type of SNMP request is validated with respect to the
        access privilege of the matching entry (e.g. a SET Request is rejected
        for an entry having read-only privilege).

        Use of this table constitutes 'trivial authentication', i.e., no
        mechanism is employed to confirm the received SNMP request was indeed
        originated by the host identified by the IP source address."
    ::= { usdSnmpCommunity 1 }

usdSnmpCommunityEntry OBJECT-TYPE
    SYNTAX      UsdSnmpCommunityEntry
    MAX-ACCESS  not-accessible
    STATUS      current
    DESCRIPTION
        "A table entry describing an authentic SNMP Community."
    INDEX     { IMPLIED usdSnmpCommunityName }
    ::= {usdSnmpCommunityTable 1 }

UsdSnmpCommunityEntry ::= SEQUENCE {
    usdSnmpCommunityName                 UsdSnmpCommunityName,
    usdSnmpCommunityRowStatus            RowStatus,
    usdSnmpCommunityPrivilege            INTEGER,
    usdSnmpCommunityAccessList           Integer32,
    usdSnmpCommunityAccessListName       UsdSnmpAccessListName,
    usdSnmpCommunityView                 INTEGER
}

usdSnmpCommunityName OBJECT-TYPE
    SYNTAX      UsdSnmpCommunityName
    MAX-ACCESS  read-only
    STATUS      current
    DESCRIPTION
        "An SNMP community name."
    ::= { usdSnmpCommunityEntry 1 }

usdSnmpCommunityRowStatus OBJECT-TYPE
    SYNTAX      RowStatus
    MAX-ACCESS  read-create
    STATUS      current
    DESCRIPTION
        "Controls creation/deletion of entries in this table.  Only
        'createAndGo' and 'destroy' enumeration values are supported."
    ::= { usdSnmpCommunityEntry 2 }

usdSnmpCommunityPrivilege OBJECT-TYPE
    SYNTAX      INTEGER {
                    readOnly(1),
                    readWrite(2),
                    admin(3)
                }
    MAX-ACCESS  read-create
    STATUS      current
    DESCRIPTION
        "The access privilege for an SNMP Community authenticated by this entry
        (used in conjunction with MIB view as specified via
        usdSnmpCommunityView).

            readOnly    Read-only access to MIB with associated view.
            readWrite   Read-write access to MIB with associated view.
            admin       Read-write access to entire MIB (for backward
                        compatibility, automatically defaults to 'everything'
                        view and 'readWrite' privilege)."
    DEFVAL    { readOnly }
    ::= { usdSnmpCommunityEntry 3 }

usdSnmpCommunityAccessList OBJECT-TYPE
    SYNTAX      Integer32 (0..10000)
    MAX-ACCESS  read-create
    STATUS      current
    DESCRIPTION
        "If nonzero, the number of an IP access list that describes the IP hosts
        permitted SNMP management access to this device via the corresponding
        community name contained in this entry."
    ::= { usdSnmpCommunityEntry 4 }

usdSnmpCommunityAccessListName OBJECT-TYPE
    SYNTAX      UsdSnmpAccessListName
    MAX-ACCESS  read-create
    STATUS      current
    DESCRIPTION
        "If not null, the name of an IP access list that describes the IP hosts
        permitted SNMP management access to this device via the corresponding
        community name contained in this entry."
    ::= { usdSnmpCommunityEntry 5 }

usdSnmpCommunityView OBJECT-TYPE
    SYNTAX      INTEGER {
                    everything(1),
                    user(2),
                    nothing(3)
                }
    MAX-ACCESS  read-create
    STATUS      current
    DESCRIPTION
        "The view associated with an SNMP Community authenticated by this entry.
            everything    Access to the entire MIB.
            user          Access to non-administrative portions of MIB.
            nothing       No access.

        'Administrative' portions of the MIB are those portions that pertain to
        management access into the managed device."
    DEFVAL    { user }
    ::= { usdSnmpCommunityEntry 6 }

--
-- SNMP Trap Filter Objects
--
usdSnmpTrapGlobalFilter OBJECT-TYPE
    SYNTAX      UsdSnmpTrapMask
    MAX-ACCESS  read-write
    STATUS      current
    DESCRIPTION
        "This object provides global control over trap generation by this agent.
        For each bit position, a '1' or '0' indicates the corresponding trap
        category is enabled or disabled, respectively."
    ::= { usdSnmpTrap 1 }

usdSnmpTrapSource OBJECT-TYPE
    SYNTAX      Integer32 (0..2147483647)
    MAX-ACCESS  read-write
    STATUS      current
    DESCRIPTION
        "The ifIndex of the interface whose IP address is used as the source IP
        address for outbound SNMP traps.

        If zero, no interface is specified, the mechanism for selecting a source
        IP address is implementation-dependent, and may vary with each trap
        sent."
    ::= { usdSnmpTrap 2 }

usdSnmpTrapHostTable OBJECT-TYPE
    SYNTAX      SEQUENCE OF UsdSnmpTrapHostEntry
    MAX-ACCESS  not-accessible
    STATUS      current
    DESCRIPTION
        "Table of SNMP Trap recipient."
    ::= { usdSnmpTrap 3 }

usdSnmpTrapHostEntry OBJECT-TYPE
    SYNTAX      UsdSnmpTrapHostEntry
    MAX-ACCESS  not-accessible
    STATUS      current
    DESCRIPTION
        "A table entry describing an SNMP Trap recipient."
    INDEX   { usdSnmpTrapHostIpAddress }
    ::= {usdSnmpTrapHostTable 1 }

UsdSnmpTrapHostEntry ::= SEQUENCE {
    usdSnmpTrapHostIpAddress         IpAddress,
    usdSnmpTrapHostRowStatus         RowStatus,
    usdSnmpTrapHostUdpPort           Integer32,
    usdSnmpTrapHostCommunity         UsdSnmpCommunityName,
    usdSnmpTrapHostProtocolVersion   INTEGER,
    usdSnmpTrapHostFilter            UsdSnmpTrapMask,
    usdSnmpTrapHostSends             Counter32,
    usdSnmpTrapHostDiscards          Counter32,
    usdSnmpTrapHostSeverityFilter    UsdTrapSeverity
}

usdSnmpTrapHostIpAddress OBJECT-TYPE
    SYNTAX      IpAddress
    MAX-ACCESS  read-only
    STATUS      current
    DESCRIPTION
        "IP address of an authorized SNMP Trap recipient.  This must be a host
        IP address."
    ::= { usdSnmpTrapHostEntry 1 }

usdSnmpTrapHostRowStatus OBJECT-TYPE
    SYNTAX      RowStatus
    MAX-ACCESS  read-create
    STATUS      current
    DESCRIPTION
        "Controls creation/deletion of entries in this table.  Only
        'createAndGo' and 'destroy' enumeration values are supported."
    ::= { usdSnmpTrapHostEntry 2 }

usdSnmpTrapHostUdpPort OBJECT-TYPE
    SYNTAX      Integer32 (1..65535)
    MAX-ACCESS  read-create
    STATUS      current
    DESCRIPTION
        "The destination UDP port to which traps will be sent."
    DEFVAL    { 162 } -- default UDP port for SNMP traps
    ::= { usdSnmpTrapHostEntry 3 }

usdSnmpTrapHostCommunity OBJECT-TYPE
    SYNTAX      UsdSnmpCommunityName
    MAX-ACCESS  read-create
    STATUS      current
    DESCRIPTION
        "An SNMP community name to be used in traps sent to this destination."
    ::= { usdSnmpTrapHostEntry 4 }

usdSnmpTrapHostProtocolVersion OBJECT-TYPE
    SYNTAX      INTEGER {
                    v1(0),
                    v2c(1),
                    v3(2)
                }
    MAX-ACCESS  read-create
    STATUS      current
    DESCRIPTION
        "The format of the SNMP trap PDU to be sent to this trap destination.
            v1      Trap-PDU defined in RFC1157, encapsulated in the message
                    structure also defined in RFC1157.
            v2c     SNMPv2-Trap-PDU defined in RFC1905, encapsulated in the
                    message structure defined in RFC1901.
            v3      SNMPv2-Trap-PDU defined in RFC1905, encapsulated in the
                    message structure defined in RFC2571."
    DEFVAL    { v1 }
    ::= { usdSnmpTrapHostEntry 5 }

usdSnmpTrapHostFilter OBJECT-TYPE
    SYNTAX      UsdSnmpTrapMask
    MAX-ACCESS  read-create
    STATUS      current
    DESCRIPTION
        "Bit mask designating the specific trap types enabled for transmission
        to this trap destination.  For each bit position, a '1' or '0' indicates
        the corresponding trap type is enabled or disabled, respectively.

        Note, trap generation is further constrained by the value
        usdSnmpTrapGlobalFilter."
    ::= { usdSnmpTrapHostEntry 6 }

usdSnmpTrapHostSends OBJECT-TYPE
    SYNTAX      Counter32
    MAX-ACCESS  read-only
    STATUS      current
    DESCRIPTION
        "The number of traps submitted for transmission to this destination."
    ::= { usdSnmpTrapHostEntry 7 }

usdSnmpTrapHostDiscards OBJECT-TYPE
    SYNTAX      Counter32
    MAX-ACCESS  read-only
    STATUS      current
    DESCRIPTION
        "The number of trap requests that were discarded.  A trap may be
        discarded because the trap type is either not a configured type in
        usdSnmpTrapHostFilter, or because the traps's priority is below the
        minimum trap severity filter defined by usdSnmpTrapHostSeverityFilter."
    ::= { usdSnmpTrapHostEntry 8 }

usdSnmpTrapHostSeverityFilter OBJECT-TYPE
    SYNTAX      UsdTrapSeverity
    MAX-ACCESS  read-create
    STATUS      current
    DESCRIPTION
        "The minimum severity value an snmp trap must have in order to be
        forwarded to this host."
    ::= { usdSnmpTrapHostEntry 9 }


usdSnmpTrapProxy OBJECT-TYPE
    SYNTAX      TruthValue
    MAX-ACCESS  read-write
    STATUS      current
    DESCRIPTION
        "The configuration setting for snmp trap proxying.  Enabling this
        management object configures the associated SNMP agent to proxy
        internally generated traps.

        Note that some implementations may support a single snmp trap proxy per
        system."
    ::= { usdSnmpTrap 4 }

usdSnmpTrapTrapSeverity     OBJECT-TYPE
    SYNTAX      UsdTrapSeverity
    MAX-ACCESS  accessible-for-notify
    STATUS      current
    DESCRIPTION
        "The severity level of the trap."
    ::= { usdSnmpTrap 5 }

usdSnmpTrapGlobalDiscards OBJECT-TYPE
    SYNTAX      Counter32
    MAX-ACCESS  read-only
    STATUS      current
    DESCRIPTION
        "The number of trap requests that were discarded.  A trap may be
        discarded because the trap type is either not globally configured in
        usdSnmpTrapGlobalFilter, or because the traps's priority is below the
        minimum trap severity filter defined by
        usdSnmpTrapGlobalSeverityFilter."
    ::= { usdSnmpTrap 6 }

usdSnmpTrapGlobalSeverityFilter OBJECT-TYPE
    SYNTAX      UsdTrapSeverity
    MAX-ACCESS  read-write
    STATUS      current
    DESCRIPTION
        "Traps flow through two levels of filtering: global and then host.  The
        value of this object defines the global minimum severity level a trap
        must have in order to be forwarded to the host level trap processing.  A
        trap will be discarded and counted in usdSnmpTrapGlobalDiscards if its
        severity level is less then the value of this object."
    ::= { usdSnmpTrap 7 }


-- ++++++++++++++++++++++++++++++++++++++++++++++++++++++++++++++++++++++
-- Traps & Trap Control
-- ++++++++++++++++++++++++++++++++++++++++++++++++++++++++++++++++++++++

--
-- No traps are defined in this MIB.
--
-- SNMP authentication failures can cause the SNMP standard
-- 'authenticationFailure' trap to be generated.  This trap and
-- its associated control object are defined in SNMPv2-MIB (RFC 1907).
-- The following objects are included in that trap to identify the
-- host that failed authentication.
--
usdSnmpAuthFailIdIpAddress OBJECT-TYPE
    SYNTAX      IpAddress
    MAX-ACCESS  accessible-for-notify
    STATUS      current
    DESCRIPTION
        "The source IP address contained in a received SNMP request that failed
        authentication."
    ::= { usdSnmpAuthFailId 1 }

usdSnmpAuthFailIdUdpPort OBJECT-TYPE
    SYNTAX      Integer32
    MAX-ACCESS  accessible-for-notify
    STATUS      current
    DESCRIPTION
        "The source UDP port contained in a received SNMP request that failed
        authentication."
    ::= { usdSnmpAuthFailId 2 }

usdSnmpAuthFailIdCommunity OBJECT-TYPE
    SYNTAX      OCTET STRING  -- no defined limit on SIZE
    MAX-ACCESS  accessible-for-notify
    STATUS      current
    DESCRIPTION
        "The SNMP community contained in a received SNMP request that failed
        authentication."
    ::= { usdSnmpAuthFailId 3 }

usdSnmpAuthFailIdReason OBJECT-TYPE
    SYNTAX      INTEGER {
                    other(0),
                    badCommunityName(1),
                    badCommmunityUse(2),
                    hostDenied(3)
                }
    MAX-ACCESS  accessible-for-notify
    STATUS      current
    DESCRIPTION
        "The reason a received SNMP request failed authentication:
            other               Unspecified reason.
            badCommunityName    The community is not recognized.
            badCommunityUse     The community does not have privilege for the
                                SNMP request type (e.g. SET request with a
                                community having read-only privilege).
            hostDenied          The host IP address was denied by the
                                community's associated access list."
    ::= { usdSnmpAuthFailId 4 }


-- ++++++++++++++++++++++++++++++++++++++++++++++++++++++++++++++++++++++
-- Conformance information
-- ++++++++++++++++++++++++++++++++++++++++++++++++++++++++++++++++++++++
usdSnmpCompliances OBJECT IDENTIFIER ::= { usdSnmpConformance 1 }
usdSnmpGroups      OBJECT IDENTIFIER ::= { usdSnmpConformance 2 }

--
-- compliance statements
--
usdSnmpCompliance MODULE-COMPLIANCE
    STATUS      obsolete
    DESCRIPTION
        "Obsolete compliance statement for entities which implement the
        Unisphere SNMP MIB.  This statement became obsolete when View support
        and Named Access List support were added."
    MODULE   -- this module
        MANDATORY-GROUPS {
            usdSnmpGroup,
            usdSnmpAuthFailGroup }
    ::= { usdSnmpCompliances 1 }                                       -- RX 1.0

usdSnmpCompliance2 MODULE-COMPLIANCE
    STATUS      obsolete
    DESCRIPTION
        "Obsolete compliance statement for entities which implement the
        Unisphere SNMP MIB.  This statement became obsolete when
        usdSnmpInterfaceMode was added."
    MODULE   -- this module
        MANDATORY-GROUPS {
            usdSnmpGroup2,
            usdSnmpAuthFailGroup }
    ::= { usdSnmpCompliances 2 }                                       -- RX 2.0

usdSnmpCompliance3 MODULE-COMPLIANCE
    STATUS      obsolete
    DESCRIPTION
        "Obsolete compliance statement for entities which implement the
        Unisphere SNMP MIB.  This statement became obsolete when support for
        interface compress, trap severities and trap severity filtering was
        added and usdSnmpInterfaceMode was obsoleted."
    MODULE   -- this module
        MANDATORY-GROUPS {
            usdSnmpGroup3,
            usdSnmpAuthFailGroup }
    ::= { usdSnmpCompliances 3 }                                       -- RX 2.3

usdSnmpCompliance4 MODULE-COMPLIANCE
    STATUS       obsolete
    DESCRIPTION
        "The compliance statement for entities which implement the Unisphere
        SNMP MIB.  This statement became obsolete when support for SNMP proxy
        enable/disable was added."
    MODULE   -- this module
        MANDATORY-GROUPS {
            usdSnmpGeneralGroup,
            usdSnmpAccessGroup,
            usdSnmpTrapGroup,
            usdSnmpAuthFailGroup }
    ::= { usdSnmpCompliances 4 }                                       -- RX 3.3

usdSnmpCompliance5 MODULE-COMPLIANCE
    STATUS      current
    DESCRIPTION
        "The compliance statement for entities which implement the Unisphere
        SNMP MIB."
    MODULE   -- this module
        MANDATORY-GROUPS {
            usdSnmpGeneralGroup2,
            usdSnmpAccessGroup,
            usdSnmpTrapGroup,
            usdSnmpAuthFailGroup }
    ::= { usdSnmpCompliances 5 }                                       -- RX 3.4


--
-- units of conformance
--
usdSnmpGroup OBJECT-GROUP
    OBJECTS {
        -- General objects
        usdSnmpMaxPduSize,

        -- Manager objects
        usdSnmpCommunityName,
        usdSnmpCommunityRowStatus,
        usdSnmpCommunityPrivilege,
        usdSnmpCommunityAccessList,

        -- Trap objects
        usdSnmpTrapGlobalFilter,
        usdSnmpTrapSource,
        usdSnmpTrapProxy,

        usdSnmpTrapHostIpAddress,
        usdSnmpTrapHostRowStatus,
        usdSnmpTrapHostUdpPort,
        usdSnmpTrapHostCommunity,
        usdSnmpTrapHostProtocolVersion,
        usdSnmpTrapHostFilter,
        usdSnmpTrapHostSends }
    STATUS      obsolete
    DESCRIPTION
        "Obsolete collection of management objects pertaining to SNMP Agent
        capability in a Unisphere product.  This group became obsolete when
        View support and Named Access List support were added."
    ::= { usdSnmpGroups 1 }

usdSnmpAuthFailGroup OBJECT-GROUP
    OBJECTS {
        usdSnmpAuthFailIdIpAddress,
        usdSnmpAuthFailIdUdpPort,
        usdSnmpAuthFailIdCommunity,
        usdSnmpAuthFailIdReason }
    STATUS      current
    DESCRIPTION
        "A collection of management objects pertaining to an SNMP authentication
        failure in a Unisphere product."
    ::= { usdSnmpGroups 2 }

usdSnmpGroup2 OBJECT-GROUP
    OBJECTS {
        -- General objects
        usdSnmpMaxPduSize,

        -- Manager objects
        usdSnmpCommunityName,
        usdSnmpCommunityRowStatus,
        usdSnmpCommunityPrivilege,
        usdSnmpCommunityAccessList,
        usdSnmpCommunityAccessListName,
        usdSnmpCommunityView,

        -- Trap objects
        usdSnmpTrapGlobalFilter,
        usdSnmpTrapSource,
        usdSnmpTrapProxy,

        usdSnmpTrapHostIpAddress,
        usdSnmpTrapHostRowStatus,
        usdSnmpTrapHostUdpPort,
        usdSnmpTrapHostCommunity,
        usdSnmpTrapHostProtocolVersion,
        usdSnmpTrapHostFilter,
        usdSnmpTrapHostSends }
    STATUS      obsolete
    DESCRIPTION
        "Obsolete collection of management objects pertaining to SNMP Agent
        capability in a Unisphere product.  This group became obsolete when
        usdSnmpInterfaceMode was added."
    ::= { usdSnmpGroups 3 }

usdSnmpGroup3 OBJECT-GROUP
    OBJECTS {
        -- General objects
        usdSnmpMaxPduSize,
        usdSnmpInterfaceMode,

        -- Manager objects
        usdSnmpCommunityName,
        usdSnmpCommunityRowStatus,
        usdSnmpCommunityPrivilege,
        usdSnmpCommunityAccessList,
        usdSnmpCommunityAccessListName,
        usdSnmpCommunityView,

        -- Trap objects
        usdSnmpTrapGlobalFilter,
        usdSnmpTrapSource,
        usdSnmpTrapProxy,

        usdSnmpTrapHostIpAddress,
        usdSnmpTrapHostRowStatus,
        usdSnmpTrapHostUdpPort,
        usdSnmpTrapHostCommunity,
        usdSnmpTrapHostProtocolVersion,
        usdSnmpTrapHostFilter,
        usdSnmpTrapHostSends }
    STATUS      obsolete
    DESCRIPTION
        "Obsolete collection of management objects pertaining to SNMP Agent
        capability in a Unisphere product.  This group became obsolete when
        support for interface compress, trap severities and trap severity
        filtering was added and usdSnmpInterfaceMode was obsoleted."
    ::= { usdSnmpGroups 4 }

usdSnmpGeneralGroup OBJECT-GROUP
    OBJECTS {
        usdSnmpMaxPduSize,
        usdSnmpIntfCompCompressed,
        usdSnmpIntfCompEnhanced,
        usdSnmpIntfCompEnhancedDisplay,
        usdSnmpIntfCompRestricted,
        usdSnmpIntfCompRestrictedDisplay }
    STATUS      obsolete
    DESCRIPTION
        "Obsolete collection of management objects pertaining to general SNMP
        Agent capabilities in a Unisphere product.  This group became obsolete
        when proxey enable/disable support was added."
    ::= { usdSnmpGroups 5 }

usdSnmpAccessGroup OBJECT-GROUP
    OBJECTS {
        usdSnmpCommunityName,
        usdSnmpCommunityRowStatus,
        usdSnmpCommunityPrivilege,
        usdSnmpCommunityAccessList,
        usdSnmpCommunityAccessListName,
        usdSnmpCommunityView }
    STATUS      current
    DESCRIPTION
        "A collection of management objects pertaining to SNMP Agent access
        capabilities in a Unisphere product."
    ::= { usdSnmpGroups 6 }

usdSnmpTrapGroup OBJECT-GROUP
    OBJECTS {
        usdSnmpTrapGlobalFilter,
        usdSnmpTrapSource,
        usdSnmpTrapProxy,

        usdSnmpTrapHostIpAddress,
        usdSnmpTrapHostRowStatus,
        usdSnmpTrapHostUdpPort,
        usdSnmpTrapHostCommunity,
        usdSnmpTrapHostProtocolVersion,
        usdSnmpTrapHostFilter,
        usdSnmpTrapHostSends,
        usdSnmpTrapHostDiscards,
        usdSnmpTrapHostSeverityFilter,
        usdSnmpTrapTrapSeverity,
        usdSnmpTrapGlobalDiscards,
        usdSnmpTrapGlobalSeverityFilter }
    STATUS      current
    DESCRIPTION
        "A collection of management objects pertaining to SNMP Agent trap
        capabilities in a Unisphere product."
    ::= { usdSnmpGroups 7 }

usdSnmpGeneralGroup2 OBJECT-GROUP
    OBJECTS {
        usdSnmpMaxPduSize,
        usdSnmpProxyStatus,
        usdSnmpIntfCompCompressed,
        usdSnmpIntfCompEnhanced,
        usdSnmpIntfCompEnhancedDisplay,
        usdSnmpIntfCompRestricted,
        usdSnmpIntfCompRestrictedDisplay }
    STATUS      current
    DESCRIPTION
        "A collection of management objects pertaining to general SNMP Agent
        capabilities in a Unisphere product."
    ::= { usdSnmpGroups 8 }

END
