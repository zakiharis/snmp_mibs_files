-- *****************************************************************************
-- Unisphere-Data-PPP-Profile-CONF
--
-- SNMP Agent Capabilities definitions for the PPP Profile MIB.
--
-- Copyright (c) 2001, 2002 Unisphere Networks, Inc.  All rights reserved.
-- *****************************************************************************

Unisphere-Data-PPP-Profile-CONF DEFINITIONS ::= BEGIN

IMPORTS
    MODULE-IDENTITY
        FROM SNMPv2-SMI
    AGENT-CAPABILITIES
        FROM SNMPv2-CONF
    usdProfileAgents
        FROM Unisphere-Data-Agents
    usdPppProfileGroup, usdPppProfileGroup2, usdPppProfileGroup3,
    usdPppProfileGroup4
        FROM Unisphere-Data-PPP-PROFILE-MIB;

usdPppProfileAgent MODULE-IDENTITY
    LAST-UPDATED "200201251410Z"  -- 25-Jan-02 09:10 AM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the PPP Profile component of the
        SNMP agent in the Unisphere Routing Switch family of products."
    -- Revision History
    REVISION    "200201251410Z"  -- 25-Jan-02 09:10 AM EST  - RX 4.0
    DESCRIPTION
        "Added the authenticator virtual router object."
    REVISION    "200201161758Z"  -- 16-Jan-02 12:58 PM EST  - RX 3.4
    DESCRIPTION
        "Added the IPCP netmask option object."
    REVISION    "200201081943Z"  -- 08-Jan-02 02:43 PM EST  - RX 3.3
    DESCRIPTION
        "Added support for dynamic multi-link PPP (MLPPP) interfaces."
    REVISION    "200110171710Z"  -- 17-Oct-01 01:10 PM EDT  - RX 3.2
    DESCRIPTION
        "The initial release of this management information module."
    ::= { usdProfileAgents 3 }

usdPppProfileAgentV1 AGENT-CAPABILITIES
    PRODUCT-RELEASE
        "Version 1 of the PPP Profile component of the Unisphere Routing Switch
        SNMP agent.  This version of the PPP Profile component was supported in
        the Unisphere RX 3.0 through 3.2 system releases."
    STATUS      obsolete
    DESCRIPTION
        "The MIB supported by the SNMP agent for the PPP Profile application in
        the Unisphere Routing Switch.  These capabilities became obsolete when
        the dynamic multilink PPP object was added."
    SUPPORTS    Unisphere-Data-PPP-PROFILE-MIB
        INCLUDES  {
            usdPppProfileGroup }
    ::= { usdPppProfileAgent 1 }

usdPppProfileAgentV2 AGENT-CAPABILITIES
    PRODUCT-RELEASE
        "Version 2 of the PPP Profile component of the Unisphere Routing Switch
        SNMP agent.  This version of the PPP Profile component was supported in
        the Unisphere RX 3.3 system release."
    STATUS      obsolete
    DESCRIPTION
        "The MIB supported by the SNMP agent for the PPP Profile application in
        the Unisphere Routing Switch.  These capabilities became obsolete when
        the IPCP netmask option object was added."
    SUPPORTS    Unisphere-Data-PPP-PROFILE-MIB
        INCLUDES  {
            usdPppProfileGroup2 }
    ::= { usdPppProfileAgent 2 }

usdPppProfileAgentV3 AGENT-CAPABILITIES
    PRODUCT-RELEASE
        "Version 3 of the PPP Profile component of the Unisphere Routing Switch
        SNMP agent.  This version of the PPP Profile component was supported in
        the Unisphere RX 3.4 and subsequent 3.x system releases."
    STATUS      obsolete
    DESCRIPTION
        "The MIB supported by the SNMP agent for the PPP Profile application in
        the Unisphere Routing Switch.  These capabilities became obsolete when
        the authenticator virtual router object was added."
    SUPPORTS    Unisphere-Data-PPP-PROFILE-MIB
        INCLUDES  {
            usdPppProfileGroup3 }
    ::= { usdPppProfileAgent 3 }


usdPppProfileAgentV4 AGENT-CAPABILITIES
    PRODUCT-RELEASE
        "Version 4 of the PPP Profile component of the Unisphere Routing Switch
        SNMP agent.  This version of the PPP Profile component is supported in
        the Unisphere RX 4.0 and subsequent system releases."
    STATUS      current
    DESCRIPTION
        "The MIB supported by the SNMP agent for the PPP Profile application in
        the Unisphere Routing Switch."
    SUPPORTS    Unisphere-Data-PPP-PROFILE-MIB
        INCLUDES  {
            usdPppProfileGroup4 }
    ::= { usdPppProfileAgent 4 }

END
