-- *****************************************************************************
-- Unisphere-Data-SONET-CONF
--
-- SNMP Agent Capabilities definitions for the SONET MIBs.
--
-- Copyright (c) 2001, 2002 Unisphere Networks, Inc.  All rights reserved.
-- *****************************************************************************

Unisphere-Data-SONET-CONF  DEFINITIONS ::= BEGIN

IMPORTS
    MODULE-IDENTITY
        FROM SNMPv2-SMI
    AGENT-CAPABILITIES
        FROM SNMPv2-CONF
    usDataAgents
        FROM Unisphere-Data-Agents
    sonetMediumStuff, sonetMediumTimeElapsed, sonetMediumValidIntervals,
    sonetMediumLineCoding, sonetMediumLineType, sonetSectionStuff,
    sonetLineStuff, sonetPathStuff, sonetVTStuff, sonetMediumStuff2,
    sonetMediumLoopbackConfig, sonetSectionStuff2, sonetLineStuff2,
    sonetFarEndLineStuff2, sonetPathStuff2, sonetFarEndPathStuff2,
    sonetVTStuff2, sonetFarEndVTStuff2
        FROM SONET-MIB
    usdSonetGroup, usdSonetPathGroup, usdSonetVirtualTributaryGroup
        FROM Unisphere-Data-SONET-MIB;

usdSonetAgent  MODULE-IDENTITY
    LAST-UPDATED "200202042135Z"  -- 04-Feb-02 04:35 PM EST
    ORGANIZATION "Unisphere Networks, Inc."
    CONTACT-INFO
        "       Unisphere Networks, Inc.
        Postal: 10 Technology Park Drive
                Westford, MA  01886
                USA
        Tel:    +1 978 589 5800
        E-mail: mib@UnisphereNetworks.com"
    DESCRIPTION
        "The agent capabilities definitions for the SONET component of the SNMP
        agent in the Unisphere Routing Switch family of products."
    -- Revision History
    REVISION    "200202042135Z"  -- 04-Feb-02 04:35 PM EST  - RX 3.3
    DESCRIPTION
        "Separate out the SONET VT support."
    REVISION    "200104032235Z"  -- 03-Apr-01 06:35 PM EDT  - RX 3.2
    DESCRIPTION
        "The initial release of this management information module."
    ::= { usDataAgents 40 }


-- *****************************************************************************
-- SONET general agent capabilities
-- *****************************************************************************
usdSonetAgentV1  AGENT-CAPABILITIES
    PRODUCT-RELEASE
        "Version 1 of the SONET component of the Unisphere Routing Switch SNMP
        agent.  This version of the SONET component was supported in the
        Unisphere RX 1.x system releases."
    STATUS      obsolete
    DESCRIPTION
        "The MIBs supported by the SNMP agent for the SONET application in the
        Unisphere Routing Switch.  These capabilities became obsolete when
        support for the standard VT group was added."
    SUPPORTS    SONET-MIB  -- RFC 1595
        INCLUDES  {
            sonetMediumStuff,
            sonetSectionStuff,
            sonetLineStuff,
            sonetPathStuff }
        VARIATION   sonetMediumTimeElapsed
            DESCRIPTION
                "Returns zero."
        VARIATION   sonetMediumValidIntervals
            DESCRIPTION
                "Returns zero."
        VARIATION   sonetMediumLineCoding
            ACCESS      read-only
            DESCRIPTION
                "Only supports NRZ (4)."
        VARIATION   sonetMediumLineType
            ACCESS      read-only
            DESCRIPTION
                "Only supports Multi-Mode (4)."
    SUPPORTS    Unisphere-Data-SONET-MIB
        INCLUDES {
            usdSonetGroup }
    ::= { usdSonetAgent 1 }

usdSonetAgentV2  AGENT-CAPABILITIES
    PRODUCT-RELEASE
        "Version 2 of the SONET component of the Unisphere Routing Switch SNMP
        agent.  This version of the SONET component was supported in the
        Unisphere RX 2.x system releases."
    STATUS      obsolete
    DESCRIPTION
        "The MIBs supported by the SNMP agent for the SONET application in the
        Unisphere Routing Switch.  These capabilities became obsolete when
        support for the proprietary path and VT groups were added."
    SUPPORTS    SONET-MIB  -- RFC 1595
        INCLUDES {
            sonetMediumStuff,
            sonetSectionStuff,
            sonetLineStuff,
            sonetPathStuff,
            sonetVTStuff }
        VARIATION   sonetMediumTimeElapsed
            DESCRIPTION
                "Returns zero."
        VARIATION   sonetMediumValidIntervals
            DESCRIPTION
                "Returns zero."
        VARIATION   sonetMediumLineCoding
            ACCESS      read-only
            DESCRIPTION
                "Only supports NRZ (4)."
        VARIATION   sonetMediumLineType
            ACCESS      read-only
            DESCRIPTION
                "Only supports Multi-Mode (4)."
    SUPPORTS    Unisphere-Data-SONET-MIB
        INCLUDES {
            usdSonetGroup }
    ::= { usdSonetAgent 2 }

usdSonetAgentV3  AGENT-CAPABILITIES
    PRODUCT-RELEASE
        "Version 3 of the SONET component of the Unisphere Routing Switch SNMP
        agent.  This version of the SONET component was supported in the
        Unisphere RX 3.0 and 3.1 system releases."
    STATUS      obsolete
    DESCRIPTION
        "The MIBs supported by the SNMP agent for the SONET application in the
        Unisphere Routing Switch.  These capabilities became obsolete when
        support for the RFC-2558 version of the SONET-MIB and far-end statistics
        were added."
    SUPPORTS    SONET-MIB  -- RFC 1595
        INCLUDES {
            sonetMediumStuff,
            sonetSectionStuff,
            sonetLineStuff,
            sonetPathStuff,
            sonetVTStuff }
        VARIATION   sonetMediumLineCoding
            ACCESS      read-only
            DESCRIPTION
                "Only supports NRZ (4)."
        VARIATION   sonetMediumLineType
            ACCESS      read-only
            DESCRIPTION
                "Only supports Multi-Mode (4)."
    SUPPORTS    Unisphere-Data-SONET-MIB
        INCLUDES {
            usdSonetGroup,
            usdSonetPathGroup,
            usdSonetVirtualTributaryGroup }
    ::= { usdSonetAgent 3 }

usdSonetAgentV4  AGENT-CAPABILITIES
    PRODUCT-RELEASE
        "Version 4 of the SONET component of the Unisphere Routing Switch SNMP
        agent.  This version of the SONET component was supported in the
        Unisphere RX 3.2 system release."
    STATUS      obsolete
    DESCRIPTION
        "The MIBs supported by the SNMP agent for the SONET application in the
        Unisphere Routing Switch.  These capabilities became obsolete when
        Virtual Tributary (VT) support was searated out into a separate
        capabilities statement."
    SUPPORTS    SONET-MIB  -- RFC 2558
        INCLUDES {
            sonetMediumStuff2,
            sonetSectionStuff2,
            sonetLineStuff2,
            sonetFarEndLineStuff2,
            sonetPathStuff2,
            sonetFarEndPathStuff2,
            sonetVTStuff2,
            sonetFarEndVTStuff2 }
        VARIATION   sonetMediumLineCoding
            ACCESS      read-only
            DESCRIPTION
                "Only supports NRZ (4)."
        VARIATION   sonetMediumLineType
            ACCESS      read-only
            DESCRIPTION
                "Only supports Multi-Mode (4)."
        VARIATION   sonetMediumLoopbackConfig
            DESCRIPTION
                "Only supports setting one loopback state at a time; a value
                with more than one bit set will be rejected.  Setting
                sonetOtherLoop (bit 3) is also not a valid operation."
    SUPPORTS    Unisphere-Data-SONET-MIB
        INCLUDES {
            usdSonetGroup,
            usdSonetPathGroup,
            usdSonetVirtualTributaryGroup }
    ::= { usdSonetAgent 4 }


-- *****************************************************************************
-- SONET basic agent capabilities
-- *****************************************************************************
usdSonetBasicAgent OBJECT IDENTIFIER ::= { usdSonetAgent 5 }

usdSonetBasicAgentV1  AGENT-CAPABILITIES
    PRODUCT-RELEASE
        "Version 1 of the basic SONET component of the Unisphere Routing Switch
        SNMP agent.  It does not include Virtual Tributary (VT) support.  This
        version of the basic SONET component is supported in the Unisphere RX
        3.3 and subsequent system releases."
    STATUS      current
    DESCRIPTION
        "The MIB conformance groups supported by the SNMP agent for the SONET
        application in the Unisphere Routing Switch."
    SUPPORTS    SONET-MIB  -- RFC 2558
        INCLUDES {
            sonetMediumStuff2,
            sonetSectionStuff2,
            sonetLineStuff2,
            sonetFarEndLineStuff2,
            sonetPathStuff2,
            sonetFarEndPathStuff2 }
        VARIATION   sonetMediumLineCoding
            ACCESS      read-only
            DESCRIPTION
                "Only supports NRZ (4)."
        VARIATION   sonetMediumLineType
            ACCESS      read-only
            DESCRIPTION
                "Only supports Multi-Mode (4)."
        VARIATION   sonetMediumLoopbackConfig
            DESCRIPTION
                "Only supports setting one loopback state at a time; a value
                with more than one bit set will be rejected.  Setting
                sonetOtherLoop (bit 3) is also not a valid operation."
    SUPPORTS    Unisphere-Data-SONET-MIB
        INCLUDES {
            usdSonetGroup,
            usdSonetPathGroup }
    ::= { usdSonetBasicAgent 1 }


-- *****************************************************************************
-- SONET Virtual Tributary (VT) agent capabilities
-- *****************************************************************************
usdSonetVTAgent OBJECT IDENTIFIER ::= { usdSonetAgent 6 }

usdSonetVTAgentV1  AGENT-CAPABILITIES
    PRODUCT-RELEASE
        "Version 1 of the SONET VT component of the Unisphere Routing Switch
        SNMP agent.  This version of the SONET component is supported in the
        Unisphere RX 3.3 and subsequent system releases."
    STATUS      current
    DESCRIPTION
        "The MIB conformance groups supported by the SNMP agent for the SONET
        application in the Unisphere Routing Switch."
    SUPPORTS    SONET-MIB  -- RFC 2558
        INCLUDES {
            sonetVTStuff2,
            sonetFarEndVTStuff2 }
    SUPPORTS    Unisphere-Data-SONET-MIB
        INCLUDES {
            usdSonetVirtualTributaryGroup }
    ::= { usdSonetVTAgent 1 }

END
