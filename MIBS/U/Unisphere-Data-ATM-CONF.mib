-- *****************************************************************************
-- Unisphere-Data-ATM-CONF
--
-- SNMP Agent Capabilities definitions for the ATM MIBs.
--
-- Copyright (c) 2001, 2002 Unisphere Networks, Inc.  All rights reserved.
-- *****************************************************************************

Unisphere-Data-ATM-CONF DEFINITIONS ::= BEGIN

IMPORTS
    MODULE-IDENTITY
        FROM SNMPv2-SMI
    AGENT-CAPABILITIES
        FROM SNMPv2-CONF
    usDataAgents
        FROM Unisphere-Data-Agents
    atmInterfaceTCGroup, aal5VccGroup, atmInterfaceConfGroup2,
    atmTrafficDescrGroup2, atmVccTerminationGroup2, atmVclAdminStatus,
    atmVclReceiveTrafficDescrIndex, atmVclTransmitTrafficDescrIndex,
    atmVccAalType, atmVclRowStatus, atmVclCastType, atmVclConnKind,
    atmVplCrossConnectGroup, atmVpPvcCrossConnectGroup, atmVclCrossConnectGroup,
    atmVcPvcCrossConnectGroup
        FROM ATM-MIB
    atmSwitchServcHostGroup, atmSigSSCOPConEvents, atmSigSSCOPErrdPdus,
    atmSigDetectSetupAttempts, atmSigEmitSetupAttempts,
    atmSigDetectUnavailRoutes, atmSigEmitUnavailRoutes,
    atmSigDetectUnavailResrcs, atmSigEmitUnavailResrcs,
    atmSigDetectCldPtyEvents, atmSigEmitCldPtyEvents, atmSigDetectMsgErrors,
    atmSigEmitMsgErrors, atmSigDetectClgPtyEvents, atmSigEmitClgPtyEvents,
    atmSigDetectTimerExpireds, atmSigEmitTimerExpireds, atmSigDetectRestarts,
    atmSigEmitRestarts, atmSigInEstabls, atmSigOutEstabls, atmVplLogicalPortDef,
    atmVplLogicalPortIndex, atmInterfaceConfMaxSvpcVpi,
    atmInterfaceCurrentMaxSvpcVpi, atmInterfaceConfMaxSvccVpi,
    atmInterfaceCurrentMaxSvccVpi, atmInterfaceConfMinSvccVci,
    atmInterfaceCurrentMinSvccVci, atmIntfSigVccRxTrafficDescrIndex,
    atmIntfSigVccTxTrafficDescrIndex, atmIntfPvcFailures,
    atmIntfCurrentlyFailingPVpls, atmIntfCurrentlyFailingPVcls,
    atmIntfPvcNotificationInterval, atmIntfPvcFailuresTrapEnable,
    atmIntfLeafSetupFailures, atmIntfLeafSetupRequests, atmIntfConfigType,
    atmIntfActualType, atmIntfConfigSide, atmIntfActualSide,
    atmIntfIlmiAdminStatus, atmIntfIlmiOperStatus, atmIntfIlmiFsmState,
    atmIntfIlmiEstablishConPollIntvl, atmIntfIlmiCheckConPollIntvl,
    atmIntfIlmiConPollInactFactor, atmIntfIlmiPublicPrivateIndctr,
    atmCurrentlyFailingPVplTimeStamp, atmCurrentlyFailingPVclTimeStamp
        FROM ATM2-MIB
    atmfM4General, atmfM4NeVersion, atmfM4NeStartTime,
    atmfM4NeAlarmSeverityIndex, atmfM4NeSuppressZeroStats, atmfM4AtmLayerGroup,
    atmfM4IfType, atmfM4IfSubscriberAddress, atmfM4IfPreferredCarrier,
    atmfM4IfFarEndCarrierNetwork, atmfM4VplGroup, atmfM4VclGroup,
    atmfM4VclSegEndPt, atmfM4VpTestGroup, atmfM4VcTestGroup
        FROM ATM-FORUM-SNMP-M4-MIB
    usdAtmGroup, usdAtmAal5Group, usdAtmSubIfGroup, usdAtmVpTunnelGroup,
    usdAtmNbmaMapGroup, usdAtmSubIfGroup2, usdAtmVpPingControlGroup,
    usdAtmVcPingControlGroup, usdAtmPingTrapGroup, usdAtmGroup2,
    usdAtmTrafficShapingGroup, usdAtmGroup3, usdAtmSvcGroup, usdAtmSubIfGroup3
        FROM Unisphere-Data-ATM-MIB;

usdAtmAgent MODULE-IDENTITY
    LAST-UPDATED "200201291518Z"  -- 29-Jan-02 10:18 AM EST
    ORGANIZATION "Unisphere Networks, Inc."
    CONTACT-INFO
        "       Unisphere Networks, Inc.
        Postal: 10 Technology Park Drive
                Westford, MA 01886
                USA
        Tel:    +1 978 589 5800
        E-mail: mib@UnisphereNetworks.com"
    DESCRIPTION
        "The agent capabilities definitions for the ATM component of the SNMP
        agent in the Unisphere Routing Switch family of products."
    -- Revision History
    REVISION    "200201291518Z"  -- 29-Jan-02 10:18 AM EST  - RX 4.0
    DESCRIPTION
        "Added ATM switched virtual connection (SVC) support to the
        Unisphere-Data-ATM-MIB VCC end point capabilities."
    REVISION    "200201241416Z"  -- 24-Jan-02 09:16 AM EST  - RX 3.4
    DESCRIPTION
        "Added support for ATM connection admission control (CAC) to the
        Unisphere-Data-ATM-MIB VCC end point capabilities."
    REVISION    "200112141951Z"  -- 14-Dec-01 02:51 PM EST  - RX 3.3
    DESCRIPTION
        "Added ATM traffic shaping capabilities."
    REVISION    "200105231612Z"  -- 23-May-01 12:12 PM EDT  - RX 3.2
    DESCRIPTION
        "The initial release of this management information module."
    ::= { usDataAgents 3 }


-- *****************************************************************************
-- ATM VCC end point agent capabilities
-- *****************************************************************************
usdAtmVccEndPointAgent OBJECT IDENTIFIER ::= { usdAtmAgent 1 }

usdAtmVccEndPointAgentV1 AGENT-CAPABILITIES
    PRODUCT-RELEASE
        "Version 1 of the ATM VCC end point agent subcomponent of the Unisphere
        Routing Switch SNMP agent.  This version of the ATM end point
        subcomponent was supported in the Unisphere RX 3.0 and 3.1 system
        releases."
    STATUS      obsolete
    DESCRIPTION
        "The MIBs supported by the SNMP agent for the ATM application in the
        Unisphere Routing Switch.  These capabilities became obsolete when new
        objects were added to the usdAtmSubIfGroup and support for the
        atmfM4IfLoopbackLocationCode object was added."
    SUPPORTS    ATM-MIB
        INCLUDES  {
            atmInterfaceTCGroup,
            aal5VccGroup,
            atmInterfaceConfGroup2,
            atmVccTerminationGroup2 }
        VARIATION   atmVclAdminStatus
            ACCESS      read-only
            DESCRIPTION
                "The atmVccTerminationGroup2 is not used for configuring VCCs.
                Use the Unisphere-Data-ATM-MIB."
        VARIATION   atmVclReceiveTrafficDescrIndex
            ACCESS      read-only
            DESCRIPTION
                "The atmVccTerminationGroup2 is not used for configuring VCCs.
                Use the Unisphere-Data-ATM-MIB."
        VARIATION   atmVclTransmitTrafficDescrIndex
            ACCESS      read-only
            DESCRIPTION
                "The atmVccTerminationGroup2 is not used for configuring VCCs.
                Use the Unisphere-Data-ATM-MIB."
        VARIATION   atmVccAalType
            ACCESS      read-only
            DESCRIPTION
                "The atmVccTerminationGroup2 is not used for configuring VCCs.
                Use the Unisphere-Data-ATM-MIB."
        VARIATION   atmVclRowStatus
            ACCESS      read-only
            DESCRIPTION
                "The atmVccTerminationGroup2 is not used for configuring VCCs.
                Use the Unisphere-Data-ATM-MIB."
        VARIATION   atmVclCastType
            ACCESS      read-only
            DESCRIPTION
                "The atmVccTerminationGroup2 is not used for configuring VCCs.
                Use the Unisphere-Data-ATM-MIB."
        VARIATION   atmVclConnKind
            ACCESS      read-only
            DESCRIPTION
                "The atmVccTerminationGroup2 is not used for configuring VCCs.
                Use the Unisphere-Data-ATM-MIB."
    SUPPORTS    Unisphere-Data-ATM-MIB
        INCLUDES  {
            usdAtmGroup,
            usdAtmAal5Group,
            usdAtmSubIfGroup }
    ::= { usdAtmVccEndPointAgent 1 }

usdAtmVccEndPointAgentV2 AGENT-CAPABILITIES
    PRODUCT-RELEASE
        "Version 2 of the ATM VCC end point agent subcomponent of the Unisphere
        Routing Switch SNMP agent.  This version of the ATM end point
        subcomponent was supported in the Unisphere RX 3.2 and RX 3.3 system
        releases."
    STATUS      obsolete
    DESCRIPTION
        "The MIBs supported by the SNMP agent for the ATM application in the
        Unisphere Routing Switch.  These capabilities became obsolete when
        support was added to the Unisphere-Data-ATM-MIB for connection admission
        control (CAC)."
    SUPPORTS    ATM-MIB
        INCLUDES  {
            atmInterfaceTCGroup,
            aal5VccGroup,
            atmInterfaceConfGroup2,
            atmVccTerminationGroup2 }
        VARIATION   atmVclAdminStatus
            ACCESS      read-only
            DESCRIPTION
                "The atmVccTerminationGroup2 is not used for configuring VCCs.
                Use the Unisphere-Data-ATM-MIB."
        VARIATION   atmVclReceiveTrafficDescrIndex
            ACCESS      read-only
            DESCRIPTION
                "The atmVccTerminationGroup2 is not used for configuring VCCs.
                Use the Unisphere-Data-ATM-MIB."
        VARIATION   atmVclTransmitTrafficDescrIndex
            ACCESS      read-only
            DESCRIPTION
                "The atmVccTerminationGroup2 is not used for configuring VCCs.
                Use the Unisphere-Data-ATM-MIB."
        VARIATION   atmVccAalType
            ACCESS      read-only
            DESCRIPTION
                "The atmVccTerminationGroup2 is not used for configuring VCCs.
                Use the Unisphere-Data-ATM-MIB."
        VARIATION   atmVclRowStatus
            ACCESS      read-only
            DESCRIPTION
                "The atmVccTerminationGroup2 is not used for configuring VCCs.
                Use the Unisphere-Data-ATM-MIB."
        VARIATION   atmVclCastType
            ACCESS      read-only
            DESCRIPTION
                "The atmVccTerminationGroup2 is not used for configuring VCCs.
                Use the Unisphere-Data-ATM-MIB."
        VARIATION   atmVclConnKind
            ACCESS      read-only
            DESCRIPTION
                "The atmVccTerminationGroup2 is not used for configuring VCCs.
                Use the Unisphere-Data-ATM-MIB."
    SUPPORTS    ATM-FORUM-SNMP-M4-MIB
        INCLUDES  {
            atmfM4General,
            atmfM4AtmLayerGroup,
            atmfM4VpTestGroup,
            atmfM4VcTestGroup }
        VARIATION   atmfM4NeVersion
            ACCESS      not-implemented
            DESCRIPTION
                "The atmfM4NeVersion object is not supported."
        VARIATION   atmfM4NeStartTime
            ACCESS      not-implemented
            DESCRIPTION
                "The atmfM4NeStartTime object is not supported."
        VARIATION   atmfM4NeAlarmSeverityIndex
            ACCESS      not-implemented
            DESCRIPTION
                "The atmfM4NeAlarmSeverityIndex is not supported."
        VARIATION   atmfM4NeSuppressZeroStats
            ACCESS      not-implemented
            DESCRIPTION
                "The atmfM4NeSuppressZeroStats object is not supported."
        VARIATION   atmfM4IfType
            ACCESS      not-implemented
            DESCRIPTION
                "The atmfM4IfType object is not supported."
        VARIATION   atmfM4IfSubscriberAddress
            ACCESS      not-implemented
            DESCRIPTION
                "The atmfM4IfSubscriberAddress object is not supported."
        VARIATION   atmfM4IfPreferredCarrier
            ACCESS      not-implemented
            DESCRIPTION
                "The atmfM4IfPreferredCarrier object is not supported."
        VARIATION   atmfM4IfFarEndCarrierNetwork
            ACCESS      not-implemented
            DESCRIPTION
                "The IfFarEndCarrierNetwork object is not supported."
        VARIATION   atmfM4VclSegEndPt
            ACCESS      read-only
            DESCRIPTION
                "An atmfM4VclEntry cannot be created/modified via SNMP."
    SUPPORTS    Unisphere-Data-ATM-MIB
        INCLUDES  {
            usdAtmGroup2,
            usdAtmAal5Group,
            usdAtmSubIfGroup2,
            usdAtmVpPingControlGroup,
            usdAtmVcPingControlGroup,
            usdAtmPingTrapGroup }
    ::= { usdAtmVccEndPointAgent 2 }

usdAtmVccEndPointAgentV3 AGENT-CAPABILITIES
    PRODUCT-RELEASE
        "Version 3 of the ATM VCC end point agent subcomponent of the Unisphere
        Routing Switch SNMP agent.  This version of the ATM end point
        subcomponent was supported in the Unisphere RX 3.4 and subsequent 3.x
        system releases."
    STATUS      obsolete
    DESCRIPTION
        "The MIBs supported by the SNMP agent for the ATM application in the
        Unisphere Routing Switch.  These capabilities became obsolete when
        support was added to the Unisphere-Data-ATM-MIB for switched virtual
        connection (SVC)."
    SUPPORTS    ATM-MIB
        INCLUDES  {
            atmInterfaceTCGroup,
            aal5VccGroup,
            atmInterfaceConfGroup2,
            atmVccTerminationGroup2 }
        VARIATION   atmVclAdminStatus
            ACCESS      read-only
            DESCRIPTION
                "The atmVccTerminationGroup2 is not used for configuring VCCs.
                Use the Unisphere-Data-ATM-MIB."
        VARIATION   atmVclReceiveTrafficDescrIndex
            ACCESS      read-only
            DESCRIPTION
                "The atmVccTerminationGroup2 is not used for configuring VCCs.
                Use the Unisphere-Data-ATM-MIB."
        VARIATION   atmVclTransmitTrafficDescrIndex
            ACCESS      read-only
            DESCRIPTION
                "The atmVccTerminationGroup2 is not used for configuring VCCs.
                Use the Unisphere-Data-ATM-MIB."
        VARIATION   atmVccAalType
            ACCESS      read-only
            DESCRIPTION
                "The atmVccTerminationGroup2 is not used for configuring VCCs.
                Use the Unisphere-Data-ATM-MIB."
        VARIATION   atmVclRowStatus
            ACCESS      read-only
            DESCRIPTION
                "The atmVccTerminationGroup2 is not used for configuring VCCs.
                Use the Unisphere-Data-ATM-MIB."
        VARIATION   atmVclCastType
            ACCESS      read-only
            DESCRIPTION
                "The atmVccTerminationGroup2 is not used for configuring VCCs.
                Use the Unisphere-Data-ATM-MIB."
        VARIATION   atmVclConnKind
            ACCESS      read-only
            DESCRIPTION
                "The atmVccTerminationGroup2 is not used for configuring VCCs.
                Use the Unisphere-Data-ATM-MIB."
    SUPPORTS    ATM-FORUM-SNMP-M4-MIB
        INCLUDES  {
            atmfM4General,
            atmfM4AtmLayerGroup,
            atmfM4VpTestGroup,
            atmfM4VcTestGroup }
        VARIATION   atmfM4NeVersion
            ACCESS      not-implemented
            DESCRIPTION
                "The atmfM4NeVersion object is not supported."
        VARIATION   atmfM4NeStartTime
            ACCESS      not-implemented
            DESCRIPTION
                "The atmfM4NeStartTime object is not supported."
        VARIATION   atmfM4NeAlarmSeverityIndex
            ACCESS      not-implemented
            DESCRIPTION
                "The atmfM4NeAlarmSeverityIndex is not supported."
        VARIATION   atmfM4NeSuppressZeroStats
            ACCESS      not-implemented
            DESCRIPTION
                "The atmfM4NeSuppressZeroStats object is not supported."
        VARIATION   atmfM4IfType
            ACCESS      not-implemented
            DESCRIPTION
                "The atmfM4IfType object is not supported."
        VARIATION   atmfM4IfSubscriberAddress
            ACCESS      not-implemented
            DESCRIPTION
                "The atmfM4IfSubscriberAddress object is not supported."
        VARIATION   atmfM4IfPreferredCarrier
            ACCESS      not-implemented
            DESCRIPTION
                "The atmfM4IfPreferredCarrier object is not supported."
        VARIATION   atmfM4IfFarEndCarrierNetwork
            ACCESS      not-implemented
            DESCRIPTION
                "The IfFarEndCarrierNetwork object is not supported."
        VARIATION   atmfM4VclSegEndPt
            ACCESS      read-only
            DESCRIPTION
                "An atmfM4VclEntry cannot be created/modified via SNMP."
    SUPPORTS    Unisphere-Data-ATM-MIB
        INCLUDES  {
            usdAtmGroup3,
            usdAtmAal5Group,
            usdAtmSubIfGroup2,
            usdAtmVpPingControlGroup,
            usdAtmVcPingControlGroup,
            usdAtmPingTrapGroup }
    ::= { usdAtmVccEndPointAgent 3 }

usdAtmVccEndPointAgentV4 AGENT-CAPABILITIES
    PRODUCT-RELEASE
        "Version 4 of the ATM VCC end point agent subcomponent of the Unisphere
        Routing Switch SNMP agent.  This version of the ATM end point
        subcomponent is supported in the Unisphere RX 4.0 and subsequent system
        releases."
    STATUS      current
    DESCRIPTION
        "The MIBs supported by the SNMP agent for the ATM application in the
        Unisphere Routing Switch."
    SUPPORTS    ATM-MIB
        INCLUDES  {
            atmInterfaceTCGroup,
            aal5VccGroup,
            atmInterfaceConfGroup2,
            atmVccTerminationGroup2 }
        VARIATION   atmVclAdminStatus
            ACCESS      read-only
            DESCRIPTION
                "The atmVccTerminationGroup2 is not used for configuring VCCs.
                Use the Unisphere-Data-ATM-MIB."
        VARIATION   atmVclReceiveTrafficDescrIndex
            ACCESS      read-only
            DESCRIPTION
                "The atmVccTerminationGroup2 is not used for configuring VCCs.
                Use the Unisphere-Data-ATM-MIB."
        VARIATION   atmVclTransmitTrafficDescrIndex
            ACCESS      read-only
            DESCRIPTION
                "The atmVccTerminationGroup2 is not used for configuring VCCs.
                Use the Unisphere-Data-ATM-MIB."
        VARIATION   atmVccAalType
            ACCESS      read-only
            DESCRIPTION
                "The atmVccTerminationGroup2 is not used for configuring VCCs.
                Use the Unisphere-Data-ATM-MIB."
        VARIATION   atmVclRowStatus
            ACCESS      read-only
            DESCRIPTION
                "The atmVccTerminationGroup2 is not used for configuring VCCs.
                Use the Unisphere-Data-ATM-MIB."
        VARIATION   atmVclCastType
            ACCESS      read-only
            DESCRIPTION
                "The atmVccTerminationGroup2 is not used for configuring VCCs.
                Use the Unisphere-Data-ATM-MIB."
        VARIATION   atmVclConnKind
            ACCESS      read-only
            DESCRIPTION
                "The atmVccTerminationGroup2 is not used for configuring VCCs.
                Use the Unisphere-Data-ATM-MIB."
    SUPPORTS    ATM-FORUM-SNMP-M4-MIB
        INCLUDES  {
            atmfM4General,
            atmfM4AtmLayerGroup,
            atmfM4VpTestGroup,
            atmfM4VcTestGroup }
        VARIATION   atmfM4NeVersion
            ACCESS      not-implemented
            DESCRIPTION
                "The atmfM4NeVersion object is not supported."
        VARIATION   atmfM4NeStartTime
            ACCESS      not-implemented
            DESCRIPTION
                "The atmfM4NeStartTime object is not supported."
        VARIATION   atmfM4NeAlarmSeverityIndex
            ACCESS      not-implemented
            DESCRIPTION
                "The atmfM4NeAlarmSeverityIndex is not supported."
        VARIATION   atmfM4NeSuppressZeroStats
            ACCESS      not-implemented
            DESCRIPTION
                "The atmfM4NeSuppressZeroStats object is not supported."
        VARIATION   atmfM4IfType
            ACCESS      not-implemented
            DESCRIPTION
                "The atmfM4IfType object is not supported."
        VARIATION   atmfM4IfSubscriberAddress
            ACCESS      not-implemented
            DESCRIPTION
                "The atmfM4IfSubscriberAddress object is not supported."
        VARIATION   atmfM4IfPreferredCarrier
            ACCESS      not-implemented
            DESCRIPTION
                "The atmfM4IfPreferredCarrier object is not supported."
        VARIATION   atmfM4IfFarEndCarrierNetwork
            ACCESS      not-implemented
            DESCRIPTION
                "The IfFarEndCarrierNetwork object is not supported."
        VARIATION   atmfM4VclSegEndPt
            ACCESS      read-only
            DESCRIPTION
                "An atmfM4VclEntry cannot be created/modified via SNMP."
    SUPPORTS    Unisphere-Data-ATM-MIB
        INCLUDES  {
            usdAtmGroup3,
            usdAtmAal5Group,
            usdAtmSubIfGroup3,
            usdAtmVpPingControlGroup,
            usdAtmVcPingControlGroup,
            usdAtmPingTrapGroup,
            usdAtmSvcGroup }
    ::= { usdAtmVccEndPointAgent 4 }


-- *****************************************************************************
-- ATM VP tunnel agent capabilities
-- *****************************************************************************
usdAtmVpTunnelAgent OBJECT IDENTIFIER ::= { usdAtmAgent 2 }

usdAtmVpTunnelAgentV1 AGENT-CAPABILITIES
    PRODUCT-RELEASE
        "Version 1 of the ATM VP tunnel subcomponent of the Unisphere Routing
        Switch SNMP agent.  This version of the ATM tunnel subcomponent is
        supported in the Unisphere RX 3.0 and subsequent system releases."
    STATUS      current
    DESCRIPTION
        "The MIBs supported by the SNMP agent for the ATM application in the
        Unisphere Routing Switch."
    SUPPORTS    Unisphere-Data-ATM-MIB
        INCLUDES  {
            usdAtmVpTunnelGroup }
    ::= { usdAtmVpTunnelAgent 1 }


-- *****************************************************************************
-- ATM NBMA interface agent capabilities
-- *****************************************************************************
usdAtmNbmaAgent OBJECT IDENTIFIER ::= { usdAtmAgent 3 }

usdAtmNbmaAgentV1 AGENT-CAPABILITIES
    PRODUCT-RELEASE
        "Version 1 of the ATM NBMA interface subcomponent of the Unisphere
        Routing Switch SNMP agent.  This version of the ATM NBMA subcomponent is
        supported in the Unisphere RX 3.2 and subsequent system releases."
    STATUS      current
    DESCRIPTION
        "The MIBs supported by the SNMP agent for the ATM application in the
        Unisphere Routing Switch."
    SUPPORTS    Unisphere-Data-ATM-MIB
        INCLUDES  {
            usdAtmNbmaMapGroup }
    ::= { usdAtmNbmaAgent 1 }


-- *****************************************************************************
-- ATM Switch agent capabilities
-- *****************************************************************************
usdAtmSwitchAgent OBJECT IDENTIFIER ::= { usdAtmAgent 4 }

usdAtmSwitchAgentV1 AGENT-CAPABILITIES
    PRODUCT-RELEASE
        "Version 1 of the ATM switch (cross connect) subcomponent of the
        Unisphere Routing Switch SNMP agent.  This version of the ATM switch
        subcomponent is supported in the Unisphere RX 3.2 and subsequent system
        releases."
    STATUS      current
    DESCRIPTION
        "The MIBs supported by the SNMP agent for the ATM application in the
        Unisphere Routing Switch."
    SUPPORTS    ATM-MIB
        INCLUDES  {
            atmTrafficDescrGroup2,
            atmVplCrossConnectGroup,
            atmVpPvcCrossConnectGroup,
            atmVclCrossConnectGroup,
            atmVcPvcCrossConnectGroup }
    SUPPORTS    ATM2-MIB
        INCLUDES  {
            atmSwitchServcHostGroup }
        VARIATION   atmSigSSCOPConEvents
            ACCESS      not-implemented
            DESCRIPTION
                "The atmSigStatTable is not supported."
        VARIATION   atmSigSSCOPErrdPdus
            ACCESS      not-implemented
            DESCRIPTION
                "The atmSigStatTable is not supported."
        VARIATION   atmSigDetectSetupAttempts
            ACCESS      not-implemented
            DESCRIPTION
                "The atmSigStatTable is not supported."
        VARIATION   atmSigEmitSetupAttempts
            ACCESS      not-implemented
            DESCRIPTION
                "The atmSigStatTable is not supported."
        VARIATION   atmSigDetectUnavailRoutes
            ACCESS      not-implemented
            DESCRIPTION
                "The atmSigStatTable is not supported."
        VARIATION   atmSigEmitUnavailRoutes
            ACCESS      not-implemented
            DESCRIPTION
                "The atmSigStatTable is not supported."
        VARIATION   atmSigDetectUnavailResrcs
            ACCESS      not-implemented
            DESCRIPTION
                "The atmSigStatTable is not supported."
        VARIATION   atmSigEmitUnavailResrcs
            ACCESS      not-implemented
            DESCRIPTION
                "The atmSigStatTable is not supported."
        VARIATION   atmSigDetectCldPtyEvents
            ACCESS      not-implemented
            DESCRIPTION
                "The atmSigStatTable is not supported."
        VARIATION   atmSigEmitCldPtyEvents
            ACCESS      not-implemented
            DESCRIPTION
                "The atmSigStatTable is not supported."
        VARIATION   atmSigDetectMsgErrors
            ACCESS      not-implemented
            DESCRIPTION
                "The atmSigStatTable is not supported."
        VARIATION   atmSigEmitMsgErrors
            ACCESS      not-implemented
            DESCRIPTION
                "The atmSigStatTable is not supported."
        VARIATION   atmSigDetectClgPtyEvents
            ACCESS      not-implemented
            DESCRIPTION
                "The atmSigStatTable is not supported."
        VARIATION   atmSigEmitClgPtyEvents
            ACCESS      not-implemented
            DESCRIPTION
                "The atmSigStatTable is not supported."
        VARIATION   atmSigDetectTimerExpireds
            ACCESS      not-implemented
            DESCRIPTION
                "The atmSigStatTable is not supported."
        VARIATION   atmSigEmitTimerExpireds
            ACCESS      not-implemented
            DESCRIPTION
                "The atmSigStatTable is not supported."
        VARIATION   atmSigDetectRestarts
            ACCESS      not-implemented
            DESCRIPTION
                "The atmSigStatTable is not supported."
        VARIATION   atmSigEmitRestarts
            ACCESS      not-implemented
            DESCRIPTION
                "The atmSigStatTable is not supported."
        VARIATION   atmSigInEstabls
            ACCESS      not-implemented
            DESCRIPTION
                "The atmSigStatTable is not supported."
        VARIATION   atmSigOutEstabls
            ACCESS      not-implemented
            DESCRIPTION
                "The atmSigStatTable is not supported."
        VARIATION   atmVplLogicalPortDef
            ACCESS      not-implemented
            DESCRIPTION
                "The atmVplLogicalPortTable is not supported."
        VARIATION   atmVplLogicalPortIndex
            ACCESS      not-implemented
            DESCRIPTION
                "The atmVplLogicalPortTable is not supported."
        VARIATION   atmIntfConfigType
            ACCESS      not-implemented
            DESCRIPTION
                "The atmInterfaceExtTable is not supported."
        VARIATION   atmIntfActualType
            ACCESS      not-implemented
            DESCRIPTION
                "The atmInterfaceExtTable is not supported."
        VARIATION   atmIntfConfigSide
            ACCESS      not-implemented
            DESCRIPTION
                "The atmInterfaceExtTable is not supported."
        VARIATION   atmIntfActualSide
            ACCESS      not-implemented
            DESCRIPTION
                "The atmInterfaceExtTable is not supported."
        VARIATION   atmIntfIlmiAdminStatus
            ACCESS      not-implemented
            DESCRIPTION
                "The atmInterfaceExtTable is not supported."
        VARIATION   atmIntfIlmiOperStatus
            ACCESS      not-implemented
            DESCRIPTION
                "The atmInterfaceExtTable is not supported."
        VARIATION   atmIntfIlmiFsmState
            ACCESS      not-implemented
            DESCRIPTION
                "The atmInterfaceExtTable is not supported."
        VARIATION   atmIntfIlmiEstablishConPollIntvl
            ACCESS      not-implemented
            DESCRIPTION
                "The atmInterfaceExtTable is not supported."
        VARIATION   atmIntfIlmiCheckConPollIntvl
            ACCESS      not-implemented
            DESCRIPTION
                "The atmInterfaceExtTable is not supported."
        VARIATION   atmIntfIlmiConPollInactFactor
            ACCESS      not-implemented
            DESCRIPTION
                "The atmInterfaceExtTable is not supported."
        VARIATION   atmIntfIlmiPublicPrivateIndctr
            ACCESS      not-implemented
            DESCRIPTION
                "The atmInterfaceExtTable is not supported."
        VARIATION   atmInterfaceConfMaxSvpcVpi
            ACCESS      not-implemented
            DESCRIPTION
                "The atmInterfaceExtTable is not supported."
        VARIATION   atmInterfaceCurrentMaxSvpcVpi
            ACCESS      not-implemented
            DESCRIPTION
                "The atmInterfaceExtTable is not supported."
        VARIATION   atmInterfaceConfMaxSvccVpi
            ACCESS      not-implemented
            DESCRIPTION
                "The atmInterfaceExtTable is not supported."
        VARIATION   atmInterfaceCurrentMaxSvccVpi
            ACCESS      not-implemented
            DESCRIPTION
                "The atmInterfaceExtTable is not supported."
        VARIATION   atmInterfaceConfMinSvccVci
            ACCESS      not-implemented
            DESCRIPTION
                "The atmInterfaceExtTable is not supported."
        VARIATION   atmInterfaceCurrentMinSvccVci
            ACCESS      not-implemented
            DESCRIPTION
                "The atmInterfaceExtTable is not supported."
        VARIATION   atmIntfSigVccRxTrafficDescrIndex
            ACCESS      not-implemented
            DESCRIPTION
                "The atmInterfaceExtTable is not supported."
        VARIATION   atmIntfSigVccTxTrafficDescrIndex
            ACCESS      not-implemented
            DESCRIPTION
                "The atmInterfaceExtTable is not supported."
        VARIATION   atmIntfPvcFailures
            ACCESS      not-implemented
            DESCRIPTION
                "The atmInterfaceExtTable is not supported."
        VARIATION   atmIntfCurrentlyFailingPVpls
            ACCESS      not-implemented
            DESCRIPTION
                "The atmInterfaceExtTable is not supported."
        VARIATION   atmIntfCurrentlyFailingPVcls
            ACCESS      not-implemented
            DESCRIPTION
                "The atmInterfaceExtTable is not supported."
        VARIATION   atmIntfPvcFailuresTrapEnable
            ACCESS      not-implemented
            DESCRIPTION
                "The atmInterfaceExtTable is not supported."
        VARIATION   atmIntfPvcNotificationInterval
            ACCESS      not-implemented
            DESCRIPTION
                "The atmInterfaceExtTable is not supported."
        VARIATION   atmIntfLeafSetupFailures
            ACCESS      not-implemented
            DESCRIPTION
                "The atmInterfaceExtTable is not supported."
        VARIATION   atmIntfLeafSetupRequests
            ACCESS      not-implemented
            DESCRIPTION
                "The atmInterfaceExtTable is not supported."
        VARIATION   atmCurrentlyFailingPVplTimeStamp
            ACCESS      not-implemented
            DESCRIPTION
                "The atmCurrentlyFailingPVplTable is not supported."
        VARIATION   atmCurrentlyFailingPVclTimeStamp
            ACCESS      not-implemented
            DESCRIPTION
                "The atmCurrentlyFailingPVclTable is not supported."
    SUPPORTS    ATM-FORUM-SNMP-M4-MIB
        INCLUDES  {
            atmfM4VplGroup,
            atmfM4VclGroup }
    ::= { usdAtmSwitchAgent 1 }


-- *****************************************************************************
-- ATM traffic shaping agent capabilities
-- *****************************************************************************
usdAtmTrafficShapingAgent OBJECT IDENTIFIER ::= { usdAtmAgent 5 }

usdAtmTrafficShapingAgentV1 AGENT-CAPABILITIES
    PRODUCT-RELEASE
        "Version 1 of the ATM traffic shaping subcomponent of the Unisphere
        Routing Switch SNMP agent.  This version of the ATM traffic shaping
        subcomponent is supported in the Unisphere RX 3.3 and subsequent system
        releases."
    STATUS      current
    DESCRIPTION
        "The MIBs supported by the SNMP agent for the ATM application in the
        Unisphere Routing Switch."
    SUPPORTS    Unisphere-Data-ATM-MIB
        INCLUDES  {
            usdAtmTrafficShapingGroup }
    ::= { usdAtmTrafficShapingAgent 1 }

END
