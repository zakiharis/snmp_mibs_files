-- *****************************************************************
-- BENU-PLATFORM-MIB.txt : Structure of Management Information for
-- Benu Platform
--
-- Copyright (C) 2012  by Benu Networks, Inc.
-- All rights reserved.
-- *****************************************************************
BENU-PLATFORM-MIB DEFINITIONS ::= BEGIN

    IMPORTS
        MODULE-IDENTITY
            FROM SNMPv2-SMI
        benu
            FROM BENU-ENTERPRISE-MIB;


    benuPlatform  MODULE-IDENTITY
            LAST-UPDATED "201210180000Z" -- October 18, 2012
            ORGANIZATION "Benu Networks,Inc"
            CONTACT-INFO "Benu Networks,Inc
                          Corporate Headquarters
                          300 Concord Road, Suite 110
                          Billerica, MA 01821 USA
                          Tel: +1 978-223-4700
                          Fax: +1 978-362-1908
                          Email: info@benunets.com"
            DESCRIPTION
                "The Structure of Management Information for the
                Benu Platform ."
            REVISION "201210180000Z" -- October 18, 2012
            DESCRIPTION "Initial Version."

        ::= { benu 1 }

END
