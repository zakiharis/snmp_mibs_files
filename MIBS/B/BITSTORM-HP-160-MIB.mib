-- File Name : BITSTORM-HP-160.my
-- Date      : Thu Dec 13 08:59:41 CST 2006
-- Author    : AdventNet Agent Toolkit Java Edition - MIB Editor 6


-- *****************************************************************
-- Zhone Enterprise MIB
-- Product Name: BITSTORM-HP-160
-- Version: 4.6
--
-- Update and Release Notes:
--  Data(Y/M/D) | MIB version |   Note
--  2006-12-27      V1.0        1.First Release
--  2007-01-16      V1.1        1.remove BITSTORM-HP-160CfgClusterStatusTable
--                              2.add BITSTORM-HP-160CfgClusterState
--                                add BITSTORM-HP-160CfgClusterMemberState
--  2007-01-19      V1.2        1.remove events: GBE-LINKUP(201),
--     	                                         GBE-LINKDOWN(202),
--                              2.add alarm : GBE-LOS(201)
--                              3.remove event trap :BITSTORM-HP-160TrapEvtGBELinkUp
--                                                   BITSTORM-HP-160TrapEvtGBELinkDown
--
--                              4.add alarm trap :  BITSTORM-HP-160TrapAlmGBELOS
--                              5.rename   BITSTORM-HP-160TrapEvtVDSLPerf-NE-DAY-ESE to BITSTORM-HP-160TrapEvtVDSLPerf-NE-DAY-SES
--                                         BITSTORM-HP-160TrapEvtVDSLPerf-FE-DAY-ESE to  BITSTORM-HP-160TrapEvtVDSLPerf-FE-DAY-SES
--
--  2007-01-24      V1.3        1.add BITSTORM-HP-160MtnSyslogService
--                              2.remove BITSTORM-HP-160BridgevlanCrossConnectTable
--  2007-01-26      V1.4        1.update BITSTORM-HP-160LineTestResult value list
--  2007 01-30      V1.5        1.update syntax of BITSTORM-HP-160CfgPppoeVsaMode
--  2007 01-31      V1.5        1.update syntax of BITSTORM-HP-160SysAlmStatus and BITSTORM-HP-160CfgCLIFlags
--  2007 02-01      V1.6        1.add column BITSTORM-HP-160CfgAtmTrafficType
--                                           BITSTORM-HP-160CfgEnetTrafficPCR
--                                           BITSTORM-HP-160CfgEnetTrafficCDVT
--                              2.update syntax of BITSTORM-HP-160CfgEnetTrafficDescrIndex
--  2007 02-06      V1.7        1.define column range of BITSTORM-HP-160CfgEnetTrafficDescrTable
--  2007 02-13      V1.8        1.remove BITSTORM-HP-160CfgIgmpAclProfileBank-
--                              2.remove BITSTORM-HP-160CfgCLIFlags
--  2007 02-14      V1.9        1.remove BITSTORM-HP-160CfgIgmpAclProfileBank
--                              2.rename BITSTORM-HP-160CfgIgmpAclProfileMcMumber to BITSTORM-HP-160CfgIgmpAclProfileMcCount
--  2007 03-02      V2.0        1.update syntax of BITSTORM-HP-160SysAlmStatus
--  2007 03-06      V2.1        1.update syntax of BITSTORM-HP-160CfgCLITimeout  (range 1..59 is not allowed)
--
--
--
--  2007 03-26      V2.2        1.add Column BITSTORM-HP-160CfgIgmpAclProfileUsedCount
--                              2.add Column BITSTORM-HP-160IwPolicerUsedCount
--                              3.add Column BITSTORM-HP-160CfgEnetTrafficUsedCount
--  2007 03-27      V2.3        1.update syntax of BITSTORM-HP-160CfgDhcpCircuitIdType 0..4
--  2007 03-29      V2.4        1.add new table  BITSTORM-HP-160BportVlanRateLimitTable
--                                add BITSTORM-HP-160CfgVpmtGroup and three tables
--                                     BITSTORM-HP-160CfgVpmtTrunkTable
--                                     BITSTORM-HP-160CfgVpmtBportProfileTable
--                                     BITSTORM-HP-160CfgVpmtBridgePortBindTable
--
--                              2.update table BITSTORM-HP-160BportRateLimitTable   add BITSTORM-HP-160BportRateLimitEgressIwPolicerIdx and BITSTORM-HP-160BportRateLimitIngressIwPolicerIdx
--                                update table BITSTORM-HP-160CfgIgmpAclProfileTable   add BITSTORM-HP-160CfgIgmpAclProfileVlanEgressMap
--  2007 03-30      V2.5        1.remove  BITSTORM-HP-160MtnFlashBackupInfoTable
--                                        BITSTORM-HP-160MtnFlashBackupEntryCount
--                                        BITSTORM-HP-160MtnFlashBackupEntryType
--                                        BITSTORM-HP-160MtnFlashBackupActiveIndex
--                                and add BITSTORM-HP-160MtnFlashBackupInbandTable
--                                 BITSTORM-HP-160MtnFlashBackupGeneralTable
--                                 BITSTORM-HP-160MtnFlashBackupInbandActiveIndex
--                                 BITSTORM-HP-160MtnFlashBackupGeneralActiveIndex
--  2007 04-04      V2.6        1.file name size 32->64      (BITSTORM-HP-160MtnRemoteFTPFileName and BITSTORM-HP-160MtnCliCfgFTPFileName)
--  2007 04-11      V2.7        1.update BITSTORM-HP-160CfgEnetTrafficWeight range 1..10000
--                              2.add BITSTORM-HP-160CfgSystemConfiguration
--                                add BITSTORM-HP-160CfgSystemAclMode
--                                add BITSTORM-HP-160CfgSystemExtEtherType
--  2007 04-25      V2.8        1.remove BITSTORM-HP-160PhyEnetAdminStatus and BITSTORM-HP-160PhyEnetOperStatus
--  2007 04-26      V2.9        1.update syntax of BITSTORM-HP-160MtnActivePartition
--                              2.update value range of BITSTORM-HP-160CfgInbandManageVlanId
--  2007 05-02      V3.0        1.update syntax of BITSTORM-HP-160CfgBridgeProtocolFilter
--                              2.remove BITSTORM-HP-160CfgIgmpSourceTable
--  2007 05-09      V3.1        1.add BITSTORM-HP-160CfgBridgeNetBiosFilterTable and BITSTORM-HP-160CfgBridgeArpBcastFilterTable
--                              2.move the location of BITSTORM-HP-160CfgBridgePrioTagFilterTable   from 1.3.6.1.4.1.5833.18.2.4.3.4 to 1.3.6.1.4.1.5833.18.2.4.2.7.8
--  2007 05-24      V3.2        1.remove BITSTORM-HP-160CfgFdbCurrentCount
--  2007 06-05      V3.3        1.rename BITSTORM-HP-160CfgDefaultGateway to BITSTORM-HP-160CfgOutbandDefaultGateway
--  2007 06-08      V3.4        1.add BITSTORM-HP-160CfgIgmpAclProfileMsgCount
--
--  2007 06-21      V3.5        1.add BITSTORM-HP-160SysTemperatureDslValue read-only
--                                add BITSTORM-HP-160AgingTimeTable
--                                add BITSTORM-HP-160SnoopArpRequestTable
--                              2.BITSTORM-HP-160CfgSystemConfiguration add
--                                BITSTORM-HP-160CfgSystemAllowDownstreamBc
--                                BITSTORM-HP-160CfgSystemAllowIpFilter
--                                BITSTORM-HP-160CfgSystemAddAllowIpBySnoopDHCP
--                                BITSTORM-HP-160CfgSystemAgingTimePerPort
--                                BITSTORM-HP-160CfgSystemReplaceArpMac
--                                BITSTORM-HP-160CfgSystemSnoopArpDefaultGatewayMac
--                              3.BITSTORM-HP-160MtnCliCfgActionType add CLICONFIG-CHANGE-DETECT(21)
--                                add BITSTORM-HP-160MtnCliCfgConfigUnsaved
--                              4.change oid of BITSTORM-HP-160MtnFlashBackup	from BITSTORM-HP-160MtnCliConfig   to  BITSTORM-HP-160MtnMgt
--                              5.add BITSTORM-HP-160MtnImageProfileDisplayName
--                              6.add BITSTORM-HP-160BportPortBcRateLimitTable
--                              7.add BITSTORM-HP-160CfgBridgeAllowedIpFilterTable
--  2007 07-09      V3.6        1.add BITSTORM-HP-160SNTPSynchronize
--  2007 07-17      V3.7        1.update range (1..4095)
--                                  BITSTORM-HP-160BridgePortDefaultVlan
--                                  BITSTORM-HP-160CfgIgmpGroupVlan
--                                  BITSTORM-HP-160CfgIgmpRouterPortVlanId
--                                  BITSTORM-HP-160McBcRateLimitVlanId
--                                  BITSTORM-HP-160McFldRateLimitVlanId
--  2007 07-23      V3.8        1.add BITSTORM-HP-160SysInvCardType
--  2007 07-26      for Phase II
--  2007 07-26      V3.9        1.remove vsamode
--                              2.BITSTORM-HP-160CfgSystemConfiguration add
--                                BITSTORM-HP-160CfgSystemArpSpoofing
--                                BITSTORM-HP-160CfgSystemAntiMacSpoofing
--                              3.update the syntax of BITSTORM-HP-160CfgDhcpMode
--                              4.update the syntax of BITSTORM-HP-160CfgDslCircuitID and BITSTORM-HP-160CfgDslRemoteID
--                              5.remove BITSTORM-HP-160CfgDslIdForwardMode
--                              6.add BITSTORM-HP-160CfgDslpppoeMode
--                              7.remove BITSTORM-HP-160BridgePortVlanStacking
--                              8.add new table  BITSTORM-HP-160BportVlanTranslationTable
--                                               BITSTORM-HP-160BridgeArpSpoofingTable
--                                               BITSTORM-HP-160CfgDhcpServerProfileTable
--                                               BITSTORM-HP-160CfgDhcpServerProfileBindTable
--                                               BITSTORM-HP-160CfgDhcpQueryClientTable
--                                               BITSTORM-HP-160CfgDhcpStaticIPTable
--                                               BITSTORM-HP-160CfgBridgeL4SrcPortFilterTable
--                                               BITSTORM-HP-160CfgBridgeDstMacFilterTable
--                              9.add BITSTORM-HP-160CfgIgmpRouterPortRouterIp and BITSTORM-HP-160CfgIgmpRouterPortRouterReportIp  on BITSTORM-HP-160CfgIgmpRouterPortTable
--                              10.update syntax of BITSTORM-HP-160AtmTrafficType
--  2007 08-01      V4.0        1.remove BITSTORM-HP-160CfgSystemAclMode and BITSTORM-HP-160CfgSystemAllowIpFilter
--                              2.add BITSTORM-HP-160CfgLayerIIServiceOption
--                                add  BITSTORM-HP-160CfgAclService;
--                                     BITSTORM-HP-160CfgPppoeService;
--                                     BITSTORM-HP-160CfgDhcpService;
--                                     BITSTORM-HP-160CfgRateLimitService;
--                                     BITSTORM-HP-160CfgStackVlanService;
--                                     BITSTORM-HP-160BITSTORM-HP-160CfgAllowIpService;
--  2007 08-08      V4.1        1.remove BITSTORM-HP-160CfgDhcpService and BITSTORM-HP-160CfgAllowIpService
--                              2.add BITSTORM-HP-160CfgFilterAndPriorityRemarkService and BITSTORM-HP-160CfgNetBiosDenialService
--  2007 08-10      V4.2        1.add BITSTORM-HP-160StpBridgeID
--                              2.remove VDSL-CONFIG-INIT-FAILURE(606),
--		                         VDSL-PROTOCOL-INIT-FAILURE(607),
--                                remove BITSTORM-HP-160TrapAlmVdslConfigInitFailure and BITSTORM-HP-160TrapAlmVdslProtocolInitFailure
--                              3.update VDSL-DATA-INIT-FAILURE(605) to VDSL-INIT-FAILURE(605)
--                                update BITSTORM-HP-160TrapAlmVdslDataInitFailure to BITSTORM-HP-160TrapAlmVdslInitFailure
--                              4.update syntax of BITSTORM-HP-160CfgBridgeTpFdbStatus
--  2007 08-14      V4.3        1.add BITSTORM-HP-160CfgAllowIpService
--  2007 08-17      V4.4        1.update BITSTORM-HP-160CfgEnetTrafficWeight     SYNTAX      Unsigned32 (1..127)
--  2007 09-06      V4.5        1.update syntax of BITSTORM-HP-160MtnFlashWrite
--                                remove BITSTORM-HP-160MtnDlStatus
--                                add BITSTORM-HP-160MtnBootLoaderUpdate
--  2007 09-06      V4.5        1.add BITSTORM-HP-160SysInvBootLoaderVersion
--                                    BITSTORM-HP-160SysInvPortCount
--                                    BITSTORM-HP-160SysSysFanSupported
--                              2.update BITSTORM-HP-160CfgEnetTrafficWeight     SYNTAX      Unsigned32 (1..42)
--  2007 09-19      V4.6        1.add BITSTORM-HP-160CfgIgmpLeaveMode
--*****************************************************************

BITSTORM-HP-160-MIB	DEFINITIONS ::= BEGIN
	IMPORTS
		PhysicalIndex, entPhysicalIndex
			FROM ENTITY-MIB
		PhysAddress, RowStatus, TAddress, TEXTUAL-CONVENTION, TruthValue
			FROM SNMPv2-TC
		OBJECT-TYPE
			FROM RFC-1212
		ifIndex, InterfaceIndex
			FROM IF-MIB
		Integer32, IpAddress, Unsigned32, NOTIFICATION-TYPE, enterprises, MODULE-IDENTITY, OBJECT-TYPE
			FROM SNMPv2-SMI;
--	  zhone
--			FROM Zhone;

  org OBJECT IDENTIFIER
    ::=  {  iso  3  }

  dod OBJECT IDENTIFIER
    ::=  {  org  6  }

  internet  OBJECT IDENTIFIER
    ::=  {  dod  1  }

  private OBJECT IDENTIFIER
    ::=  {  internet  4  }

  enterprises OBJECT IDENTIFIER
    ::=  {  private  1  }

  zhone OBJECT IDENTIFIER
    ::=  {  enterprises  5504  }

	bitSTORM-HP-160	MODULE-IDENTITY
		LAST-UPDATED	"200608100000Z"
		ORGANIZATION	"Zhone"
		CONTACT-INFO	"Zhone"
		DESCRIPTION		"Zhone IP-DSLAM root MIB module."
		REVISION		"200608100000Z"
		DESCRIPTION		"The modified revision : v4.4"
		::=  { zhone 18 }

-- TEXTUAL-CONVENTIONS --
   VdslLineEntity ::= TEXTUAL-CONVENTION
       STATUS       current
       DESCRIPTION
           "Identifies a transceiver as being either Vtuc or Vtur.
           A VDSL line consists of two transceivers, a Vtuc and a
           Vtur.  Attributes with this syntax reference the two sides
           of a line.  Specified as an INTEGER, the two values are:

           vtuc(1)  -- central site transceiver
           vtur(2)  -- remote site transceiver"
       SYNTAX  INTEGER
           {
           vtuc(1),
           vtur(2)
           }

	BITSTORM-HP-160EventType ::= TEXTUAL-CONVENTION
		DISPLAY-HINT	""
		STATUS			current
		DESCRIPTION
			"The event type identifier number."
		SYNTAX 			INTEGER  {
		systemrestart(1),
		systemdownloadbegin(2),
		systemdownloadsuccess(3),
		systemdownloadfail(4),
		systemprovisiondataexport(5),
		systemprovisiondataimport(6),
		systemprovisiondatasetdefault(7),
		systemalarmlogclear(9),
		systemeventlogclear(10),
		systemrtcdatetimechange(11),
		systemsoftwareacobuttonset(12),
		systemsoftwareacobuttonclear(13),
		systemalarmlevelmaskflagchange(14),
		systemsnmpauthfail(15),
		systemftpreceptionstart(17),
		systemftpreceptioncomplete(18),
		systemftpreceptionincomplete(19),
		systemsntptimezonechange(21),
		systemsntpprovisionchanged(23),
		systemdatabasesavingfailed(25),
		atmcreatevcl(102),
		atmmodifyvcl(103),
		atmdeletevcl(104),
		atmoamcreateloopback(105),
		atmoamdeleteloopback(106),
		--gbe-linkup(201),
		--gbe-linkdown(202),
		xdsl-port-info-changed(501),
		vdsl-port-binding-changed(601),
		vdsl-port-enabled(602),
		vdsl-port-disabled(603),
		vdsl-port-reenabled(604),
		vdsl-port-linkup(605),
		vdsl-port-linkdown(606),
		vdsl-line-conf-profile-created(607),
		vdsl-line-conf-profile-deleted(608),
		vdsl-line-conf-profile-changed(609),
		vdsl-line-alarm-conf-profile-created(610),
		vdsl-line-alarm-conf-profile-deleted(611),
		vdsl-line-alarm-conf-profile-changed(612),
		vdsl-port-profile-transfer-failed(613),

                vdsl-loopback-set(614),
                vdsl-delt-set(615),
                vdsl-delt-done(616),

		vdsl-perf-ne-es(651),
		vdsl-perf-ne-ses(652),
		vdsl-perf-ne-uas(653),
		vdsl-perf-fe-es(654),
		vdsl-perf-fe-ses(655),
		vdsl-perf-fe-uas(656),
		vdsl-perf-ne-day-es(657),
		vdsl-perf-ne-day-ses(658),
		vdsl-perf-ne-day-uas(659),
		vdsl-perf-fe-day-es(660),
		vdsl-perf-fe-day-ses(661),
		vdsl-perf-fe-day-uas(662),
		vdsl-down-max-snr-mgn(663),
		vdsl-down-min-snr-mgn(664),
		vdsl-up-max-snr-mgn(665),
		vdsl-up-min-snr-mgn(666),
		vdsl-init-failure-trap(667)
		}

	MacAddress ::= TEXTUAL-CONVENTION
		DISPLAY-HINT	""
		STATUS			current
		DESCRIPTION
			""
		SYNTAX 			OCTET STRING  ( SIZE ( 6  ) )

	BITSTORM-HP-160LedType ::= TEXTUAL-CONVENTION
		DISPLAY-HINT	""
		STATUS			current
		DESCRIPTION
			"LED status"
		SYNTAX 			INTEGER  { bitstorm-hp-160ledoff ( 0 ) , bitstorm-hp-160ledred ( 1 ) , bitstorm-hp-160ledgreen ( 2 ) , bitstorm-hp-160ledyellow ( 3 ) , bitstorm-hp-160ledredflash ( 5 ) , bitstorm-hp-160ledgreenflash ( 6 ) , bitstorm-hp-160ledyellowflash ( 7 ) }

         BITSTORM-HP-160EnetTrafficType ::= TEXTUAL-CONVENTION
                DISPLAY-HINT	""
                STATUS    current
                DESCRIPTION
                        "Traffic Descriptor Type"
                SYNTAX    INTEGER
                {
                  enetpktshapingwfq(1),
                  enetpktshapingppr(2),
                  enetpktshapingcir(3),
                  enetpktshapingcireir(4)
                 }

         BITSTORM-HP-160AtmTrafficType ::= TEXTUAL-CONVENTION
                DISPLAY-HINT	""
                STATUS    current
                DESCRIPTION
                        "Atm Traffic Descriptor Type"
                SYNTAX    INTEGER
                {
                  atmPolicingCBR(9),
                  atmPolicingUBR(12)
                 }

	PortList ::= TEXTUAL-CONVENTION
		DISPLAY-HINT	""
		STATUS			current
		DESCRIPTION
			"Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
		SYNTAX 			OCTET STRING

	BITSTORM-HP-160AlmType ::= TEXTUAL-CONVENTION
		DISPLAY-HINT	""
		STATUS			current
		DESCRIPTION
			"The alarm type identifier number."
		SYNTAX 			INTEGER  {
		sys-housekeep1(101),
		sys-housekeep2(102),
		sys-housekeep3(103),
		sys-housekeep4(104),
		sys-fan(105),
		sys-selftestfailed(106),
		sys-abovetemp(107),
		sys-belowtemp(108),
		gbe-los(201),
		vdsl-lof(601),
		vdsl-los(602),
		vdsl-losq(603),
		vdsl-lol(604),
		vdsl-init-failure(605),
--		vdsl-config-init-failure(606),
--		vdsl-protocol-init-failure(607),
		vdsl-ese(608),
		vdsl-ncd-slow(609),
		vdsl-lcd-slow(610),
		vdsl-ncd-fast(611),
		vdsl-lcd-fast(612),
		vdsl-lof-fe(613),
		vdsl-los-fe(614),
		vdsl-lpr-fe(615),
		vdsl-losq-fe(616),
		vdsl-no-peer-vtu-present-fe(617),
		vdsl-ese-fe(618),
		vdsl-ncd-slow-fe(619),
		vdsl-lcd-slow-fe(620),
		vdsl-ncd-fast-fe(621),
		vdsl-lcd-fast-fe(622)
		}


--	AdslPlusTransmissionModeType ::= TEXTUAL-CONVENTION
--		DISPLAY-HINT	""
--		STATUS			current
--		DESCRIPTION
--			"A set of ADSL line transmission modes, with one bit
  --                 per mode.  The notes (F) and (L) denote Full-Rate
    --               and G.Lite respectively:
      --               Bit 00 : Regional Std. (ANSI T1.413) (F)
      --               Bit 01 : Regional Std. (ETSI DTS/TM06006) (F)
--                     Bit 02 : G.992.1 POTS non-overlapped (F)
--                     Bit 03 : G.992.1 POTS overlapped (F)
--                     Bit 04 : G.992.1 ISDN non-overlapped (F)
--                     Bit 05 : G.992.1 ISDN overlapped (F)
--                     Bit 06 : G.992.1 TCM-ISDN non-overlapped (F)
--                     Bit 07 : G.992.1 TCM-ISDN overlapped (F)
--                     Bit 08 : G.992.2 POTS non-overlapped (L)
--                     Bit 09 : G.992.2 POTS overlapped (L)
--                     Bit 10 : G.992.2 with TCM-ISDN non-overlapped (L)
--                     Bit 11 : G.992.2 with TCM-ISDN overlapped (L)
--                     Bit 12 : G.992.1 TCM-ISDN symmetric (F)
--                     Bit 13 : ADSL plus pots non-overlapped
--                     Bit 14 : G.992.1 Annex I TCM-ISDN non-overlapped
--                     Bit 15 : G.992.1 Annex I TCM-ISDN overlapped
--                     Bit 16 : G.992.2 Annex I TCM-ISDN non-overlapped
--                     Bit 17 : G.992.2 Annex I TCM-ISDN overlapped
--                     Bit 18 : ADSL plus pots overlapped
--                     Bit 22 : G.992.3 Annex READSL2 POTS overlapped
--                     Bit 23 : G.992.3 Annex READSL2 POTS non-overlapped
--                     Bit 26 : G.992.3 Annex ADSL2 Plus POTS non-overlapped
--                     Bit 27 : G.992.3 Annex ADSL2 Plus POTS overlapped
--                     Bit 28 : G.992.3 Annex ADSL2 POTS non-overlapped
--                     Bit 29 : G.992.3 Annex ADSL2 POTS overlapped
 --                    Bit 30 : G.992.1 G.Span Plus POTS overlapped
 --                    Bit 31 : G.992.1 G.Span Plus POTS non-overlapped
 --                 "
--		SYNTAX 			BITS  { ansit1413 ( 0 ) , etsi ( 1 ) , q9921PotsNonOverlapped ( 2 ) , q9921PotsOverlapped ( 3 ) , q9921IsdnNonOverlapped ( 4 ) , q9921IsdnOverlapped ( 5 ) , q9921TcmIsdnNonOverlapped ( 6 ) , q9921TcmIsdnOverlapped ( 7 ) , q9922PotsNonOverlapeed ( 8 ) , q9922PotsOverlapped ( 9 ) , q9922TcmIsdnNonOverlapped ( 10 ) , q9922TcmIsdnOverlapped ( 11 ) , q9921TcmIsdnSymmetric ( 12 ) , adslPlusPotsNonOverlapped ( 13 ) , q9921AnnexItcmIsdnNonOverlapped ( 14 ) , q9921AnnexItcmIsdnOverlapped ( 15 ) , q9922AnnexItcmIsdnNonOverlapped ( 16 ) , q9922AnnexItcmIsdnOverlapped ( 17 ) , adslPlusPotsOverlapped ( 18 ) , q9923AnnexREADSL2PotsOverlapped ( 22 ) , q9923AnnexREADSL2PotsNonOverlapped ( 23 ) , q9923AnnexADSL2PlusPotsNonOverlapped ( 26 ) , q9923AnnexADSL2PlusPotsOverlapped ( 27 ) , q9923AnnexADSL2PotsNonOverlapped ( 28 ) , q9923AnnexADSL2PotsOverlapped ( 29 ) , q9921GSpanPlusPotsOverlapped ( 30 ) , q9921GSpanPlusPotsNonOverlapped ( 31 ) }

--	org	OBJECT IDENTIFIER
--		::=  {  iso  3  }
--
--	dod	OBJECT IDENTIFIER
--		::=  {  org  6  }
--
--	internet	OBJECT IDENTIFIER
--		::=  {  dod  1  }
--
--	private	OBJECT IDENTIFIER
--		::=  {  internet  4  }
--
--	enterprises	OBJECT IDENTIFIER
--		::=  {  private  1  }
--
--	Zhone	OBJECT IDENTIFIER
--		::=  {  enterprises  5504  }

bitSTORM-HP-160MibVersion  OBJECT-TYPE
        SYNTAX  OCTET STRING(SIZE(1..16))
        MAX-ACCESS  read-only
        STATUS  current
        DESCRIPTION
        "This object value presents that current  NE by implementation
         is compliant to which version the enterprise MIB belongs to.
        "
   ::= {bitSTORM-HP-160 1}

	bitSTORM-HP-160CfgMgt	OBJECT IDENTIFIER
		::=  {  bitSTORM-HP-160  2  }

	bitSTORM-HP-160SysMgt	OBJECT IDENTIFIER
		::=  {  bitSTORM-HP-160  3  }

	bitSTORM-HP-160MtnMgt	OBJECT IDENTIFIER
		::=  {  bitSTORM-HP-160  4  }

	bitSTORM-HP-160AlmMgt	OBJECT IDENTIFIER
		::=  {  bitSTORM-HP-160  5  }

	bitSTORM-HP-160PerfMgt	OBJECT IDENTIFIER
		::=  {  bitSTORM-HP-160  6  }

	bitSTORM-HP-160TrapMgt	OBJECT IDENTIFIER
		::=  {  bitSTORM-HP-160  7  }

	bitSTORM-HP-160CfgTime	OBJECT IDENTIFIER
		::=  {  bitSTORM-HP-160CfgMgt  1  }

	bitSTORM-HP-160CfgAddress	OBJECT IDENTIFIER
		::=  {  bitSTORM-HP-160CfgMgt  2  }

	bitSTORM-HP-160CfgPhy	OBJECT IDENTIFIER
		::=  {  bitSTORM-HP-160CfgMgt  3  }

--	bitSTORM-HP-160CfgIfc	OBJECT IDENTIFIER
--		::=  {  bitSTORM-HP-160CfgMgt  4  }

	bitSTORM-HP-160CfgBridge	OBJECT IDENTIFIER
		::=  {  bitSTORM-HP-160CfgMgt  4  }

	bitSTORM-HP-160CfgXdslSetting	OBJECT IDENTIFIER
		::=  {  bitSTORM-HP-160CfgMgt  5  }

	bitSTORM-HP-160CfgCLISettings	OBJECT IDENTIFIER  
		::=  {  bitSTORM-HP-160CfgMgt  6  }

	bitSTORM-HP-160CfgCluster	OBJECT IDENTIFIER
		::=  {  bitSTORM-HP-160CfgMgt  7  }

--	bitSTORM-HP-160CfgEnetTrafficDescrTable	OBJECT IDENTIFIER
--		::=  {  bitSTORM-HP-160CfgMgt  9  }
bitSTORM-HP-160CfgEnetTrafficDescrTable	OBJECT-TYPE
		SYNTAX		SEQUENCE  OF  BITSTORM-HP-160CfgEnetTrafficDescrEntry
		MAX-ACCESS	not-accessible
		STATUS		current
		DESCRIPTION	"Description"
		::=  { bitSTORM-HP-160CfgMgt  8 }

		

	bitSTORM-HP-160SysInventory	OBJECT IDENTIFIER
		::=  {  bitSTORM-HP-160SysMgt  1  }

	bitSTORM-HP-160LED	OBJECT IDENTIFIER
		::=  {  bitSTORM-HP-160SysMgt  2  }

	bitSTORM-HP-160SysTemperature	OBJECT IDENTIFIER
		::=  {  bitSTORM-HP-160SysMgt  3  }

	bitSTORM-HP-160SystemRestart	OBJECT-TYPE
		SYNTAX			INTEGER  { active ( 1 ) , ready ( 0 ) }
		MAX-ACCESS		read-write
		STATUS			current
		DESCRIPTION		"Always use active(1) to restart the system."
		::=  {  bitSTORM-HP-160MtnMgt  1  }

	bitSTORM-HP-160RestartSNMPAgent	OBJECT-TYPE
		SYNTAX			INTEGER  { active ( 1 ) , ready ( 0 ) }
		MAX-ACCESS		read-write
		STATUS			current
		DESCRIPTION		"SNMP Agent Restart.
       active: Restart SNMP Agent"
		::=  {  bitSTORM-HP-160MtnMgt  2  }

--	bitSTORM-HP-160MtnDatabase	OBJECT IDENTIFIER
--		::=  {  bitSTORM-HP-160MtnMgt  3  }

	bitSTORM-HP-160MtnFirmware	OBJECT IDENTIFIER
		::=  {  bitSTORM-HP-160MtnMgt  3  }

	bitSTORM-HP-160MtnSyslog	OBJECT IDENTIFIER
		::=  {  bitSTORM-HP-160MtnMgt  4  }

	bitSTORM-HP-160MtnAtmOamLoopbackTest	OBJECT IDENTIFIER
		::=  {  bitSTORM-HP-160MtnMgt  5  }
         
	bitSTORM-HP-160LineTestResult	OBJECT-TYPE
		SYNTAX			Integer32  (0..4294967295)
		MAX-ACCESS		read-write
		STATUS			current
		DESCRIPTION		"
		bitmap
		POST :    Bit[1..0] --> 0:ALL PASS, 1:TESTING , 2:NO TEST, 3:FATAL ERROR

                <BME-1> <BME-2> <BME-3> <Discription>
                Bit[ 2] Bit[12] Bit[22] BME Status                                  --> 0:READY, 1:NA
                Bit[ 3] Bit[13] Bit[23] HIC Host-BME Connection Test                --> 0:PASS, 1:FAIL
                Bit[ 4] Bit[14] Bit[24] BME Core & Mem Clk, EMI Initialization      --> 0:PASS, 1:FAIL
                Bit[ 5] Bit[15] Bit[25] HIC PIO SDRAM Read/Write Tests              --> 0:PASS, 1:FAIL
                Bit[ 6] Bit[16] Bit[26] SDRAM Address & Data Bus Connection Tests   --> 0:PASS, 1:FAIL
                Bit[ 7] Bit[17] Bit[27] Memory to Memory BME DMA Tests              --> 0:PASS, 1:FAIL
                Bit[ 8] Bit[18] Bit[28] External Memory Interface Test              --> 0:PASS, 1:FAIL
                Bit[ 9] Bit[19] Bit[29] BME-AFE DDR Bus Connection Tests            --> 0:PASS, 1:FAIL
                Bit[10] Bit[20] Bit[30] AFE Register Read/Write Tests               --> 0:PASS, 1:FAIL
                Bit[11] Bit[21] Bit[31] IFE Register Read/Write Tests               --> 0:PASS, 1:FAIL
                "
		::=  {  bitSTORM-HP-160MtnMgt  6  }

	bitSTORM-HP-160MtnCliConfig 	OBJECT IDENTIFIER
		::=  {  bitSTORM-HP-160MtnMgt  7  }
		
	bitSTORM-HP-160AlmMain	OBJECT IDENTIFIER
		::=  {  bitSTORM-HP-160AlmMgt  1  }

	bitSTORM-HP-160AlmProfileTable	OBJECT-TYPE
		SYNTAX		SEQUENCE  OF  BITSTORM-HP-160AlmProfileEntry
		MAX-ACCESS	not-accessible
		STATUS		current
		DESCRIPTION	"Used to specify alarm log critera."
		::=  { bitSTORM-HP-160AlmMgt  2 }

	bitSTORM-HP-160AlmProfileEntry	OBJECT-TYPE
		SYNTAX		BITSTORM-HP-160AlmProfileEntry
		MAX-ACCESS	not-accessible
		STATUS		current
		DESCRIPTION	"An Entry in the alarm profile table."
		INDEX		{  bitSTORM-HP-160AlmProfileTypeId  }
		::=  { bitSTORM-HP-160AlmProfileTable 1 }

	BITSTORM-HP-160AlmProfileEntry  ::=  SEQUENCE {
		bitSTORM-HP-160AlmProfileTypeId  BITSTORM-HP-160AlmType,
		bitSTORM-HP-160AlmMask  INTEGER,
		bitSTORM-HP-160AlmLevelSet  INTEGER
		}


	bitSTORM-HP-160AlmProfileTypeId	OBJECT-TYPE	
		SYNTAX			BITSTORM-HP-160AlmType
		MAX-ACCESS		not-accessible
		STATUS			current
		DESCRIPTION		"The alarm type identifier number."
		::=  {  bitSTORM-HP-160AlmProfileEntry  1  }


	bitSTORM-HP-160AlmMask	OBJECT-TYPE	
		SYNTAX			INTEGER  { almMask ( 0 ) , almNonMask ( 1 ) } 
		MAX-ACCESS		read-write
		STATUS			current
		DESCRIPTION		"This object specifies an alarm for which notification
         generation is enabled or disabled.

         0: Mask the alarm.
         1: Non-mask the alarm. "
		::=  {  bitSTORM-HP-160AlmProfileEntry  2  }


	bitSTORM-HP-160AlmLevelSet	OBJECT-TYPE	
		SYNTAX			INTEGER  { almLevelMinor ( 1 ) , almLevelMajor ( 2 ) } 
		MAX-ACCESS		read-write
		STATUS			current
		DESCRIPTION		"This object specifies the alarm level.

         1: Minor
         2: Major "
		::=  {  bitSTORM-HP-160AlmProfileEntry  3  }

	bitSTORM-HP-160AlmCurrentTable	OBJECT-TYPE
		SYNTAX		SEQUENCE  OF  BITSTORM-HP-160AlmCurrentEntry
		MAX-ACCESS	not-accessible
		STATUS		current
		DESCRIPTION	"The current alarm table."
		::=  { bitSTORM-HP-160AlmMgt  3 }

	bitSTORM-HP-160AlmCurrentEntry	OBJECT-TYPE
		SYNTAX		BITSTORM-HP-160AlmCurrentEntry
		MAX-ACCESS	not-accessible
		STATUS		current
		DESCRIPTION	"An Entry in the current alarm table."
		INDEX		{  bitSTORM-HP-160AlmSeqId  }
		::=  { bitSTORM-HP-160AlmCurrentTable 1 }

	BITSTORM-HP-160AlmCurrentEntry  ::=  SEQUENCE {
		bitSTORM-HP-160AlmCurrentEntPhyIndex  PhysicalIndex,
		bitSTORM-HP-160AlmCurrentIfIndex  InterfaceIndex,
		bitSTORM-HP-160AlmCurrentTypeId  BITSTORM-HP-160AlmType,
		bitSTORM-HP-160AlmCurrentLevel  INTEGER,
		bitSTORM-HP-160AlmCurrentState  INTEGER,
		bitSTORM-HP-160AlmCurrentTime  OCTET STRING
		}


	bitSTORM-HP-160AlmCurrentEntPhyIndex	OBJECT-TYPE	
		SYNTAX			PhysicalIndex  ( 1 .. 2147483647  ) 
		MAX-ACCESS		read-only
		STATUS			current
		DESCRIPTION		"This attribute indicates the suffered entity by the entPhysicalIndex."
		::=  {  bitSTORM-HP-160AlmCurrentEntry  1  }


	bitSTORM-HP-160AlmCurrentIfIndex	OBJECT-TYPE	
		SYNTAX			InterfaceIndex
		MAX-ACCESS		read-only
		STATUS			current
		DESCRIPTION		"This attribute indicates the suffered interface index by ifIndex."
		::=  {  bitSTORM-HP-160AlmCurrentEntry  2  }


	bitSTORM-HP-160AlmCurrentTypeId	OBJECT-TYPE	
		SYNTAX			BITSTORM-HP-160AlmType
		MAX-ACCESS		read-only
		STATUS			current
		DESCRIPTION		"This attribute indicates the suffered alarm type name."
		::=  {  bitSTORM-HP-160AlmCurrentEntry  3  }


	bitSTORM-HP-160AlmCurrentLevel	OBJECT-TYPE	
		SYNTAX			INTEGER  { bitSTORM-HP-160AlmLevelMinor ( 1 ) , bitSTORM-HP-160AlmLevelMajor ( 2 ) } 
		MAX-ACCESS		read-only
		STATUS			current
		DESCRIPTION		"This attribute indicates the alarm level specified by alarm profile.

        1: Minor
        2: Major"
		::=  {  bitSTORM-HP-160AlmCurrentEntry  4  }


	bitSTORM-HP-160AlmCurrentState	OBJECT-TYPE	
		SYNTAX			INTEGER  { bitSTORM-HP-160AlmStateSet ( 1 ) , bitSTORM-HP-160AlmStateClear ( 2 ) } 
		MAX-ACCESS		read-only
		STATUS			current
		DESCRIPTION		"This attribute indicates the alarm occurrence.

        1: Alarm has not occurred
        2: Alarm has occurred-----by current alarm table definition, this attribute will be always this value. "
		::=  {  bitSTORM-HP-160AlmCurrentEntry  5  }


	bitSTORM-HP-160AlmCurrentTime	OBJECT-TYPE	
		SYNTAX			OCTET STRING  ( SIZE ( 32  ) ) 
		MAX-ACCESS		read-only
		STATUS			current
		DESCRIPTION		"This attribute indicates the alarm occurence time of the
        current alarm table."
		::=  {  bitSTORM-HP-160AlmCurrentEntry  6  }

	bitSTORM-HP-160AlmTable	OBJECT-TYPE
		SYNTAX		SEQUENCE  OF  BITSTORM-HP-160AlmEntry
		MAX-ACCESS	not-accessible
		STATUS		current
		DESCRIPTION	"The alarm log table."
		::=  { bitSTORM-HP-160AlmMgt  4 }

	bitSTORM-HP-160AlmEntry	OBJECT-TYPE
		SYNTAX		BITSTORM-HP-160AlmEntry
		MAX-ACCESS	not-accessible
		STATUS		current
		DESCRIPTION	"An Entry in the alarm log table."
		INDEX		{  bitSTORM-HP-160AlmSeqId  }
		::=  { bitSTORM-HP-160AlmTable 1 }

	BITSTORM-HP-160AlmEntry  ::=  SEQUENCE {
		bitSTORM-HP-160AlmSeqId  Integer32,
		bitSTORM-HP-160AlmEntPhyIndex  PhysicalIndex,
		bitSTORM-HP-160AlmIfIndex  InterfaceIndex,
		bitSTORM-HP-160AlmTypeId  BITSTORM-HP-160AlmType,
		bitSTORM-HP-160AlmLevel  INTEGER,
		bitSTORM-HP-160AlmState  INTEGER,
		bitSTORM-HP-160AlmTime  OCTET STRING
		}


	bitSTORM-HP-160AlmSeqId	OBJECT-TYPE	
		SYNTAX			Integer32  ( 1 .. 65535  ) 
		MAX-ACCESS		read-only
		STATUS			current
		DESCRIPTION		"This object is used by the alarm log table
        to identify the row of this table.
        To check new row number for a new alarm occurrence,
        just obtain this value by
        bitSTORM-HP-160AlmSeqIdNext."
		::=  {  bitSTORM-HP-160AlmEntry  1  }


	bitSTORM-HP-160AlmEntPhyIndex	OBJECT-TYPE	
		SYNTAX			PhysicalIndex
		MAX-ACCESS		read-only
		STATUS			current
		DESCRIPTION		"This attribute indicates the suffered entity by its entPhysicalIndex."
		::=  {  bitSTORM-HP-160AlmEntry  2  }


	bitSTORM-HP-160AlmIfIndex	OBJECT-TYPE	
		SYNTAX			InterfaceIndex
		MAX-ACCESS		read-only
		STATUS			current
		DESCRIPTION		"This attribute indicates the suffered interface by its ifIndex."
		::=  {  bitSTORM-HP-160AlmEntry  3  }


	bitSTORM-HP-160AlmTypeId	OBJECT-TYPE	
		SYNTAX			BITSTORM-HP-160AlmType
		MAX-ACCESS		read-only
		STATUS			current
		DESCRIPTION		"This attribute indicates the suffered alarm type name."
		::=  {  bitSTORM-HP-160AlmEntry  4  }


	bitSTORM-HP-160AlmLevel	OBJECT-TYPE	
		SYNTAX			INTEGER  { bitSTORM-HP-160AlmLevelMinor ( 1 ) , bitSTORM-HP-160AlmLevelMajor ( 2 ) }
		MAX-ACCESS		read-only
		STATUS			current
		DESCRIPTION		"This attribute indicates the suffered alarm level defined by the alarm profile.

        1: Minor
        2: Major"
		::=  {  bitSTORM-HP-160AlmEntry  5  }


	bitSTORM-HP-160AlmState	OBJECT-TYPE	
		SYNTAX			INTEGER  { bitSTORM-HP-160AlmStateSet ( 1 ) , bitSTORM-HP-160AlmStateClear ( 2 ) } 
		MAX-ACCESS		read-only
		STATUS			current
		DESCRIPTION		"This attribute indicates the alarm occurrence or disappearance.

        1: Alarm has not occurred
        2: Alarm has occurred "
		::=  {  bitSTORM-HP-160AlmEntry  6  }


	bitSTORM-HP-160AlmTime	OBJECT-TYPE	
		SYNTAX			OCTET STRING  ( SIZE ( 32  ) ) 
		MAX-ACCESS		read-only
		STATUS			current
		DESCRIPTION		"This attributes indicates the alarm occurence time."
		::=  {  bitSTORM-HP-160AlmEntry  7  }

	bitSTORM-HP-160AlmSeqIdNext	OBJECT-TYPE	
		SYNTAX			Integer32  ( 1 .. 65535  ) 
		MAX-ACCESS		read-only
		STATUS			current
		DESCRIPTION		"1. This object contains an appropriate value to
        be used for bitSTORM-HP-160AlmSeqId when creating
        entries in the bitSTORM-HP-160AlmTable by agent itself.
        2.This indicates the next sequential number used by the alarm table.
      "
		::=  {  bitSTORM-HP-160AlmMgt  5  }

	bitSTORM-HP-160AlmEventTable	OBJECT-TYPE
		SYNTAX		SEQUENCE  OF  BITSTORM-HP-160AlmEventEntry
		MAX-ACCESS	not-accessible
		STATUS		current
		DESCRIPTION	"The Event Log table."
		::=  { bitSTORM-HP-160AlmMgt  6 }

	bitSTORM-HP-160AlmEventEntry	OBJECT-TYPE
		SYNTAX		BITSTORM-HP-160AlmEventEntry
		MAX-ACCESS	not-accessible
		STATUS		current
		DESCRIPTION	"An Entry in the Event table."
		INDEX		{  bitSTORM-HP-160AlmEventSeqId  }
		::=  { bitSTORM-HP-160AlmEventTable 1 }

	BITSTORM-HP-160AlmEventEntry  ::=  SEQUENCE {
		bitSTORM-HP-160AlmEventSeqId  Integer32,
		bitSTORM-HP-160AlmEventEntPhyIndex  PhysicalIndex,
		bitSTORM-HP-160AlmEventIfIndex  InterfaceIndex,
		bitSTORM-HP-160AlmEventTypeId  BITSTORM-HP-160EventType,
		bitSTORM-HP-160AlmEventName  OCTET STRING,
		bitSTORM-HP-160AlmEventTime  OCTET STRING
		}


	bitSTORM-HP-160AlmEventSeqId	OBJECT-TYPE	
		SYNTAX			Integer32  ( 1 .. 65535  ) 
		MAX-ACCESS		read-only
		STATUS			current
		DESCRIPTION		"This object is used by the event table
        to identify the row of this table, when creating a new row in the table by SNMP Agent itself."
		::=  {  bitSTORM-HP-160AlmEventEntry  1  }


	bitSTORM-HP-160AlmEventEntPhyIndex	OBJECT-TYPE	
		SYNTAX			PhysicalIndex
		MAX-ACCESS		read-only
		STATUS			current
		DESCRIPTION		"This attribute indicates the occurrence entity by entPhysicalIndex."
		::=  {  bitSTORM-HP-160AlmEventEntry  2  }


	bitSTORM-HP-160AlmEventIfIndex	OBJECT-TYPE	
		SYNTAX			InterfaceIndex
		MAX-ACCESS		read-only
		STATUS			current
		DESCRIPTION		"This attribute indicates the occurrence interface by ifIndex."
		::=  {  bitSTORM-HP-160AlmEventEntry  3  }


	bitSTORM-HP-160AlmEventTypeId	OBJECT-TYPE	
		SYNTAX			BITSTORM-HP-160EventType
		MAX-ACCESS		read-only
		STATUS			current
		DESCRIPTION		"This command indicates the event type name."
		::=  {  bitSTORM-HP-160AlmEventEntry  4  }

	bitSTORM-HP-160AlmEventName	OBJECT-TYPE
		SYNTAX			OCTET STRING  ( SIZE ( 32  ) ) 
		MAX-ACCESS		read-only
		STATUS			current
		DESCRIPTION		"This attribute indicates the event name
        of the event table."
		::=  {  bitSTORM-HP-160AlmEventEntry  5  }

	bitSTORM-HP-160AlmEventTime	OBJECT-TYPE
		SYNTAX			OCTET STRING  ( SIZE ( 32  ) )
		MAX-ACCESS		read-only
		STATUS			current
		DESCRIPTION		"This attribute indicates the event occurence time
        of the event table."
		::=  {  bitSTORM-HP-160AlmEventEntry  6  }

	bitSTORM-HP-160AlmEventSeqIdNext	OBJECT-TYPE	
		SYNTAX			Integer32  ( 0 .. 65535  ) 
		MAX-ACCESS		read-only
		STATUS			current
		DESCRIPTION		"1.This object contains an appropriate value to
          be used for bitSTORM-HP-160AlmEventSeqId when creating
          entries in the bitSTORM-HP-160AlmEventTable.
        2.This indicates the next sequential number used by the Event log table.
        3.When wrote to 0, this indicates almLogTable will be clear."
		::=  {  bitSTORM-HP-160AlmMgt  7  }

	bitSTORM-HP-160AlmClear	OBJECT-TYPE	
		SYNTAX			INTEGER  { active ( 1 ) , ready ( 2 ) } 
		MAX-ACCESS		read-write
		STATUS			current
		DESCRIPTION		"clear syatem alarm log."
		::=  {  bitSTORM-HP-160AlmMgt  8  }

	bitSTORM-HP-160AlmEventClear	OBJECT-TYPE	
		SYNTAX			INTEGER  { active ( 1 ) , ready ( 2 ) } 
		MAX-ACCESS		read-write
		STATUS			current
		DESCRIPTION		"clear syatem event log."
		::=  {  bitSTORM-HP-160AlmMgt  9  }



--bitSTORM-HP-160PerfDataTable OBJECT-TYPE
--    SYNTAX  SEQUENCE OF bitSTORM-HP-160PerfDataEntry
--    MAX-ACCESS  not-accessible
--    STATUS  current
--    DESCRIPTION
--       "PM table"
--     ::= { bitSTORM-HP-160PerfMgt 1 }
--
--bitSTORM-HP-160PerfDataEntry OBJECT-TYPE
--    SYNTAX  bitSTORM-HP-160PerfDataEntry
--    MAX-ACCESS  not-accessible
--    STATUS  current
--    DESCRIPTION
--       "An Entry of PM table."
--    INDEX   { ifIndex,
--            bitSTORM-HP-160vdslPhysSide }
--     ::= { bitSTORM-HP-160PerfDataTable 1 }
--
--bitSTORM-HP-160PerfDataEntry ::=
--    SEQUENCE {
--         bitSTORM-HP-160vdslPhysSide                   VdslLineEntity,
--         bitSTORM-HP-160PerfDataCellCount         INTEGER,
--         bitSTORM-HP-160PerfDataHEC               INTEGER
--    }

--   bitSTORM-HP-160vdslPhysSide OBJECT-TYPE
--       SYNTAX       VdslLineEntity
--       MAX-ACCESS   not-accessible
--       STATUS       current
--       DESCRIPTION
--           "Identifies whether the transceiver is the Vtuc or Vtur."
--       ::= { bitSTORM-HP-160PerfDataEntry 1 }
--bitSTORM-HP-160PerfDataCellCount     OBJECT-TYPE
--    SYNTAX  INTEGER
--    MAX-ACCESS  read-only
--    STATUS  current
--    DESCRIPTION
--        ""
--     ::= { bitSTORM-HP-160PerfDataEntry 2 }
--
--bitSTORM-HP-160PerfDataHEC     OBJECT-TYPE
--    SYNTAX  INTEGER
--    MAX-ACCESS  read-only
--    STATUS  current
--    DESCRIPTION
--        ""
--     ::= { bitSTORM-HP-160PerfDataEntry 3 }


	bitSTORM-HP-160Traps	OBJECT IDENTIFIER
		::=  {  bitSTORM-HP-160TrapMgt  1  }

	bitSTORM-HP-160SysDate	OBJECT-TYPE
		SYNTAX			OCTET STRING  ( SIZE ( 8 .. 10  ) )
		MAX-ACCESS		read-write
		STATUS			current
		DESCRIPTION		"System date.

        Format: YYYY/MM/DD
        YYYY: Year
        MM: Month
        DD: Day

        03/04/2005 is equivalent to 3/4/2005.
        "
		::=  {  bitSTORM-HP-160CfgTime  1  }

	bitSTORM-HP-160SysTime	OBJECT-TYPE	
		SYNTAX			OCTET STRING  ( SIZE ( 8  ) ) 
		MAX-ACCESS		read-write
		STATUS			current
		DESCRIPTION		"System time.

        Format: hh:mm:ss
        hh: hour
        mm: minute
        ss: second

        Use pattern like 13:03:02 instead of 13:3:2
        "
		::=  {  bitSTORM-HP-160CfgTime  2  }

	bitSTORM-HP-160SNTP	OBJECT IDENTIFIER
		::=  {  bitSTORM-HP-160CfgTime  3  }

	bitSTORM-HP-160CfgInband	OBJECT IDENTIFIER
		::=  {  bitSTORM-HP-160CfgAddress  1  }

	bitSTORM-HP-160CfgOutband	OBJECT IDENTIFIER
		::=  {  bitSTORM-HP-160CfgAddress  2  }

	bitSTORM-HP-160CfgInbandRouteTable	OBJECT-TYPE
		SYNTAX		SEQUENCE  OF  BITSTORM-HP-160CfgInbandRouteEntry
		MAX-ACCESS	not-accessible
		STATUS		current
		DESCRIPTION	"The Inband Route table."
		::=  { bitSTORM-HP-160CfgAddress  3 }

	bitSTORM-HP-160CfgInbandRouteEntry	OBJECT-TYPE
		SYNTAX		BITSTORM-HP-160CfgInbandRouteEntry
		MAX-ACCESS	not-accessible
		STATUS		current
		DESCRIPTION	"An Entry in the bitSTORM-HP-160CfgInbandRouteTable."
		INDEX		{  bitSTORM-HP-160CfgInbandRouteIndex  }
		::=  { bitSTORM-HP-160CfgInbandRouteTable 1 }

	BITSTORM-HP-160CfgInbandRouteEntry  ::=  SEQUENCE {
		bitSTORM-HP-160CfgInbandRouteIndex  Integer32,
		bitSTORM-HP-160CfgInbandRouteDstIp  IpAddress,
		bitSTORM-HP-160CfgInbandRouteNetmask  IpAddress,
		bitSTORM-HP-160CfgInbandRouteGateway  IpAddress,
		bitSTORM-HP-160CfgInbandRouteRowStatus  RowStatus
		}


	bitSTORM-HP-160CfgInbandRouteIndex	OBJECT-TYPE	
		SYNTAX			Integer32
		MAX-ACCESS		not-accessible
		STATUS			current
		DESCRIPTION		"Inband Route Index."
		::=  {  bitSTORM-HP-160CfgInbandRouteEntry  1  }


	bitSTORM-HP-160CfgInbandRouteDstIp	OBJECT-TYPE	
		SYNTAX			IpAddress
		MAX-ACCESS		read-create
		STATUS			current
		DESCRIPTION		"Inband Route Dst IP."
		::=  {  bitSTORM-HP-160CfgInbandRouteEntry  2  }


	bitSTORM-HP-160CfgInbandRouteNetmask	OBJECT-TYPE	
		SYNTAX			IpAddress
		MAX-ACCESS		read-create
		STATUS			current
		DESCRIPTION		"Inband Route Netmask."
		::=  {  bitSTORM-HP-160CfgInbandRouteEntry  3  }


	bitSTORM-HP-160CfgInbandRouteGateway	OBJECT-TYPE	
		SYNTAX			IpAddress
		MAX-ACCESS		read-create
		STATUS			current
		DESCRIPTION		"Inband Route Gateway."
		::=  {  bitSTORM-HP-160CfgInbandRouteEntry  4  }


	bitSTORM-HP-160CfgInbandRouteRowStatus	OBJECT-TYPE	
		SYNTAX			RowStatus
		MAX-ACCESS		read-create
		STATUS			current
		DESCRIPTION		"RowStatus."
		::=  {  bitSTORM-HP-160CfgInbandRouteEntry  5  }

	bitSTORM-HP-160CfgOutbandDefaultGateway	OBJECT-TYPE
		SYNTAX			TAddress
		MAX-ACCESS		read-write
		STATUS			current
		DESCRIPTION		"This field change will probably disconnect the current link."
		::=  {  bitSTORM-HP-160CfgAddress  4  }

--
	bitSTORM-HP-160CfgOutbandRouteTable	OBJECT-TYPE
		SYNTAX		SEQUENCE  OF  BITSTORM-HP-160CfgOutbandRouteEntry
		MAX-ACCESS	not-accessible
		STATUS		current
		DESCRIPTION	"The Outband Route table."
		::=  { bitSTORM-HP-160CfgAddress  5 }

	bitSTORM-HP-160CfgOutbandRouteEntry	OBJECT-TYPE
		SYNTAX		BITSTORM-HP-160CfgOutbandRouteEntry
		MAX-ACCESS	not-accessible
		STATUS		current
		DESCRIPTION	"An Entry Out the bitSTORM-HP-160CfgOutbandRouteTable."
		INDEX		{  bitSTORM-HP-160CfgOutbandRouteIndex  }
		::=  { bitSTORM-HP-160CfgOutbandRouteTable 1 }

	BITSTORM-HP-160CfgOutbandRouteEntry  ::=  SEQUENCE {
		bitSTORM-HP-160CfgOutbandRouteIndex  Integer32,
		bitSTORM-HP-160CfgOutbandRouteDstIp  IpAddress,
		bitSTORM-HP-160CfgOutbandRouteNetmask  IpAddress,
		bitSTORM-HP-160CfgOutbandRouteGateway  IpAddress,
		bitSTORM-HP-160CfgOutbandRouteRowStatus  RowStatus
		}


	bitSTORM-HP-160CfgOutbandRouteIndex	OBJECT-TYPE	
		SYNTAX			Integer32
		MAX-ACCESS		not-accessible
		STATUS			current
		DESCRIPTION		"Outband Route Index."
		::=  {  bitSTORM-HP-160CfgOutbandRouteEntry  1  }


	bitSTORM-HP-160CfgOutbandRouteDstIp	OBJECT-TYPE	
		SYNTAX			IpAddress
		MAX-ACCESS		read-create
		STATUS			current
		DESCRIPTION		"Outband Route Dst IP."
		::=  {  bitSTORM-HP-160CfgOutbandRouteEntry  2  }


	bitSTORM-HP-160CfgOutbandRouteNetmask	OBJECT-TYPE	
		SYNTAX			IpAddress
		MAX-ACCESS		read-create
		STATUS			current
		DESCRIPTION		"Outband Route Netmask."
		::=  {  bitSTORM-HP-160CfgOutbandRouteEntry  3  }


	bitSTORM-HP-160CfgOutbandRouteGateway	OBJECT-TYPE	
		SYNTAX			IpAddress
		MAX-ACCESS		read-create
		STATUS			current
		DESCRIPTION		"Outband Route Gateway."
		::=  {  bitSTORM-HP-160CfgOutbandRouteEntry  4  }


	bitSTORM-HP-160CfgOutbandRouteRowStatus	OBJECT-TYPE	
		SYNTAX			RowStatus
		MAX-ACCESS		read-create
		STATUS			current
		DESCRIPTION		"RowStatus."
		::=  {  bitSTORM-HP-160CfgOutbandRouteEntry  5  }
--
	bitSTORM-HP-160CfgPhyEnetTable	OBJECT-TYPE
		SYNTAX		SEQUENCE  OF  BITSTORM-HP-160CfgPhyEnetEntry
		MAX-ACCESS	not-accessible
		STATUS		current
		DESCRIPTION	""
		::=  { bitSTORM-HP-160CfgPhy  1 }

	bitSTORM-HP-160CfgPhyEnetEntry	OBJECT-TYPE
		SYNTAX		BITSTORM-HP-160CfgPhyEnetEntry
		MAX-ACCESS	not-accessible
		STATUS		current
		DESCRIPTION	""
		INDEX		{  bitSTORM-HP-160PhyEnetPortIndex  }
		::=  { bitSTORM-HP-160CfgPhyEnetTable 1 }

	BITSTORM-HP-160CfgPhyEnetEntry  ::=  SEQUENCE {
		bitSTORM-HP-160PhyEnetPortIndex  Integer32,
		bitSTORM-HP-160PhyEnetMode  INTEGER,
		bitSTORM-HP-160PhyEnetLinkStatus  INTEGER,
		bitSTORM-HP-160PhyEnetCopperFiberSelect  INTEGER,
		bitSTORM-HP-160PhyEnetCopperFiberStatus  INTEGER
--		bitSTORM-HP-160PhyEnetAdminStatus  INTEGER,
--		bitSTORM-HP-160PhyEnetOperStatus  INTEGER
		}


	bitSTORM-HP-160PhyEnetPortIndex	OBJECT-TYPE
		SYNTAX			Integer32  ( 1 .. 2  )
		MAX-ACCESS		read-only
		STATUS			current
		DESCRIPTION		""
		::=  {  bitSTORM-HP-160CfgPhyEnetEntry  1  }


	bitSTORM-HP-160PhyEnetMode	OBJECT-TYPE
		SYNTAX			INTEGER  { autoNegotiate ( 1 ) , config10MbpsHalf ( 2 ) , config10MbpsFull ( 3 ) , config100MbpsHalf ( 4 ) , config100MbpsFull ( 5 ) , other ( 6 ) , unknown ( 7 ) , config1000Mbps ( 8 ) }
		MAX-ACCESS		read-write
		STATUS			current
		DESCRIPTION		""
		DEFVAL			{ autoNegotiate }
		::=  {  bitSTORM-HP-160CfgPhyEnetEntry  2  }


	bitSTORM-HP-160PhyEnetLinkStatus	OBJECT-TYPE
		SYNTAX			INTEGER  { link-down ( 1 ) , link-10mbpsfull ( 2 ) , link-10mbpshalf ( 3 ) , link-100mbpsfull ( 4 ) , link-100mbpshalf ( 5 ) , link-1000mbpscopper ( 6 ) , link-1000mbpsfiber ( 7 ) }
		MAX-ACCESS		read-only
		STATUS			current
		DESCRIPTION		""
		::=  {  bitSTORM-HP-160CfgPhyEnetEntry  3  }


	bitSTORM-HP-160PhyEnetCopperFiberSelect	OBJECT-TYPE
		SYNTAX			INTEGER  { fiber-first ( 0 ) , copper-first ( 1 ) }
		MAX-ACCESS		read-write
		STATUS			current
		DESCRIPTION		""
		DEFVAL			{ fiber-first }
		::=  {  bitSTORM-HP-160CfgPhyEnetEntry  4  }


	bitSTORM-HP-160PhyEnetCopperFiberStatus	OBJECT-TYPE
		SYNTAX			INTEGER  { fiber ( 0 ) , copper ( 1 )  }
		MAX-ACCESS		read-only
		STATUS			current
		DESCRIPTION		""
		::=  {  bitSTORM-HP-160CfgPhyEnetEntry  5  }

                                                                    
--	bitSTORM-HP-160PhyEnetAdminStatus	OBJECT-TYPE
--		SYNTAX			INTEGER  { off ( 0 ) , on ( 1 )  }
--		MAX-ACCESS		read-write
--		STATUS			current
--		DESCRIPTION		""
--		DEFVAL			{ on }
--		::=  {  bitSTORM-HP-160CfgPhyEnetEntry  6  }

--	bitSTORM-HP-160PhyEnetOperStatus	OBJECT-TYPE
--		SYNTAX			INTEGER  { on ( 1 ) , off ( 2 ) }
--		MAX-ACCESS		read-only
--		STATUS			current
--		DESCRIPTION		""
--		::=  {  bitSTORM-HP-160CfgPhyEnetEntry  7  }

--	bitSTORM-HP-160CfgIfcTable	OBJECT-TYPE
--		SYNTAX		SEQUENCE  OF  BITSTORM-HP-160CfgIfcEntry
--		MAX-ACCESS	not-accessible
--		STATUS		current
--		DESCRIPTION	""
--		::=  { bitSTORM-HP-160CfgIfc  1 }

--	bitSTORM-HP-160CfgIfcEntry	OBJECT-TYPE
--		SYNTAX		BITSTORM-HP-160CfgIfcEntry
--		MAX-ACCESS	not-accessible
--		STATUS		current
--		DESCRIPTION	""
--		INDEX		{  bitSTORM-HP-160CfgIfcIndex  }
--		::=  { bitSTORM-HP-160CfgIfcTable 1 }

--	BITSTORM-HP-160CfgIfcEntry  ::=  SEQUENCE {
--		bitSTORM-HP-160CfgIfcIndex  InterfaceIndex,
--		bitSTORM-HP-160CfgIfcType  INTEGER,
--		bitSTORM-HP-160CfgIfcDevIndex  Integer32,
--		bitSTORM-HP-160CfgIfcConnectionType  INTEGER,
--		bitSTORM-HP-160CfgIfcRxConnectionIdx  Integer32,
--		bitSTORM-HP-160CfgIfcTxConnectionIdx  Integer32,
--		bitSTORM-HP-160CfgIfcRowStatus  RowStatus
--		}

--	bitSTORM-HP-160CfgIfcIndex	OBJECT-TYPE
--		SYNTAX			InterfaceIndex
--		MAX-ACCESS		read-only
--		STATUS			current
--		DESCRIPTION		""
--		::=  {  bitSTORM-HP-160CfgIfcEntry  1  }

--	bitSTORM-HP-160CfgIfcType	OBJECT-TYPE
--		SYNTAX			INTEGER  { enet1 ( 1 ) , enet2 ( 2 ) , gbi1 ( 3 ) , gbi2 ( 4 ) , atm1 ( 5 ) , atm2 ( 6 ) , imaGroup ( 7 ) }
--		MAX-ACCESS		read-create
--		STATUS			current
--		DESCRIPTION		""
--		DEFVAL			{ atm2 }
--		::=  {  bitSTORM-HP-160CfgIfcEntry  2  }

--	bitSTORM-HP-160CfgIfcDevIndex	OBJECT-TYPE
--		SYNTAX			Integer32  ( 0 .. 123  )
--		MAX-ACCESS		read-create
--		STATUS			current
--		DESCRIPTION		""
--		DEFVAL			{ 0 }
--		::=  {  bitSTORM-HP-160CfgIfcEntry  3  }

--  	bitSTORM-HP-160CfgIfcConnectionType	OBJECT-TYPE
--		SYNTAX			INTEGER  { vpl ( 1 ) , vcl ( 2 ) , la ( 3 ) , multivcl ( 4 ) , none ( 5 ) }
--		MAX-ACCESS		read-create
--		STATUS			current
--		DESCRIPTION		""
--		DEFVAL			{ vcl }
--		::=  {  bitSTORM-HP-160CfgIfcEntry  4  }

-- 	bitSTORM-HP-160CfgIfcRxConnectionIdx	OBJECT-TYPE
--		SYNTAX			Integer32  ( 0 .. 65535  )
--		MAX-ACCESS		read-create
--		STATUS			current
--		DESCRIPTION		""
--		DEFVAL			{ 65535 }
--		::=  {  bitSTORM-HP-160CfgIfcEntry  5  }

--  	bitSTORM-HP-160CfgIfcTxConnectionIdx	OBJECT-TYPE
--		SYNTAX			Integer32  ( 0 .. 65535  )
--		MAX-ACCESS		read-create
--		STATUS			current
--		DESCRIPTION		""
--		DEFVAL			{ 65535 }
--		::=  {  bitSTORM-HP-160CfgIfcEntry  6  }

--	bitSTORM-HP-160CfgIfcRowStatus	OBJECT-TYPE
--		SYNTAX			RowStatus
--		MAX-ACCESS		read-create
--		STATUS			current
--		DESCRIPTION		""
--		DEFVAL			{ createAndGo }
--		::=  {  bitSTORM-HP-160CfgIfcEntry  7  }

--	bitSTORM-HP-160CfgIfcReset	OBJECT-TYPE
--		SYNTAX			INTEGER  { none ( 0 ) , all ( 1 ) , gbi1 ( 2 ) , gbi2 ( 3 ) , gbiLA ( 4 ) }
--		MAX-ACCESS		read-write
--		STATUS			current
--		DESCRIPTION		""
--		::=  {  bitSTORM-HP-160CfgIfc  2  }

	bitSTORM-HP-160BridgePortTable	OBJECT-TYPE
		SYNTAX		SEQUENCE  OF  BITSTORM-HP-160BridgePortEntry
		MAX-ACCESS	not-accessible
		STATUS		current
		DESCRIPTION	""
		::=  { bitSTORM-HP-160CfgBridge  1 }

	bitSTORM-HP-160BridgePortEntry	OBJECT-TYPE
		SYNTAX		BITSTORM-HP-160BridgePortEntry
		MAX-ACCESS	not-accessible
		STATUS		current
		DESCRIPTION	""
		INDEX		{  bitSTORM-HP-160BridgePortIfcIndex  }
		::=  { bitSTORM-HP-160BridgePortTable 1 }

	BITSTORM-HP-160BridgePortEntry  ::=  SEQUENCE {
		bitSTORM-HP-160BridgePortIfcIndex  InterfaceIndex,
		bitSTORM-HP-160BridgePortDefaultVlan  Integer32,
		bitSTORM-HP-160BridgePortVlanPriority  Integer32,
		bitSTORM-HP-160BridgePortDefaultVlanTagging  INTEGER,
		bitSTORM-HP-160BridgePortVpmtMode  INTEGER,
		bitSTORM-HP-160BridgePortnodeLinkAggrMode  INTEGER,
		bitSTORM-HP-160BridgePortIngressMode  INTEGER,
		bitSTORM-HP-160BridgePortLinkMode  INTEGER,
		--bitSTORM-HP-160BridgePortVlanStacking  INTEGER,
		bitSTORM-HP-160BridgePortMaxMac  Integer32,
		bitSTORM-HP-160BridgePortAcceptableFrameType  INTEGER,
		bitSTORM-HP-160BridgePortIsolationMode  INTEGER,
		bitSTORM-HP-160BridgePortRowStatus  RowStatus
		}


	bitSTORM-HP-160BridgePortIfcIndex	OBJECT-TYPE	
		SYNTAX			InterfaceIndex
		MAX-ACCESS		read-only
		STATUS			current
		DESCRIPTION		""
		::=  {  bitSTORM-HP-160BridgePortEntry  1  }


	bitSTORM-HP-160BridgePortDefaultVlan	OBJECT-TYPE
		SYNTAX			Integer32  ( 1 .. 4094  )   --960803
		MAX-ACCESS		read-create
		STATUS			current
		DESCRIPTION		""
		::=  {  bitSTORM-HP-160BridgePortEntry  2  }


	bitSTORM-HP-160BridgePortVlanPriority	OBJECT-TYPE	
		SYNTAX			Integer32  ( 0 .. 7  ) 
		MAX-ACCESS		read-create
		STATUS			current
		DESCRIPTION		""
		::=  {  bitSTORM-HP-160BridgePortEntry  3  }


	bitSTORM-HP-160BridgePortDefaultVlanTagging	OBJECT-TYPE	
		SYNTAX			INTEGER  { tagged ( 1 ) , untagged ( 2 ) } 
		MAX-ACCESS		read-create
		STATUS			current
		DESCRIPTION		""
		DEFVAL			{ tagged }
		::=  {  bitSTORM-HP-160BridgePortEntry  4  }


	bitSTORM-HP-160BridgePortVpmtMode	OBJECT-TYPE	
		SYNTAX			INTEGER  { disabled ( 0 ) , singleVc ( 1 ) , multiVc ( 2 ) } 
		MAX-ACCESS		read-create
		STATUS			current
		DESCRIPTION		""
		DEFVAL			{ disabled }
		::=  {  bitSTORM-HP-160BridgePortEntry  5  }


	bitSTORM-HP-160BridgePortnodeLinkAggrMode	OBJECT-TYPE	
		SYNTAX			INTEGER  { disabled ( 0 ) , enabled ( 1 ) } 
		MAX-ACCESS		read-create
		STATUS			current
		DESCRIPTION		""
		DEFVAL			{ disabled }
		::=  {  bitSTORM-HP-160BridgePortEntry  6  }


	bitSTORM-HP-160BridgePortIngressMode	OBJECT-TYPE	
		SYNTAX			INTEGER  { disabled ( 0 ) , enabled ( 1 ) } 
		MAX-ACCESS		read-create
		STATUS			current
		DESCRIPTION		""
		DEFVAL			{ enabled }
		::=  {  bitSTORM-HP-160BridgePortEntry  7  }


	bitSTORM-HP-160BridgePortLinkMode	OBJECT-TYPE	
		SYNTAX			INTEGER  { user ( 0 ) , uplink ( 1 ) } 
		MAX-ACCESS		read-create
		STATUS			current
		DESCRIPTION		""
		DEFVAL			{ user }
		::=  {  bitSTORM-HP-160BridgePortEntry  8  }


--	bitSTORM-HP-160BridgePortVlanStacking	OBJECT-TYPE
--		SYNTAX			INTEGER  { disabled ( 0 ) , enabled ( 1 ) }
--		MAX-ACCESS		read-create
--		STATUS			current
--		DESCRIPTION		""
--		DEFVAL			{ disabled }
--		::=  {  bitSTORM-HP-160BridgePortEntry  9  }


	bitSTORM-HP-160BridgePortMaxMac	OBJECT-TYPE	
		SYNTAX			Integer32  ( 0 .. 65535  ) 
		MAX-ACCESS		read-create
		STATUS			current
		DESCRIPTION		""
		DEFVAL			{ 128 }
		::=  {  bitSTORM-HP-160BridgePortEntry  10  }


	bitSTORM-HP-160BridgePortAcceptableFrameType	OBJECT-TYPE	
		SYNTAX			INTEGER  { only-vlantagged ( 0 ) , only-untagged ( 1 ) , all ( 2 ) } 
		MAX-ACCESS		read-create
		STATUS			current
		DESCRIPTION		""
		DEFVAL			{ all }
		::=  {  bitSTORM-HP-160BridgePortEntry  11  }


	bitSTORM-HP-160BridgePortIsolationMode	OBJECT-TYPE	
		SYNTAX			INTEGER  { disabled ( 0 ) , same ( 2 ) } 
		MAX-ACCESS		read-create
		STATUS			current
		DESCRIPTION		""
		DEFVAL			{ disabled }
		::=  {  bitSTORM-HP-160BridgePortEntry  12  }


	bitSTORM-HP-160BridgePortRowStatus	OBJECT-TYPE	
		SYNTAX			RowStatus
		MAX-ACCESS		read-create
		STATUS			current
		DESCRIPTION		""
		DEFVAL			{ createAndGo }
		::=  {  bitSTORM-HP-160BridgePortEntry  13  }

	bitSTORM-HP-160CfgVlanGroup	OBJECT IDENTIFIER
		::=  {  bitSTORM-HP-160CfgBridge  2  }

	bitSTORM-HP-160CfgFilterGroup	OBJECT IDENTIFIER
		::=  {  bitSTORM-HP-160CfgBridge  3  }

	bitSTORM-HP-160CfgLacpGroup	OBJECT IDENTIFIER
		::=  {  bitSTORM-HP-160CfgBridge  4  }

	bitSTORM-HP-160CfgIgmpGroup	OBJECT IDENTIFIER
		::=  {  bitSTORM-HP-160CfgBridge  5  }

	bitSTORM-HP-160CfgRstpGroup	OBJECT IDENTIFIER
		::=  {  bitSTORM-HP-160CfgBridge  6  }

	bitSTORM-HP-160CfgRelayGroup	OBJECT IDENTIFIER
		::=  {  bitSTORM-HP-160CfgBridge  7  }

	bitSTORM-HP-160CfgVpmtGroup	OBJECT IDENTIFIER
		::=  {  bitSTORM-HP-160CfgBridge  8  }
		
        bitSTORM-HP-160CfgSystemConfiguration	OBJECT IDENTIFIER
		::=  {  bitSTORM-HP-160CfgBridge  9  }
		
        bitSTORM-HP-160CfgLayerIIServiceOption	OBJECT IDENTIFIER
		::=  {  bitSTORM-HP-160CfgBridge  13  }

		
	bitSTORM-HP-160AgingTimeTable	OBJECT-TYPE
		SYNTAX		SEQUENCE  OF  BITSTORM-HP-160AgingTimeEntry
		MAX-ACCESS	not-accessible
		STATUS		current
		DESCRIPTION	""
		::=  { bitSTORM-HP-160CfgBridge  10 }

	bitSTORM-HP-160AgingTimeEntry	OBJECT-TYPE
		SYNTAX		BITSTORM-HP-160AgingTimeEntry
		MAX-ACCESS	not-accessible
		STATUS		current
		DESCRIPTION	""
		INDEX		{  bitSTORM-HP-160AgingTimeIfcIndex  }
		::=  { bitSTORM-HP-160AgingTimeTable 1 }

	BITSTORM-HP-160AgingTimeEntry  ::=  SEQUENCE {
		bitSTORM-HP-160AgingTimeIfcIndex  InterfaceIndex,
		bitSTORM-HP-160AgingTime  Integer32
		}


	bitSTORM-HP-160AgingTimeIfcIndex	OBJECT-TYPE
		SYNTAX			InterfaceIndex
		MAX-ACCESS		read-only
		STATUS			current
		DESCRIPTION		""
		::=  {  bitSTORM-HP-160AgingTimeEntry  1  }


	bitSTORM-HP-160AgingTime	OBJECT-TYPE
		SYNTAX			Integer32  ( 10 .. 600  )
		MAX-ACCESS		read-create
		STATUS			current
		DESCRIPTION		"10..600 second"
		::=  {  bitSTORM-HP-160AgingTimeEntry  2  }





	bitSTORM-HP-160SnoopArpRequestTable	OBJECT-TYPE
		SYNTAX		SEQUENCE  OF  BITSTORM-HP-160SnoopArpRequestEntry
		MAX-ACCESS	not-accessible
		STATUS		current
		DESCRIPTION	""
		::=  { bitSTORM-HP-160CfgBridge  11 }

	bitSTORM-HP-160SnoopArpRequestEntry	OBJECT-TYPE
		SYNTAX		BITSTORM-HP-160SnoopArpRequestEntry
		MAX-ACCESS	not-accessible
		STATUS		current
		DESCRIPTION	""
		INDEX		{  bitSTORM-HP-160SnoopArpIfcIndex  }
		::=  { bitSTORM-HP-160SnoopArpRequestTable 1 }

	BITSTORM-HP-160SnoopArpRequestEntry  ::=  SEQUENCE {
		bitSTORM-HP-160SnoopArpIfcIndex  InterfaceIndex,
		bitSTORM-HP-160LearnByDhcp  INTEGER,
		bitSTORM-HP-160DefaultGatewayMac  PhysAddress
		}


	bitSTORM-HP-160SnoopArpIfcIndex	OBJECT-TYPE
		SYNTAX			InterfaceIndex
		MAX-ACCESS		read-only
		STATUS			current
		DESCRIPTION		""
		::=  {  bitSTORM-HP-160SnoopArpRequestEntry  1  }


	bitSTORM-HP-160LearnByDhcp	OBJECT-TYPE
		SYNTAX			INTEGER{ false ( 0 ) , true ( 1 ) }
		MAX-ACCESS		read-create
		STATUS			current
		DESCRIPTION		"0:defaultGatewayMac is preconfigured, 1:defaultGatewayMac is learnByDhcp.
                                        Once the value is changed, the defaultGatewayMac will be cleared to FF:FF:FF:FF:FF:FF"
		::=  {  bitSTORM-HP-160SnoopArpRequestEntry  2  }


	bitSTORM-HP-160DefaultGatewayMac	OBJECT-TYPE
		SYNTAX			PhysAddress
		MAX-ACCESS		read-create
		STATUS			current
		DESCRIPTION		"string hex mac format in DB, example->FF:FF:FF:FF:FF:FF
                                        FF:FF:FF:FF:FF:FF means empty entry, the bport doesn't exist."
		::=  {  bitSTORM-HP-160SnoopArpRequestEntry  3  }



--
	bitSTORM-HP-160BridgeArpSpoofingTable	OBJECT-TYPE
		SYNTAX		SEQUENCE  OF  BITSTORM-HP-160BridgeArpSpoofingEntry
		MAX-ACCESS	not-accessible
		STATUS		current
		DESCRIPTION	""
		::=  { bitSTORM-HP-160CfgBridge  12 }

	bitSTORM-HP-160BridgeArpSpoofingEntry	OBJECT-TYPE
		SYNTAX		BITSTORM-HP-160BridgeArpSpoofingEntry
		MAX-ACCESS	not-accessible
		STATUS		current
		DESCRIPTION	""
		INDEX		{  bitSTORM-HP-160ArpSpoofingIndex  }
		::=  { bitSTORM-HP-160BridgeArpSpoofingTable 1 }       		
		
                                                        
	BITSTORM-HP-160BridgeArpSpoofingEntry  ::=  SEQUENCE {
		bitSTORM-HP-160ArpSpoofingIndex  Integer32,
		bitSTORM-HP-160ArpSpoofingBpIndex  Integer32,
		bitSTORM-HP-160ArpSpoofingSrcIp  IpAddress,
		bitSTORM-HP-160ArpSpoofingSrcMac  PhysAddress,
		bitSTORM-HP-160ArpSpoofingRowStatus  RowStatus
		}


	bitSTORM-HP-160ArpSpoofingIndex	OBJECT-TYPE
		SYNTAX			Integer32(0..1536)
		MAX-ACCESS		read-only
		STATUS			current
		DESCRIPTION		""
		::=  {  bitSTORM-HP-160BridgeArpSpoofingEntry  1  }


	bitSTORM-HP-160ArpSpoofingBpIndex	OBJECT-TYPE
		SYNTAX			Integer32(4..219)
		MAX-ACCESS		read-create
		STATUS			current
		DESCRIPTION		""
		::=  {  bitSTORM-HP-160BridgeArpSpoofingEntry  2  }

	bitSTORM-HP-160ArpSpoofingSrcIp	OBJECT-TYPE
		SYNTAX			IpAddress
		MAX-ACCESS		read-create
		STATUS			current
		DESCRIPTION		""
		::=  {  bitSTORM-HP-160BridgeArpSpoofingEntry  3  }

	bitSTORM-HP-160ArpSpoofingSrcMac	OBJECT-TYPE
		SYNTAX			PhysAddress
		MAX-ACCESS		read-create
		STATUS			current
		DESCRIPTION		"string hex mac format in DB, example->FF:FF:FF:FF:FF:FF"
		::=  {  bitSTORM-HP-160BridgeArpSpoofingEntry  4  }
	bitSTORM-HP-160ArpSpoofingRowStatus	OBJECT-TYPE
		SYNTAX			RowStatus
		MAX-ACCESS		read-create
		STATUS			current
		DESCRIPTION		""
		::=  {  bitSTORM-HP-160BridgeArpSpoofingEntry  5  }
--



--	bitSTORM-HP-160CfgAclService	OBJECT-TYPE
--		SYNTAX			INTEGER  { disable ( 0 ) , enable ( 1 ) }
--		MAX-ACCESS		read-write
--		STATUS			current
--		DESCRIPTION		""
--		DEFVAL			{ enable }
--		::=  {  bitSTORM-HP-160CfgBridge  8  }

	bitSTORM-HP-160CfgXdslLineInfoTable	OBJECT-TYPE
		SYNTAX		SEQUENCE  OF  BITSTORM-HP-160CfgXdslLineInfoEntry
		MAX-ACCESS	not-accessible
		STATUS		current
		DESCRIPTION	"The Xdsl Line configuration table."
		::=  { bitSTORM-HP-160CfgXdslSetting  2 }

	bitSTORM-HP-160CfgXdslLineInfoEntry	OBJECT-TYPE
		SYNTAX		BITSTORM-HP-160CfgXdslLineInfoEntry
		MAX-ACCESS	not-accessible
		STATUS		current
		DESCRIPTION	"An Entry in the BITSTORM-HP-160CfgXdslLineInfoTable"
		INDEX		{  bitSTORM-HP-160CfgXdslIfIndex  }
		::=  { bitSTORM-HP-160CfgXdslLineInfoTable 1 }

	BITSTORM-HP-160CfgXdslLineInfoEntry  ::=  SEQUENCE {
		bitSTORM-HP-160CfgXdslIfIndex  InterfaceIndex,
		bitSTORM-HP-160CfgXdslLinePortID  OCTET STRING,
		bitSTORM-HP-160CfgXdslLinePortDescr  OCTET STRING,
		bitSTORM-HP-160CfgXdslLinePortPhoneNbr  OCTET STRING
		}


	bitSTORM-HP-160CfgXdslIfIndex	OBJECT-TYPE	
		SYNTAX			InterfaceIndex
		MAX-ACCESS		not-accessible
		STATUS			current
		DESCRIPTION		"IfIndex."
		::=  {  bitSTORM-HP-160CfgXdslLineInfoEntry  1  }


	bitSTORM-HP-160CfgXdslLinePortID	OBJECT-TYPE	
		SYNTAX			OCTET STRING  ( SIZE ( 0 .. 32  ) )
		MAX-ACCESS		read-write
		STATUS			current
		DESCRIPTION		"The Port Identifier."
		::=  {  bitSTORM-HP-160CfgXdslLineInfoEntry  2  }


	bitSTORM-HP-160CfgXdslLinePortDescr	OBJECT-TYPE	
		SYNTAX			OCTET STRING  ( SIZE ( 0 .. 48  ) ) 
		MAX-ACCESS		read-write
		STATUS			current
		DESCRIPTION		"The Port Description."
		::=  {  bitSTORM-HP-160CfgXdslLineInfoEntry  3  }


	bitSTORM-HP-160CfgXdslLinePortPhoneNbr	OBJECT-TYPE	
		SYNTAX			OCTET STRING  ( SIZE ( 0 .. 32  ) )
		MAX-ACCESS		read-write
		STATUS			current
		DESCRIPTION		"The Port Phone No."
		::=  {  bitSTORM-HP-160CfgXdslLineInfoEntry  4  }

	bitSTORM-HP-160CfgXdslLineTable	OBJECT-TYPE
		SYNTAX		SEQUENCE  OF  BITSTORM-HP-160CfgXdslLineEntry
		MAX-ACCESS	not-accessible
		STATUS		current
		DESCRIPTION	""
		::=  { bitSTORM-HP-160CfgXdslSetting  3 }

	bitSTORM-HP-160CfgXdslLineEntry	OBJECT-TYPE
		SYNTAX		BITSTORM-HP-160CfgXdslLineEntry
		MAX-ACCESS	not-accessible
		STATUS		current
		DESCRIPTION	""
		INDEX		{  bitSTORM-HP-160CfgXdslIfIndex  }
		::=  { bitSTORM-HP-160CfgXdslLineTable 1 }

	BITSTORM-HP-160CfgXdslLineEntry  ::=  SEQUENCE {
		bitSTORM-HP-160CfgXdslIfIndex  InterfaceIndex,
		bitSTORM-HP-160CfgXdslLineAdminStatus  INTEGER,
		bitSTORM-HP-160CfgXdslLineOperStatus  INTEGER
		}

 	bitSTORM-HP-160CfgXdslIfIndex	OBJECT-TYPE
		SYNTAX			InterfaceIndex
		MAX-ACCESS		not-accessible
		STATUS			current
		DESCRIPTION		"IfIndex."
		::=  {  bitSTORM-HP-160CfgXdslLineEntry  1  }


	bitSTORM-HP-160CfgXdslLineAdminStatus	OBJECT-TYPE
		SYNTAX			INTEGER  { up ( 1 ) , down ( 2 ) }
		MAX-ACCESS		read-write
		STATUS			current
		DESCRIPTION		"The desired state of the interface. When a
            managed system initializes, all interfaces start with
            ifAdminStatus in the down(2) state.  "
		::=  {  bitSTORM-HP-160CfgXdslLineEntry  2  }


	bitSTORM-HP-160CfgXdslLineOperStatus	OBJECT-TYPE
		SYNTAX			INTEGER  
		{ idle(0),
                  handshake(1),
                  training(2),
                  data(3),
                  test(4),
                  deltinit(5),
                  deltdone(6) }
		MAX-ACCESS		read-only
		STATUS			current
		DESCRIPTION		""
		::=  {  bitSTORM-HP-160CfgXdslLineEntry  3  }

	bitSTORM-HP-160CfgCLITimeout	OBJECT-TYPE
		SYNTAX			Integer32  (0..65535)
                UNITS        "second"
		MAX-ACCESS		read-write
		STATUS			current
		DESCRIPTION		"60 ~ 65535 seconds, 0 : no timeout
		1 ~ 59 is not allowed."
		::=  {  bitSTORM-HP-160CfgCLISettings  1  }

--	bitSTORM-HP-160CfgCLIFlags	OBJECT-TYPE
--		SYNTAX			BITS {
--                showAlarm(15),
--                showEvent(14)
--		}
--		MAX-ACCESS		read-write
--		STATUS			current
--		DESCRIPTION		"alarm /event notify of all cli interface"
--		::=  {  bitSTORM-HP-160CfgCLISettings  2  }

	bitSTORM-HP-160CfgClusterConfig	OBJECT IDENTIFIER
		::=  {  bitSTORM-HP-160CfgCluster  1  }

--	bitSTORM-HP-160CfgClusterStatusTable	OBJECT-TYPE
--		SYNTAX		SEQUENCE  OF  BITSTORM-HP-160CfgClusterStatusEntry
--		MAX-ACCESS	not-accessible
--		STATUS		current
--		DESCRIPTION	""
--		::=  { bitSTORM-HP-160CfgCluster  2 }
  --
--	bitSTORM-HP-160CfgClusterStatusEntry	OBJECT-TYPE
--		SYNTAX		BITSTORM-HP-160CfgClusterStatusEntry
--		MAX-ACCESS	not-accessible
--		STATUS		current
--		DESCRIPTION	""
--		INDEX		{  bitSTORM-HP-160CfgClusterId  }
--		::=  { bitSTORM-HP-160CfgClusterStatusTable 1 }
  --
--	BITSTORM-HP-160CfgClusterStatusEntry  ::=  SEQUENCE {
--		bitSTORM-HP-160CfgClusterId  Integer32,
--		bitSTORM-HP-160CfgClusterState  INTEGER,
--		}
  --
--	bitSTORM-HP-160CfgClusterId	OBJECT-TYPE
--		SYNTAX			Integer32  ( 1..16  )
--		MAX-ACCESS		read-only
--		STATUS			current
--		DESCRIPTION		""
--		::=  {  bitSTORM-HP-160CfgClusterStatusEntry  1  }
  --

--	bitSTORM-HP-160CfgClusterState	OBJECT-TYPE
--		SYNTAX			INTEGER  {
--		  IDLE(0),
  --		  REINIT(1),
  --		  DISCOVERING(2),
  --		  REQUESTING(3),
--		  VOTING(4),
--		  SLAVE(5),
--		  MASTER(6)
--		 }
--		MAX-ACCESS		read-only
--		STATUS			current
--		DESCRIPTION		""
--		::=  {  bitSTORM-HP-160CfgClusterStatusEntry  2  }
  
	bitSTORM-HP-160CfgClusterMemberInfoTable	OBJECT-TYPE
		SYNTAX		SEQUENCE  OF  BITSTORM-HP-160CfgClusterMemberInfoEntry
		MAX-ACCESS	not-accessible
		STATUS		current
		DESCRIPTION	""
		::=  { bitSTORM-HP-160CfgCluster  2 }

	bitSTORM-HP-160CfgClusterMemberInfoEntry	OBJECT-TYPE
		SYNTAX		BITSTORM-HP-160CfgClusterMemberInfoEntry
		MAX-ACCESS	not-accessible
		STATUS		current
		DESCRIPTION	""
		INDEX		{  bitSTORM-HP-160CfgClusterMemberId  }
		::=  { bitSTORM-HP-160CfgClusterMemberInfoTable 1 }

	BITSTORM-HP-160CfgClusterMemberInfoEntry  ::=  SEQUENCE {
		bitSTORM-HP-160CfgClusterMemberId  Integer32,
		bitSTORM-HP-160CfgClusterMemberIp  TAddress,
		bitSTORM-HP-160CfgClusterMemberName  OCTET STRING,
		bitSTORM-HP-160CfgClusterMemberState INTEGER
		}

	bitSTORM-HP-160CfgClusterMemberId	OBJECT-TYPE
		SYNTAX			Integer32  ( -2147483648 .. 2147483647  )
		MAX-ACCESS		read-only
		STATUS			current
		DESCRIPTION		""
		::=  {  bitSTORM-HP-160CfgClusterMemberInfoEntry  1  }


	bitSTORM-HP-160CfgClusterMemberIp	OBJECT-TYPE
		SYNTAX			TAddress
		MAX-ACCESS		read-only
		STATUS			current
		DESCRIPTION		""
		::=  {  bitSTORM-HP-160CfgClusterMemberInfoEntry  2  }


	bitSTORM-HP-160CfgClusterMemberName	OBJECT-TYPE
		SYNTAX			OCTET STRING  ( SIZE ( 0 .. 32  ) )
		MAX-ACCESS		read-only
		STATUS			current
		DESCRIPTION		""
		::=  {  bitSTORM-HP-160CfgClusterMemberInfoEntry  3  }

	bitSTORM-HP-160CfgClusterMemberState	OBJECT-TYPE
		SYNTAX			INTEGER  { slave ( 0 ) , master ( 1 ) }
		MAX-ACCESS		read-only
		STATUS			current
		DESCRIPTION		""
		::=  {  bitSTORM-HP-160CfgClusterMemberInfoEntry  4  }

	bitSTORM-HP-160SysInvSWVersion	OBJECT-TYPE
		SYNTAX			OCTET STRING  ( SIZE ( 1 .. 30  ) )
		MAX-ACCESS		read-only
		STATUS			current
		DESCRIPTION		"The software version of the system."
		::=  {  bitSTORM-HP-160SysInventory  1  }

	bitSTORM-HP-160SysInvFWVersion	OBJECT-TYPE	
		SYNTAX			OCTET STRING  ( SIZE ( 1 .. 30  ) ) 
		MAX-ACCESS		read-only
		STATUS			current
		DESCRIPTION		"The firmware version of the system."
		::=  {  bitSTORM-HP-160SysInventory  2  }

	bitSTORM-HP-160SysInvHWVersion	OBJECT-TYPE
		SYNTAX			OCTET STRING  ( SIZE ( 1 .. 30  ) )
		MAX-ACCESS		read-only
		STATUS			current
		DESCRIPTION		"The hardware version of the system."
		::=  {  bitSTORM-HP-160SysInventory  3  }

	bitSTORM-HP-160SysInvModelInfo	OBJECT-TYPE
		SYNTAX			OCTET STRING  ( SIZE ( 1 .. 15  ) ) 
		MAX-ACCESS		read-only
		STATUS			current
		DESCRIPTION		"Model information."
		::=  {  bitSTORM-HP-160SysInventory  4  }

	bitSTORM-HP-160SysInvPartNbr	OBJECT-TYPE
		SYNTAX			OCTET STRING  ( SIZE ( 1 .. 15  ) ) 
		MAX-ACCESS		read-only
		STATUS			current
		DESCRIPTION		"Part Nbr."
		::=  {  bitSTORM-HP-160SysInventory  5  }

	bitSTORM-HP-160SysInvHWRev	OBJECT-TYPE
		SYNTAX			OCTET STRING  ( SIZE ( 1 .. 8  ) ) 
		MAX-ACCESS		read-only
		STATUS			current
		DESCRIPTION		"Hardware Rev."
		::=  {  bitSTORM-HP-160SysInventory  6  }

	bitSTORM-HP-160SysInvSerialNum	OBJECT-TYPE
		SYNTAX			OCTET STRING  ( SIZE ( 1 .. 30  ) ) 
		MAX-ACCESS		read-only
		STATUS			current
		DESCRIPTION		"The serial number string for the system."
		::=  {  bitSTORM-HP-160SysInventory  7  }

--	bitSTORM-HP-160SysInvCardType	OBJECT-TYPE
--		SYNTAX			INTEGER  { gbe ( 1 ) }
--		MAX-ACCESS		read-only
--		STATUS			current
--		DESCRIPTION		"The card type of the system card."
--		::=  {  bitSTORM-HP-160SysInventory  8  }

	bitSTORM-HP-160SysInvSplitterType	OBJECT-TYPE
		SYNTAX			INTEGER  { 
	        etsi270-pots-splitter(0),
                ansi600-pots-splitter(1),
                ansi900-pots-splitter(2),
                isdn-splitter(4),
                no-splitter(7)
                }   
		MAX-ACCESS		read-only
		STATUS			current
		DESCRIPTION		
		"
		ETSI270-POTS-Splitter(0),
                ANSI600-POTS-Splitter(1),
                ANSI900-POTS-Splitter(2),
                ISDN-Splitter(4),
                No-Splitter(7)"
		::=  {  bitSTORM-HP-160SysInventory  8  }

	bitSTORM-HP-160SysInvCPLDVersion	OBJECT-TYPE
		SYNTAX			INTEGER
		MAX-ACCESS		read-only
		STATUS			current
		DESCRIPTION		"The cpld version of the system card."
		::=  {  bitSTORM-HP-160SysInventory  9  }

	bitSTORM-HP-160SysInvCardType	OBJECT-TYPE
		SYNTAX			INTEGER
		MAX-ACCESS		read-only
		STATUS			current
		DESCRIPTION		"The card type of the system card."
		::=  {  bitSTORM-HP-160SysInventory  10  }
		
	bitSTORM-HP-160SysInvBootLoaderVersion 	OBJECT-TYPE
		SYNTAX			OCTET STRING  ( SIZE ( 1 .. 16  ) )
		MAX-ACCESS		read-only
		STATUS			current
		DESCRIPTION		"The winmon version."
		::=  {  bitSTORM-HP-160SysInventory  11  }

	bitSTORM-HP-160SysInvPortCount 	OBJECT-TYPE
		SYNTAX			INTEGER
		MAX-ACCESS		read-only
		STATUS			current
		DESCRIPTION		"Port count."
		::=  {  bitSTORM-HP-160SysInventory  12  }
		
	bitSTORM-HP-160SysSysFanSupported 	OBJECT-TYPE
		SYNTAX			INTEGER  { false ( 0 ) , true ( 1 ) }
		MAX-ACCESS		read-only
		STATUS			current
		DESCRIPTION		""
		::=  {  bitSTORM-HP-160SysMgt  4  }


	bitSTORM-HP-160SysLED	OBJECT-TYPE
		SYNTAX			BITSTORM-HP-160LedType
		MAX-ACCESS		read-only
		STATUS			current
		DESCRIPTION		"System LED status of the DSLAM.

        Normal operation: bitSTORM-HP-160LedGreen(2)
        Self-test fail  : bitSTORM-HP-160LedRed(1)
        Power on        : bitSTORM-HP-160LedYellow(3)
       "
		::=  {  bitSTORM-HP-160LED  1  }

	bitSTORM-HP-160AlmLED	OBJECT-TYPE	
		SYNTAX			BITSTORM-HP-160LedType
		MAX-ACCESS		read-only
		STATUS			current
		DESCRIPTION		"Alarm LED status for bitSTORM-HP-160 of the DSLAM.

        Normal operation         : bitSTORM-HP-160LedGreen(2)
        Major alarm set          : bitSTORM-HP-160LedRed(1)
        Minor alarm set          : bitSTORM-HP-160LedYellow(3)
        Major and minor alarm set: bitSTORM-HP-160LedRedFlash(5)
        Power on                 : bitSTORM-HP-160LedYellow(3)"
		::=  {  bitSTORM-HP-160LED  2  }

	bitSTORM-HP-160Gbe1LED	OBJECT-TYPE	
		SYNTAX			BITSTORM-HP-160LedType
		MAX-ACCESS		read-only
		STATUS			current
		DESCRIPTION		"GbE1 LED status for bitSTORM-HP-160 of the DSLAM.

        Normal operation         : bitSTORM-HP-160LedGreen(2)"
		::=  {  bitSTORM-HP-160LED  3  }

	bitSTORM-HP-160Gbe2LED	OBJECT-TYPE	
		SYNTAX			BITSTORM-HP-160LedType
		MAX-ACCESS		read-only
		STATUS			current
		DESCRIPTION		"GbE2 LED status for bitSTORM-HP-160 of the DSLAM.

        Normal operation         : bitSTORM-HP-160LedGreen(2)"
		::=  {  bitSTORM-HP-160LED  4  }

bitSTORM-HP-160XdslChlLEDTable        OBJECT-TYPE
    SYNTAX  SEQUENCE OF BITSTORM-HP-160XdslChlLEDEntry
    MAX-ACCESS  not-accessible
    STATUS  current
    DESCRIPTION
       "The Channel Led table of system.
       "
     ::= {bitSTORM-HP-160LED 5 }


bitSTORM-HP-160XdslChlLEDEntry OBJECT-TYPE
    SYNTAX  BITSTORM-HP-160XdslChlLEDEntry
    MAX-ACCESS  not-accessible
    STATUS  current
    DESCRIPTION
       "An Entry in the Channel Led table. Support 24 channel."
    INDEX   { ifIndex }
     ::= {bitSTORM-HP-160XdslChlLEDTable 1 }




BITSTORM-HP-160XdslChlLEDEntry ::=
    SEQUENCE {
                bitSTORM-HP-160xdslChlLEDStatus     BITSTORM-HP-160LedType
    }


bitSTORM-HP-160xdslChlLEDStatus    OBJECT-TYPE    --04-25
    SYNTAX BITSTORM-HP-160LedType
    MAX-ACCESS  read-only
    STATUS  current
    DESCRIPTION
       "The LED Status of xDSL Channel
        Port Normal operation   : bitSTORM-HP-160LedGreen (2)
        Port training           : bitSTORM-HP-160LedGreenFlash (6)
        Port not provisioned    : bitSTORM-HP-160LedOff (0)
       "
     ::= {bitSTORM-HP-160XdslChlLEDEntry 1 }   

	bitSTORM-HP-160SysTemperatureUpShfThreshold	OBJECT-TYPE	
		SYNTAX			Integer32  ( -55 .. 85  ) 
		MAX-ACCESS		read-write
		STATUS			current
		DESCRIPTION		"If current temperature exceeds bitSTORM-HP-160SysTemperatureUpShfThreshold, Alarm Manager will
        declare that there is a high temperature alarm after bitSTORM-HP-160SysTemperatureUpShfTime
        seconds.

       "
		DEFVAL			{ 65 }
		::=  {  bitSTORM-HP-160SysTemperature  1  }

	bitSTORM-HP-160SysTemperatureDwShfThreshold	OBJECT-TYPE
		SYNTAX			Integer32  ( -55 .. 85  )
		MAX-ACCESS		read-write
		STATUS			current
		DESCRIPTION		"If current temperature descends below to bitSTORM-HP-160SysTemperatureDwShfThreshold, Alarm Manager will
        declare that there is a lower temperature alarm after bitSTORM-HP-160SysTemperatureDwShfTime
        seconds.
       "
		DEFVAL			{ 65 }
		::=  {  bitSTORM-HP-160SysTemperature  2  }

	bitSTORM-HP-160SysTemperatureUpShfTime	OBJECT-TYPE
		SYNTAX			Integer32  ( 1 .. 255  )
		MAX-ACCESS		read-write
		STATUS			current
		DESCRIPTION		"The bitSTORM-HP-160SysTemperatureUpShfTime will start to count when bitSTORM-HP-160SysTemperatureValue
        excessing bitSTORM-HP-160SysTemperatureUpShfThreshold.

       "
		DEFVAL			{ 10 }
		::=  {  bitSTORM-HP-160SysTemperature  3  }

	bitSTORM-HP-160SysTemperatureDwShfTime	OBJECT-TYPE
		SYNTAX			Integer32  ( 1 .. 255  )
		MAX-ACCESS		read-write
		STATUS			current
		DESCRIPTION		"The bitSTORM-HP-160SysTemperatureDwShfTime will start to count when bitSTORM-HP-160SysTemperatureValue
        excessing bitSTORM-HP-160SysTemperatureDwShfThreshold.
       "
		DEFVAL			{ 10 }
		::=  {  bitSTORM-HP-160SysTemperature  4  }

	bitSTORM-HP-160SysTemperatureaFanThreshold	OBJECT-TYPE
		SYNTAX			Integer32  ( -40 .. 15  )
		MAX-ACCESS		read-write
		STATUS			current
		DESCRIPTION		"If Fan temperature exceeds bitSTORM-HP-160SysTemperatureaFanThreshold, Fan will be turned on."
		::=  {  bitSTORM-HP-160SysTemperature  5  }

	bitSTORM-HP-160SysTemperatureValue	OBJECT-TYPE
		SYNTAX			Integer32  ( -55 .. 125  )
		MAX-ACCESS		read-only
		STATUS			current
		DESCRIPTION		"The current temperature value."
		::=  {  bitSTORM-HP-160SysTemperature  6  }   

	bitSTORM-HP-160SysTemperatureDslValue	OBJECT-TYPE
		SYNTAX			Integer32  
		MAX-ACCESS		read-only
		STATUS			current
		DESCRIPTION		"The DSL temperature value."
		::=  {  bitSTORM-HP-160SysTemperature  7  }
		
--	bitSTORM-HP-160MtnRemoteTFTPServer	OBJECT IDENTIFIER
--		::=  {  bitSTORM-HP-160MtnDatabase  1  }

--	bitSTORM-HP-160MtBootCfgPartition	OBJECT-TYPE
--		SYNTAX			INTEGER  { partition0 ( 0 ) , partition1 ( 1 ) }
--		MAX-ACCESS		read-write
--		STATUS			current
--		DESCRIPTION		"The partition of Flash used when system boot."
--		::=  {  bitSTORM-HP-160MtnDatabase  2  }

--	bitSTORM-HP-160MtnCfgPartitionSelect	OBJECT-TYPE
--		SYNTAX			INTEGER  { partition1 ( 1 ) , partition2 ( 2 ) }
--		MAX-ACCESS		read-write
--		STATUS			current
--		DESCRIPTION		"The partition of Flash used when doing import/reload."
--		::=  {  bitSTORM-HP-160MtnDatabase  3  }

--	bitSTORM-HP-160MtnConfigureDownload	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to download a
--         copy of the configuration file. The
--         manager will retrieve the file via tftp-get.
--
--         The values for setting operations are as follows.
--         1: import active
--
--         The value for status/read operations are as follows:
--         2: import complete
--         3: import fail
--         4: import in progress"
--		::=  {  bitSTORM-HP-160MtnDatabase  4  }

--	bitSTORM-HP-160MtnImportConfigureToRunning	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to save a download
--         copy of the configuration file.
--
--         The values for setting operations are as follows.
--         1: active
--
--         The value for status/read operations are as follows:
--         2: complete
--         3: fail
--         4: in progress"
--		::=  {  bitSTORM-HP-160MtnDatabase  5  }
--
--	bitSTORM-HP-160MtnImportConfigureToNvRAM	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to save a download
--         copy of the configuration file.
--
--         The values for setting operations are as follows.
--         1: active
--
--         The value for status/read operations are as follows:
--         2: complete
--         3: fail
--         4: in progress"
--		::=  {  bitSTORM-HP-160MtnDatabase  6  }
--
--	bitSTORM-HP-160MtnExportConfigure	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to make a
--         copy of the current runnung configuration file. The
--         manager will send the file to tftp server.
--
--         The values for setting operations are as follows.
--         1: active
--
--         The value for status/read operations are as follows:
--         2: complete
--         3: fail
--         4: in progress"
--		::=  {  bitSTORM-HP-160MtnDatabase  7  }
--
--	bitSTORM-HP-160MtnSaveRunningCfg	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to save all configuration data to select partition NvRAM.
--
--         The values for setting operations are as follows.
--         1: active
--
--         The value for status/read operations are as follows:
--         2: complete
--         3: fail
--         4: in progress"
--		::=  {  bitSTORM-HP-160MtnDatabase  8  }
--
--	bitSTORM-HP-160MtnLoadSystemCfg	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to load select partition NvRAM to running configuration.
--
--         The values for setting operations are as follows.
--         1: active
--
--         The value for status/read operations are as follows:
--         2: complete
--         3: fail
--         4: in progress"
--		::=  {  bitSTORM-HP-160MtnDatabase  9  }

--	bitSTORM-HP-160MtnSetFactoryDefault	OBJECT-TYPE
--		SYNTAX			INTEGER  { ready ( 0 ) , active ( 1 ) , complete ( 2 ) , fail ( 3 ) , inprogress ( 4 ) }
--		MAX-ACCESS		read-write
--		STATUS			current
--		DESCRIPTION		"Always use avtive(1) to set all configuration data to default.
--
--         The values for setting operations are as follows.
--         1: active
--
--         The value for status/read operations are as follows:
--         2: complete
--         3: fail
--         4: in progress"
--		::=  {  bitSTORM-HP-160MtnDatabase  10  }

	bitSTORM-HP-160MtnRemoteFTPServer	OBJECT IDENTIFIER
		::=  {  bitSTORM-HP-160MtnFirmware  1  }

	bitSTORM-HP-160MtnCliCfgFTPServer	OBJECT IDENTIFIER
		::=  {  bitSTORM-HP-160MtnCliConfig  1  }

	bitSTORM-HP-160MtnCliCfgInbandIndex	OBJECT-TYPE
		SYNTAX			INTEGER
		MAX-ACCESS		read-write
		STATUS			current
		DESCRIPTION		""
		::=  {  bitSTORM-HP-160MtnCliConfig  2  }

	bitSTORM-HP-160MtnCliCfgGeneralIndex	OBJECT-TYPE
		SYNTAX			INTEGER
		MAX-ACCESS		read-write
		STATUS			current
		DESCRIPTION		""
		::=  {  bitSTORM-HP-160MtnCliConfig  3  }

	bitSTORM-HP-160MtnCliCfgInbandBackupName	OBJECT-TYPE
		SYNTAX			OCTET STRING  ( SIZE ( 0 .. 32  ) )
		MAX-ACCESS		read-write
		STATUS			current
		DESCRIPTION		""
		::=  {  bitSTORM-HP-160MtnCliConfig  4  }

	bitSTORM-HP-160MtnCliCfgGeneralBackupName	OBJECT-TYPE
		SYNTAX			OCTET STRING  ( SIZE ( 0 .. 32  ) )
		MAX-ACCESS		read-write
		STATUS			current
		DESCRIPTION		""
		::=  {  bitSTORM-HP-160MtnCliConfig  5  }

	bitSTORM-HP-160MtnCliCfgActionType	OBJECT-TYPE
		SYNTAX			INTEGER  {
                cliconfig-save(1),
--                cliconfig-load-nvram(2),
--                cliconfig-load-internal(3),
--                cliconfig-restore-by-name(4),
                cliconfig-restore-by-index(5),
                cliconfig-clear-all(6),
                cliconfig-clear-general(7),
                cliconfig-export-binary(8),
--                cliconfig-export-text(9),
                cliconfig-export-cli(10),
                cliconfig-get-binary(11),
                cliconfig-get-cli(12),
                cliconfig-put-binary(13),
                cliconfig-put-cli(14),
--                cliconfig-import-binary(15),
--                cliconfig-import-cli(16),
                cliconfig-import-download-binary(17),
                cliconfig-import-download-cli(18),
                cliconfig-change-detect(21)
		 }
		MAX-ACCESS		read-write
		STATUS			current
		DESCRIPTION		"
		Action to be taken:

                CLICONFIG-SAVE:
                   Save database to flash
                   Use cliCfgBackupNameInband with MASK_cliCfgBackupNameInband to specify name for inband database.
                   Use cliCfgBackupNameGeneral with MASK_cliCfgBackupNameGeneral to specify name for general database.
--                CLICONFIG-LOAD-NVRAM:
--                   Load database from flash (used by OAMP internally)
--                CLICONFIG-LOAD-INTERNAL:
--                   Load database from flash (used by OAMP internally)
--                CLICONFIG-RESTORE-BY-NAME:
--                   Restore database with the specific names
--                   Use cliCfgBackupNameInband with MASK_cliCfgBackupNameInband to specify name for inband database.
--                   Use cliCfgBackupNameGeneral with MASK_cliCfgBackupNameGeneral to specify name for general database.
                CLICONFIG-RESTORE-BY-INDEX:
                   Restore database with the specific indexes
                   Use cliCfgParam1 with MASK_cliCfgParam1 to specify index for inband database.
                   Use cliCfgParam2 with MASK_cliCfgParam2 to specify index for general database.
                CLICONFIG-CLEAR-ALL:
                   Clear Inband/General database
                CLICONFIG-CLEAR-GENERAL:
                   Clear General database
                CLICONFIG-EXPORT-BINARY:
                   Export database (binary)
--                CLICONFIG-EXPORT-TEXT:
--                   Export database (text)
                CLICONFIG-EXPORT-CLI:
                   Export database as a CLI script
                   (gbe ip/netmask,route not exported)
                CLICONFIG-GET-BINARY:
                   Get binary database image from a FTP server.
                CLICONFIG-GET-CLI:
                   Get CLI script from a FTP server.
                CLICONFIG-PUT-BINARY:
                   Put binary database image to a FTP server.
                CLICONFIG-PUT-CLI:
                   Put CLI script to a FTP server.
--                CLICONFIG-IMPORT-BINARY:
--                   Import from binary database images
--                CLICONFIG-IMPORT-CLI:
--                   Import from a CLI script
                CLICONFIG-IMPORT-DOWNLOAD-BINARY:
                   As previous CLICONFIG-WRITE-DOWNLOAD.
                   Import from downloaded binary images.
                CLICONFIG-IMPORT-DOWNLOAD-CLI:
                   Import from download CLI script.
                CLICONFIG-CHANGE-DETECT
                   Detect database changes, for agents. 
          "
		::=  {  bitSTORM-HP-160MtnCliConfig  6  }

	bitSTORM-HP-160MtnCliCfgStatus	OBJECT-TYPE
		SYNTAX			INTEGER  {
		ftpputsuccess(1),
		ftpputfail(2),
		ftpputinprogress(3),
		ftpgetsuccess(4),
		ftpgetfail(5),
		ftpgetinprogress(6),
		memorywritesuccess(7),
		memorywritefail(8),
		memorywriteinprogress(9),
		memoryreadsuccess(10),
		memoryreadfail(11),
		memoryreadinprogress(12)
		}
		MAX-ACCESS		read-only
		STATUS			current
		DESCRIPTION		"This object is to report the cli configuration status aftert config action."
		::=  {  bitSTORM-HP-160MtnCliConfig  7  }

	bitSTORM-HP-160MtnCliCfgConfigUnsaved	OBJECT-TYPE
		SYNTAX			INTEGER  {
		false(0),
		true(1)
		}
		MAX-ACCESS		read-only
		STATUS			current
		DESCRIPTION		"Must set bitSTORM-HP-160MtnCliCfgActionType to CLICONFIG-CHANGE-DETECT(21).
                                         After bitSTORM-HP-160MtnCliCfgStatus is changed to MEMORYWRITESUCCESS(7), this field is non-zero if there are unsaved database changes."
		::=  {  bitSTORM-HP-160MtnCliConfig  8  }

	bitSTORM-HP-160MtnFlashBackup	OBJECT IDENTIFIER
		::=  { bitSTORM-HP-160MtnMgt   8  } 

--	bitSTORM-HP-160MtnFlashBackupInfoTable	OBJECT-TYPE
--		SYNTAX		SEQUENCE  OF  BITSTORM-HP-160MtnFlashBackupInfoEntry
--		MAX-ACCESS	not-accessible
--		STATUS		current
--		DESCRIPTION	""
--		::=  { bitSTORM-HP-160MtnFlashBackup  1 }

--	bitSTORM-HP-160MtnFlashBackupInfoEntry	OBJECT-TYPE
--		SYNTAX		BITSTORM-HP-160MtnFlashBackupInfoEntry
--		MAX-ACCESS	not-accessible
--		STATUS		current
--		DESCRIPTION	""
--		INDEX		{  bitSTORM-HP-160MtnFlashBackupIndex  }
--		::=  { bitSTORM-HP-160MtnFlashBackupInfoTable 1 }
  --
--	BITSTORM-HP-160MtnFlashBackupInfoEntry  ::=  SEQUENCE {
--		bitSTORM-HP-160MtnFlashBackupIndex  INTEGER,
--		bitSTORM-HP-160MtnFlashBackupEntryName  OCTET STRING,
--		bitSTORM-HP-160MtnFlashBackupEntrySize  Integer32
--		}

--	bitSTORM-HP-160MtnFlashBackupIndex	OBJECT-TYPE
--		SYNTAX			INTEGER  (1..16)
--		MAX-ACCESS		not-accessible
--		STATUS			current
--		DESCRIPTION		""
--		::=  {  bitSTORM-HP-160MtnFlashBackupInfoEntry  1  }

--	bitSTORM-HP-160MtnFlashBackupEntryName	OBJECT-TYPE
--		SYNTAX			OCTET STRING
--		MAX-ACCESS		read-only
--		STATUS			current
--		DESCRIPTION		""
--		::=  {  bitSTORM-HP-160MtnFlashBackupInfoEntry  2  }

--	bitSTORM-HP-160MtnFlashBackupEntrySize	OBJECT-TYPE
--		SYNTAX			Integer32
--		MAX-ACCESS		read-only
--		STATUS			current
--		DESCRIPTION		""
--		::=  {  bitSTORM-HP-160MtnFlashBackupInfoEntry  3  }

	bitSTORM-HP-160MtnFlashBackupInbandTable	OBJECT-TYPE
		SYNTAX		SEQUENCE  OF  BITSTORM-HP-160MtnFlashBackupInbandEntry
		MAX-ACCESS	not-accessible
		STATUS		current
		DESCRIPTION	""
		::=  { bitSTORM-HP-160MtnFlashBackup  1 }

	bitSTORM-HP-160MtnFlashBackupInbandEntry	OBJECT-TYPE
		SYNTAX		BITSTORM-HP-160MtnFlashBackupInbandEntry
		MAX-ACCESS	not-accessible
		STATUS		current
		DESCRIPTION	""
		INDEX		{  bitSTORM-HP-160MtnFlashBackupInbandIndex  }
		::=  { bitSTORM-HP-160MtnFlashBackupInbandTable 1 }

	BITSTORM-HP-160MtnFlashBackupInbandEntry  ::=  SEQUENCE {
		bitSTORM-HP-160MtnFlashBackupInbandIndex  INTEGER,
		bitSTORM-HP-160MtnFlashBackupInbandEntryName  OCTET STRING
		}

	bitSTORM-HP-160MtnFlashBackupInbandIndex	OBJECT-TYPE
		SYNTAX			INTEGER  (1..16)
		MAX-ACCESS		not-accessible
		STATUS			current
		DESCRIPTION		""
		::=  {  bitSTORM-HP-160MtnFlashBackupInbandEntry  1  }

	bitSTORM-HP-160MtnFlashBackupInbandEntryName	OBJECT-TYPE
		SYNTAX			OCTET STRING   ( SIZE ( 1 .. 32  ) )
		MAX-ACCESS		read-only
		STATUS			current
		DESCRIPTION		""
		::=  {  bitSTORM-HP-160MtnFlashBackupInbandEntry  2  }

	bitSTORM-HP-160MtnFlashBackupGeneralTable	OBJECT-TYPE        
		SYNTAX		SEQUENCE  OF  BITSTORM-HP-160MtnFlashBackupGeneralEntry
		MAX-ACCESS	not-accessible
		STATUS		current
		DESCRIPTION	""
		::=  { bitSTORM-HP-160MtnFlashBackup  2 }

	bitSTORM-HP-160MtnFlashBackupGeneralEntry	OBJECT-TYPE
		SYNTAX		BITSTORM-HP-160MtnFlashBackupGeneralEntry
		MAX-ACCESS	not-accessible
		STATUS		current
		DESCRIPTION	""
		INDEX		{  bitSTORM-HP-160MtnFlashBackupGeneralIndex  }
		::=  { bitSTORM-HP-160MtnFlashBackupGeneralTable 1 }

	BITSTORM-HP-160MtnFlashBackupGeneralEntry  ::=  SEQUENCE {
		bitSTORM-HP-160MtnFlashBackupGeneralIndex  INTEGER,
		bitSTORM-HP-160MtnFlashBackupGeneralEntryName  OCTET STRING
		}

	bitSTORM-HP-160MtnFlashBackupGeneralIndex	OBJECT-TYPE
		SYNTAX			INTEGER  (1..16)
		MAX-ACCESS		not-accessible
		STATUS			current
		DESCRIPTION		""
		::=  {  bitSTORM-HP-160MtnFlashBackupGeneralEntry  1  }

	bitSTORM-HP-160MtnFlashBackupGeneralEntryName	OBJECT-TYPE
		SYNTAX			OCTET STRING   ( SIZE ( 1 .. 32  ) )
		MAX-ACCESS		read-only
		STATUS			current
		DESCRIPTION		""
		::=  {  bitSTORM-HP-160MtnFlashBackupGeneralEntry  2  }

--  	bitSTORM-HP-160MtnFlashBackupActiveIndex	OBJECT-TYPE
--		SYNTAX			Integer32
--		MAX-ACCESS		read-only
--		STATUS			current
--		DESCRIPTION		""
--		::=  {  bitSTORM-HP-160MtnFlashBackup  2  }

  	bitSTORM-HP-160MtnFlashBackupInbandActiveIndex	OBJECT-TYPE
		SYNTAX			Integer32
		MAX-ACCESS		read-only
		STATUS			current
		DESCRIPTION		""
		::=  {  bitSTORM-HP-160MtnFlashBackup  3  }

  	bitSTORM-HP-160MtnFlashBackupGeneralActiveIndex	OBJECT-TYPE
		SYNTAX			Integer32
		MAX-ACCESS		read-only
		STATUS			current
		DESCRIPTION		""
		::=  {  bitSTORM-HP-160MtnFlashBackup  4  }
--	bitSTORM-HP-160MtnFlashBackupEntryCount	OBJECT-TYPE
--		SYNTAX			Integer32
--		MAX-ACCESS		read-only
--		STATUS			current
--		DESCRIPTION		""
--		::=  {  bitSTORM-HP-160MtnFlashBackup  3  }

--	bitSTORM-HP-160MtnFlashBackupEntryType	OBJECT-TYPE
--		SYNTAX			INTEGER {
--		  Inband(1),
  --                General(2)
--		}
--		MAX-ACCESS		read-only
--		STATUS			current
--		DESCRIPTION		""
--		::=  {  bitSTORM-HP-160MtnFlashBackup  4  }

--	bitSTORM-HP-160MtnGeneralTable	OBJECT-TYPE
--		SYNTAX		SEQUENCE  OF  BITSTORM-HP-160MtnGeneralEntry
--		MAX-ACCESS	not-accessible
--		STATUS		current
--		DESCRIPTION	""
--		::=  { bitSTORM-HP-160MtnFlashBackup  2 }

--	bitSTORM-HP-160MtnGeneralEntry	OBJECT-TYPE
--		SYNTAX		BITSTORM-HP-160MtnGeneralEntry
--		MAX-ACCESS	not-accessible
--		STATUS		current
--		DESCRIPTION	""
--		INDEX		{  bitSTORM-HP-160MtnGeneralIndex  }
--		::=  { bitSTORM-HP-160MtnGeneralTable 1 }

--	BITSTORM-HP-160MtnGeneralEntry  ::=  SEQUENCE {
--		bitSTORM-HP-160MtnGeneralIndex  Integer32,
--		bitSTORM-HP-160MtnGeneralEntryName  OCTET STRING,
--		bitSTORM-HP-160MtnGeneralActiveIndex  Integer32,
--		bitSTORM-HP-160MtnGeneralEntryCount  Integer32
--		}

--	bitSTORM-HP-160MtnGeneralIndex	OBJECT-TYPE
--		SYNTAX			Integer32
--		MAX-ACCESS		not-accessible
--		STATUS			current
--		DESCRIPTION		""
--		::=  {  bitSTORM-HP-160MtnGeneralEntry  1  }

--	bitSTORM-HP-160MtnGeneralEntryName	OBJECT-TYPE
--		SYNTAX			OCTET STRING
--		MAX-ACCESS		read-only
--		STATUS			current
--		DESCRIPTION		""
--		::=  {  bitSTORM-HP-160MtnGeneralEntry  2  }

--  	bitSTORM-HP-160MtnGeneralActiveIndex	OBJECT-TYPE
--		SYNTAX			Integer32
--		MAX-ACCESS		read-only
--		STATUS			current
--		DESCRIPTION		""
--		::=  {  bitSTORM-HP-160MtnGeneralEntry  3  }

--	bitSTORM-HP-160MtnGeneralEntryCount	OBJECT-TYPE
--		SYNTAX			Integer32
--		MAX-ACCESS		read-only
--		STATUS			current
--		DESCRIPTION		""
--		::=  {  bitSTORM-HP-160MtnGeneralEntry  4  }

--	bitSTORM-HP-160MtnFirmwareDownload	OBJECT-TYPE
--		SYNTAX			INTEGER  { ready ( 0 ) , active ( 1 ) , complete ( 2 ) , fail ( 3 ) , inprogress ( 4 ) }
--		MAX-ACCESS		read-write
--		STATUS			current
--		DESCRIPTION		"This object is to notify the system to
--       download a new firmware image  file. The
--         manager will retrieve the file via ftp-get.
--
--         The values for setting operations are as follows.
--         1: download active
--
--         The value for status/read operations are as follows:
--         2: download complete
--         3: download fail
--         4: download in progress"
--		::=  {  bitSTORM-HP-160MtnFirmware  2  }

--	bitSTORM-HP-160MtnFlashWrite	OBJECT-TYPE
--		SYNTAX			INTEGER  { ready ( 0 ) , active ( 1 ) }
--		MAX-ACCESS		read-write
--		STATUS			current
--		DESCRIPTION		"Set this object to active,
--		the system will get image file via ftp and then
  --              write the new firmware to the flash and restart itself.
    --      "
--		::=  {  bitSTORM-HP-160MtnFirmware  2  }

	bitSTORM-HP-160MtnFlashWrite	OBJECT-TYPE
		SYNTAX			INTEGER  {
		idle(0),
		active(1),
		ftpsuccess(2),
		ftpfail(3),
		ftpinprogress(4),
		flashwritesucces(5),
		flashwritefail(6),
		flashwriteinprog(7) }
		MAX-ACCESS		read-write
		STATUS			current
		DESCRIPTION		"Set this object to active,
		the system will get image file via ftp and then
                write the new firmware to the flash and restart itself.
                Get this object to know the status.
                
                The values for setting operations are as follows.
        	1: ACTIVE(1)
 	
 	        The value for status/read operations are as follows:
 	        2: FTPSUCCESS(2)
 	        3: FTPFAIL(3)
 	        4: FTPINPROGRESS(4)
        	5: FLASHWRITESUCCES(5)
        	6: FLASHWRITEFAIL(6)
        	7: FLASHWRITEINPROG(7)
                "
		::=  {  bitSTORM-HP-160MtnFirmware  2  }

--	bitSTORM-HP-160MtnDlStatus	OBJECT-TYPE
--		SYNTAX			INTEGER  {
--              IDLE(0),
--                FTPSUCCESS(1),
--                FTPFAIL(2),
--                FTPINPROGRESS(3),
--                FLASHWRITESUCCES(4),
--                FLASHWRITEFAIL(5),
--                FLASHWRITEINPROG(6)
--                                }
--		MAX-ACCESS		read-only
--		STATUS			current
--		DESCRIPTION		"This object is to report the remote download status aftert flash write"
--
--		::=  {  bitSTORM-HP-160MtnFirmware  3  }

	bitSTORM-HP-160MtnBootLoaderUpdate	OBJECT-TYPE
		SYNTAX			INTEGER  {
		idle(0),
		active(1),
		ftpsuccess(2),
		ftpfail(3),
		ftpinprogress(4),
		bootloadercodewritesucces(5),
		bootloaderwritefail(6),
		bootloaderwriteinprog(7) }
		MAX-ACCESS		read-write
		STATUS			current
		DESCRIPTION		"Set this object to active,
		the system will get bootloader file via ftp and then
                write the new bootloader to the flash and restart itself.
                Get this object to know the status.
                
                The values for setting operations are as follows.
        	1: ACTIVE(1)
 	
 	        The value for status/read operations are as follows:
 	        2: FTPSUCCESS(2)
 	        3: FTPFAIL(3)
 	        4: FTPINPROGRESS(4)
        	5: BOOTLOADERWRITESUCCES(5)
        	6: BOOTLOADERWRITEFAIL(6)
        	7: BOOTLOADERWRITEINPROG(7)
                "

		::=  {  bitSTORM-HP-160MtnFirmware  3  }

	bitSTORM-HP-160MtnImageProfileTable	OBJECT-TYPE
		SYNTAX		SEQUENCE  OF  BITSTORM-HP-160MtnImageProfileEntry
		MAX-ACCESS	not-accessible
		STATUS		current
		DESCRIPTION	"The Flash Image Profile table."
		::=  { bitSTORM-HP-160MtnFirmware  4 }

	bitSTORM-HP-160MtnImageProfileEntry	OBJECT-TYPE
		SYNTAX		BITSTORM-HP-160MtnImageProfileEntry
		MAX-ACCESS	not-accessible
		STATUS		current
		DESCRIPTION	"An Entry in the ImageProfile table."
		INDEX		{  bitSTORM-HP-160MtnImageProfileIndex  }
		::=  { bitSTORM-HP-160MtnImageProfileTable 1 }

	BITSTORM-HP-160MtnImageProfileEntry  ::=  SEQUENCE {
		bitSTORM-HP-160MtnImageProfileIndex  Integer32,
		bitSTORM-HP-160MtnImageProfileDate  OCTET STRING,
		bitSTORM-HP-160MtnImageProfileVersion  OCTET STRING,
		bitSTORM-HP-160MtnImageProfileDisplayName  OCTET STRING
		}


	bitSTORM-HP-160MtnImageProfileIndex	OBJECT-TYPE	
		SYNTAX			Integer32  ( 0 .. 1  ) 
		MAX-ACCESS		read-only
		STATUS			current
		DESCRIPTION		"If current temperature exceeds bitSTORM-HP-160SysTemperatureUpShfThreshold, Alarm Manager will
        declare that there is a high temperature alarm after bitSTORM-HP-160SysTemperatureUpShfTime
        seconds.

       "
		::=  {  bitSTORM-HP-160MtnImageProfileEntry  1  }


	bitSTORM-HP-160MtnImageProfileDate	OBJECT-TYPE	
		SYNTAX			OCTET STRING  ( SIZE ( 1 .. 16  ) ) 
		MAX-ACCESS		read-only
		STATUS			current
		DESCRIPTION		"Flash image date."
		::=  {  bitSTORM-HP-160MtnImageProfileEntry  2  }


	bitSTORM-HP-160MtnImageProfileVersion	OBJECT-TYPE
		SYNTAX			OCTET STRING  ( SIZE ( 1 .. 16  ) ) 
		MAX-ACCESS		read-only
		STATUS			current
		DESCRIPTION		"Flash image version."
		::=  {  bitSTORM-HP-160MtnImageProfileEntry  3  }

	bitSTORM-HP-160MtnImageProfileDisplayName	OBJECT-TYPE
		SYNTAX			OCTET STRING  ( SIZE ( 1 .. 32  ) )
		MAX-ACCESS		read-only
		STATUS			current
		DESCRIPTION		"Flash image display name."
		::=  {  bitSTORM-HP-160MtnImageProfileEntry  4  }

	bitSTORM-HP-160MtnActivePartition	OBJECT-TYPE
		SYNTAX			INTEGER  { partition0 ( 0 ) , partition1 ( 1 ) }
		MAX-ACCESS		read-write
		STATUS			current
		DESCRIPTION		"This object is to select the partition which is active."
		::=  {  bitSTORM-HP-160MtnFirmware  5  }

	bitSTORM-HP-160MtnSyslogService	OBJECT-TYPE
		SYNTAX			INTEGER  { enable ( 1 ) , disable ( 2 ) } 
		MAX-ACCESS		read-write
		STATUS			current
		DESCRIPTION		"Syslog Service On/Off.
       enable: service on
       disable: service off"
		::=  {  bitSTORM-HP-160MtnSyslog  1  }
	bitSTORM-HP-160MtnSyslogServerIP	OBJECT-TYPE	
		SYNTAX			TAddress
		MAX-ACCESS		read-write
		STATUS			current
		DESCRIPTION		"The Syslog Server IP."
		::=  {  bitSTORM-HP-160MtnSyslog  2  }
	bitSTORM-HP-160MtnSyslogMaxFileSize	OBJECT-TYPE
		SYNTAX			INTEGER  (16..1024)
		MAX-ACCESS		read-write
		STATUS			current
		DESCRIPTION		"The maximum size of the log file for syslog. (16 ~ 1024 KB)."
		::=  {  bitSTORM-HP-160MtnSyslog  3  }

	bitSTORM-HP-160MtnOAMCellGeneration	OBJECT-TYPE	
		SYNTAX			INTEGER  { enable ( 1 ) , disable ( 0 ) } 
		MAX-ACCESS		read-write
		STATUS			current
		DESCRIPTION		""
		::=  {  bitSTORM-HP-160MtnAtmOamLoopbackTest  1  }

	bitSTORM-HP-160MtnAtmLoopbackTable	OBJECT-TYPE
		SYNTAX		SEQUENCE  OF  BITSTORM-HP-160MtnAtmLoopbackEntry
		MAX-ACCESS	not-accessible
		STATUS		current
		DESCRIPTION	"The Atm Loopback table."
		::=  { bitSTORM-HP-160MtnAtmOamLoopbackTest  2 }

	bitSTORM-HP-160MtnAtmLoopbackEntry	OBJECT-TYPE
		SYNTAX		BITSTORM-HP-160MtnAtmLoopbackEntry
		MAX-ACCESS	not-accessible
		STATUS		current
		DESCRIPTION	"An Entry in the AtmLoopback table."
		INDEX		{  bitSTORM-HP-160MtnAtmLoopbackIfIndex  }
		::=  { bitSTORM-HP-160MtnAtmLoopbackTable 1 }

	BITSTORM-HP-160MtnAtmLoopbackEntry  ::=  SEQUENCE {
		bitSTORM-HP-160MtnAtmLoopbackIfIndex  InterfaceIndex,
		bitSTORM-HP-160MtnAtmLoopbackId  OCTET STRING,
		bitSTORM-HP-160MtnAtmIfTestType  INTEGER,
		bitSTORM-HP-160MtnAtmIfTestState  INTEGER,
		bitSTORM-HP-160MtnAtmRowStatus  RowStatus
		}


	bitSTORM-HP-160MtnAtmLoopbackIfIndex	OBJECT-TYPE	
		SYNTAX			InterfaceIndex
		MAX-ACCESS		not-accessible
		STATUS			current
		DESCRIPTION		"AtmLoopback IfIndex."
		::=  {  bitSTORM-HP-160MtnAtmLoopbackEntry  1  }


	bitSTORM-HP-160MtnAtmLoopbackId	OBJECT-TYPE	
		SYNTAX			OCTET STRING  ( SIZE ( 1 .. 32  ) ) 
		MAX-ACCESS		read-create
		STATUS			current
		DESCRIPTION		"AtmLoopback Id."
		::=  {  bitSTORM-HP-160MtnAtmLoopbackEntry  2  }


	bitSTORM-HP-160MtnAtmIfTestType	OBJECT-TYPE	
		SYNTAX			INTEGER  { vce2e ( 2 ) , vcsegment ( 3 ) } 
		MAX-ACCESS		read-create
		STATUS			current
		DESCRIPTION		"Atm If Test Type."
		::=  {  bitSTORM-HP-160MtnAtmLoopbackEntry  3  }


	bitSTORM-HP-160MtnAtmIfTestState	OBJECT-TYPE	
		SYNTAX			INTEGER  { idle ( 0 ) , inprogess ( 1 ) , fail ( 2 ) , success ( 3 ) } 
		MAX-ACCESS		read-only
		STATUS			current
		DESCRIPTION		"Atm If Test State."
		::=  {  bitSTORM-HP-160MtnAtmLoopbackEntry  4  }


	bitSTORM-HP-160MtnAtmRowStatus	OBJECT-TYPE	
		SYNTAX			RowStatus
		MAX-ACCESS		read-create
		STATUS			current
		DESCRIPTION		"Atm If RowStatus."
		::=  {  bitSTORM-HP-160MtnAtmLoopbackEntry  5  }

	bitSTORM-HP-160SysAlmStatus	OBJECT-TYPE
		SYNTAX			BITS  {
		housekeep1Alarm ( 17 ) ,
		housekeep2Alarm ( 18 ) ,
		housekeep3Alarm ( 19 ) ,
		housekeep4Alarm ( 20 ) ,
		fanAlarm ( 21 ) ,
		selftestFailAlarm ( 22 ) ,
		aboveTempAlarm ( 23 ) ,
		belowTempAlarm ( 24 )
                }
		MAX-ACCESS		read-only
		STATUS			current
		DESCRIPTION		"Indicates current system-level alarm state.  This is a
                 bit-map of possible conditions.  The various bit
                 positions from left to right are:

          17      housekeep1Alarm        Housekeeping pin 1 detect an alarm input.
          18      housekeep2Alarm        Housekeeping pin 2 detect an alarm input.
          19      housekeep3Alarm        Housekeeping pin 3 detect an alarm input.
          20      housekeep4Alarm        Housekeeping pin 4 detect an alarm input.
          21      fanAlarm               Fan module reports fan failure.
          22      selftestFailAlarm      A module reports self-test failure.
          23      aboveTempAlarm         Temperature above normal.
          24      belowTempAlarm         Temperature below normal.
           "
		::=  {  bitSTORM-HP-160AlmMain  1  }

	bitSTORM-HP-160AlmMajorAlmStatus	OBJECT-TYPE	
		SYNTAX			INTEGER  { majorAlmStatusClear ( 0 ) , majorAlmStatusSet ( 1 ) } 
		MAX-ACCESS		read-only
		STATUS			current
		DESCRIPTION		"Major alarm state is detected or not.

       0: No major alarm detected
       1: Major alarms detected "
		::=  {  bitSTORM-HP-160AlmMain  2  }

	bitSTORM-HP-160AlmMinorAlmStatus	OBJECT-TYPE	
		SYNTAX			INTEGER  { minorAlmStatusClear ( 0 ) , minorAlmStatusSet ( 1 ) } 
		MAX-ACCESS		read-only
		STATUS			current
		DESCRIPTION		"Minor alarm state is detected or not.

       0: No minor alarm detected
       1: Minor alarms detected "
		::=  {  bitSTORM-HP-160AlmMain  3  }

	bitSTORM-HP-160AlmCutOff	OBJECT-TYPE	
		SYNTAX			INTEGER  { acoDeactive ( 0 ) , acoActive ( 1 ) } 
		MAX-ACCESS		read-write
		STATUS			current
		DESCRIPTION		"This command allows the ACO to be activated.
 	
 	0: Alarm cutoff deactive (only for read, not for write)
 	1: Alarm cutoff active"
		::=  {  bitSTORM-HP-160AlmMain  4  }

	bitSTORM-HP-160TrapAlarmPrefix	OBJECT IDENTIFIER
		::=  {  bitSTORM-HP-160Traps  1  }

	bitSTORM-HP-160TrapEventPrefix	OBJECT IDENTIFIER
		::=  {  bitSTORM-HP-160Traps  2  }

	bitSTORM-HP-160SNTPTimeZone	OBJECT-TYPE	
		SYNTAX			OCTET STRING  ( SIZE ( 8  ) ) 
		MAX-ACCESS		read-write
		STATUS			current
		DESCRIPTION		"This command is used to set the time zone. The CCT is +8 relative to Greenwich mean time (GMT).

        This field change will probably end up with time change too.
        "
		DEFVAL			{ gmt }
		::=  {  bitSTORM-HP-160SNTP  1  }

	bitSTORM-HP-160SNTPPollingInterval	OBJECT-TYPE	
		SYNTAX			Integer32  ( 60 .. 65535  ) 
		MAX-ACCESS		read-write
		STATUS			current
		DESCRIPTION		"This command sets the SNTP client to automatically send a time synchronization
        request (specific to the mode) to the network at a specific interval. If the
        poll-interval is set to 0, the polling mechanism will be disabled."
		DEFVAL			{ 600 }
		::=  {  bitSTORM-HP-160SNTP  2  }

	bitSTORM-HP-160SNTPServerIP	OBJECT-TYPE	
		SYNTAX			TAddress  ( SIZE ( 1 .. 255  ) ) 
		MAX-ACCESS		read-write
		STATUS			current
		DESCRIPTION		"This command is used to set the dedicated unicast server ipaddress for the SNTP client."
		::=  {  bitSTORM-HP-160SNTP  3  }

	bitSTORM-HP-160SNTPSynchronize	OBJECT-TYPE
		SYNTAX			INTEGER  { active ( 1 ) , ready ( 0 ) }
		MAX-ACCESS		read-write
		STATUS			current
		DESCRIPTION		"Always use active(1) to do SNTP Synchronization."
		::=  {  bitSTORM-HP-160SNTP  4  }
		
	bitSTORM-HP-160CfgInbandIPAddress	OBJECT-TYPE
		SYNTAX			TAddress
		MAX-ACCESS		read-write
		STATUS			current
		DESCRIPTION		"This field change will probably disconnect the current link."
		::=  {  bitSTORM-HP-160CfgInband  1  }

	bitSTORM-HP-160CfgInbandSubnetMask	OBJECT-TYPE
		SYNTAX			TAddress
		MAX-ACCESS		read-write
		STATUS			current
		DESCRIPTION		"This field change will probably disconnect the current link."
		::=  {  bitSTORM-HP-160CfgInband  2  }

	bitSTORM-HP-160CfgInbandMACAddress	OBJECT-TYPE
		SYNTAX			TAddress  ( SIZE ( 1 .. 255  ) ) 
		MAX-ACCESS		read-only
		STATUS			current
		DESCRIPTION		"This field can't be changed."
		::=  {  bitSTORM-HP-160CfgInband  3  }

	bitSTORM-HP-160CfgInbandManageVlanId	OBJECT-TYPE
		SYNTAX			Integer32  ( 0 .. 4094  ) 
		MAX-ACCESS		read-write
		STATUS			current
		DESCRIPTION		""
		::=  {  bitSTORM-HP-160CfgInband  4  }

	bitSTORM-HP-160CfgInbandManagePriority	OBJECT-TYPE
		SYNTAX			Integer32  ( 0 .. 7  )
		MAX-ACCESS		read-write
		STATUS			current
		DESCRIPTION		""
		::=  {  bitSTORM-HP-160CfgInband  5  }

	bitSTORM-HP-160CfgOutbandIPAddress	OBJECT-TYPE
		SYNTAX			TAddress
		MAX-ACCESS		read-write
		STATUS			current
		DESCRIPTION		"This field change will probably disconnect the current link."
		::=  {  bitSTORM-HP-160CfgOutband  1  }

	bitSTORM-HP-160CfgOutbandSubnetMask	OBJECT-TYPE	
		SYNTAX			TAddress
		MAX-ACCESS		read-write
		STATUS			current
		DESCRIPTION		"This field change will probably disconnect the current link."
		::=  {  bitSTORM-HP-160CfgOutband  2  }

--	bitSTORM-HP-160CfgOutbandDhcpStatus	OBJECT-TYPE
--		SYNTAX			INTEGER  { disable ( 0 ) , enable ( 1 ) , renew ( 2 ) }
--		MAX-ACCESS		read-write
--		STATUS			current
--		DESCRIPTION		"The DHCP admin status."
--		::=  {  bitSTORM-HP-160CfgOutband  3  }

--	bitSTORM-HP-160CfgOutbandDhcpTimeOut	OBJECT-TYPE	
--		SYNTAX			Unsigned32
--		MAX-ACCESS		read-write
--		STATUS			current
--		DESCRIPTION		"Dhcp TimeOut"
--		DEFVAL			{ 60 }
--		::=  {  bitSTORM-HP-160CfgOutband  4  }
  
--	bitSTORM-HP-160CfgOutbandDhcpLeaseTime	OBJECT-TYPE
--		SYNTAX			Unsigned32  ( 0 .. 4294967295  )
--		MAX-ACCESS		read-write
--		STATUS			current
--		DESCRIPTION		"DhcpLeaseTime"
--		DEFVAL			{ 600 }
--		::=  {  bitSTORM-HP-160CfgOutband  5  }

	bitSTORM-HP-160CfgBridgeMemberSetTable	OBJECT-TYPE
		SYNTAX		SEQUENCE  OF  BITSTORM-HP-160CfgBridgeMemberSetEntry
		MAX-ACCESS	not-accessible
		STATUS		current
		DESCRIPTION	""
		::=  { bitSTORM-HP-160CfgVlanGroup  1 }

	bitSTORM-HP-160CfgBridgeMemberSetEntry	OBJECT-TYPE
		SYNTAX		BITSTORM-HP-160CfgBridgeMemberSetEntry
		MAX-ACCESS	not-accessible
		STATUS		current
		DESCRIPTION	"the ports for a specific VLAN"
		INDEX		{  bitSTORM-HP-160CfgBridgeMemberSetVlanId  }
		::=  { bitSTORM-HP-160CfgBridgeMemberSetTable 1 }

	BITSTORM-HP-160CfgBridgeMemberSetEntry  ::=  SEQUENCE {
		bitSTORM-HP-160CfgBridgeMemberSetVlanId  Integer32,
		bitSTORM-HP-160CfgBridgeMemberSetEgressPorts  PortList,
		bitSTORM-HP-160CfgBridgeMemberSetUntaggedPorts  PortList,
		bitSTORM-HP-160CfgBridgeMemberSetIsolationPorts  PortList,
		bitSTORM-HP-160CfgBridgeMemberSetDefaultPorts  PortList,
		bitSTORM-HP-160CfgBridgeMemberSetRowStatus  RowStatus
		}


	bitSTORM-HP-160CfgBridgeMemberSetVlanId	OBJECT-TYPE	
		SYNTAX			Integer32
		MAX-ACCESS		read-only
		STATUS			current
		DESCRIPTION		"The identity of MemberSet."
		::=  {  bitSTORM-HP-160CfgBridgeMemberSetEntry  1  }


	bitSTORM-HP-160CfgBridgeMemberSetEgressPorts	OBJECT-TYPE	
		SYNTAX			PortList
		MAX-ACCESS		read-create
		STATUS			current
		DESCRIPTION		"28 Bytes for bridge port 0~219."
		::=  {  bitSTORM-HP-160CfgBridgeMemberSetEntry  2  }


	bitSTORM-HP-160CfgBridgeMemberSetUntaggedPorts	OBJECT-TYPE
		SYNTAX			PortList
		MAX-ACCESS		read-create
		STATUS			current
		DESCRIPTION		"28 Bytes for bridge port 0~219."
		::=  {  bitSTORM-HP-160CfgBridgeMemberSetEntry  3  }


	bitSTORM-HP-160CfgBridgeMemberSetIsolationPorts	OBJECT-TYPE
		SYNTAX			PortList
		MAX-ACCESS		read-create
		STATUS			current
		DESCRIPTION		"28 Bytes for bridge port 0~219."
		::=  {  bitSTORM-HP-160CfgBridgeMemberSetEntry  4  }


	bitSTORM-HP-160CfgBridgeMemberSetDefaultPorts	OBJECT-TYPE
		SYNTAX			PortList
		MAX-ACCESS		read-only
		STATUS			current
		DESCRIPTION		"28 Bytes for bridge port 0~219."
		::=  {  bitSTORM-HP-160CfgBridgeMemberSetEntry  5  }


	bitSTORM-HP-160CfgBridgeMemberSetRowStatus	OBJECT-TYPE
		SYNTAX			RowStatus
		MAX-ACCESS		read-create
		STATUS			current
		DESCRIPTION		""
		DEFVAL			{ createAndGo }
		::=  {  bitSTORM-HP-160CfgBridgeMemberSetEntry  6  }

	bitSTORM-HP-160CfgBridgeVlanListTable	OBJECT-TYPE
		SYNTAX		SEQUENCE  OF  BITSTORM-HP-160CfgBridgeVlanListEntry
		MAX-ACCESS	not-accessible
		STATUS		current
		DESCRIPTION	""
		::=  { bitSTORM-HP-160CfgVlanGroup  2 }

	bitSTORM-HP-160CfgBridgeVlanListEntry	OBJECT-TYPE
		SYNTAX		BITSTORM-HP-160CfgBridgeVlanListEntry
		MAX-ACCESS	not-accessible
		STATUS		current
		DESCRIPTION	"the VLANs for a specific port"
		INDEX		{  bitSTORM-HP-160CfgBridgeVlanListPortIndex  }
		::=  { bitSTORM-HP-160CfgBridgeVlanListTable 1 }

	BITSTORM-HP-160CfgBridgeVlanListEntry  ::=  SEQUENCE {
		bitSTORM-HP-160CfgBridgeVlanListPortIndex  Integer32,
		bitSTORM-HP-160CfgBridgeVlanListVIDs  OCTET STRING
		}


	bitSTORM-HP-160CfgBridgeVlanListPortIndex	OBJECT-TYPE	
		SYNTAX			Integer32
		MAX-ACCESS		read-only
		STATUS			current
		DESCRIPTION		"The identity of VlanList."
		::=  {  bitSTORM-HP-160CfgBridgeVlanListEntry  1  }


	bitSTORM-HP-160CfgBridgeVlanListVIDs	OBJECT-TYPE	
		SYNTAX			OCTET STRING
		MAX-ACCESS		read-only
		STATUS			current
		DESCRIPTION		""
		::=  {  bitSTORM-HP-160CfgBridgeVlanListEntry  2  }

	bitSTORM-HP-160CfgBridgeTpFdbTable	OBJECT-TYPE
		SYNTAX		SEQUENCE  OF  BITSTORM-HP-160CfgBridgeTpFdbEntry
		MAX-ACCESS	not-accessible
		STATUS		current
		DESCRIPTION	"A table containing filtering information for Unicast
        MAC addresses for each Filtering Database, configured
        into the device by (local or network) management
        specifying the set of ports to which frames received
        from specific ports and containing specific unicast
        destination addresses are allowed to be forwarded.  A
        value of zero in this table as the port number from
        which frames with a specific destination address are
        received, is used to specify all ports for which there
        is no specific entry in this table for that particular
        destination address.  Entries are valid for unicast
        addresses only."
		::=  { bitSTORM-HP-160CfgVlanGroup  3 }

	bitSTORM-HP-160CfgBridgeTpFdbEntry	OBJECT-TYPE
		SYNTAX		BITSTORM-HP-160CfgBridgeTpFdbEntry
		MAX-ACCESS	not-accessible
		STATUS		current
		DESCRIPTION	"Filtering information configured into the device by
        (local or network) management specifying the set of
        ports to which frames received from a specific port and
        containing a specific unicast destination address are
        allowed to be forwarded."
		INDEX		{  bitSTORM-HP-160CfgBridgeTpFdbId  }
		::=  { bitSTORM-HP-160CfgBridgeTpFdbTable 1 }

	BITSTORM-HP-160CfgBridgeTpFdbEntry  ::=  SEQUENCE {
		bitSTORM-HP-160CfgBridgeTpFdbId  Unsigned32,
		bitSTORM-HP-160CfgBridgeTpFdbMacAddress  PhysAddress,
		bitSTORM-HP-160CfgBridgeTpFdbReceivePort  Integer32,
		bitSTORM-HP-160CfgBridgeTpFdbVlan  Integer32,
		bitSTORM-HP-160CfgBridgeTpFdbStatus  INTEGER,
		bitSTORM-HP-160CfgBridgeTpFdbAgingBit  INTEGER,
		bitSTORM-HP-160CfgBridgeTpFdbProcessMode  INTEGER,
		bitSTORM-HP-160CfgBridgeTpFdbUnknownMacMode  INTEGER
		}


	bitSTORM-HP-160CfgBridgeTpFdbId	OBJECT-TYPE	
		SYNTAX			Unsigned32
		MAX-ACCESS		read-only
		STATUS			current
		DESCRIPTION		"The identity of this Filtering Database."
		::=  {  bitSTORM-HP-160CfgBridgeTpFdbEntry  1  }


	bitSTORM-HP-160CfgBridgeTpFdbMacAddress	OBJECT-TYPE	
		SYNTAX			PhysAddress
		MAX-ACCESS		read-only
		STATUS			current
		DESCRIPTION		"The destination MAC address in a frame to which this
        entry's filtering information applies.  This object must
        take the value of a unicast address."
		::=  {  bitSTORM-HP-160CfgBridgeTpFdbEntry  2  }


	bitSTORM-HP-160CfgBridgeTpFdbReceivePort	OBJECT-TYPE	
		SYNTAX			Integer32  ( 0 .. 65535  ) 
		MAX-ACCESS		read-only
		STATUS			current
		DESCRIPTION		"Either the value '0', or the port number of the port
        from which a frame must be received in order for this
        entry's filtering information to apply.  A value of zero
        indicates that this entry applies on all ports of the
        device for which there is no other applicable entry."
		::=  {  bitSTORM-HP-160CfgBridgeTpFdbEntry  3  }


	bitSTORM-HP-160CfgBridgeTpFdbVlan	OBJECT-TYPE	
		SYNTAX			Integer32  ( 0 .. 4094  )   --960803 
		MAX-ACCESS		read-only
		STATUS			current
		DESCRIPTION		""
		::=  {  bitSTORM-HP-160CfgBridgeTpFdbEntry  4  }


	bitSTORM-HP-160CfgBridgeTpFdbStatus	OBJECT-TYPE          
		SYNTAX			INTEGER  { static ( 0 ) , dynamic ( 1 ) , admin ( 2 )  }
		MAX-ACCESS		read-only
		STATUS			current
		DESCRIPTION		""   		
		::=  {  bitSTORM-HP-160CfgBridgeTpFdbEntry  5  }


	bitSTORM-HP-160CfgBridgeTpFdbAgingBit	OBJECT-TYPE	
		SYNTAX			INTEGER  { false ( 0 ) , true ( 1 ) } 
		MAX-ACCESS		read-only
		STATUS			current
		DESCRIPTION		""
		::=  {  bitSTORM-HP-160CfgBridgeTpFdbEntry  6  }


	bitSTORM-HP-160CfgBridgeTpFdbProcessMode	OBJECT-TYPE	
		SYNTAX			INTEGER  { pass ( 0 ) , deny ( 1 ) , direct-term ( 2 ) , res-mc-term ( 3 ) , svl-uc-pass ( 4 ) } 
		MAX-ACCESS		read-only
		STATUS			current
		DESCRIPTION		""
		::=  {  bitSTORM-HP-160CfgBridgeTpFdbEntry  7  }


	bitSTORM-HP-160CfgBridgeTpFdbUnknownMacMode	OBJECT-TYPE	
		SYNTAX			INTEGER  { disabled ( 0 ) , unitcast ( 1 ) , multicast ( 2 ) } 
		MAX-ACCESS		read-only
		STATUS			current
		DESCRIPTION		""
		::=  {  bitSTORM-HP-160CfgBridgeTpFdbEntry  8  }

	bitSTORM-HP-160CfgBridgeFdbStaticTable	OBJECT-TYPE
		SYNTAX		SEQUENCE  OF  BITSTORM-HP-160CfgBridgeFdbStaticEntry
		MAX-ACCESS	not-accessible
		STATUS		current
		DESCRIPTION	"A table containing filtering information for Multicast
        and Broadcast MAC addresses for each VLAN, configured
        into the device by (local or network) management
        specifying the set of ports to which frames received
        from specific ports and containing specific Multicast
        and Broadcast destination addresses are allowed to be
        forwarded.  A value of zero in this table as the port
        number from which frames with a specific destination
        address are received, is used to specify all ports for
        which there is no specific entry in this table for that
        particular destination address.  Entries are valid for
        Multicast and Broadcast addresses only."
		::=  { bitSTORM-HP-160CfgVlanGroup  4 }

	bitSTORM-HP-160CfgBridgeFdbStaticEntry	OBJECT-TYPE
		SYNTAX		BITSTORM-HP-160CfgBridgeFdbStaticEntry
		MAX-ACCESS	not-accessible
		STATUS		current
		DESCRIPTION	"Filtering information configured into the device by
        (local or network) management specifying the set of
        ports to which frames received from this specific port
        for this VLAN and containing this Multicast or Broadcast
        destination address are allowed to be forwarded."
		INDEX		{  bitSTORM-HP-160CfgBridgeFdbStaticId  }
		::=  { bitSTORM-HP-160CfgBridgeFdbStaticTable 1 }

	BITSTORM-HP-160CfgBridgeFdbStaticEntry  ::=  SEQUENCE {
		bitSTORM-HP-160CfgBridgeFdbStaticId  Unsigned32,
		bitSTORM-HP-160CfgBridgeFdbStaticAddress  OCTET STRING,
		bitSTORM-HP-160CfgBridgeFdbStaticOutPort  Integer32,
		bitSTORM-HP-160CfgBridgeFdbStaticVlan  Integer32,
		bitSTORM-HP-160CfgBridgeFdbStaticrProcessMode  INTEGER,
		bitSTORM-HP-160CfgBridgeFdbStaticrRowStatus  RowStatus
		}


	bitSTORM-HP-160CfgBridgeFdbStaticId	OBJECT-TYPE	
		SYNTAX			Unsigned32
		MAX-ACCESS		read-only
		STATUS			current
		DESCRIPTION		"The identity of this Filtering Database."
		::=  {  bitSTORM-HP-160CfgBridgeFdbStaticEntry  1  }


	bitSTORM-HP-160CfgBridgeFdbStaticAddress	OBJECT-TYPE	
		SYNTAX			OCTET STRING  ( SIZE ( 17  ) )
		MAX-ACCESS		read-create
		STATUS			current
		DESCRIPTION		"The destination MAC address in a frame to which this
        entry's filtering information applies.  This object must
        take the value of a Multicast or Broadcast address."
		::=  {  bitSTORM-HP-160CfgBridgeFdbStaticEntry  2  }


	bitSTORM-HP-160CfgBridgeFdbStaticOutPort	OBJECT-TYPE	
		SYNTAX			Integer32  ( 0 .. 65535  ) 
		MAX-ACCESS		read-create
		STATUS			current
		DESCRIPTION		"Either the value '0', or the port number of the port
        from which a frame must be received in order for this
        entry's filtering information to apply.  A value of zero
        indicates that this entry applies on all ports of the
        device for which there is no other applicable entry."
		::=  {  bitSTORM-HP-160CfgBridgeFdbStaticEntry  3  }


	bitSTORM-HP-160CfgBridgeFdbStaticVlan	OBJECT-TYPE	
		SYNTAX			Integer32  ( 0 .. 4094  )   --960803 
		MAX-ACCESS		read-create
		STATUS			current
		DESCRIPTION		""
		::=  {  bitSTORM-HP-160CfgBridgeFdbStaticEntry  4  }


	bitSTORM-HP-160CfgBridgeFdbStaticrProcessMode	OBJECT-TYPE	
		SYNTAX			INTEGER  { deny ( 0 ) , pass ( 1 ) } 
		MAX-ACCESS		read-create
		STATUS			current
		DESCRIPTION		""
		::=  {  bitSTORM-HP-160CfgBridgeFdbStaticEntry  5  }


	bitSTORM-HP-160CfgBridgeFdbStaticrRowStatus	OBJECT-TYPE	
		SYNTAX			RowStatus
		MAX-ACCESS		read-create
		STATUS			current
		DESCRIPTION		"The status of this 
          bitSTORM-HP-160CfgBridgeFdbStaticEntry entry."
		::=  {  bitSTORM-HP-160CfgBridgeFdbStaticEntry  6  }

	bitSTORM-HP-160CfgRateLimitGroup	OBJECT IDENTIFIER
		::=  {  bitSTORM-HP-160CfgVlanGroup  6  }

	bitSTORM-HP-160CfgVlanPriorityGroup	OBJECT IDENTIFIER
		::=  {  bitSTORM-HP-160CfgVlanGroup  7  }


	bitSTORM-HP-160CfgBridgeProtocolFilterTable	OBJECT-TYPE
		SYNTAX		SEQUENCE  OF  BITSTORM-HP-160CfgBridgeProtocolFilterEntry
		MAX-ACCESS	not-accessible
		STATUS		current
		DESCRIPTION	"The Protocol filter configuration table."
		::=  { bitSTORM-HP-160CfgFilterGroup  1 }

	bitSTORM-HP-160CfgBridgeProtocolFilterEntry	OBJECT-TYPE
		SYNTAX		BITSTORM-HP-160CfgBridgeProtocolFilterEntry
		MAX-ACCESS	not-accessible
		STATUS		current
		DESCRIPTION	"An Entry in the bitSTORM-HP-160CfgBridgeProtocolFilterTable"
		INDEX		{  bitSTORM-HP-160CfgBridgeProtocolFilterIndex  }
		::=  { bitSTORM-HP-160CfgBridgeProtocolFilterTable 1 }

	BITSTORM-HP-160CfgBridgeProtocolFilterEntry  ::=  SEQUENCE {
		bitSTORM-HP-160CfgBridgeProtocolFilterIndex  Integer32,
		bitSTORM-HP-160CfgBridgeProtocolFilterInputBridgePort  InterfaceIndex,
		bitSTORM-HP-160CfgBridgeProtocolFilter  INTEGER,
		bitSTORM-HP-160CfgBridgeProtocolFilterRowStatus  RowStatus
		}


	bitSTORM-HP-160CfgBridgeProtocolFilterIndex	OBJECT-TYPE	
		SYNTAX			Integer32
		MAX-ACCESS		read-only
		STATUS			current
		DESCRIPTION		""
		::=  {  bitSTORM-HP-160CfgBridgeProtocolFilterEntry  1  }


	bitSTORM-HP-160CfgBridgeProtocolFilterInputBridgePort	OBJECT-TYPE	
		SYNTAX			InterfaceIndex
		MAX-ACCESS		read-create
		STATUS			current
		DESCRIPTION		""
		::=  {  bitSTORM-HP-160CfgBridgeProtocolFilterEntry  2  }


	bitSTORM-HP-160CfgBridgeProtocolFilter	OBJECT-TYPE
		SYNTAX			INTEGER  { 
		udp(17),
                tcp(6),
                ospf(89),
                igmp(2),
                igp(9),
                eigrp(88),
                ipinip(4),
                gre(47),
                icmp(1)
                }
		MAX-ACCESS		read-create
		STATUS			current
		DESCRIPTION		""
		::=  {  bitSTORM-HP-160CfgBridgeProtocolFilterEntry  3  }


	bitSTORM-HP-160CfgBridgeProtocolFilterRowStatus	OBJECT-TYPE	
		SYNTAX			RowStatus
		MAX-ACCESS		read-create
		STATUS			current
		DESCRIPTION		""
		::=  {  bitSTORM-HP-160CfgBridgeProtocolFilterEntry  4  }

	bitSTORM-HP-160CfgBridgeL4DstPortFilterTable	OBJECT-TYPE
		SYNTAX		SEQUENCE  OF  BITSTORM-HP-160CfgBridgeL4DstPortFilterEntry
		MAX-ACCESS	not-accessible
		STATUS		current
		DESCRIPTION	"The L4 dst filter configuration table."
		::=  { bitSTORM-HP-160CfgFilterGroup  2 }

	bitSTORM-HP-160CfgBridgeL4DstPortFilterEntry	OBJECT-TYPE
		SYNTAX		BITSTORM-HP-160CfgBridgeL4DstPortFilterEntry
		MAX-ACCESS	not-accessible
		STATUS		current
		DESCRIPTION	"An Entry in the bitSTORM-HP-160CfgBridgeL4DstPortFilterTable"
		INDEX		{  bitSTORM-HP-160CfgBridgeL4DstPortFilterIndex  }
		::=  { bitSTORM-HP-160CfgBridgeL4DstPortFilterTable 1 }

	BITSTORM-HP-160CfgBridgeL4DstPortFilterEntry  ::=  SEQUENCE {
		bitSTORM-HP-160CfgBridgeL4DstPortFilterIndex  Integer32,
		bitSTORM-HP-160CfgBridgeL4DstPortFilterInputBridgePort  InterfaceIndex,
		bitSTORM-HP-160CfgBridgeL4DstPortFilterDestinationPort  Integer32,
		bitSTORM-HP-160CfgBridgeL4DstPortFilterRowStatus  RowStatus
		}


	bitSTORM-HP-160CfgBridgeL4DstPortFilterIndex	OBJECT-TYPE	
		SYNTAX			Integer32
		MAX-ACCESS		read-only
		STATUS			current
		DESCRIPTION		""
		::=  {  bitSTORM-HP-160CfgBridgeL4DstPortFilterEntry  1  }


	bitSTORM-HP-160CfgBridgeL4DstPortFilterInputBridgePort	OBJECT-TYPE	
		SYNTAX			InterfaceIndex
		MAX-ACCESS		read-create
		STATUS			current
		DESCRIPTION		""
		::=  {  bitSTORM-HP-160CfgBridgeL4DstPortFilterEntry  2  }


	bitSTORM-HP-160CfgBridgeL4DstPortFilterDestinationPort	OBJECT-TYPE	
		SYNTAX			Integer32
		MAX-ACCESS		read-create
		STATUS			current
		DESCRIPTION		""
		::=  {  bitSTORM-HP-160CfgBridgeL4DstPortFilterEntry  3  }


	bitSTORM-HP-160CfgBridgeL4DstPortFilterRowStatus	OBJECT-TYPE	
		SYNTAX			RowStatus
		MAX-ACCESS		read-create
		STATUS			current
		DESCRIPTION		""
		::=  {  bitSTORM-HP-160CfgBridgeL4DstPortFilterEntry  4  }

	bitSTORM-HP-160CfgBridgeSrcMacFilterTable	OBJECT-TYPE
		SYNTAX		SEQUENCE  OF  BITSTORM-HP-160CfgBridgeSrcMacFilterEntry
		MAX-ACCESS	not-accessible
		STATUS		current
		DESCRIPTION	""
		::=  { bitSTORM-HP-160CfgFilterGroup  3 }

	bitSTORM-HP-160CfgBridgeSrcMacFilterEntry	OBJECT-TYPE
		SYNTAX		BITSTORM-HP-160CfgBridgeSrcMacFilterEntry
		MAX-ACCESS	not-accessible
		STATUS		current
		DESCRIPTION	""
		INDEX		{  bitSTORM-HP-160BridgeSrcMacFilterIndex  }
		::=  { bitSTORM-HP-160CfgBridgeSrcMacFilterTable 1 }

	BITSTORM-HP-160CfgBridgeSrcMacFilterEntry  ::=  SEQUENCE {
		bitSTORM-HP-160BridgeSrcMacFilterIndex  Integer32,
		bitSTORM-HP-160BridgeSrcMacFilterBpIndex  InterfaceIndex,
		bitSTORM-HP-160BridgeSrcMacFilterSrcMac  PhysAddress,
		bitSTORM-HP-160BridgeSrcMacFilterRowStatus  RowStatus
		}


	bitSTORM-HP-160BridgeSrcMacFilterIndex	OBJECT-TYPE	
		SYNTAX			Integer32  ( 1 .. 4095  ) 
		MAX-ACCESS		read-only
		STATUS			current
		DESCRIPTION		""
		::=  {  bitSTORM-HP-160CfgBridgeSrcMacFilterEntry  1  }


	bitSTORM-HP-160BridgeSrcMacFilterBpIndex	OBJECT-TYPE	
		SYNTAX			InterfaceIndex
		MAX-ACCESS		read-create
		STATUS			current
		DESCRIPTION		""
		::=  {  bitSTORM-HP-160CfgBridgeSrcMacFilterEntry  2  }


	bitSTORM-HP-160BridgeSrcMacFilterSrcMac	OBJECT-TYPE	
		SYNTAX			PhysAddress
		MAX-ACCESS		read-create
		STATUS			current
		DESCRIPTION		""
		::=  {  bitSTORM-HP-160CfgBridgeSrcMacFilterEntry  3  }


	bitSTORM-HP-160BridgeSrcMacFilterRowStatus	OBJECT-TYPE	
		SYNTAX			RowStatus
		MAX-ACCESS		read-create
		STATUS			current
		DESCRIPTION		""
		DEFVAL			{ createAndGo }
		::=  {  bitSTORM-HP-160CfgBridgeSrcMacFilterEntry  4  }
		
--
	bitSTORM-HP-160CfgBridgeL4SrcPortFilterTable	OBJECT-TYPE
		SYNTAX		SEQUENCE  OF  BITSTORM-HP-160CfgBridgeL4SrcPortFilterEntry
		MAX-ACCESS	not-accessible
		STATUS		current
		DESCRIPTION	"The L4 Src filter configuration table."
		::=  { bitSTORM-HP-160CfgFilterGroup  4 }

	bitSTORM-HP-160CfgBridgeL4SrcPortFilterEntry	OBJECT-TYPE
		SYNTAX		BITSTORM-HP-160CfgBridgeL4SrcPortFilterEntry
		MAX-ACCESS	not-accessible
		STATUS		current
		DESCRIPTION	"An Entry in the bitSTORM-HP-160CfgBridgeL4SrcPortFilterTable"
		INDEX		{  bitSTORM-HP-160CfgBridgeL4SrcPortFilterIndex  }
		::=  { bitSTORM-HP-160CfgBridgeL4SrcPortFilterTable 1 }

	BITSTORM-HP-160CfgBridgeL4SrcPortFilterEntry  ::=  SEQUENCE {
		bitSTORM-HP-160CfgBridgeL4SrcPortFilterIndex  Integer32,
		bitSTORM-HP-160CfgBridgeL4SrcPortFilterInputBridgePort  InterfaceIndex,
		bitSTORM-HP-160CfgBridgeL4SrcPortFilterDestinationPort  Integer32,
		bitSTORM-HP-160CfgBridgeL4SrcPortFilterRowStatus  RowStatus
		}


	bitSTORM-HP-160CfgBridgeL4SrcPortFilterIndex	OBJECT-TYPE	
		SYNTAX			Integer32
		MAX-ACCESS		read-only
		STATUS			current
		DESCRIPTION		""
		::=  {  bitSTORM-HP-160CfgBridgeL4SrcPortFilterEntry  1  }


	bitSTORM-HP-160CfgBridgeL4SrcPortFilterInputBridgePort	OBJECT-TYPE	
		SYNTAX			InterfaceIndex
		MAX-ACCESS		read-create
		STATUS			current
		DESCRIPTION		""
		::=  {  bitSTORM-HP-160CfgBridgeL4SrcPortFilterEntry  2  }


	bitSTORM-HP-160CfgBridgeL4SrcPortFilterDestinationPort	OBJECT-TYPE	
		SYNTAX			Integer32
		MAX-ACCESS		read-create
		STATUS			current
		DESCRIPTION		""
		::=  {  bitSTORM-HP-160CfgBridgeL4SrcPortFilterEntry  3  }


	bitSTORM-HP-160CfgBridgeL4SrcPortFilterRowStatus	OBJECT-TYPE	
		SYNTAX			RowStatus
		MAX-ACCESS		read-create
		STATUS			current
		DESCRIPTION		""
		::=  {  bitSTORM-HP-160CfgBridgeL4SrcPortFilterEntry  4  }
--		

--	bitSTORM-HP-160CfgBridgePrioTagFilterTable	OBJECT-TYPE
--		SYNTAX		SEQUENCE  OF  BITSTORM-HP-160CfgBridgePrioTagFilterEntry
--		MAX-ACCESS	not-accessible
--		STATUS		current
--		DESCRIPTION	""
--		::=  { bitSTORM-HP-160CfgFilterGroup  4 }

--	bitSTORM-HP-160CfgBridgePrioTagFilterEntry	OBJECT-TYPE
--		SYNTAX		BITSTORM-HP-160CfgBridgePrioTagFilterEntry
--		MAX-ACCESS	not-accessible
--		STATUS		current
--		DESCRIPTION	""
--		INDEX		{  bitSTORM-HP-160BridgePrioTagFilterIndex  }
--		::=  { bitSTORM-HP-160CfgBridgePrioTagFilterTable 1 }

--	BITSTORM-HP-160CfgBridgePrioTagFilterEntry  ::=  SEQUENCE {
--		bitSTORM-HP-160BridgePrioTagFilterIndex  Integer32,
--		bitSTORM-HP-160BridgePrioTagInputBridgePort  InterfaceIndex,
--		bitSTORM-HP-160BridgePrioTagOutgoingVlanPriority  Integer32,
--		bitSTORM-HP-160BridgePrioTagIncomingVlanPriority  Integer32,
--		bitSTORM-HP-160BridgePrioTagFilterRowStatus  RowStatus
--		}


--	bitSTORM-HP-160BridgePrioTagFilterIndex	OBJECT-TYPE
--		SYNTAX			Integer32  ( 1 .. 4095  )
--		MAX-ACCESS		read-only
--		STATUS			current
--		DESCRIPTION		""
--		::=  {  bitSTORM-HP-160CfgBridgePrioTagFilterEntry  1  }


--	bitSTORM-HP-160BridgePrioTagInputBridgePort	OBJECT-TYPE
--		SYNTAX			InterfaceIndex
--		MAX-ACCESS		read-create
--		STATUS			current
--		DESCRIPTION		""
--		::=  {  bitSTORM-HP-160CfgBridgePrioTagFilterEntry  2  }


--	bitSTORM-HP-160BridgePrioTagOutgoingVlanPriority	OBJECT-TYPE
--		SYNTAX			Integer32  ( 0 .. 7  )
--		MAX-ACCESS		read-create
--		STATUS			current
--		DESCRIPTION		""
--		DEFVAL			{ 0 }
--		::=  {  bitSTORM-HP-160CfgBridgePrioTagFilterEntry  3  }


--	bitSTORM-HP-160BridgePrioTagIncomingVlanPriority	OBJECT-TYPE
--		SYNTAX			Integer32  ( 0 .. 7  )
--		MAX-ACCESS		read-create
--		STATUS			current
--		DESCRIPTION		""
--		DEFVAL			{ 0 }
--		::=  {  bitSTORM-HP-160CfgBridgePrioTagFilterEntry  4  }


--	bitSTORM-HP-160BridgePrioTagFilterRowStatus	OBJECT-TYPE
--		SYNTAX			RowStatus
--		MAX-ACCESS		read-create
--		STATUS			current
--		DESCRIPTION		""
--		DEFVAL			{ createAndGo }
--		::=  {  bitSTORM-HP-160CfgBridgePrioTagFilterEntry  5  }

	bitSTORM-HP-160CfgBridgeSrcIpFilterTable	OBJECT-TYPE
		SYNTAX		SEQUENCE  OF  BITSTORM-HP-160CfgBridgeSrcIpFilterEntry
		MAX-ACCESS	not-accessible
		STATUS		current
		DESCRIPTION	""
		::=  { bitSTORM-HP-160CfgFilterGroup  5 }

	bitSTORM-HP-160CfgBridgeSrcIpFilterEntry	OBJECT-TYPE
		SYNTAX		BITSTORM-HP-160CfgBridgeSrcIpFilterEntry
		MAX-ACCESS	not-accessible
		STATUS		current
		DESCRIPTION	""
		INDEX		{  bitSTORM-HP-160BridgeSrcIpFilterIndex  }
		::=  { bitSTORM-HP-160CfgBridgeSrcIpFilterTable 1 }

	BITSTORM-HP-160CfgBridgeSrcIpFilterEntry  ::=  SEQUENCE {
		bitSTORM-HP-160BridgeSrcIpFilterIndex  Integer32,
		bitSTORM-HP-160BridgeSrcIpFilterBpIndex  InterfaceIndex,
		bitSTORM-HP-160BridgeSrcIpFilterSrcIpStart  IpAddress,
		bitSTORM-HP-160BridgeSrcIpFilterSrcIpEnd  IpAddress,
		bitSTORM-HP-160BridgeSrcIpFilterRowStatus  RowStatus
		}


	bitSTORM-HP-160BridgeSrcIpFilterIndex	OBJECT-TYPE	
		SYNTAX			Integer32  ( 1 .. 4095  ) 
		MAX-ACCESS		read-only
		STATUS			current
		DESCRIPTION		""
		::=  {  bitSTORM-HP-160CfgBridgeSrcIpFilterEntry  1  }


	bitSTORM-HP-160BridgeSrcIpFilterBpIndex	OBJECT-TYPE	
		SYNTAX			InterfaceIndex
		MAX-ACCESS		read-create
		STATUS			current
		DESCRIPTION		""
		::=  {  bitSTORM-HP-160CfgBridgeSrcIpFilterEntry  2  }


	bitSTORM-HP-160BridgeSrcIpFilterSrcIpStart	OBJECT-TYPE	
		SYNTAX			IpAddress
		MAX-ACCESS		read-create
		STATUS			current
		DESCRIPTION		""
		::=  {  bitSTORM-HP-160CfgBridgeSrcIpFilterEntry  3  }


	bitSTORM-HP-160BridgeSrcIpFilterSrcIpEnd	OBJECT-TYPE	
		SYNTAX			IpAddress
		MAX-ACCESS		read-create
		STATUS			current
		DESCRIPTION		""
		::=  {  bitSTORM-HP-160CfgBridgeSrcIpFilterEntry  4  }


	bitSTORM-HP-160BridgeSrcIpFilterRowStatus	OBJECT-TYPE	
		SYNTAX			RowStatus
		MAX-ACCESS		read-create
		STATUS			current
		DESCRIPTION		""
		DEFVAL			{ createAndGo }
		::=  {  bitSTORM-HP-160CfgBridgeSrcIpFilterEntry  5  }

	bitSTORM-HP-160CfgBridgeDstIpFilterTable	OBJECT-TYPE
		SYNTAX		SEQUENCE  OF  BITSTORM-HP-160CfgBridgeDstIpFilterEntry
		MAX-ACCESS	not-accessible
		STATUS		current
		DESCRIPTION	""
		::=  { bitSTORM-HP-160CfgFilterGroup  6 }   

	bitSTORM-HP-160CfgBridgeDstIpFilterEntry	OBJECT-TYPE
		SYNTAX		BITSTORM-HP-160CfgBridgeDstIpFilterEntry
		MAX-ACCESS	not-accessible
		STATUS		current
		DESCRIPTION	""
		INDEX		{  bitSTORM-HP-160BridgeDstIpFilterIndex  }
		::=  { bitSTORM-HP-160CfgBridgeDstIpFilterTable 1 }

	BITSTORM-HP-160CfgBridgeDstIpFilterEntry  ::=  SEQUENCE {
		bitSTORM-HP-160BridgeDstIpFilterIndex  Integer32,
		bitSTORM-HP-160BridgeDstIpFilterBpIndex  InterfaceIndex,
		bitSTORM-HP-160BridgeDstIpFilterSrcIpStart  IpAddress,
		bitSTORM-HP-160BridgeDstIpFilterSrcIpEnd  IpAddress,
		bitSTORM-HP-160BridgeDstIpFilterRowStatus  RowStatus
		}


	bitSTORM-HP-160BridgeDstIpFilterIndex	OBJECT-TYPE
		SYNTAX			Integer32  ( 1 .. 4095  )
		MAX-ACCESS		read-only
		STATUS			current
		DESCRIPTION		""
		::=  {  bitSTORM-HP-160CfgBridgeDstIpFilterEntry  1  }


	bitSTORM-HP-160BridgeDstIpFilterBpIndex	OBJECT-TYPE
		SYNTAX			InterfaceIndex
		MAX-ACCESS		read-create
		STATUS			current
		DESCRIPTION		""
		::=  {  bitSTORM-HP-160CfgBridgeDstIpFilterEntry  2  }


	bitSTORM-HP-160BridgeDstIpFilterSrcIpStart	OBJECT-TYPE
		SYNTAX			IpAddress
		MAX-ACCESS		read-create
		STATUS			current
		DESCRIPTION		""
		::=  {  bitSTORM-HP-160CfgBridgeDstIpFilterEntry  3  }


	bitSTORM-HP-160BridgeDstIpFilterSrcIpEnd	OBJECT-TYPE
		SYNTAX			IpAddress
		MAX-ACCESS		read-create
		STATUS			current
		DESCRIPTION		""
		::=  {  bitSTORM-HP-160CfgBridgeDstIpFilterEntry  4  }


	bitSTORM-HP-160BridgeDstIpFilterRowStatus	OBJECT-TYPE
		SYNTAX			RowStatus
		MAX-ACCESS		read-create
		STATUS			current
		DESCRIPTION		""
		DEFVAL			{ createAndGo }
		::=  {  bitSTORM-HP-160CfgBridgeDstIpFilterEntry  5  }








	bitSTORM-HP-160CfgBridgeNetBiosFilterTable	OBJECT-TYPE
		SYNTAX		SEQUENCE  OF  BITSTORM-HP-160CfgBridgeNetBiosFilterEntry
		MAX-ACCESS	not-accessible
		STATUS		current
		DESCRIPTION	""
		::=  { bitSTORM-HP-160CfgFilterGroup  7 }

	bitSTORM-HP-160CfgBridgeNetBiosFilterEntry	OBJECT-TYPE
		SYNTAX		BITSTORM-HP-160CfgBridgeNetBiosFilterEntry
		MAX-ACCESS	not-accessible
		STATUS		current
		DESCRIPTION	"An Entry in the bitSTORM-HP-160CfgBridgeNetBiosFilterTable"
		INDEX		{  bitSTORM-HP-160CfgBridgeNetBiosFilterInputBridgePort  }
		::=  { bitSTORM-HP-160CfgBridgeNetBiosFilterTable 1 }

	BITSTORM-HP-160CfgBridgeNetBiosFilterEntry  ::=  SEQUENCE {
		bitSTORM-HP-160CfgBridgeNetBiosFilterInputBridgePort  InterfaceIndex,
		bitSTORM-HP-160CfgBridgeNetBiosFilterStatus  INTEGER,
		bitSTORM-HP-160CfgBridgeNetBiosFilterRowStatus  RowStatus
		}


	bitSTORM-HP-160CfgBridgeNetBiosFilterInputBridgePort	OBJECT-TYPE
		SYNTAX			InterfaceIndex
		MAX-ACCESS		read-only
		STATUS			current
		DESCRIPTION		""
		::=  {  bitSTORM-HP-160CfgBridgeNetBiosFilterEntry  1  }


	bitSTORM-HP-160CfgBridgeNetBiosFilterStatus	OBJECT-TYPE
		SYNTAX			INTEGER  { enable ( 1 ) , disable ( 0 ) }
		MAX-ACCESS		read-create
		STATUS			current
		DESCRIPTION		""
		::=  {  bitSTORM-HP-160CfgBridgeNetBiosFilterEntry  2  }


	bitSTORM-HP-160CfgBridgeNetBiosFilterRowStatus	OBJECT-TYPE
		SYNTAX			RowStatus
		MAX-ACCESS		read-create
		STATUS			current
		DESCRIPTION		""
		::=  {  bitSTORM-HP-160CfgBridgeNetBiosFilterEntry  3  }

                                                                    

	bitSTORM-HP-160CfgBridgeArpBcastFilterTable	OBJECT-TYPE
		SYNTAX		SEQUENCE  OF  BITSTORM-HP-160CfgBridgeArpBcastFilterEntry
		MAX-ACCESS	not-accessible
		STATUS		current
		DESCRIPTION	""
		::=  { bitSTORM-HP-160CfgFilterGroup  8 }

	bitSTORM-HP-160CfgBridgeArpBcastFilterEntry	OBJECT-TYPE
		SYNTAX		BITSTORM-HP-160CfgBridgeArpBcastFilterEntry
		MAX-ACCESS	not-accessible
		STATUS		current
		DESCRIPTION	"An Entry in the bitSTORM-HP-160CfgBridgeArpBcastFilterTable"
		INDEX		{  bitSTORM-HP-160CfgBridgeArpBcastFilterInputBridgePort  }
		::=  { bitSTORM-HP-160CfgBridgeArpBcastFilterTable 1 }

	BITSTORM-HP-160CfgBridgeArpBcastFilterEntry  ::=  SEQUENCE {
		bitSTORM-HP-160CfgBridgeArpBcastFilterInputBridgePort  InterfaceIndex,
		bitSTORM-HP-160CfgBridgeArpBcastFilterStatus  INTEGER,
		bitSTORM-HP-160CfgBridgeArpBcastFilterRowStatus  RowStatus
		}


	bitSTORM-HP-160CfgBridgeArpBcastFilterInputBridgePort	OBJECT-TYPE
		SYNTAX			InterfaceIndex
		MAX-ACCESS		read-only
		STATUS			current
		DESCRIPTION		""
		::=  {  bitSTORM-HP-160CfgBridgeArpBcastFilterEntry  1  }


	bitSTORM-HP-160CfgBridgeArpBcastFilterStatus	OBJECT-TYPE
		SYNTAX			INTEGER  { enable ( 1 ) , disable ( 0 ) }
		MAX-ACCESS		read-create
		STATUS			current
		DESCRIPTION		""
		::=  {  bitSTORM-HP-160CfgBridgeArpBcastFilterEntry  2  }


	bitSTORM-HP-160CfgBridgeArpBcastFilterRowStatus	OBJECT-TYPE
		SYNTAX			RowStatus
		MAX-ACCESS		read-create
		STATUS			current
		DESCRIPTION		""
		::=  {  bitSTORM-HP-160CfgBridgeArpBcastFilterEntry  3  }






  	bitSTORM-HP-160CfgBridgeAllowedIpFilterTable	OBJECT-TYPE
		SYNTAX		SEQUENCE  OF  BITSTORM-HP-160CfgBridgeAllowedIpFilterEntry
		MAX-ACCESS	not-accessible
		STATUS		current
		DESCRIPTION	""
		::=  { bitSTORM-HP-160CfgFilterGroup  9 }

	bitSTORM-HP-160CfgBridgeAllowedIpFilterEntry	OBJECT-TYPE
		SYNTAX		BITSTORM-HP-160CfgBridgeAllowedIpFilterEntry
		MAX-ACCESS	not-accessible
		STATUS		current
		DESCRIPTION	""
		INDEX		{  bitSTORM-HP-160BridgeAllowedIpFilterIndex  }
		::=  { bitSTORM-HP-160CfgBridgeAllowedIpFilterTable 1 }
		

	BITSTORM-HP-160CfgBridgeAllowedIpFilterEntry  ::=  SEQUENCE {
		bitSTORM-HP-160BridgeAllowedIpFilterIndex  Integer32,
		bitSTORM-HP-160BridgeAllowedIpFilterBpIndex  InterfaceIndex,
		bitSTORM-HP-160BridgeAllowedIpFilterIsDynamic  INTEGER,
		bitSTORM-HP-160BridgeAllowedIpFilterSrcIp  IpAddress,
		bitSTORM-HP-160BridgeAllowedIpFilterRowStatus  RowStatus
		}


	bitSTORM-HP-160BridgeAllowedIpFilterIndex	OBJECT-TYPE	
		SYNTAX			Integer32  ( 1 .. 1920  )
		MAX-ACCESS		read-only
		STATUS			current
		DESCRIPTION		""
		::=  {  bitSTORM-HP-160CfgBridgeAllowedIpFilterEntry  1  }


	bitSTORM-HP-160BridgeAllowedIpFilterBpIndex	OBJECT-TYPE	
		SYNTAX			InterfaceIndex
		MAX-ACCESS		read-create
		STATUS			current
		DESCRIPTION		""
		::=  {  bitSTORM-HP-160CfgBridgeAllowedIpFilterEntry  2  }


	bitSTORM-HP-160BridgeAllowedIpFilterIsDynamic	OBJECT-TYPE
		SYNTAX			INTEGER  { manual ( 0 ) , auto-learn ( 1 ) }
		MAX-ACCESS		read-create
		STATUS			current
		DESCRIPTION		""
		::=  {  bitSTORM-HP-160CfgBridgeAllowedIpFilterEntry  3  }


	bitSTORM-HP-160BridgeAllowedIpFilterSrcIp	OBJECT-TYPE	
		SYNTAX			IpAddress
		MAX-ACCESS		read-create
		STATUS			current
		DESCRIPTION		""
		::=  {  bitSTORM-HP-160CfgBridgeAllowedIpFilterEntry  4  }


	bitSTORM-HP-160BridgeAllowedIpFilterRowStatus	OBJECT-TYPE
		SYNTAX			RowStatus
		MAX-ACCESS		read-create
		STATUS			current
		DESCRIPTION		""
		DEFVAL			{ createAndGo }
		::=  {  bitSTORM-HP-160CfgBridgeAllowedIpFilterEntry  5  }



--
	bitSTORM-HP-160CfgBridgeDstMacFilterTable	OBJECT-TYPE
		SYNTAX		SEQUENCE  OF  BITSTORM-HP-160CfgBridgeDstMacFilterEntry
		MAX-ACCESS	not-accessible
		STATUS		current
		DESCRIPTION	""
		::=  { bitSTORM-HP-160CfgFilterGroup  10 }

	bitSTORM-HP-160CfgBridgeDstMacFilterEntry	OBJECT-TYPE
		SYNTAX		BITSTORM-HP-160CfgBridgeDstMacFilterEntry
		MAX-ACCESS	not-accessible
		STATUS		current
		DESCRIPTION	""
		INDEX		{  bitSTORM-HP-160BridgeDstMacFilterIndex  }
		::=  { bitSTORM-HP-160CfgBridgeDstMacFilterTable 1 }

	BITSTORM-HP-160CfgBridgeDstMacFilterEntry  ::=  SEQUENCE {
		bitSTORM-HP-160BridgeDstMacFilterIndex  Integer32,
		bitSTORM-HP-160BridgeDstMacFilterBpIndex  InterfaceIndex,
		bitSTORM-HP-160BridgeDstMacFilterDstMac  PhysAddress,
		bitSTORM-HP-160BridgeDstMacFilterRowStatus  RowStatus
		}


	bitSTORM-HP-160BridgeDstMacFilterIndex	OBJECT-TYPE	
		SYNTAX			Integer32  ( 1 .. 4095  ) 
		MAX-ACCESS		read-only
		STATUS			current
		DESCRIPTION		""
		::=  {  bitSTORM-HP-160CfgBridgeDstMacFilterEntry  1  }


	bitSTORM-HP-160BridgeDstMacFilterBpIndex	OBJECT-TYPE	
		SYNTAX			InterfaceIndex
		MAX-ACCESS		read-create
		STATUS			current
		DESCRIPTION		""
		::=  {  bitSTORM-HP-160CfgBridgeDstMacFilterEntry  2  }


	bitSTORM-HP-160BridgeDstMacFilterDstMac	OBJECT-TYPE
		SYNTAX			PhysAddress
		MAX-ACCESS		read-create
		STATUS			current
		DESCRIPTION		""
		::=  {  bitSTORM-HP-160CfgBridgeDstMacFilterEntry  3  }


	bitSTORM-HP-160BridgeDstMacFilterRowStatus	OBJECT-TYPE	
		SYNTAX			RowStatus
		MAX-ACCESS		read-create
		STATUS			current
		DESCRIPTION		""
		DEFVAL			{ createAndGo }
		::=  {  bitSTORM-HP-160CfgBridgeDstMacFilterEntry  4  }
--






	bitSTORM-HP-160CfgLACPMode	OBJECT-TYPE
		SYNTAX			INTEGER  { on ( 1 ) , off ( 0 ) }
		MAX-ACCESS		read-write
		STATUS			current
		DESCRIPTION		"System ID of LACP port."
		::=  {  bitSTORM-HP-160CfgLacpGroup  1  }

	bitSTORM-HP-160CfgIgmpMode	OBJECT-TYPE
		SYNTAX			INTEGER  { snoopingMode ( 1 ) , proxyMode ( 2 ) }
		MAX-ACCESS		read-write
		STATUS			current
		DESCRIPTION		""
		::=  {  bitSTORM-HP-160CfgIgmpGroup  1  }

	bitSTORM-HP-160CfgIgmpTimeoutQuery	OBJECT-TYPE
		SYNTAX			Integer32  ( 1 .. 500  )
		MAX-ACCESS		read-write
		STATUS			current
		DESCRIPTION		""
		::=  {  bitSTORM-HP-160CfgIgmpGroup  2  }

	bitSTORM-HP-160CfgIgmpTimeoutUri	OBJECT-TYPE
		SYNTAX			Integer32  ( 1 .. 500  )
		MAX-ACCESS		read-write
		STATUS			current
		DESCRIPTION		""
		::=  {  bitSTORM-HP-160CfgIgmpGroup  3  }

	bitSTORM-HP-160CfgIgmpTimeoutBc	OBJECT-TYPE	
		SYNTAX			Integer32  ( 1 .. 500  ) 
		MAX-ACCESS		read-write
		STATUS			current
		DESCRIPTION		""
		::=  {  bitSTORM-HP-160CfgIgmpGroup  4  }

	bitSTORM-HP-160CfgIgmpTimeoutMrt	OBJECT-TYPE	
		SYNTAX			Integer32  ( 1 .. 500  ) 
		MAX-ACCESS		read-write
		STATUS			current
		DESCRIPTION		""
		::=  {  bitSTORM-HP-160CfgIgmpGroup  5  }

	bitSTORM-HP-160CfgIgmpTimeoutLmqt	OBJECT-TYPE	
		SYNTAX			Integer32  ( 1 .. 500  ) 
		MAX-ACCESS		read-write
		STATUS			current
		DESCRIPTION		""
		::=  {  bitSTORM-HP-160CfgIgmpGroup  6  }

	bitSTORM-HP-160CfgIgmpTimeoutGmt	OBJECT-TYPE	
		SYNTAX			Integer32  ( 1 .. 500  ) 
		MAX-ACCESS		read-write
		STATUS			current
		DESCRIPTION		""
		::=  {  bitSTORM-HP-160CfgIgmpGroup  7  }

	bitSTORM-HP-160CfgIgmpVersion	OBJECT-TYPE	
		SYNTAX			INTEGER  { igmpv1 ( 1 ) , igmpv2 ( 2 ) , igmpv3 ( 3 ) } 
		MAX-ACCESS		read-write
		STATUS			current
		DESCRIPTION		""
		::=  {  bitSTORM-HP-160CfgIgmpGroup  8  }

	bitSTORM-HP-160CfgIgmpAclMode	OBJECT-TYPE
		SYNTAX			TruthValue  { true ( 1 ) , false ( 2 ) } 
		MAX-ACCESS		read-write
		STATUS			current
		DESCRIPTION		""
		::=  {  bitSTORM-HP-160CfgIgmpGroup  9  }

	bitSTORM-HP-160CfgIgmpLeaveMode	OBJECT-TYPE
		SYNTAX			INTEGER  { normal ( 0 ) , fast ( 1 ) }
		MAX-ACCESS		read-write
		STATUS			current
		DESCRIPTION		""
		::=  {  bitSTORM-HP-160CfgIgmpGroup  10  }

	bitSTORM-HP-160CfgIgmpGroupTable	OBJECT-TYPE
		SYNTAX		SEQUENCE  OF  BITSTORM-HP-160IgmpGroupEntry
		MAX-ACCESS	not-accessible
		STATUS		current
		DESCRIPTION	""
		::=  { bitSTORM-HP-160CfgIgmpGroup  13 }

	bitSTORM-HP-160CfgIgmpGroupEntry	OBJECT-TYPE
		SYNTAX		BITSTORM-HP-160IgmpGroupEntry
		MAX-ACCESS	not-accessible
		STATUS		current
		DESCRIPTION	""
		INDEX		{  bitSTORM-HP-160CfgIgmpGroupIp, bitSTORM-HP-160CfgIgmpGroupVlan  }
		::=  { bitSTORM-HP-160CfgIgmpGroupTable 1 }

	BITSTORM-HP-160IgmpGroupEntry  ::=  SEQUENCE {
		bitSTORM-HP-160CfgIgmpGroupIp  IpAddress,
		bitSTORM-HP-160CfgIgmpGroupVlan  Integer32,
		bitSTORM-HP-160CfgIgmpGroupAddActions  Integer32,
		bitSTORM-HP-160CfgIgmpGroupNumOfEntries  Integer32,
		bitSTORM-HP-160CfgIgmpGroupInclude  Integer32,
		bitSTORM-HP-160CfgIgmpGroupBitmap  OCTET STRING
		}


	bitSTORM-HP-160CfgIgmpGroupIp	OBJECT-TYPE	
		SYNTAX			IpAddress
		MAX-ACCESS		read-only
		STATUS			current
		DESCRIPTION		""
		::=  {  bitSTORM-HP-160CfgIgmpGroupEntry  1  }


	bitSTORM-HP-160CfgIgmpGroupVlan	OBJECT-TYPE
		SYNTAX			Integer32  ( 1 .. 4094  )   --960803
		MAX-ACCESS		read-only
		STATUS			current
		DESCRIPTION		""
		::=  {  bitSTORM-HP-160CfgIgmpGroupEntry  2  }


	bitSTORM-HP-160CfgIgmpGroupAddActions	OBJECT-TYPE	
		SYNTAX			Integer32
		MAX-ACCESS		read-only
		STATUS			current
		DESCRIPTION		""
		::=  {  bitSTORM-HP-160CfgIgmpGroupEntry  3  }


	bitSTORM-HP-160CfgIgmpGroupNumOfEntries	OBJECT-TYPE	
		SYNTAX			Integer32
		MAX-ACCESS		read-only
		STATUS			current
		DESCRIPTION		""
		::=  {  bitSTORM-HP-160CfgIgmpGroupEntry  4  }


	bitSTORM-HP-160CfgIgmpGroupInclude	OBJECT-TYPE	
		SYNTAX			Integer32
		MAX-ACCESS		read-only
		STATUS			current
		DESCRIPTION		""
		::=  {  bitSTORM-HP-160CfgIgmpGroupEntry  5  }


	bitSTORM-HP-160CfgIgmpGroupBitmap	OBJECT-TYPE	
		SYNTAX			OCTET STRING  ( SIZE ( 0 .. 513  ) )
		MAX-ACCESS		read-only
		STATUS			current
		DESCRIPTION		""
		::=  {  bitSTORM-HP-160CfgIgmpGroupEntry  6  }

	bitSTORM-HP-160CfgIgmpSource	OBJECT IDENTIFIER
		::=  {  bitSTORM-HP-160CfgIgmpGroup  14  }

	bitSTORM-HP-160CfgIgmpRouterPortTable	OBJECT-TYPE
		SYNTAX		SEQUENCE  OF  BITSTORM-HP-160CfgIgmpRouterPortEntry
		MAX-ACCESS	not-accessible
		STATUS		current
		DESCRIPTION	""
		::=  { bitSTORM-HP-160CfgIgmpGroup  15 }

	bitSTORM-HP-160CfgIgmpRouterPortEntry	OBJECT-TYPE
		SYNTAX		BITSTORM-HP-160CfgIgmpRouterPortEntry
		MAX-ACCESS	not-accessible
		STATUS		current
		DESCRIPTION	""
		INDEX		{  bitSTORM-HP-160CfgIgmpRouterPortVlanId, bitSTORM-HP-160CfgIgmpRouterPortBportIndex  }
		::=  { bitSTORM-HP-160CfgIgmpRouterPortTable 1 }

	BITSTORM-HP-160CfgIgmpRouterPortEntry  ::=  SEQUENCE {
		bitSTORM-HP-160CfgIgmpRouterPortVlanId  Integer32,
		bitSTORM-HP-160CfgIgmpRouterPortBportIndex  InterfaceIndex,
		bitSTORM-HP-160CfgIgmpRouterPortBitmap  InterfaceIndex,
		bitSTORM-HP-160CfgIgmpRouterPortRouterIp  OCTET STRING,
		bitSTORM-HP-160CfgIgmpRouterPortRouterReportIp  OCTET STRING,
		bitSTORM-HP-160CfgIgmpRouterPortRowStatus  RowStatus
		}

	bitSTORM-HP-160CfgIgmpRouterPortVlanId	OBJECT-TYPE
		SYNTAX			Integer32  ( 1 .. 4094  )   --960803
		MAX-ACCESS		read-only
		STATUS			current
		DESCRIPTION		""
		::=  {  bitSTORM-HP-160CfgIgmpRouterPortEntry  1  }


	bitSTORM-HP-160CfgIgmpRouterPortBportIndex	OBJECT-TYPE	
		SYNTAX			InterfaceIndex
		MAX-ACCESS		read-only
		STATUS			current
		DESCRIPTION		""
		::=  {  bitSTORM-HP-160CfgIgmpRouterPortEntry  2  }


	bitSTORM-HP-160CfgIgmpRouterPortBitmap	OBJECT-TYPE	
		SYNTAX			InterfaceIndex
		MAX-ACCESS		read-create
		STATUS			current
		DESCRIPTION		""
		::=  {  bitSTORM-HP-160CfgIgmpRouterPortEntry  3  }


	bitSTORM-HP-160CfgIgmpRouterPortRouterIp	OBJECT-TYPE
		SYNTAX			OCTET STRING  ( SIZE ( 0 .. 15  ) )
		MAX-ACCESS		read-create
		STATUS			current
		DESCRIPTION		""
		::=  {  bitSTORM-HP-160CfgIgmpRouterPortEntry  4  }

	bitSTORM-HP-160CfgIgmpRouterPortRouterReportIp	OBJECT-TYPE
		SYNTAX			OCTET STRING  ( SIZE ( 0 .. 15  ) )
		MAX-ACCESS		read-create
		STATUS			current
		DESCRIPTION		""
		::=  {  bitSTORM-HP-160CfgIgmpRouterPortEntry  5  }

	bitSTORM-HP-160CfgIgmpRouterPortRowStatus	OBJECT-TYPE
		SYNTAX			RowStatus
		MAX-ACCESS		read-create
		STATUS			current
		DESCRIPTION		""
		DEFVAL			{ createAndGo }
		::=  {  bitSTORM-HP-160CfgIgmpRouterPortEntry  6  }

	bitSTORM-HP-160CfgIgmpAclProfileTable	OBJECT-TYPE
		SYNTAX		SEQUENCE  OF  BITSTORM-HP-160CfgIgmpAclProfileEntry
		MAX-ACCESS	not-accessible
		STATUS		current
		DESCRIPTION	""
		::=  { bitSTORM-HP-160CfgIgmpGroup  16 }

	bitSTORM-HP-160CfgIgmpAclProfileEntry	OBJECT-TYPE
		SYNTAX		BITSTORM-HP-160CfgIgmpAclProfileEntry
		MAX-ACCESS	not-accessible
		STATUS		current
		DESCRIPTION	""
		INDEX		{  bitSTORM-HP-160CfgIgmpAclProfileIndex  }
		::=  { bitSTORM-HP-160CfgIgmpAclProfileTable 1 }

	BITSTORM-HP-160CfgIgmpAclProfileEntry  ::=  SEQUENCE {
		bitSTORM-HP-160CfgIgmpAclProfileIndex  Integer32,
		bitSTORM-HP-160CfgIgmpAclProfileChMap  OCTET STRING,
		bitSTORM-HP-160CfgIgmpAclProfileVlanMap  OCTET STRING,
		bitSTORM-HP-160CfgIgmpAclProfileVlanEgressMap  OCTET STRING,   --20070329
--		bitSTORM-HP-160CfgIgmpAclProfileBank  Integer32,
		bitSTORM-HP-160CfgIgmpAclProfileMcCount  Integer32,
		bitSTORM-HP-160CfgIgmpAclProfileRowStatus  RowStatus,
		bitSTORM-HP-160CfgIgmpAclProfileUsedCount  INTEGER,
		bitSTORM-HP-160CfgIgmpAclProfileMsgCount  Integer32
		}

	bitSTORM-HP-160CfgIgmpAclProfileIndex	OBJECT-TYPE	
		SYNTAX			Integer32  (1..24)
		MAX-ACCESS		not-accessible
		STATUS			current
		DESCRIPTION		""
		::=  {  bitSTORM-HP-160CfgIgmpAclProfileEntry  1  }


	bitSTORM-HP-160CfgIgmpAclProfileChMap	OBJECT-TYPE	
		SYNTAX			OCTET STRING
		MAX-ACCESS		read-create
		STATUS			current
		DESCRIPTION		"IP address
		total 1024 bytes.
		byte 1~256 for bank1 (64 ip address)
		byte 257~512 for bank2 (64 ip address)
		byte 513~768 for bank3 (64 ip address)
		byte 769~1024 for bank4 (64 ip address)
		"
		::=  {  bitSTORM-HP-160CfgIgmpAclProfileEntry  2  }


	bitSTORM-HP-160CfgIgmpAclProfileVlanMap	OBJECT-TYPE
		SYNTAX			OCTET STRING
		MAX-ACCESS		read-create
		STATUS			current
		DESCRIPTION		"User (packet) VLAN id
		total 512 bytes.
		byte 1~128 for bank1 (64 vlan id)
		byte 129~256 for bank2 (64 vlan id)
		byte 257~384 for bank3 (64 vlan id)
		byte 385~512 for bank4 (64 vlan id)
		"
		::=  {  bitSTORM-HP-160CfgIgmpAclProfileEntry  3  }


	bitSTORM-HP-160CfgIgmpAclProfileVlanEgressMap	OBJECT-TYPE
		SYNTAX			OCTET STRING
		MAX-ACCESS		read-create
		STATUS			current
		DESCRIPTION		"VlanEgressMap
		total 256 bytes.
		1: tag, 2 : untag
		"
		::=  {  bitSTORM-HP-160CfgIgmpAclProfileEntry  4  }

--	bitSTORM-HP-160CfgIgmpAclProfileBank	OBJECT-TYPE
--		SYNTAX			Integer32  ( 0 .. 3  )
--		MAX-ACCESS		read-create
--		STATUS			current
--		DESCRIPTION		"0..3, 0 for ChMap 1~64, 1 for ChMap 65~128 ..."
--		::=  {  bitSTORM-HP-160CfgIgmpAclProfileEntry  4  }

	bitSTORM-HP-160CfgIgmpAclProfileMcCount	OBJECT-TYPE
		SYNTAX			Integer32  ( 0 .. 10  )
		MAX-ACCESS		read-create
		STATUS			current
		DESCRIPTION		"Max Channel Count"
		::=  {  bitSTORM-HP-160CfgIgmpAclProfileEntry  5  }

	bitSTORM-HP-160CfgIgmpAclProfileRowStatus	OBJECT-TYPE
		SYNTAX			RowStatus  { active ( 1 ) , notInService ( 2 ) , notReady ( 3 ) , createAndGo ( 4 ) , createAndWait ( 5 ) , destroy ( 6 ) }
		MAX-ACCESS		read-create
		STATUS			current
		DESCRIPTION		""
		::=  {  bitSTORM-HP-160CfgIgmpAclProfileEntry  6  }

	bitSTORM-HP-160CfgIgmpAclProfileUsedCount	OBJECT-TYPE
		SYNTAX			INTEGER
		MAX-ACCESS		read-only
		STATUS			current
		DESCRIPTION		"The value is not zero means the profile is in used,then the profile can't be delete."
		::=  {  bitSTORM-HP-160CfgIgmpAclProfileEntry  7  }

	bitSTORM-HP-160CfgIgmpAclProfileMsgCount	OBJECT-TYPE
		SYNTAX			Integer32  ( 0 .. 65535  )
		MAX-ACCESS		read-create
		STATUS			current
		DESCRIPTION		"Max IGMP Message Count. Default value is 128."
		::=  {  bitSTORM-HP-160CfgIgmpAclProfileEntry  8  }
		
	bitSTORM-HP-160CfgIgmpBridgePortBindTable	OBJECT-TYPE
		SYNTAX		SEQUENCE  OF  BITSTORM-HP-160CfgIgmpBridgePortBindEntry
		MAX-ACCESS	not-accessible
		STATUS		current
		DESCRIPTION	""
		::=  { bitSTORM-HP-160CfgIgmpGroup  17 }

	bitSTORM-HP-160CfgIgmpBridgePortBindEntry	OBJECT-TYPE
		SYNTAX		BITSTORM-HP-160CfgIgmpBridgePortBindEntry
		MAX-ACCESS	not-accessible
		STATUS		current
		DESCRIPTION	""
		INDEX		{  bitSTORM-HP-160CfgIgmpBindBpId  }
		::=  { bitSTORM-HP-160CfgIgmpBridgePortBindTable 1 }

	BITSTORM-HP-160CfgIgmpBridgePortBindEntry  ::=  SEQUENCE {
		bitSTORM-HP-160CfgIgmpBindBpId  Integer32,
		bitSTORM-HP-160CfgIgmpBindProfileId  Integer32
--		bitSTORM-HP-160CfgIgmpAclProfileBank-  Integer32
		}


	bitSTORM-HP-160CfgIgmpBindBpId	OBJECT-TYPE	
		SYNTAX			Integer32
		MAX-ACCESS		not-accessible
		STATUS			current
		DESCRIPTION		""
		::=  {  bitSTORM-HP-160CfgIgmpBridgePortBindEntry  1  }


	bitSTORM-HP-160CfgIgmpBindProfileId	OBJECT-TYPE
		SYNTAX			Integer32
		MAX-ACCESS		read-write
		STATUS			current
		DESCRIPTION		""
		::=  {  bitSTORM-HP-160CfgIgmpBridgePortBindEntry  2  }


--	bitSTORM-HP-160CfgIgmpAclProfileBank-	OBJECT-TYPE
--		SYNTAX			Integer32 (0..3)
--		MAX-ACCESS		read-write
--		STATUS			current
--		DESCRIPTION		""
--		::=  {  bitSTORM-HP-160CfgIgmpBridgePortBindEntry  3  }

	bitSTORM-HP-160CfgRstpForceVersion	OBJECT-TYPE	
		SYNTAX			INTEGER  { stp ( 0 ) , rstp ( 2 ) } 
		MAX-ACCESS		read-write
		STATUS			current
		DESCRIPTION		""
		DEFVAL			{ rstp }
		::=  {  bitSTORM-HP-160CfgRstpGroup  1  }

	bitSTORM-HP-160StpEnable	OBJECT-TYPE
		SYNTAX			INTEGER  { disabled ( 0 ) , enabled ( 1 ) }
		MAX-ACCESS		read-write
		STATUS			current
		DESCRIPTION		""
		DEFVAL			{ disabled }
		::=  {  bitSTORM-HP-160CfgRstpGroup  2  }

	bitSTORM-HP-160CfgRstpPortTable	OBJECT-TYPE
		SYNTAX		SEQUENCE  OF  BITSTORM-HP-160CfgRstpPortEntry
		MAX-ACCESS	not-accessible
		STATUS		current
		DESCRIPTION	""
		::=  { bitSTORM-HP-160CfgRstpGroup  3 }

	bitSTORM-HP-160CfgRstpPortEntry	OBJECT-TYPE
		SYNTAX		BITSTORM-HP-160CfgRstpPortEntry
		MAX-ACCESS	not-accessible
		STATUS		current
		DESCRIPTION	""
		INDEX		{  bitSTORM-HP-160CfgRstpPortIndex  }
		::=  { bitSTORM-HP-160CfgRstpPortTable 1 }

	BITSTORM-HP-160CfgRstpPortEntry  ::=  SEQUENCE {
		bitSTORM-HP-160CfgRstpPortIndex  Integer32,
		bitSTORM-HP-160CfgRstpPortAdminEdge  INTEGER,
		bitSTORM-HP-160CfgRstpPortAdminPoint2Point  INTEGER,
		bitSTORM-HP-160CfgRstpPortAdminNonSTP  INTEGER
		}


	bitSTORM-HP-160CfgRstpPortIndex	OBJECT-TYPE
		SYNTAX			Integer32
		MAX-ACCESS		read-only
		STATUS			current
		DESCRIPTION		""
		::=  {  bitSTORM-HP-160CfgRstpPortEntry  1  }


	bitSTORM-HP-160CfgRstpPortAdminEdge	OBJECT-TYPE
		SYNTAX			INTEGER  { false ( 0 ) , true ( 1 ) }
		MAX-ACCESS		read-write
		STATUS			current
		DESCRIPTION		""
		DEFVAL			{ false }
		::=  {  bitSTORM-HP-160CfgRstpPortEntry  2  }


	bitSTORM-HP-160CfgRstpPortAdminPoint2Point	OBJECT-TYPE
		SYNTAX			INTEGER  { true ( 0 ) , false ( 1 ) , auto ( 2 ) }
		MAX-ACCESS		read-write
		STATUS			current
		DESCRIPTION		""
		DEFVAL			{ false }
		::=  {  bitSTORM-HP-160CfgRstpPortEntry  3  }


	bitSTORM-HP-160CfgRstpPortAdminNonSTP	OBJECT-TYPE
		SYNTAX			INTEGER  { false ( 0 ) , true ( 1 ) }
		MAX-ACCESS		read-write
		STATUS			current
		DESCRIPTION		""
		DEFVAL			{ false }
		::=  {  bitSTORM-HP-160CfgRstpPortEntry  4  }

--
	bitSTORM-HP-160StpBridgeID	OBJECT-TYPE
		SYNTAX			OCTET STRING (SIZE (8))
		MAX-ACCESS		read-only
		STATUS			current
		DESCRIPTION		""
		::=  {  bitSTORM-HP-160CfgRstpGroup  4  }
--
	bitSTORM-HP-160CfgDhcpMode	OBJECT-TYPE
		SYNTAX			INTEGER  { transparent ( 0 ) , relay ( 1 ) , server ( 3 )}
		MAX-ACCESS		read-write
		STATUS			current
		DESCRIPTION		""
		::=  {  bitSTORM-HP-160CfgRelayGroup  1  }

	bitSTORM-HP-160CfgDhcpSubOptMode	OBJECT-TYPE
		SYNTAX			INTEGER  { circuitID ( 1 ) , remoteID ( 2 ) , both ( 3 ) }
		MAX-ACCESS		read-write
		STATUS			current
		DESCRIPTION		""
		::=  {  bitSTORM-HP-160CfgRelayGroup  2  }

	bitSTORM-HP-160CfgDhcpCircuitIdType	OBJECT-TYPE
		SYNTAX			INTEGER  { default(0),
		                                   scbv(1),
		                                   scv(2),
		                                   sc(3),
		                                   customer(4) }		
		MAX-ACCESS		read-write
		STATUS			current
		DESCRIPTION		"
		default               Set circuit default type
		scbv                  Set circuit scbv type
		scv                   Set circuit scv type
		sc                    Set circuit sc type
		customer              Set circuit customer type"
		::=  {  bitSTORM-HP-160CfgRelayGroup  3  }

--	bitSTORM-HP-160CfgDhcpRemoteIdType	OBJECT-TYPE	
--		SYNTAX			INTEGER  { default ( 0 ) , id ( 1 ) , descr ( 2 ) , phonenum ( 3 ) , customer ( 4 ) }
--		MAX-ACCESS		read-write
--		STATUS			current
--		DESCRIPTION		"
--		default            Set circuit default type
--		id                Set remote line id
--		descr                  Set remote line description
--		phonenum                    Set remote line phone number
--		customer       Set remote customer type"
--		::=  {  bitSTORM-HP-160CfgRelayGroup  4  }

	bitSTORM-HP-160CfgDhcpName	OBJECT-TYPE
		SYNTAX			OCTET STRING
		MAX-ACCESS		read-write
		STATUS			current
		DESCRIPTION		""
		::=  {  bitSTORM-HP-160CfgRelayGroup  4  }

--	bitSTORM-HP-160CfgPppoeVsaMode	OBJECT-TYPE
--		SYNTAX			INTEGER  { disable ( 0 ) , enable ( 1 )  }
--		MAX-ACCESS		read-write
--		STATUS			current
--		DESCRIPTION		""
--		::=  {  bitSTORM-HP-160CfgRelayGroup  5  }

	bitSTORM-HP-160CfgPppoeAcName	OBJECT-TYPE
		SYNTAX			OCTET STRING
		MAX-ACCESS		read-write
		STATUS			current
		DESCRIPTION		""
		::=  {  bitSTORM-HP-160CfgRelayGroup  5  }

	bitSTORM-HP-160CfgPppoeSrvName	OBJECT-TYPE	
		SYNTAX			OCTET STRING
		MAX-ACCESS		read-write
		STATUS			current
		DESCRIPTION		""
		::=  {  bitSTORM-HP-160CfgRelayGroup  6  }

	bitSTORM-HP-160CfgDhcpDslIdConfigTable	OBJECT-TYPE
		SYNTAX		SEQUENCE  OF  BITSTORM-HP-160CfgDhcpDslIdConfigEntry
		MAX-ACCESS	not-accessible
		STATUS		current
		DESCRIPTION	""
		::=  { bitSTORM-HP-160CfgRelayGroup  8 }

	bitSTORM-HP-160CfgDhcpDslIdConfigEntry	OBJECT-TYPE
		SYNTAX		BITSTORM-HP-160CfgDhcpDslIdConfigEntry
		MAX-ACCESS	not-accessible
		STATUS		current
		DESCRIPTION	""
		INDEX		{  bitSTORM-HP-160CfgDhcpDslIfIndex  }
		::=  { bitSTORM-HP-160CfgDhcpDslIdConfigTable 1 }

	BITSTORM-HP-160CfgDhcpDslIdConfigEntry  ::=  SEQUENCE {
		bitSTORM-HP-160CfgDhcpDslIfIndex  InterfaceIndex,
		bitSTORM-HP-160CfgDslCircuitID  OCTET STRING,
		bitSTORM-HP-160CfgDslRemoteID  OCTET STRING,
		bitSTORM-HP-160CfgDslIdTrusted  TruthValue,
		--bitSTORM-HP-160CfgDslIdForwardMode  INTEGER,
		bitSTORM-HP-160CfgDslpppoeMode  INTEGER
		}


	bitSTORM-HP-160CfgDhcpDslIfIndex	OBJECT-TYPE	
		SYNTAX			InterfaceIndex
		MAX-ACCESS		not-accessible
		STATUS			current
		DESCRIPTION		"IfIndex."
		::=  {  bitSTORM-HP-160CfgDhcpDslIdConfigEntry  1  }


	bitSTORM-HP-160CfgDslCircuitID	OBJECT-TYPE
		SYNTAX			OCTET STRING  ( SIZE ( 0 .. 63  ) ) 
		MAX-ACCESS		read-write
		STATUS			current
		DESCRIPTION		""
		::=  {  bitSTORM-HP-160CfgDhcpDslIdConfigEntry  2  }


	bitSTORM-HP-160CfgDslRemoteID	OBJECT-TYPE	
		SYNTAX			OCTET STRING  ( SIZE ( 0 .. 63  ) ) 
		MAX-ACCESS		read-write
		STATUS			current
		DESCRIPTION		""
		::=  {  bitSTORM-HP-160CfgDhcpDslIdConfigEntry  3  }


	bitSTORM-HP-160CfgDslIdTrusted	OBJECT-TYPE
		SYNTAX			TruthValue  { true ( 1 ) , false ( 2 ) } 
		MAX-ACCESS		read-write
		STATUS			current
		DESCRIPTION		""
		::=  {  bitSTORM-HP-160CfgDhcpDslIdConfigEntry  4  }


--	bitSTORM-HP-160CfgDslIdForwardMode	OBJECT-TYPE
--		SYNTAX			INTEGER  { default ( 0 ) , append ( 1 ) , replace ( 2 ) , forward ( 3 ) , discard ( 4 ) , chaddr ( 5 ) }
--		MAX-ACCESS		read-write
--		STATUS			current
--		DESCRIPTION		""
--		::=  {  bitSTORM-HP-160CfgDhcpDslIdConfigEntry  5  }
		
	bitSTORM-HP-160CfgDslpppoeMode	OBJECT-TYPE
		SYNTAX			INTEGER  { transparent ( 0 ) , relay ( 1 ) }
		MAX-ACCESS		read-write
		STATUS			current
		DESCRIPTION		""
		::=  {  bitSTORM-HP-160CfgDhcpDslIdConfigEntry  5  }
		


--
	bitSTORM-HP-160CfgDhcpServerProfileTable	OBJECT-TYPE
		SYNTAX		SEQUENCE  OF  BITSTORM-HP-160CfgDhcpServerProfileEntry
		MAX-ACCESS	not-accessible
		STATUS		current
		DESCRIPTION	""
		::=  { bitSTORM-HP-160CfgRelayGroup  9 }

	bitSTORM-HP-160CfgDhcpServerProfileEntry	OBJECT-TYPE
		SYNTAX		BITSTORM-HP-160CfgDhcpServerProfileEntry
		MAX-ACCESS	not-accessible
		STATUS		current
		DESCRIPTION	""
		INDEX		{  bitSTORM-HP-160CfgDhcpServerPrfIndex  }
		::=  { bitSTORM-HP-160CfgDhcpServerProfileTable 1 }
		

	BITSTORM-HP-160CfgDhcpServerProfileEntry  ::=  SEQUENCE {
		bitSTORM-HP-160CfgDhcpServerPrfIndex  Integer32,
		bitSTORM-HP-160CfgDhcpServerPrfStartIp  OCTET STRING,
		bitSTORM-HP-160CfgDhcpServerPrfEndIp  OCTET STRING,

		bitSTORM-HP-160CfgDhcpServerPrfIpMsk  OCTET STRING,
		bitSTORM-HP-160CfgDhcpServerPrfDefGatewayIp  OCTET STRING,
		bitSTORM-HP-160CfgDhcpServerPrfDNS1Ip  OCTET STRING,
		bitSTORM-HP-160CfgDhcpServerPrfDNS2Ip  OCTET STRING,
		bitSTORM-HP-160CfgDhcpServerPrfLeaseTime  Integer32,
		bitSTORM-HP-160CfgDhcpServerPrfUsedCount  INTEGER,
		bitSTORM-HP-160CfgDhcpServerPrfRowStatus  RowStatus
		}



	bitSTORM-HP-160CfgDhcpServerPrfIndex	OBJECT-TYPE
		SYNTAX			Integer32(1..24)
		MAX-ACCESS		not-accessible
		STATUS			current
		DESCRIPTION		""
		::=  {  bitSTORM-HP-160CfgDhcpServerProfileEntry  1  }


	bitSTORM-HP-160CfgDhcpServerPrfStartIp	OBJECT-TYPE
		SYNTAX			OCTET STRING  ( SIZE ( 0 .. 15  ) )
		MAX-ACCESS		read-create
		STATUS			current
		DESCRIPTION		""
		::=  {  bitSTORM-HP-160CfgDhcpServerProfileEntry  2  }

	bitSTORM-HP-160CfgDhcpServerPrfEndIp	OBJECT-TYPE
		SYNTAX			OCTET STRING  ( SIZE ( 0 .. 15  ) )
		MAX-ACCESS		read-create
		STATUS			current
		DESCRIPTION		""
		::=  {  bitSTORM-HP-160CfgDhcpServerProfileEntry  3  }
		
	bitSTORM-HP-160CfgDhcpServerPrfIpMsk	OBJECT-TYPE
		SYNTAX			OCTET STRING  ( SIZE ( 0 .. 15  ) )
		MAX-ACCESS		read-create
		STATUS			current
		DESCRIPTION		""
		::=  {  bitSTORM-HP-160CfgDhcpServerProfileEntry  4  }
	bitSTORM-HP-160CfgDhcpServerPrfDefGatewayIp	OBJECT-TYPE
		SYNTAX			OCTET STRING  ( SIZE ( 0 .. 15  ) )
		MAX-ACCESS		read-create
		STATUS			current
		DESCRIPTION		""
		::=  {  bitSTORM-HP-160CfgDhcpServerProfileEntry  5  }
		
	bitSTORM-HP-160CfgDhcpServerPrfDNS1Ip	OBJECT-TYPE
		SYNTAX			OCTET STRING  ( SIZE ( 0 .. 15  ) )
		MAX-ACCESS		read-create
		STATUS			current
		DESCRIPTION		""
		::=  {  bitSTORM-HP-160CfgDhcpServerProfileEntry  6  }
		
	bitSTORM-HP-160CfgDhcpServerPrfDNS2Ip	OBJECT-TYPE
		SYNTAX			OCTET STRING  ( SIZE ( 0 .. 15  ) )
		MAX-ACCESS		read-create
		STATUS			current
		DESCRIPTION		""
		::=  {  bitSTORM-HP-160CfgDhcpServerProfileEntry  7  }

	bitSTORM-HP-160CfgDhcpServerPrfLeaseTime	OBJECT-TYPE
		SYNTAX			Integer32 (300..86400)
		MAX-ACCESS		read-create
		STATUS			current
		DESCRIPTION		"seconds"
		::=  {  bitSTORM-HP-160CfgDhcpServerProfileEntry  8  }
	bitSTORM-HP-160CfgDhcpServerPrfUsedCount	OBJECT-TYPE
		SYNTAX			INTEGER
		MAX-ACCESS		read-only
		STATUS			current
		DESCRIPTION		""
		::=  {  bitSTORM-HP-160CfgDhcpServerProfileEntry  9  }
	bitSTORM-HP-160CfgDhcpServerPrfRowStatus	OBJECT-TYPE
		SYNTAX			RowStatus
		MAX-ACCESS		read-create
		STATUS			current
		DESCRIPTION		""
		::=  {  bitSTORM-HP-160CfgDhcpServerProfileEntry  10  }



--
--
	bitSTORM-HP-160CfgDhcpServerProfileBindTable	OBJECT-TYPE
		SYNTAX		SEQUENCE  OF  BITSTORM-HP-160CfgDhcpServerProfileBindEntry
		MAX-ACCESS	not-accessible
		STATUS		current
		DESCRIPTION	""
		::=  { bitSTORM-HP-160CfgRelayGroup  10 }

	bitSTORM-HP-160CfgDhcpServerProfileBindEntry	OBJECT-TYPE
		SYNTAX		BITSTORM-HP-160CfgDhcpServerProfileBindEntry
		MAX-ACCESS	not-accessible
		STATUS		current
		DESCRIPTION	""
		INDEX		{  bitSTORM-HP-160ServerBindBpIndex  }
		::=  { bitSTORM-HP-160CfgDhcpServerProfileBindTable 1 }

	BITSTORM-HP-160CfgDhcpServerProfileBindEntry  ::=  SEQUENCE {
		bitSTORM-HP-160ServerBindBpIndex  Integer32,
		bitSTORM-HP-160ServerBindPrfIndex  Integer32
		}

	bitSTORM-HP-160ServerBindBpIndex	OBJECT-TYPE	
		SYNTAX			Integer32 (4..219)
		MAX-ACCESS		not-accessible
		STATUS			current
		DESCRIPTION		""
		::=  {  bitSTORM-HP-160CfgDhcpServerProfileBindEntry  1  }

	bitSTORM-HP-160ServerBindPrfIndex	OBJECT-TYPE
		SYNTAX			Integer32  (1..24)
		MAX-ACCESS		read-write
		STATUS			current
		DESCRIPTION		""
		::=  {  bitSTORM-HP-160CfgDhcpServerProfileBindEntry  2  }
--
		
--
	bitSTORM-HP-160CfgDhcpQueryClientTable	OBJECT-TYPE
		SYNTAX		SEQUENCE  OF  BITSTORM-HP-160CfgDhcpQueryClientEntry
		MAX-ACCESS	not-accessible
		STATUS		current
		DESCRIPTION	""
		::=  { bitSTORM-HP-160CfgRelayGroup  11 }

	bitSTORM-HP-160CfgDhcpQueryClientEntry	OBJECT-TYPE
		SYNTAX		BITSTORM-HP-160CfgDhcpQueryClientEntry
		MAX-ACCESS	not-accessible
		STATUS		current
		DESCRIPTION	""
		INDEX		{  bitSTORM-HP-160ServerQueryBpIndex,bitSTORM-HP-160ServerQueryClientIndex  }
		::=  { bitSTORM-HP-160CfgDhcpQueryClientTable 1 }

	BITSTORM-HP-160CfgDhcpQueryClientEntry  ::=  SEQUENCE {
		bitSTORM-HP-160ServerQueryBpIndex  Integer32,
		bitSTORM-HP-160ServerQueryClientIndex  Integer32,
		bitSTORM-HP-160ServerQueryIp  OCTET STRING,       
		bitSTORM-HP-160ServerQueryMac  PhysAddress,   
		bitSTORM-HP-160ServerQueryExpTime  OCTET STRING,
		bitSTORM-HP-160ServerQueryLeaseTime  Integer32
		}

	bitSTORM-HP-160ServerQueryBpIndex	OBJECT-TYPE
		SYNTAX			Integer32 (4..219)
		MAX-ACCESS		not-accessible
		STATUS			current
		DESCRIPTION		""
		::=  {  bitSTORM-HP-160CfgDhcpQueryClientEntry  1  }


	bitSTORM-HP-160ServerQueryClientIndex	OBJECT-TYPE
		SYNTAX			Integer32  (1..10)
		MAX-ACCESS		read-only
		STATUS			current
		DESCRIPTION		""
		::=  {  bitSTORM-HP-160CfgDhcpQueryClientEntry  2  }
	bitSTORM-HP-160ServerQueryIp	OBJECT-TYPE
		SYNTAX			OCTET STRING
		MAX-ACCESS		read-only
		STATUS			current
		DESCRIPTION		""
		::=  {  bitSTORM-HP-160CfgDhcpQueryClientEntry  3  }
	bitSTORM-HP-160ServerQueryMac	OBJECT-TYPE
		SYNTAX			PhysAddress
		MAX-ACCESS		read-only
		STATUS			current
		DESCRIPTION		""
		::=  {  bitSTORM-HP-160CfgDhcpQueryClientEntry  4  }
	bitSTORM-HP-160ServerQueryExpTime	OBJECT-TYPE
		SYNTAX			OCTET STRING
		MAX-ACCESS		read-only
		STATUS			current
		DESCRIPTION		""
		::=  {  bitSTORM-HP-160CfgDhcpQueryClientEntry  5  }
        bitSTORM-HP-160ServerQueryLeaseTime	OBJECT-TYPE
		SYNTAX			Integer32
		MAX-ACCESS		read-only
		STATUS			current
		DESCRIPTION		""
		::=  {  bitSTORM-HP-160CfgDhcpQueryClientEntry  6  }
--

--
	bitSTORM-HP-160CfgDhcpStaticIPTable	OBJECT-TYPE
		SYNTAX		SEQUENCE  OF  BITSTORM-HP-160CfgDhcpStaticIPEntry
		MAX-ACCESS	not-accessible
		STATUS		current
		DESCRIPTION	""
		::=  { bitSTORM-HP-160CfgRelayGroup  12 }

	bitSTORM-HP-160CfgDhcpStaticIPEntry	OBJECT-TYPE
		SYNTAX		BITSTORM-HP-160CfgDhcpStaticIPEntry
		MAX-ACCESS	not-accessible
		STATUS		current
		DESCRIPTION	""
		INDEX		{  bitSTORM-HP-160StaticIndex  }
		::=  { bitSTORM-HP-160CfgDhcpStaticIPTable 1 }
		
		
	BITSTORM-HP-160CfgDhcpStaticIPEntry  ::=  SEQUENCE {
		bitSTORM-HP-160StaticIndex  Integer32,
		bitSTORM-HP-160StaticIPBpIndex  Integer32,
		bitSTORM-HP-160StaticIp  OCTET STRING,
		bitSTORM-HP-160StaticMac  PhysAddress,
		bitSTORM-HP-160StaticRowStatus  RowStatus
		}

	bitSTORM-HP-160StaticIndex	OBJECT-TYPE
		SYNTAX			Integer32 (1..438)
		MAX-ACCESS		not-accessible
		STATUS			current
		DESCRIPTION		""
		::=  {  bitSTORM-HP-160CfgDhcpStaticIPEntry  1  }


	bitSTORM-HP-160StaticIPBpIndex	OBJECT-TYPE
		SYNTAX			Integer32  
		MAX-ACCESS		read-create
		STATUS			current
		DESCRIPTION		""
		::=  {  bitSTORM-HP-160CfgDhcpStaticIPEntry  2  }
	bitSTORM-HP-160StaticIp	OBJECT-TYPE
		SYNTAX			OCTET STRING  ( SIZE ( 0 .. 15  ) )
		MAX-ACCESS		read-create
		STATUS			current
		DESCRIPTION		""
		::=  {  bitSTORM-HP-160CfgDhcpStaticIPEntry  3  }
	bitSTORM-HP-160StaticMac	OBJECT-TYPE
		SYNTAX			PhysAddress
		MAX-ACCESS		read-create
		STATUS			current
		DESCRIPTION		""
		::=  {  bitSTORM-HP-160CfgDhcpStaticIPEntry  4  }
	bitSTORM-HP-160StaticRowStatus	OBJECT-TYPE
		SYNTAX			RowStatus
		MAX-ACCESS		read-create
		STATUS			current
		DESCRIPTION		""
		::=  {  bitSTORM-HP-160CfgDhcpStaticIPEntry  5  }
--


   	bitSTORM-HP-160CfgVpmtTrunkTable	OBJECT-TYPE
		SYNTAX		SEQUENCE  OF  BITSTORM-HP-160CfgVpmtTrunkEntry
		MAX-ACCESS	not-accessible                      
		STATUS		current
		DESCRIPTION	""
		::=  { bitSTORM-HP-160CfgVpmtGroup  1 }

	bitSTORM-HP-160CfgVpmtTrunkEntry	OBJECT-TYPE
		SYNTAX		BITSTORM-HP-160CfgVpmtTrunkEntry
		MAX-ACCESS	not-accessible
		STATUS		current
		DESCRIPTION	""
		INDEX		{  bitSTORM-HP-160CfgVpmtIndex  }
		::=  { bitSTORM-HP-160CfgVpmtTrunkTable 1 }

	BITSTORM-HP-160CfgVpmtTrunkEntry  ::=  SEQUENCE {
		bitSTORM-HP-160CfgVpmtIndex     INTEGER,
		bitSTORM-HP-160CfgVpmtPriority  OCTET STRING,
		bitSTORM-HP-160CfgVpmtDenyMode  OCTET STRING
--                bitSTORM-HP-160CfgVpmtRowStatus RowStatus,
		}


	bitSTORM-HP-160CfgVpmtIndex	OBJECT-TYPE
		SYNTAX			INTEGER (1..3)
		MAX-ACCESS		not-accessible
		STATUS			current
		DESCRIPTION		"1..3"
		::=  {  bitSTORM-HP-160CfgVpmtTrunkEntry  1  }


	bitSTORM-HP-160CfgVpmtPriority	OBJECT-TYPE
		SYNTAX			OCTET STRING  ( SIZE ( 16  ) )
		MAX-ACCESS		read-write
		STATUS			current
		DESCRIPTION		"for priority 0..7
		                         Queue No : 0 .. 3
	                                  0 .. 2 for shaping Queue(0 : High prio, 1 : Medium prio, 2 : Low prio)
	                                         , the enetTrafficDescrType bind to this prio should be CIR/CIREIR/PPR.
	                                  3      only for WFQ Quese(Lowest prio of these 4 Queses)
	                                         , the enetTrafficDescrType bind to this prio should be WFQ.
	                                  It isn't allowed that a shaping Queue maps to enetTrafficDescrType WFQ
	                                  It isn't allowed that a WFQ Queue maps to enetTrafficDescrType CIR/CIREIR/PPR
	                                  OAMP Layer 2 will check the relationship of Queue mapping and enetTrafficDescrType."
		::=  {  bitSTORM-HP-160CfgVpmtTrunkEntry  2  }


	bitSTORM-HP-160CfgVpmtDenyMode	OBJECT-TYPE
		SYNTAX			OCTET STRING  ( SIZE ( 8  ) )
		MAX-ACCESS		read-write
		STATUS			current
		DESCRIPTION		"0:pass, 1:deny"
		::=  {  bitSTORM-HP-160CfgVpmtTrunkEntry  3  }


--	bitSTORM-HP-160CfgVpmtRowStatus	OBJECT-TYPE
--                SYNTAX  RowStatus
--                MAX-ACCESS  read-create
--                STATUS  current
--                DESCRIPTION
--                           "bitSTORM-HP-160CfgVpmtRowStatus."
--		::=  {  bitSTORM-HP-160CfgVpmtTrunkEntry  4  }



   	bitSTORM-HP-160CfgVpmtBportProfileTable	OBJECT-TYPE
		SYNTAX		SEQUENCE  OF  BITSTORM-HP-160CfgVpmtBportProfileEntry
		MAX-ACCESS	not-accessible                      
		STATUS		current
		DESCRIPTION	""
		::=  { bitSTORM-HP-160CfgVpmtGroup  2 }

	bitSTORM-HP-160CfgVpmtBportProfileEntry	OBJECT-TYPE
		SYNTAX		BITSTORM-HP-160CfgVpmtBportProfileEntry
		MAX-ACCESS	not-accessible
		STATUS		current
		DESCRIPTION	""
		INDEX		{  bitSTORM-HP-160CfgVpmtProfileIndex  }
		::=  { bitSTORM-HP-160CfgVpmtBportProfileTable 1 }

	BITSTORM-HP-160CfgVpmtBportProfileEntry  ::=  SEQUENCE {
		bitSTORM-HP-160CfgVpmtProfileIndex     INTEGER,
		bitSTORM-HP-160CfgVpmtProfilePriority  OCTET STRING,
		bitSTORM-HP-160CfgVpmtProfileDenyMode  OCTET STRING,
		bitSTORM-HP-160CfgVpmtProfileEnetProfileIndex OCTET STRING,
		bitSTORM-HP-160CfgVpmtProfileUsedCount        INTEGER,
                bitSTORM-HP-160CfgVpmtProfileRowStatus RowStatus
		}


	bitSTORM-HP-160CfgVpmtProfileIndex	OBJECT-TYPE
		SYNTAX			INTEGER (1..24)
		MAX-ACCESS		not-accessible
		STATUS			current
		DESCRIPTION		"1..3"
		::=  {  bitSTORM-HP-160CfgVpmtBportProfileEntry  1  }


	bitSTORM-HP-160CfgVpmtProfilePriority	OBJECT-TYPE
		SYNTAX			OCTET STRING  ( SIZE ( 8  ) )
		MAX-ACCESS		read-create
		STATUS			current
		DESCRIPTION		"for priority 0..7 
		                         Queue No : 0 .. 3
	                                  0 .. 2 for shaping Queue(0 : High prio, 1 : Medium prio, 2 : Low prio)
	                                         , the enetTrafficDescrType bind to this prio should be CIR/CIREIR/PPR.
	                                  3      only for WFQ Quese(Lowest prio of these 4 Queses)
	                                         , the enetTrafficDescrType bind to this prio should be WFQ.
	                                  It isn't allowed that a shaping Queue maps to enetTrafficDescrType WFQ
	                                  It isn't allowed that a WFQ Queue maps to enetTrafficDescrType CIR/CIREIR/PPR
	                                  OAMP Layer 2 will check the relationship of Queue mapping and enetTrafficDescrType."
		::=  {  bitSTORM-HP-160CfgVpmtBportProfileEntry  2  }


	bitSTORM-HP-160CfgVpmtProfileDenyMode	OBJECT-TYPE
		SYNTAX			OCTET STRING  ( SIZE ( 8  ) )
		MAX-ACCESS		read-create
		STATUS			current
		DESCRIPTION		"0:pass, 1:deny"
		::=  {  bitSTORM-HP-160CfgVpmtBportProfileEntry  3  }


	bitSTORM-HP-160CfgVpmtProfileEnetProfileIndex	OBJECT-TYPE
                SYNTAX  OCTET STRING  ( SIZE ( 8  ) )
                MAX-ACCESS  read-create
                STATUS  current
                DESCRIPTION
                           "enet traffic descriptor index."
		::=  {  bitSTORM-HP-160CfgVpmtBportProfileEntry  4  }
	bitSTORM-HP-160CfgVpmtProfileUsedCount	OBJECT-TYPE
                SYNTAX  INTEGER
                MAX-ACCESS  read-only
                STATUS  current
                DESCRIPTION
                           ""
		::=  {  bitSTORM-HP-160CfgVpmtBportProfileEntry  5  }
	bitSTORM-HP-160CfgVpmtProfileRowStatus	OBJECT-TYPE
                SYNTAX  RowStatus
                MAX-ACCESS  read-create
                STATUS  current
                DESCRIPTION
                           "bitSTORM-HP-160CfgVpmtRowStatus."
		::=  {  bitSTORM-HP-160CfgVpmtBportProfileEntry  6  }

	bitSTORM-HP-160CfgVpmtBridgePortBindTable	OBJECT-TYPE
		SYNTAX		SEQUENCE  OF  BITSTORM-HP-160CfgVpmtBridgePortBindEntry
		MAX-ACCESS	not-accessible
		STATUS		current
		DESCRIPTION	""
		::=  { bitSTORM-HP-160CfgVpmtGroup  3 }

	bitSTORM-HP-160CfgVpmtBridgePortBindEntry	OBJECT-TYPE
		SYNTAX		BITSTORM-HP-160CfgVpmtBridgePortBindEntry
		MAX-ACCESS	not-accessible
		STATUS		current
		DESCRIPTION	""
		INDEX		{  bitSTORM-HP-160CfgVpmtBindBpId  }
		::=  { bitSTORM-HP-160CfgVpmtBridgePortBindTable 1 }

	BITSTORM-HP-160CfgVpmtBridgePortBindEntry  ::=  SEQUENCE {
		bitSTORM-HP-160CfgVpmtBindBpId  Integer32,
		bitSTORM-HP-160CfgVpmtBindProfileId  Integer32
		}


	bitSTORM-HP-160CfgVpmtBindBpId	OBJECT-TYPE	
		SYNTAX			Integer32 (196..219)
		MAX-ACCESS		not-accessible
		STATUS			current
		DESCRIPTION		""
		::=  {  bitSTORM-HP-160CfgVpmtBridgePortBindEntry  1  }


	bitSTORM-HP-160CfgVpmtBindProfileId	OBJECT-TYPE
		SYNTAX			Integer32  (1..24)
		MAX-ACCESS		read-write
		STATUS			current
		DESCRIPTION		""
		::=  {  bitSTORM-HP-160CfgVpmtBridgePortBindEntry  2  }
		
		
--	bitSTORM-HP-160CfgSystemAclMode	OBJECT-TYPE
--		SYNTAX			INTEGER { Disable(0),Enable(1) }
--		MAX-ACCESS		read-write
--		STATUS			current
--		DESCRIPTION		""
--		::=  {  bitSTORM-HP-160CfgSystemConfiguration  1  }

	bitSTORM-HP-160CfgSystemExtEtherType	OBJECT-TYPE
		SYNTAX			Integer32  (0..65535)
		MAX-ACCESS		read-write
		STATUS			current
		DESCRIPTION		""
		::=  {  bitSTORM-HP-160CfgSystemConfiguration  1  }

	bitSTORM-HP-160CfgSystemAllowDownstreamBc	OBJECT-TYPE
		SYNTAX			INTEGER { disable(0),enable(1) }
		MAX-ACCESS		read-write
		STATUS			current
		DESCRIPTION		"0:disable(only ARP,DHCP are allowed), 1:enable(ALL bccast are allowed)"
		::=  {  bitSTORM-HP-160CfgSystemConfiguration  2  }

--	bitSTORM-HP-160CfgSystemAllowIpFilter	OBJECT-TYPE
--		SYNTAX			INTEGER { Disable(0),Enable(1) }
--		MAX-ACCESS		read-write
--		STATUS			current
--		DESCRIPTION		"0:disable, 1:enable"
--		::=  {  bitSTORM-HP-160CfgSystemConfiguration  4  }


	bitSTORM-HP-160CfgSystemAddAllowIpBySnoopDHCP	OBJECT-TYPE
		SYNTAX			INTEGER { disable(0),enable(1) }
		MAX-ACCESS		read-write
		STATUS			current
		DESCRIPTION		"0:disable, 1:enable,
	                                allowIpFilter should be enabled first."
		::=  {  bitSTORM-HP-160CfgSystemConfiguration  3  }


	bitSTORM-HP-160CfgSystemAgingTimePerPort	OBJECT-TYPE
		SYNTAX			INTEGER { disable(0),enable(1) }
		MAX-ACCESS		read-write
		STATUS			current
		DESCRIPTION		"1:enable, 0:disable->Old mechanism, referecne to TpAgingTime."
		::=  {  bitSTORM-HP-160CfgSystemConfiguration  4  }

	bitSTORM-HP-160CfgSystemReplaceArpMac	OBJECT-TYPE
		SYNTAX			INTEGER { disable(0),enable(1) }
		MAX-ACCESS		read-write
		STATUS			current
		DESCRIPTION		"0:disable, 1:enable(mac of arp will be replaced)"
		::=  {  bitSTORM-HP-160CfgSystemConfiguration  5  }


	bitSTORM-HP-160CfgSystemSnoopArpDefaultGatewayMac	OBJECT-TYPE
		SYNTAX			PhysAddress
		MAX-ACCESS		read-create
		STATUS			current
		DESCRIPTION		"string hex mac format in DB, example->FF:FF:FF:FF:FF:FF"
		::=  {  bitSTORM-HP-160CfgSystemConfiguration  6  }


	bitSTORM-HP-160CfgSystemArpSpoofing	OBJECT-TYPE
		SYNTAX			INTEGER { disable(0),enable(1)	 }
		MAX-ACCESS		read-write
		STATUS			current
		DESCRIPTION		"0:disable this arp spoof function, L2 will not check the arp reply packet from line side.
                                         1:enable this arp spoof function, L2 will check the arp reply packet from line side."
		::=  {  bitSTORM-HP-160CfgSystemConfiguration  7  }

	bitSTORM-HP-160CfgSystemAntiMacSpoofing	OBJECT-TYPE
		SYNTAX			INTEGER { disable(0),enable(1) }
		MAX-ACCESS		read-write
		STATUS			current
		DESCRIPTION		"0:able to provide service to users with duplicate MAC addresses (by default)
                                         1:able to deny service to users with duplicate MAC addresses."
		::=  {  bitSTORM-HP-160CfgSystemConfiguration  8  }

--
	bitSTORM-HP-160CfgAclService	OBJECT-TYPE
		SYNTAX			INTEGER { disable(0),enable(1) }
		MAX-ACCESS		read-write
		STATUS			current
		DESCRIPTION		""
		::=  {  bitSTORM-HP-160CfgLayerIIServiceOption  1  }

	bitSTORM-HP-160CfgPppoeService	OBJECT-TYPE
		SYNTAX			INTEGER { disable(0),enable(1) }
		MAX-ACCESS		read-write
		STATUS			current
		DESCRIPTION		""
		::=  {  bitSTORM-HP-160CfgLayerIIServiceOption  2  }

	bitSTORM-HP-160CfgFilterAndPriorityRemarkService	OBJECT-TYPE     
		SYNTAX			INTEGER { disable(0),enable(1) }
		MAX-ACCESS		read-write
		STATUS			current
		DESCRIPTION		""
		::=  {  bitSTORM-HP-160CfgLayerIIServiceOption  3  }

	bitSTORM-HP-160CfgRateLimitService	OBJECT-TYPE
		SYNTAX			INTEGER { disable(0),enable(1) }
		MAX-ACCESS		read-write
		STATUS			current
		DESCRIPTION		""
		::=  {  bitSTORM-HP-160CfgLayerIIServiceOption  4  }


	bitSTORM-HP-160CfgStackVlanService	OBJECT-TYPE
		SYNTAX			INTEGER { disable(0),enable(1) }
		MAX-ACCESS		read-write
		STATUS			current
		DESCRIPTION		""
		::=  {  bitSTORM-HP-160CfgLayerIIServiceOption  5  }

	bitSTORM-HP-160CfgNetBiosDenialService	OBJECT-TYPE
		SYNTAX			INTEGER { disable(0),enable(1) }
		MAX-ACCESS		read-write
		STATUS			current
		DESCRIPTION		""
		::=  {  bitSTORM-HP-160CfgLayerIIServiceOption  6  }
		
	bitSTORM-HP-160CfgAllowIpService	OBJECT-TYPE
		SYNTAX			INTEGER { disable(0),enable(1) }
		MAX-ACCESS		read-write
		STATUS			current
		DESCRIPTION		""
		::=  {  bitSTORM-HP-160CfgLayerIIServiceOption  7  }
		
--


	bitSTORM-HP-160CfgClusterName	OBJECT-TYPE
		SYNTAX			OCTET STRING  ( SIZE ( 0 .. 32  ) ) 
		MAX-ACCESS		read-write
		STATUS			current
		DESCRIPTION		""
		::=  {  bitSTORM-HP-160CfgClusterConfig  1  }

	bitSTORM-HP-160CfgClusterDomain	OBJECT-TYPE
		SYNTAX			OCTET STRING  ( SIZE ( 0 .. 32  ) )
		MAX-ACCESS		read-write
		STATUS			current
		DESCRIPTION		""
		::=  {  bitSTORM-HP-160CfgClusterConfig  2  }

	bitSTORM-HP-160CfgClusterManagementIp	OBJECT-TYPE	
		SYNTAX			TAddress
		MAX-ACCESS		read-write
		STATUS			current
		DESCRIPTION		""
		::=  {  bitSTORM-HP-160CfgClusterConfig  3  }

	bitSTORM-HP-160CfgClusterManagementNetmask	OBJECT-TYPE	
		SYNTAX			TAddress
		MAX-ACCESS		read-write
		STATUS			current
		DESCRIPTION		""
		::=  {  bitSTORM-HP-160CfgClusterConfig  4  }

	bitSTORM-HP-160CfgClusterManagementGateway	OBJECT-TYPE	
		SYNTAX			TAddress
		MAX-ACCESS		read-write
		STATUS			current
		DESCRIPTION		""
		::=  {  bitSTORM-HP-160CfgClusterConfig  5  }

	bitSTORM-HP-160CfgClusterPriority	OBJECT-TYPE	
		SYNTAX			Integer32
		MAX-ACCESS		read-write
		STATUS			current
		DESCRIPTION		""
		::=  {  bitSTORM-HP-160CfgClusterConfig  6  }

	bitSTORM-HP-160CfgClusterClustered	OBJECT-TYPE
		SYNTAX			INTEGER { disabled(0),enabled(1) }  
		MAX-ACCESS		read-write
		STATUS			current
		DESCRIPTION		""
		::=  {  bitSTORM-HP-160CfgClusterConfig  7  }

	bitSTORM-HP-160CfgClusterSlaveOnly	OBJECT-TYPE
		SYNTAX			INTEGER { masterslave(0),slaveonly(1) }
		MAX-ACCESS		read-write
		STATUS			current
		DESCRIPTION		""
		::=  {  bitSTORM-HP-160CfgClusterConfig  8  }
		
	bitSTORM-HP-160CfgClusterState	OBJECT-TYPE
		SYNTAX			INTEGER  {
		  idle(0),               
  		  reinit(1),
  		  discovering(2),
  		  requesting(3),
		  voting(4),
		  slave(5),
		  master(6)
		 }
		MAX-ACCESS		read-only
		STATUS			current
		DESCRIPTION		""
		::=  {  bitSTORM-HP-160CfgClusterConfig  9  }
		
		
bitSTORM-HP-160CfgEnetTrafficDescrEntry OBJECT-TYPE
    SYNTAX      BITSTORM-HP-160CfgEnetTrafficDescrEntry
    MAX-ACCESS  not-accessible
    STATUS      current
    DESCRIPTION
        ""
    INDEX   { bitSTORM-HP-160CfgEnetTrafficDescrIndex }
    ::= { bitSTORM-HP-160CfgEnetTrafficDescrTable 1 }

BITSTORM-HP-160CfgEnetTrafficDescrEntry ::=
    SEQUENCE {
             bitSTORM-HP-160CfgEnetTrafficDescrIndex         Integer32,
             bitSTORM-HP-160CfgEnetTrafficType               BITSTORM-HP-160EnetTrafficType,
             bitSTORM-HP-160CfgEnetTrafficWeight             Unsigned32,
--             bitSTORM-HP-160CfgEnetTrafficWeightFraction     Unsigned32,
             bitSTORM-HP-160CfgEnetTrafficPPR                Unsigned32,
             bitSTORM-HP-160CfgEnetTrafficCIR                Unsigned32,
             bitSTORM-HP-160CfgEnetTrafficEIR                Unsigned32,
             bitSTORM-HP-160CfgEnetTrafficCBS                Unsigned32,
             bitSTORM-HP-160CfgEnetTrafficEBS                Unsigned32,
             bitSTORM-HP-160CfgEnetTrafficPPRPollingSpeed    Unsigned32,
             bitSTORM-HP-160CfgEnetTrafficCIRPollingSpeed    Unsigned32,
             bitSTORM-HP-160CfgEnetTrafficEIRPollingSpeed    Unsigned32,
             bitSTORM-HP-160CfgAtmTrafficType                BITSTORM-HP-160AtmTrafficType,
             bitSTORM-HP-160CfgEnetTrafficPCR                Unsigned32,
             bitSTORM-HP-160CfgEnetTrafficCDVT               Unsigned32,
                                               
             bitSTORM-HP-160CfgEnetTrafficRowStatus          RowStatus,
             bitSTORM-HP-160CfgEnetTrafficUsedCount           INTEGER
    }

bitSTORM-HP-160CfgEnetTrafficDescrIndex  OBJECT-TYPE
    SYNTAX      Integer32 (1..16)
    MAX-ACCESS  not-accessible
    STATUS  current
    DESCRIPTION
       "1..16"
     ::= { bitSTORM-HP-160CfgEnetTrafficDescrEntry 1 }

bitSTORM-HP-160CfgEnetTrafficType OBJECT-TYPE
    SYNTAX      BITSTORM-HP-160EnetTrafficType
    MAX-ACCESS  read-write
    STATUS  current
    DESCRIPTION
        "
           ENETPKTSHAPINGWFQ(1),
           ENETPKTSHAPINGPPR(2),
           ENETPKTSHAPINGCIR(3),
           ENETPKTSHAPINGCIREIR(4)
        "
     ::= { bitSTORM-HP-160CfgEnetTrafficDescrEntry 2 }

bitSTORM-HP-160CfgEnetTrafficWeight  OBJECT-TYPE
    SYNTAX      Unsigned32 (1..42)
    MAX-ACCESS  read-write
    STATUS  current
    DESCRIPTION
       ""
     ::= { bitSTORM-HP-160CfgEnetTrafficDescrEntry 3 }

--bitSTORM-HP-160CfgEnetTrafficWeightFraction  OBJECT-TYPE
--    SYNTAX      Unsigned32
--    MAX-ACCESS  read-write
--    STATUS  current
--    DESCRIPTION
--       ""
--     ::= { bitSTORM-HP-160CfgEnetTrafficDescrEntry 4 }

bitSTORM-HP-160CfgEnetTrafficPPR  OBJECT-TYPE
    SYNTAX      Unsigned32 (1000000..100000000)
    MAX-ACCESS  read-write
    STATUS  current
    DESCRIPTION
       "Peak packet Rate.[bits/second]"
     ::= { bitSTORM-HP-160CfgEnetTrafficDescrEntry 4 }

bitSTORM-HP-160CfgEnetTrafficCIR  OBJECT-TYPE
    SYNTAX      Unsigned32 (1000000..100000000)
    MAX-ACCESS  read-write
    STATUS  current
    DESCRIPTION
       "Committed Information Rate expressed as bits/sec"
     ::= { bitSTORM-HP-160CfgEnetTrafficDescrEntry 5 }

bitSTORM-HP-160CfgEnetTrafficEIR  OBJECT-TYPE
    SYNTAX      Unsigned32 (1000000..100000000)
    MAX-ACCESS  read-write
    STATUS  current
    DESCRIPTION
       "Committed Excess Rate expressed as bits/sec"
     ::= { bitSTORM-HP-160CfgEnetTrafficDescrEntry 6 }

bitSTORM-HP-160CfgEnetTrafficCBS  OBJECT-TYPE
    SYNTAX      Unsigned32 (1..4294967295)
    MAX-ACCESS  read-write
    STATUS  current
    DESCRIPTION
       "Committed Burst Size in bits"
     ::= { bitSTORM-HP-160CfgEnetTrafficDescrEntry 7 }

bitSTORM-HP-160CfgEnetTrafficEBS  OBJECT-TYPE
    SYNTAX      Unsigned32 (1..4294967295)
    MAX-ACCESS  read-write
    STATUS  current
    DESCRIPTION
       "Excess Burst Size in bits"
     ::= { bitSTORM-HP-160CfgEnetTrafficDescrEntry 8 }

bitSTORM-HP-160CfgEnetTrafficPPRPollingSpeed  OBJECT-TYPE
    SYNTAX      Unsigned32 (1000000..2147483648)
    MAX-ACCESS  read-write
    STATUS  current
    DESCRIPTION
       "Vaule range:1000000-100000000.
        2147483648 means Auto Deactivation Mode.
       "
     ::= { bitSTORM-HP-160CfgEnetTrafficDescrEntry 9 }

bitSTORM-HP-160CfgEnetTrafficCIRPollingSpeed  OBJECT-TYPE
    SYNTAX      Unsigned32 (1000000..2147483648)
    MAX-ACCESS  read-write
    STATUS  current
    DESCRIPTION
       "Vaule range:1000000-100000000..
        2147483648 means Auto Deactivation Mode.

        Currently, Auto Deactivation is not supported.
       "
     ::= { bitSTORM-HP-160CfgEnetTrafficDescrEntry 10 }

bitSTORM-HP-160CfgEnetTrafficEIRPollingSpeed  OBJECT-TYPE
    SYNTAX      Unsigned32 (1000000..2147483648)
    MAX-ACCESS  read-write
    STATUS  current
    DESCRIPTION
       "Vaule range:1000000-100000000.
        2147483648 means Auto Deactivation Mode.

        Currently only Auto-deactivation mode is permitted.
       "
     ::= { bitSTORM-HP-160CfgEnetTrafficDescrEntry 11 }

bitSTORM-HP-160CfgAtmTrafficType OBJECT-TYPE
    SYNTAX      BITSTORM-HP-160AtmTrafficType
    MAX-ACCESS  read-write
    STATUS  current
    DESCRIPTION
        "
           AtmPolicingCBR(9),
           AtmPolicingUBR2(11)
        "
     ::= { bitSTORM-HP-160CfgEnetTrafficDescrEntry 12 }

bitSTORM-HP-160CfgEnetTrafficPCR  OBJECT-TYPE
    SYNTAX      Unsigned32 (1..65536)
    MAX-ACCESS  read-write
    STATUS  current
    DESCRIPTION
       "0-65536, Specified in units of cells/second"
     ::= { bitSTORM-HP-160CfgEnetTrafficDescrEntry 13 }
     
bitSTORM-HP-160CfgEnetTrafficCDVT  OBJECT-TYPE
    SYNTAX      Unsigned32 (1..65536)
    MAX-ACCESS  read-write
    STATUS  current
    DESCRIPTION
       "0-65536, Specified in units of 10 ns increments, this field is used by the PCR policing algorithm"
     ::= { bitSTORM-HP-160CfgEnetTrafficDescrEntry 14 }
     
bitSTORM-HP-160CfgEnetTrafficRowStatus  OBJECT-TYPE
    SYNTAX  RowStatus
    MAX-ACCESS  read-create
    STATUS  current
    DESCRIPTION
       "bitSTORM-HP-160CfgEnetTrafficRowStatus."
     ::= { bitSTORM-HP-160CfgEnetTrafficDescrEntry 15 }

bitSTORM-HP-160CfgEnetTrafficUsedCount	OBJECT-TYPE
    SYNTAX			INTEGER
    MAX-ACCESS		read-only
    STATUS			current
    DESCRIPTION		"The value is not zero means the profile is in used,then the profile can't be delete."
     ::=  {  bitSTORM-HP-160CfgEnetTrafficDescrEntry  16  }
		
--bitSTORM-HP-160CfgEnetTrafficUseCount  OBJECT-TYPE
--    SYNTAX  Unsigned32
--    MAX-ACCESS  read-only
--    STATUS  current
--    DESCRIPTION
--       "bitSTORM-HP-160CfgEnetTrafficUseCount."
--     ::= { bitSTORM-HP-160CfgEnetTrafficDescrEntry 14 }


--	bitSTORM-HP-160MtnRemoteTFTPServerIP	OBJECT-TYPE
--		SYNTAX			TAddress
--		MAX-ACCESS		read-write
--		STATUS			current
--		DESCRIPTION		""
--		::=  {  bitSTORM-HP-160MtnRemoteTFTPServer  1  }

--	bitSTORM-HP-160MtnRemoteTFTPFileName	OBJECT-TYPE
--		SYNTAX			OCTET STRING  ( SIZE ( 32  ) )
--		MAX-ACCESS		read-write
--		STATUS			current
--		DESCRIPTION		""
--		::=  {  bitSTORM-HP-160MtnRemoteTFTPServer  2  }

	bitSTORM-HP-160MtnRemoteFTPServerIP	OBJECT-TYPE
		SYNTAX			TAddress
		MAX-ACCESS		read-write
		STATUS			current
		DESCRIPTION		""
		::=  {  bitSTORM-HP-160MtnRemoteFTPServer  1  }

	bitSTORM-HP-160MtnRemoteFTPUserName	OBJECT-TYPE
		SYNTAX			OCTET STRING  ( SIZE ( 32  ) )
		MAX-ACCESS		read-write
		STATUS			current
		DESCRIPTION ""
		::=  {  bitSTORM-HP-160MtnRemoteFTPServer  2  }

	bitSTORM-HP-160MtnRemoteFTPPassword	OBJECT-TYPE
		SYNTAX			OCTET STRING  ( SIZE ( 32  ) )
		MAX-ACCESS		read-write
		STATUS			current
		DESCRIPTION		""
		::=  {  bitSTORM-HP-160MtnRemoteFTPServer  3  }

	bitSTORM-HP-160MtnRemoteFTPFileName	OBJECT-TYPE
		SYNTAX			OCTET STRING  ( SIZE ( 64  ) )
		MAX-ACCESS		read-write
		STATUS			current
		DESCRIPTION		""
		::=  {  bitSTORM-HP-160MtnRemoteFTPServer  4  }




	bitSTORM-HP-160MtnCliCfgFTPServerIP	OBJECT-TYPE
		SYNTAX			TAddress
		MAX-ACCESS		read-write
		STATUS			current
		DESCRIPTION		""
		::=  {  bitSTORM-HP-160MtnCliCfgFTPServer  1  }

	bitSTORM-HP-160MtnCliCfgFTPUserName	OBJECT-TYPE
		SYNTAX			OCTET STRING  ( SIZE ( 32  ) )
		MAX-ACCESS		read-write
		STATUS			current
	DESCRIPTION ""
		::=  {  bitSTORM-HP-160MtnCliCfgFTPServer  2  }

	bitSTORM-HP-160MtnCliCfgFTPPassword	OBJECT-TYPE
		SYNTAX			OCTET STRING  ( SIZE ( 32  ) )
		MAX-ACCESS		read-write
		STATUS			current
		DESCRIPTION		""
		::=  {  bitSTORM-HP-160MtnCliCfgFTPServer  3  }

	bitSTORM-HP-160MtnCliCfgFTPFileName	OBJECT-TYPE           
		SYNTAX			OCTET STRING  ( SIZE ( 64  ) )
		MAX-ACCESS		read-write
		STATUS			current
		DESCRIPTION		""
		::=  {  bitSTORM-HP-160MtnCliCfgFTPServer  4  }
		
	bitSTORM-HP-160SystemAlarmTrap	OBJECT IDENTIFIER
		::=  {  bitSTORM-HP-160TrapAlarmPrefix  1  }
		
        bitSTORM-HP-160GBEAlarmTrap	OBJECT IDENTIFIER
		::=  {  bitSTORM-HP-160TrapAlarmPrefix  2  }

	bitSTORM-HP-160VDSLAlarmTrap	OBJECT IDENTIFIER
		::=  {  bitSTORM-HP-160TrapAlarmPrefix  3  }

	bitSTORM-HP-160SystemEventTrap	OBJECT IDENTIFIER
		::=  {  bitSTORM-HP-160TrapEventPrefix  1  }

	bitSTORM-HP-160ATMEventTrap	OBJECT IDENTIFIER
		::=  {  bitSTORM-HP-160TrapEventPrefix  2  }

--	bitSTORM-HP-160GBEEventTrap	OBJECT IDENTIFIER
--		::=  {  bitSTORM-HP-160TrapEventPrefix  3  }

	bitSTORM-HP-160XDSLEventTrap	OBJECT IDENTIFIER
		::=  {  bitSTORM-HP-160TrapEventPrefix  3  }

	bitSTORM-HP-160VDSLEventTrap	OBJECT IDENTIFIER
		::=  {  bitSTORM-HP-160TrapEventPrefix  4  }

	bitSTORM-HP-160McBcRateLimitTable	OBJECT-TYPE
		SYNTAX		SEQUENCE  OF  BITSTORM-HP-160McBcRateLimitEntry
		MAX-ACCESS	not-accessible
		STATUS		current
		DESCRIPTION	""
		::=  { bitSTORM-HP-160CfgRateLimitGroup  1 }

	bitSTORM-HP-160McBcRateLimitEntry	OBJECT-TYPE
		SYNTAX		BITSTORM-HP-160McBcRateLimitEntry
		MAX-ACCESS	not-accessible
		STATUS		current
		DESCRIPTION	""
		INDEX		{  bitSTORM-HP-160McBcRateLimitVlanId  }
		::=  { bitSTORM-HP-160McBcRateLimitTable 1 }

	BITSTORM-HP-160McBcRateLimitEntry  ::=  SEQUENCE {
		bitSTORM-HP-160McBcRateLimitVlanId  Integer32,
		bitSTORM-HP-160McBcRateLimitCIR  Unsigned32,
		bitSTORM-HP-160McBcRateLimitLbSl  Unsigned32,
		bitSTORM-HP-160McBcRateLimitRowStatus  RowStatus
		}


	bitSTORM-HP-160McBcRateLimitVlanId	OBJECT-TYPE
		SYNTAX			Integer32  ( 1 .. 4094  )   --960803
		MAX-ACCESS		read-only
		STATUS			current
		DESCRIPTION		""
		::=  {  bitSTORM-HP-160McBcRateLimitEntry  1  }


	bitSTORM-HP-160McBcRateLimitCIR	OBJECT-TYPE	
		SYNTAX			Unsigned32  ( 1 .. 4294967295  ) 
		MAX-ACCESS		read-create
		STATUS			current
		DESCRIPTION		""
		::=  {  bitSTORM-HP-160McBcRateLimitEntry  2  }


	bitSTORM-HP-160McBcRateLimitLbSl	OBJECT-TYPE	
		SYNTAX			Unsigned32  ( 1 .. 4294967295  ) 
		MAX-ACCESS		read-create
		STATUS			current
		DESCRIPTION		""
		::=  {  bitSTORM-HP-160McBcRateLimitEntry  3  }


	bitSTORM-HP-160McBcRateLimitRowStatus	OBJECT-TYPE	
		SYNTAX			RowStatus
		MAX-ACCESS		read-create
		STATUS			current
		DESCRIPTION		""
		DEFVAL			{ createAndGo }
		::=  {  bitSTORM-HP-160McBcRateLimitEntry  4  }

	bitSTORM-HP-160McFldRateLimitTable	OBJECT-TYPE
		SYNTAX		SEQUENCE  OF  BITSTORM-HP-160McFldRateLimitEntry
		MAX-ACCESS	not-accessible
		STATUS		current
		DESCRIPTION	""
		::=  { bitSTORM-HP-160CfgRateLimitGroup  2 }

	bitSTORM-HP-160McFldRateLimitEntry	OBJECT-TYPE
		SYNTAX		BITSTORM-HP-160McFldRateLimitEntry
		MAX-ACCESS	not-accessible
		STATUS		current
		DESCRIPTION	""
		INDEX		{  bitSTORM-HP-160McFldRateLimitVlanId  }
		::=  { bitSTORM-HP-160McFldRateLimitTable 1 }

	BITSTORM-HP-160McFldRateLimitEntry  ::=  SEQUENCE {
		bitSTORM-HP-160McFldRateLimitVlanId  Integer32,
		bitSTORM-HP-160McFldRateLimitCIR  Unsigned32,
		bitSTORM-HP-160McFldRateLimitLbSl  Unsigned32,
		bitSTORM-HP-160McFldRateLimitRowStatus  RowStatus
		}


	bitSTORM-HP-160McFldRateLimitVlanId	OBJECT-TYPE
		SYNTAX			Integer32  ( 1 .. 4094  )   --960803
		MAX-ACCESS		read-only
		STATUS			current
		DESCRIPTION		""
		::=  {  bitSTORM-HP-160McFldRateLimitEntry  1  }


	bitSTORM-HP-160McFldRateLimitCIR	OBJECT-TYPE	
		SYNTAX			Unsigned32  ( 1 .. 4294967295  ) 
		MAX-ACCESS		read-create
		STATUS			current
		DESCRIPTION		""
		::=  {  bitSTORM-HP-160McFldRateLimitEntry  2  }


	bitSTORM-HP-160McFldRateLimitLbSl	OBJECT-TYPE	
		SYNTAX			Unsigned32  ( 1 .. 4294967295  ) 
		MAX-ACCESS		read-create
		STATUS			current
		DESCRIPTION		""
		::=  {  bitSTORM-HP-160McFldRateLimitEntry  3  }


	bitSTORM-HP-160McFldRateLimitRowStatus	OBJECT-TYPE	
		SYNTAX			RowStatus
		MAX-ACCESS		read-create
		STATUS			current
		DESCRIPTION		""
		DEFVAL			{ createAndGo }
		::=  {  bitSTORM-HP-160McFldRateLimitEntry  4  }

	bitSTORM-HP-160IwPolicerTable	OBJECT-TYPE
		SYNTAX		SEQUENCE  OF  BITSTORM-HP-160IwPolicerEntry
		MAX-ACCESS	not-accessible
		STATUS		current
		DESCRIPTION	""
		::=  { bitSTORM-HP-160CfgRateLimitGroup  3 }

	bitSTORM-HP-160IwpolicerEntry	OBJECT-TYPE
		SYNTAX		BITSTORM-HP-160IwPolicerEntry
		MAX-ACCESS	not-accessible
		STATUS		current
		DESCRIPTION	""
		INDEX		{  bitSTORM-HP-160IwPolicerIndex  }
		::=  { bitSTORM-HP-160IwPolicerTable 1 }

	BITSTORM-HP-160IwPolicerEntry  ::=  SEQUENCE {
		bitSTORM-HP-160IwPolicerIndex  Integer32,
		bitSTORM-HP-160IwPolicerCIR  Unsigned32,
		bitSTORM-HP-160IwPolicerLbSl  Unsigned32,
		bitSTORM-HP-160IwPolicerRowStatus  RowStatus,
		bitSTORM-HP-160IwPolicerUsedCount  INTEGER 		
		}


	bitSTORM-HP-160IwPolicerIndex	OBJECT-TYPE	
		SYNTAX			Integer32  ( 1 .. 128  ) 
		MAX-ACCESS		not-accessible
		STATUS			current
		DESCRIPTION		""
		::=  {  bitSTORM-HP-160IwpolicerEntry  1  }


	bitSTORM-HP-160IwPolicerCIR	OBJECT-TYPE	
		SYNTAX			Unsigned32
		MAX-ACCESS		read-create
		STATUS			current
		DESCRIPTION		""
		::=  {  bitSTORM-HP-160IwpolicerEntry  2  }


	bitSTORM-HP-160IwPolicerLbSl	OBJECT-TYPE	
		SYNTAX			Unsigned32  ( 1 .. 4294967295  ) 
		MAX-ACCESS		read-create
		STATUS			current
		DESCRIPTION		""
		::=  {  bitSTORM-HP-160IwpolicerEntry  3  }


	bitSTORM-HP-160IwPolicerRowStatus	OBJECT-TYPE
		SYNTAX			RowStatus
		MAX-ACCESS		read-create
		STATUS			current
		DESCRIPTION		""
		::=  {  bitSTORM-HP-160IwpolicerEntry  4  }

	bitSTORM-HP-160IwPolicerUsedCount	OBJECT-TYPE
		SYNTAX			INTEGER
		MAX-ACCESS		read-only
		STATUS			current
		DESCRIPTION		"The value is not zero means the profile is in used,then the profile can't be delete."
		::=  {  bitSTORM-HP-160IwpolicerEntry  5  }

	bitSTORM-HP-160BportRateLimitTable	OBJECT-TYPE
		SYNTAX		SEQUENCE  OF  BITSTORM-HP-160BportRateLimitEntry
		MAX-ACCESS	not-accessible
		STATUS		current
		DESCRIPTION	""
		::=  { bitSTORM-HP-160CfgRateLimitGroup  4 }

	bitSTORM-HP-160BportRateLimitEntry	OBJECT-TYPE
		SYNTAX		BITSTORM-HP-160BportRateLimitEntry
		MAX-ACCESS	not-accessible
		STATUS		current
		DESCRIPTION	""
		INDEX		{  bitSTORM-HP-160BportIfcIndex  }
		::=  { bitSTORM-HP-160BportRateLimitTable 1 }

	BITSTORM-HP-160BportRateLimitEntry  ::=  SEQUENCE {
		bitSTORM-HP-160BportIfcIndex  Integer32,
		--bitSTORM-HP-160BportRateLimitIwPolicerIdx  Unsigned32,
		bitSTORM-HP-160BportRateLimitEgressIwPolicerIdx  Unsigned32,   --20070329 add
		bitSTORM-HP-160BportRateLimitIngressIwPolicerIdx  Unsigned32   --20070329 add
--		bitSTORM-HP-160BportRateLimitRowStatus  RowStatus
		}


	bitSTORM-HP-160BportIfcIndex	OBJECT-TYPE
		SYNTAX			Integer32  ( 1 .. 219  )
		MAX-ACCESS		not-accessible
		STATUS			current
		DESCRIPTION		""
		::=  {  bitSTORM-HP-160BportRateLimitEntry  1  }


	bitSTORM-HP-160BportRateLimitEgressIwPolicerIdx	OBJECT-TYPE
		SYNTAX			Unsigned32  ( 1 .. 4294967295  )
		MAX-ACCESS		read-write
		STATUS			current
		DESCRIPTION		""
		::=  {  bitSTORM-HP-160BportRateLimitEntry  2  }


	bitSTORM-HP-160BportRateLimitIngressIwPolicerIdx	OBJECT-TYPE
		SYNTAX			Unsigned32  ( 1 .. 4294967295  )
		MAX-ACCESS		read-write
		STATUS			current
		DESCRIPTION		""
		::=  {  bitSTORM-HP-160BportRateLimitEntry  3  }

--	bitSTORM-HP-160BportRateLimitRowStatus	OBJECT-TYPE
--		SYNTAX			RowStatus
--		MAX-ACCESS		read-create
--		STATUS			current
--		DESCRIPTION		""
--		::=  {  bitSTORM-HP-160BportRateLimitEntry  4  }



	bitSTORM-HP-160BportVlanRateLimitTable	OBJECT-TYPE
		SYNTAX		SEQUENCE  OF  BITSTORM-HP-160BportVlanRateLimitEntry
		MAX-ACCESS	not-accessible
		STATUS		current
		DESCRIPTION	""
		::=  { bitSTORM-HP-160CfgRateLimitGroup  5 }

	bitSTORM-HP-160BportVlanRateLimitEntry	OBJECT-TYPE
		SYNTAX		BITSTORM-HP-160BportVlanRateLimitEntry
		MAX-ACCESS	not-accessible
		STATUS		current
		DESCRIPTION	""
		INDEX		{  bitSTORM-HP-160BportVlanRateLimitIndex  }
		::=  { bitSTORM-HP-160BportVlanRateLimitTable 1 }

	BITSTORM-HP-160BportVlanRateLimitEntry  ::=  SEQUENCE {
		bitSTORM-HP-160BportVlanRateLimitIndex  Integer32,
		bitSTORM-HP-160BportVlanRateLimitEgressIwPolicerIdx  Unsigned32,
		bitSTORM-HP-160BportVlanRateLimitIngressIwPolicerIdx  Unsigned32,
		bitSTORM-HP-160BportVlanRateLimitVlanId  Unsigned32,
		bitSTORM-HP-160BportVlanRateLimitIfcIndex  Unsigned32,
		bitSTORM-HP-160BportVlanRateLimitRowStatus  RowStatus
		}


	bitSTORM-HP-160BportVlanRateLimitIndex	OBJECT-TYPE
		SYNTAX			Integer32  ( 1 .. 219  )
		MAX-ACCESS		not-accessible
		STATUS			current
		DESCRIPTION		""
		::=  {  bitSTORM-HP-160BportVlanRateLimitEntry  1  }


	bitSTORM-HP-160BportVlanRateLimitEgressIwPolicerIdx	OBJECT-TYPE
		SYNTAX			Unsigned32  ( 1 .. 4294967295  )
		MAX-ACCESS		read-create
		STATUS			current
		DESCRIPTION		""
		::=  {  bitSTORM-HP-160BportVlanRateLimitEntry  2  }


	bitSTORM-HP-160BportVlanRateLimitIngressIwPolicerIdx	OBJECT-TYPE
		SYNTAX			Unsigned32  ( 1 .. 4294967295  )
		MAX-ACCESS		read-create
		STATUS			current
		DESCRIPTION		""
		::=  {  bitSTORM-HP-160BportVlanRateLimitEntry  3  }

	bitSTORM-HP-160BportVlanRateLimitVlanId	OBJECT-TYPE
		SYNTAX			Unsigned32  ( 1 .. 4094  )   --960803
		MAX-ACCESS		read-create
		STATUS			current
		DESCRIPTION		""
		::=  {  bitSTORM-HP-160BportVlanRateLimitEntry  4  }


	bitSTORM-HP-160BportVlanRateLimitIfcIndex	OBJECT-TYPE
		SYNTAX			Unsigned32  ( 1 .. 219  )
		MAX-ACCESS		read-create
		STATUS			current
		DESCRIPTION		""
		::=  {  bitSTORM-HP-160BportVlanRateLimitEntry  5  }

	bitSTORM-HP-160BportVlanRateLimitRowStatus	OBJECT-TYPE
		SYNTAX			RowStatus
		MAX-ACCESS		read-create
		STATUS			current
		DESCRIPTION		""
		::=  {  bitSTORM-HP-160BportVlanRateLimitEntry  6  }








	bitSTORM-HP-160BportPortBcRateLimitTable	OBJECT-TYPE
		SYNTAX		SEQUENCE  OF  BITSTORM-HP-160BportPortBcRateLimitEntry
		MAX-ACCESS	not-accessible
		STATUS		current
		DESCRIPTION	""
		::=  { bitSTORM-HP-160CfgRateLimitGroup  6 }

	bitSTORM-HP-160BportPortBcRateLimitEntry	OBJECT-TYPE
		SYNTAX		BITSTORM-HP-160BportPortBcRateLimitEntry
		MAX-ACCESS	not-accessible
		STATUS		current
		DESCRIPTION	""
		INDEX		{  bitSTORM-HP-160bcRateBridgePortIfcIndex  }
		::=  { bitSTORM-HP-160BportPortBcRateLimitTable 1 }

	BITSTORM-HP-160BportPortBcRateLimitEntry  ::=  SEQUENCE {
		bitSTORM-HP-160bcRateBridgePortIfcIndex  Integer32,
		bitSTORM-HP-160bcRateLimitIngressIwPolicerIdx  Integer32
		}

	bitSTORM-HP-160bcRateBridgePortIfcIndex	OBJECT-TYPE
		SYNTAX			Integer32  ( 1 .. 219  )
		MAX-ACCESS		not-accessible
		STATUS			current
		DESCRIPTION		""
		::=  {  bitSTORM-HP-160BportPortBcRateLimitEntry  1  }


	bitSTORM-HP-160bcRateLimitIngressIwPolicerIdx	OBJECT-TYPE
		SYNTAX			Integer32  ( 1 .. 128  )
		MAX-ACCESS		read-write
		STATUS			current
		DESCRIPTION		""
		::=  {  bitSTORM-HP-160BportPortBcRateLimitEntry  2  }






--
	bitSTORM-HP-160BportVlanTranslationTable	OBJECT-TYPE
		SYNTAX		SEQUENCE  OF  BITSTORM-HP-160BportVlanTranslationEntry
		MAX-ACCESS	not-accessible
		STATUS		current
		DESCRIPTION	""
		::=  { bitSTORM-HP-160CfgVlanGroup  8 }

	bitSTORM-HP-160BportVlanTranslationEntry	OBJECT-TYPE
		SYNTAX		BITSTORM-HP-160BportVlanTranslationEntry
		MAX-ACCESS	not-accessible
		STATUS		current
		DESCRIPTION	""
		INDEX		{  bitSTORM-HP-160BportVlanTranslationIndex  }
		::=  { bitSTORM-HP-160BportVlanTranslationTable 1 }

	BITSTORM-HP-160BportVlanTranslationEntry  ::=  SEQUENCE {
		bitSTORM-HP-160BportVlanTranslationIndex  Integer32,        --1..512
		bitSTORM-HP-160BportVlanTranslationUserPort  Integer32,    --4..219
		bitSTORM-HP-160BportVlanTranslationUserVlanId  Integer32,   --1..4094
		bitSTORM-HP-160BportVlanTranslationUplinkPort  Integer32,   --1..3
		bitSTORM-HP-160BportVlanTranslationUplinkVlanId  Integer32,  --1..4094
		bitSTORM-HP-160BportVlanTranslationUplinkPriority  Integer32,  --0..7
		bitSTORM-HP-160BportVlanTranslationRowStatus  RowStatus
		}

	bitSTORM-HP-160BportVlanTranslationIndex	OBJECT-TYPE
		SYNTAX			Integer32  ( 1 .. 512  )
		MAX-ACCESS		not-accessible
		STATUS			current
		DESCRIPTION		""
		::=  {  bitSTORM-HP-160BportVlanTranslationEntry  1  }


	bitSTORM-HP-160BportVlanTranslationUserPort	OBJECT-TYPE
		SYNTAX			Integer32  ( 4 .. 219 )
		MAX-ACCESS		read-create
		STATUS			current
		DESCRIPTION		""
		::=  {  bitSTORM-HP-160BportVlanTranslationEntry  2  }


	bitSTORM-HP-160BportVlanTranslationUserVlanId	OBJECT-TYPE
		SYNTAX			Integer32  ( 1 .. 4094  )
		MAX-ACCESS		read-create
		STATUS			current
		DESCRIPTION		""
		::=  {  bitSTORM-HP-160BportVlanTranslationEntry  3  }

	bitSTORM-HP-160BportVlanTranslationUplinkPort	OBJECT-TYPE
		SYNTAX			Integer32  ( 1 .. 3  )
		MAX-ACCESS		read-create
		STATUS			current
		DESCRIPTION		""
		::=  {  bitSTORM-HP-160BportVlanTranslationEntry  4  }


	bitSTORM-HP-160BportVlanTranslationUplinkVlanId	OBJECT-TYPE
		SYNTAX			Integer32  ( 1 .. 4094  )
		MAX-ACCESS		read-create
		STATUS			current
		DESCRIPTION		""
		::=  {  bitSTORM-HP-160BportVlanTranslationEntry  5  }

	bitSTORM-HP-160BportVlanTranslationUplinkPriority	OBJECT-TYPE
		SYNTAX			Integer32  ( 0 .. 7  )
		MAX-ACCESS		read-create
		STATUS			current
		DESCRIPTION		""
		::=  {  bitSTORM-HP-160BportVlanTranslationEntry  6  }

	bitSTORM-HP-160BportVlanTranslationRowStatus	OBJECT-TYPE
		SYNTAX			RowStatus
		MAX-ACCESS		read-create
		STATUS			current
		DESCRIPTION		""
		::=  {  bitSTORM-HP-160BportVlanTranslationEntry  7  }
--

	bitSTORM-HP-160CfgBridgeTosVpmtFilterTable	OBJECT-TYPE
		SYNTAX		SEQUENCE  OF  BITSTORM-HP-160CfgBridgeTosVpmtFilterEntry
		MAX-ACCESS	not-accessible
		STATUS		current
		DESCRIPTION	"The TOS filter configuration table."
		::=  { bitSTORM-HP-160CfgVlanPriorityGroup  1 }

	bitSTORM-HP-160CfgBridgeTosVpmtFilterEntry	OBJECT-TYPE
		SYNTAX		BITSTORM-HP-160CfgBridgeTosVpmtFilterEntry
		MAX-ACCESS	not-accessible
		STATUS		current
		DESCRIPTION	"An Entry in the bitSTORM-HP-160CfgBridgeTosVpmtFilterTable"
		INDEX		{  bitSTORM-HP-160CfgBridgeTosVpmtFilterIndex  }
		::=  { bitSTORM-HP-160CfgBridgeTosVpmtFilterTable 1 }

	BITSTORM-HP-160CfgBridgeTosVpmtFilterEntry  ::=  SEQUENCE {
		bitSTORM-HP-160CfgBridgeTosVpmtFilterIndex  Integer32,
		bitSTORM-HP-160CfgBridgeTosVpmtFilterInputBridgePort  InterfaceIndex,
		bitSTORM-HP-160CfgBridgeTosVpmtFilterIncomingTos  Integer32,
		bitSTORM-HP-160CfgBridgeTosVpmtFilterOutgoingVlanPriority  Integer32,
		bitSTORM-HP-160CfgBridgeTosVpmtFilterRowStatus  RowStatus
		}


	bitSTORM-HP-160CfgBridgeTosVpmtFilterIndex	OBJECT-TYPE	
		SYNTAX			Integer32
		MAX-ACCESS		read-only
		STATUS			current
		DESCRIPTION		""
		::=  {  bitSTORM-HP-160CfgBridgeTosVpmtFilterEntry  1  }


	bitSTORM-HP-160CfgBridgeTosVpmtFilterInputBridgePort	OBJECT-TYPE	
		SYNTAX			InterfaceIndex
		MAX-ACCESS		read-create
		STATUS			current
		DESCRIPTION		""
		::=  {  bitSTORM-HP-160CfgBridgeTosVpmtFilterEntry  2  }


	bitSTORM-HP-160CfgBridgeTosVpmtFilterIncomingTos	OBJECT-TYPE	
		SYNTAX			Integer32  ( 0 .. 7  ) 
		MAX-ACCESS		read-create
		STATUS			current
		DESCRIPTION		""
		::=  {  bitSTORM-HP-160CfgBridgeTosVpmtFilterEntry  3  }


	bitSTORM-HP-160CfgBridgeTosVpmtFilterOutgoingVlanPriority	OBJECT-TYPE	
		SYNTAX			Integer32  ( 0 .. 7  ) 
		MAX-ACCESS		read-create
		STATUS			current
		DESCRIPTION		""
		::=  {  bitSTORM-HP-160CfgBridgeTosVpmtFilterEntry  4  }


	bitSTORM-HP-160CfgBridgeTosVpmtFilterRowStatus	OBJECT-TYPE	
		SYNTAX			RowStatus
		MAX-ACCESS		read-create
		STATUS			current
		DESCRIPTION		""
		::=  {  bitSTORM-HP-160CfgBridgeTosVpmtFilterEntry  5  }

	bitSTORM-HP-160CfgBridgeDSVpmtFilterTable	OBJECT-TYPE
		SYNTAX		SEQUENCE  OF  BITSTORM-HP-160CfgBridgeDSVpmtFilterEntry
		MAX-ACCESS	not-accessible
		STATUS		current
		DESCRIPTION	"The DS filter configuration table."
		::=  { bitSTORM-HP-160CfgVlanPriorityGroup  2 }

	bitSTORM-HP-160CfgBridgeDSVpmtFilterEntry	OBJECT-TYPE
		SYNTAX		BITSTORM-HP-160CfgBridgeDSVpmtFilterEntry
		MAX-ACCESS	not-accessible
		STATUS		current
		DESCRIPTION	"An Entry in the bitSTORM-HP-160CfgBridgeDSVpmtFilterTable"
		INDEX		{  bitSTORM-HP-160CfgBridgeDSVpmtFilterIndex  }
		::=  { bitSTORM-HP-160CfgBridgeDSVpmtFilterTable 1 }

	BITSTORM-HP-160CfgBridgeDSVpmtFilterEntry  ::=  SEQUENCE {
		bitSTORM-HP-160CfgBridgeDSVpmtFilterIndex  Integer32,
		bitSTORM-HP-160CfgBridgeDSVpmtFilterInputBridgePort  InterfaceIndex,
		bitSTORM-HP-160CfgBridgeDSVpmtFilterIncomingDS  Integer32,
		bitSTORM-HP-160CfgBridgeDSVpmtFilterOutgoingVlanPriority  Integer32,
		bitSTORM-HP-160CfgBridgeDSVpmtFilterRowStatus  RowStatus
		}


	bitSTORM-HP-160CfgBridgeDSVpmtFilterIndex	OBJECT-TYPE	
		SYNTAX			Integer32  (1..256)
		MAX-ACCESS		read-only
		STATUS			current
		DESCRIPTION		""
		::=  {  bitSTORM-HP-160CfgBridgeDSVpmtFilterEntry  1  }


	bitSTORM-HP-160CfgBridgeDSVpmtFilterInputBridgePort	OBJECT-TYPE
		SYNTAX			InterfaceIndex
		MAX-ACCESS		read-create
		STATUS			current
		DESCRIPTION		""
		::=  {  bitSTORM-HP-160CfgBridgeDSVpmtFilterEntry  2  }


	bitSTORM-HP-160CfgBridgeDSVpmtFilterIncomingDS	OBJECT-TYPE	
		SYNTAX			Integer32 {
                     diffserv-default(0),
                     diffserv-af11(10),
                     diffserv-af12(12),
                     diffserv-af13(14),
                     diffserv-af21(18),
                     diffserv-af22(20),
                     diffserv-af23(22),
                     diffserv-af31(26),
                     diffserv-af32(28),
                     diffserv-af33(30),
                     diffserv-af41(34),
                     diffserv-af42(36),
                     diffserv-af43(38),
                     diffserv-ef(46)
                     }
		MAX-ACCESS		read-create
		STATUS			current
		DESCRIPTION		"
                     DIFFSERV-DEFAULT(0)
                     DIFFSERV-AF11(10)
                     DIFFSERV-AF12(12)
                     DIFFSERV-AF13(14)
                     DIFFSERV-AF21(18)
                     DIFFSERV-AF22(20)
                     DIFFSERV-AF23(22)
                     DIFFSERV-AF31(26)
                     DIFFSERV-AF32(28)
                     DIFFSERV-AF33(30)
                     DIFFSERV-AF41(34)
                     DIFFSERV-AF42(36)
                     DIFFSERV-AF43(38)
                     DIFFSERV-EF(46)
		"
		::=  {  bitSTORM-HP-160CfgBridgeDSVpmtFilterEntry  3  }


	bitSTORM-HP-160CfgBridgeDSVpmtFilterOutgoingVlanPriority	OBJECT-TYPE	
		SYNTAX			Integer32  ( 0 .. 7  ) 
		MAX-ACCESS		read-create
		STATUS			current
		DESCRIPTION		""
		::=  {  bitSTORM-HP-160CfgBridgeDSVpmtFilterEntry  4  }


	bitSTORM-HP-160CfgBridgeDSVpmtFilterRowStatus	OBJECT-TYPE	
		SYNTAX			RowStatus
		MAX-ACCESS		read-create
		STATUS			current
		DESCRIPTION		""
		::=  {  bitSTORM-HP-160CfgBridgeDSVpmtFilterEntry  5  }

	bitSTORM-HP-160CfgBridgeIpSrcVpmtFilterTable	OBJECT-TYPE
		SYNTAX		SEQUENCE  OF  BITSTORM-HP-160CfgBridgeIpSrcVpmtFilterEntry
		MAX-ACCESS	not-accessible
		STATUS		current
		DESCRIPTION	"The IP src filter configuration table."
		::=  { bitSTORM-HP-160CfgVlanPriorityGroup  3 }

	bitSTORM-HP-160CfgBridgeIpSrcVpmtFilterEntry	OBJECT-TYPE
		SYNTAX		BITSTORM-HP-160CfgBridgeIpSrcVpmtFilterEntry
		MAX-ACCESS	not-accessible
		STATUS		current
		DESCRIPTION	"An Entry in the bitSTORM-HP-160CfgBridgeIpSrcVpmtFilterTable"
		INDEX		{  bitSTORM-HP-160CfgBridgeIpSrcVpmtFilterIndex  }
		::=  { bitSTORM-HP-160CfgBridgeIpSrcVpmtFilterTable 1 }

	BITSTORM-HP-160CfgBridgeIpSrcVpmtFilterEntry  ::=  SEQUENCE {
		bitSTORM-HP-160CfgBridgeIpSrcVpmtFilterIndex  Integer32,
		bitSTORM-HP-160CfgBridgeIpSrcVpmtFilterInputBridgePort  InterfaceIndex,
		bitSTORM-HP-160CfgBridgeIpSrcVpmtFilterIncomingIpsrcstart  IpAddress,
		bitSTORM-HP-160CfgBridgeIpSrcVpmtFilterIncomingIpsrcend  IpAddress,
		bitSTORM-HP-160CfgBridgeIpSrcVpmtFilterOutgoingVlanPriority  Integer32,
		bitSTORM-HP-160CfgBridgeIpSrcVpmtFilterRowStatus  RowStatus
		}


	bitSTORM-HP-160CfgBridgeIpSrcVpmtFilterIndex	OBJECT-TYPE	
		SYNTAX			Integer32
		MAX-ACCESS		read-only
		STATUS			current
		DESCRIPTION		""
		::=  {  bitSTORM-HP-160CfgBridgeIpSrcVpmtFilterEntry  1  }


	bitSTORM-HP-160CfgBridgeIpSrcVpmtFilterInputBridgePort	OBJECT-TYPE	
		SYNTAX			InterfaceIndex
		MAX-ACCESS		read-create
		STATUS			current
		DESCRIPTION		""
		::=  {  bitSTORM-HP-160CfgBridgeIpSrcVpmtFilterEntry  2  }


	bitSTORM-HP-160CfgBridgeIpSrcVpmtFilterIncomingIpsrcstart	OBJECT-TYPE	
		SYNTAX			IpAddress
		MAX-ACCESS		read-create
		STATUS			current
		DESCRIPTION		""
		::=  {  bitSTORM-HP-160CfgBridgeIpSrcVpmtFilterEntry  3  }


	bitSTORM-HP-160CfgBridgeIpSrcVpmtFilterIncomingIpsrcend	OBJECT-TYPE	
		SYNTAX			IpAddress
		MAX-ACCESS		read-create
		STATUS			current
		DESCRIPTION		""
		::=  {  bitSTORM-HP-160CfgBridgeIpSrcVpmtFilterEntry  4  }


	bitSTORM-HP-160CfgBridgeIpSrcVpmtFilterOutgoingVlanPriority	OBJECT-TYPE	
		SYNTAX			Integer32  ( 0 .. 7  ) 
		MAX-ACCESS		read-create
		STATUS			current
		DESCRIPTION		""
		::=  {  bitSTORM-HP-160CfgBridgeIpSrcVpmtFilterEntry  5  }


	bitSTORM-HP-160CfgBridgeIpSrcVpmtFilterRowStatus	OBJECT-TYPE	
		SYNTAX			RowStatus
		MAX-ACCESS		read-create
		STATUS			current
		DESCRIPTION		""
		::=  {  bitSTORM-HP-160CfgBridgeIpSrcVpmtFilterEntry  6  }

	bitSTORM-HP-160CfgBridgeIpDstVpmtFilterTable	OBJECT-TYPE
		SYNTAX		SEQUENCE  OF  BITSTORM-HP-160CfgBridgeIpDstVpmtFilterEntry
		MAX-ACCESS	not-accessible
		STATUS		current
		DESCRIPTION	"The IP dst filter configuration table."
		::=  { bitSTORM-HP-160CfgVlanPriorityGroup  4 }

	bitSTORM-HP-160CfgBridgeIpDstVpmtFilterEntry	OBJECT-TYPE
		SYNTAX		BITSTORM-HP-160CfgBridgeIpDstVpmtFilterEntry
		MAX-ACCESS	not-accessible
		STATUS		current
		DESCRIPTION	"An Entry in the bitSTORM-HP-160CfgBridgeIpDstVpmtFilterTable"
		INDEX		{  bitSTORM-HP-160CfgBridgeIpDstVpmtFilterIndex  }
		::=  { bitSTORM-HP-160CfgBridgeIpDstVpmtFilterTable 1 }

	BITSTORM-HP-160CfgBridgeIpDstVpmtFilterEntry  ::=  SEQUENCE {
		bitSTORM-HP-160CfgBridgeIpDstVpmtFilterIndex  Integer32,
		bitSTORM-HP-160CfgBridgeIpDstVpmtFilterInputBridgePort  InterfaceIndex,
		bitSTORM-HP-160CfgBridgeIpDstVpmtFilterIncomingIpDststart  IpAddress,
		bitSTORM-HP-160CfgBridgeIpDstVpmtFilterIncomingIpDstend  IpAddress,
		bitSTORM-HP-160CfgBridgeIpDstVpmtFilterOutgoingVlanPriority  Integer32,
		bitSTORM-HP-160CfgBridgeIpDstVpmtFilterRowStatus  RowStatus
		}


	bitSTORM-HP-160CfgBridgeIpDstVpmtFilterIndex	OBJECT-TYPE	
		SYNTAX			Integer32
		MAX-ACCESS		read-only
		STATUS			current
		DESCRIPTION		""
		::=  {  bitSTORM-HP-160CfgBridgeIpDstVpmtFilterEntry  1  }


	bitSTORM-HP-160CfgBridgeIpDstVpmtFilterInputBridgePort	OBJECT-TYPE	
		SYNTAX			InterfaceIndex
		MAX-ACCESS		read-create
		STATUS			current
		DESCRIPTION		""
		::=  {  bitSTORM-HP-160CfgBridgeIpDstVpmtFilterEntry  2  }


	bitSTORM-HP-160CfgBridgeIpDstVpmtFilterIncomingIpDststart	OBJECT-TYPE	
		SYNTAX			IpAddress
		MAX-ACCESS		read-create
		STATUS			current
		DESCRIPTION		""
		::=  {  bitSTORM-HP-160CfgBridgeIpDstVpmtFilterEntry  3  }


	bitSTORM-HP-160CfgBridgeIpDstVpmtFilterIncomingIpDstend	OBJECT-TYPE	
		SYNTAX			IpAddress
		MAX-ACCESS		read-create
		STATUS			current
		DESCRIPTION		""
		::=  {  bitSTORM-HP-160CfgBridgeIpDstVpmtFilterEntry  4  }


	bitSTORM-HP-160CfgBridgeIpDstVpmtFilterOutgoingVlanPriority	OBJECT-TYPE	
		SYNTAX			Integer32  ( 0 .. 7  ) 
		MAX-ACCESS		read-create
		STATUS			current
		DESCRIPTION		""
		::=  {  bitSTORM-HP-160CfgBridgeIpDstVpmtFilterEntry  5  }


	bitSTORM-HP-160CfgBridgeIpDstVpmtFilterRowStatus	OBJECT-TYPE	
		SYNTAX			RowStatus
		MAX-ACCESS		read-create
		STATUS			current
		DESCRIPTION		""
		::=  {  bitSTORM-HP-160CfgBridgeIpDstVpmtFilterEntry  6  }

	bitSTORM-HP-160CfgBridgeMacSrcVpmtFilterTable	OBJECT-TYPE
		SYNTAX		SEQUENCE  OF  BITSTORM-HP-160CfgBridgeMacSrcVpmtFilterEntry
		MAX-ACCESS	not-accessible
		STATUS		current
		DESCRIPTION	"The MAC src filter configuration table."
		::=  { bitSTORM-HP-160CfgVlanPriorityGroup  5 }

	bitSTORM-HP-160CfgBridgeMacSrcVpmtFilterEntry	OBJECT-TYPE
		SYNTAX		BITSTORM-HP-160CfgBridgeMacSrcVpmtFilterEntry
		MAX-ACCESS	not-accessible
		STATUS		current
		DESCRIPTION	"An Entry in the bitSTORM-HP-160CfgBridgeMacSrcVpmtFilterTable"
		INDEX		{  bitSTORM-HP-160CfgBridgeMacSrcVpmtFilterIndex  }
		::=  { bitSTORM-HP-160CfgBridgeMacSrcVpmtFilterTable 1 }

	BITSTORM-HP-160CfgBridgeMacSrcVpmtFilterEntry  ::=  SEQUENCE {
		bitSTORM-HP-160CfgBridgeMacSrcVpmtFilterIndex  Integer32,
		bitSTORM-HP-160CfgBridgeMacSrcVpmtFilterInputBridgePort  InterfaceIndex,
		bitSTORM-HP-160CfgBridgeMacSrcVpmtFilterIncomingMacsrc  PhysAddress,
		bitSTORM-HP-160CfgBridgeMacSrcVpmtFilterOutgoingVlanPriority  Integer32,
		bitSTORM-HP-160CfgBridgeMacSrcVpmtFilterRowStatus  RowStatus
		}


	bitSTORM-HP-160CfgBridgeMacSrcVpmtFilterIndex	OBJECT-TYPE	
		SYNTAX			Integer32
		MAX-ACCESS		read-only
		STATUS			current
		DESCRIPTION		""
		::=  {  bitSTORM-HP-160CfgBridgeMacSrcVpmtFilterEntry  1  }


	bitSTORM-HP-160CfgBridgeMacSrcVpmtFilterInputBridgePort	OBJECT-TYPE	
		SYNTAX			InterfaceIndex
		MAX-ACCESS		read-create
		STATUS			current
		DESCRIPTION		""
		::=  {  bitSTORM-HP-160CfgBridgeMacSrcVpmtFilterEntry  2  }


	bitSTORM-HP-160CfgBridgeMacSrcVpmtFilterIncomingMacsrc	OBJECT-TYPE	
		SYNTAX			PhysAddress
		MAX-ACCESS		read-create
		STATUS			current
		DESCRIPTION		""
		::=  {  bitSTORM-HP-160CfgBridgeMacSrcVpmtFilterEntry  3  }


	bitSTORM-HP-160CfgBridgeMacSrcVpmtFilterOutgoingVlanPriority	OBJECT-TYPE	
		SYNTAX			Integer32  ( 0 .. 7  ) 
		MAX-ACCESS		read-create
		STATUS			current
		DESCRIPTION		""
		::=  {  bitSTORM-HP-160CfgBridgeMacSrcVpmtFilterEntry  4  }


	bitSTORM-HP-160CfgBridgeMacSrcVpmtFilterRowStatus	OBJECT-TYPE	
		SYNTAX			RowStatus
		MAX-ACCESS		read-create
		STATUS			current
		DESCRIPTION		""
		::=  {  bitSTORM-HP-160CfgBridgeMacSrcVpmtFilterEntry  5  }

	bitSTORM-HP-160CfgBridgeMacDstVpmtFilterTable	OBJECT-TYPE
		SYNTAX		SEQUENCE  OF  BITSTORM-HP-160CfgBridgeMacDstVpmtFilterEntry
		MAX-ACCESS	not-accessible
		STATUS		current
		DESCRIPTION	"The MAC dst filter configuration table."
		::=  { bitSTORM-HP-160CfgVlanPriorityGroup  6 }

	bitSTORM-HP-160CfgBridgeMacDstVpmtFilterEntry	OBJECT-TYPE
		SYNTAX		BITSTORM-HP-160CfgBridgeMacDstVpmtFilterEntry
		MAX-ACCESS	not-accessible
		STATUS		current
		DESCRIPTION	"An Entry in the bitSTORM-HP-160CfgBridgeMacDstVpmtFilterTable"
		INDEX		{  bitSTORM-HP-160CfgBridgeMacDstVpmtFilterIndex  }
		::=  { bitSTORM-HP-160CfgBridgeMacDstVpmtFilterTable 1 }

	BITSTORM-HP-160CfgBridgeMacDstVpmtFilterEntry  ::=  SEQUENCE {
		bitSTORM-HP-160CfgBridgeMacDstVpmtFilterIndex  Integer32,
		bitSTORM-HP-160CfgBridgeMacDstVpmtFilterInputBridgePort  InterfaceIndex,
		bitSTORM-HP-160CfgBridgeMacDstVpmtFilterIncomingMacDst  PhysAddress,
		bitSTORM-HP-160CfgBridgeMacDstVpmtFilterOutgoingVlanPriority  Integer32,
		bitSTORM-HP-160CfgBridgeMacDstVpmtFilterRowStatus  RowStatus
		}


	bitSTORM-HP-160CfgBridgeMacDstVpmtFilterIndex	OBJECT-TYPE	
		SYNTAX			Integer32
		MAX-ACCESS		read-only
		STATUS			current
		DESCRIPTION		""
		::=  {  bitSTORM-HP-160CfgBridgeMacDstVpmtFilterEntry  1  }


	bitSTORM-HP-160CfgBridgeMacDstVpmtFilterInputBridgePort	OBJECT-TYPE	
		SYNTAX			InterfaceIndex
		MAX-ACCESS		read-create
		STATUS			current
		DESCRIPTION		""
		::=  {  bitSTORM-HP-160CfgBridgeMacDstVpmtFilterEntry  2  }


	bitSTORM-HP-160CfgBridgeMacDstVpmtFilterIncomingMacDst	OBJECT-TYPE	
		SYNTAX			PhysAddress
		MAX-ACCESS		read-create
		STATUS			current
		DESCRIPTION		""
		::=  {  bitSTORM-HP-160CfgBridgeMacDstVpmtFilterEntry  3  }


	bitSTORM-HP-160CfgBridgeMacDstVpmtFilterOutgoingVlanPriority	OBJECT-TYPE	
		SYNTAX			Integer32  ( 0 .. 7  ) 
		MAX-ACCESS		read-create
		STATUS			current
		DESCRIPTION		""
		::=  {  bitSTORM-HP-160CfgBridgeMacDstVpmtFilterEntry  4  }


	bitSTORM-HP-160CfgBridgeMacDstVpmtFilterRowStatus	OBJECT-TYPE	
		SYNTAX			RowStatus
		MAX-ACCESS		read-create
		STATUS			current
		DESCRIPTION		""
		::=  {  bitSTORM-HP-160CfgBridgeMacDstVpmtFilterEntry  5  }

	bitSTORM-HP-160CfgBridgeVlanIdVpmtFilterTable	OBJECT-TYPE
		SYNTAX		SEQUENCE  OF  BITSTORM-HP-160CfgBridgeVlanIdVpmtFilterEntry
		MAX-ACCESS	not-accessible
		STATUS		current
		DESCRIPTION	"The Vlan ID filter configuration table."
		::=  { bitSTORM-HP-160CfgVlanPriorityGroup  7 }

	bitSTORM-HP-160CfgBridgeVlanIdVpmtFilterEntry	OBJECT-TYPE
		SYNTAX		BITSTORM-HP-160CfgBridgeVlanIdVpmtFilterEntry
		MAX-ACCESS	not-accessible
		STATUS		current
		DESCRIPTION	"An Entry in the bitSTORM-HP-160CfgBridgeVlanIdVpmtFilterTable"
		INDEX		{  bitSTORM-HP-160CfgBridgeVlanIdVpmtFilterIndex  }
		::=  { bitSTORM-HP-160CfgBridgeVlanIdVpmtFilterTable 1 }

	BITSTORM-HP-160CfgBridgeVlanIdVpmtFilterEntry  ::=  SEQUENCE {
		bitSTORM-HP-160CfgBridgeVlanIdVpmtFilterIndex  Integer32,
		bitSTORM-HP-160CfgBridgeVlanIdVpmtFilterInputBridgePort  InterfaceIndex,
		bitSTORM-HP-160CfgBridgeVlanIdVpmtFilterIncomingVlanid  Integer32,
		bitSTORM-HP-160CfgBridgeVlanIdVpmtFilterOutgoingVlanPriority  Integer32,
		bitSTORM-HP-160CfgBridgeVlanIdVpmtFilterRowStatus  RowStatus
		}


	bitSTORM-HP-160CfgBridgeVlanIdVpmtFilterIndex	OBJECT-TYPE	
		SYNTAX			Integer32
		MAX-ACCESS		read-only
		STATUS			current
		DESCRIPTION		""
		::=  {  bitSTORM-HP-160CfgBridgeVlanIdVpmtFilterEntry  1  }


	bitSTORM-HP-160CfgBridgeVlanIdVpmtFilterInputBridgePort	OBJECT-TYPE	
		SYNTAX			InterfaceIndex
		MAX-ACCESS		read-create
		STATUS			current
		DESCRIPTION		""
		::=  {  bitSTORM-HP-160CfgBridgeVlanIdVpmtFilterEntry  2  }


	bitSTORM-HP-160CfgBridgeVlanIdVpmtFilterIncomingVlanid	OBJECT-TYPE	
		SYNTAX			Integer32  ( 0 .. 4094  )   --960803 
		MAX-ACCESS		read-create
		STATUS			current
		DESCRIPTION		""
		::=  {  bitSTORM-HP-160CfgBridgeVlanIdVpmtFilterEntry  3  }


	bitSTORM-HP-160CfgBridgeVlanIdVpmtFilterOutgoingVlanPriority	OBJECT-TYPE	
		SYNTAX			Integer32  ( 0 .. 7  ) 
		MAX-ACCESS		read-create
		STATUS			current
		DESCRIPTION		""
		::=  {  bitSTORM-HP-160CfgBridgeVlanIdVpmtFilterEntry  4  }


	bitSTORM-HP-160CfgBridgeVlanIdVpmtFilterRowStatus	OBJECT-TYPE	
		SYNTAX			RowStatus
		MAX-ACCESS		read-create
		STATUS			current
		DESCRIPTION		""
		::=  {  bitSTORM-HP-160CfgBridgeVlanIdVpmtFilterEntry  5  }
		
		
		
		
		
	bitSTORM-HP-160CfgBridgePrioTagFilterTable	OBJECT-TYPE
		SYNTAX		SEQUENCE  OF  BITSTORM-HP-160CfgBridgePrioTagFilterEntry
		MAX-ACCESS	not-accessible
		STATUS		current
		DESCRIPTION	""
		::=  { bitSTORM-HP-160CfgVlanPriorityGroup  8 }

	bitSTORM-HP-160CfgBridgePrioTagFilterEntry	OBJECT-TYPE
		SYNTAX		BITSTORM-HP-160CfgBridgePrioTagFilterEntry
		MAX-ACCESS	not-accessible
		STATUS		current
		DESCRIPTION	""
		INDEX		{  bitSTORM-HP-160BridgePrioTagFilterIndex  }
		::=  { bitSTORM-HP-160CfgBridgePrioTagFilterTable 1 }

	BITSTORM-HP-160CfgBridgePrioTagFilterEntry  ::=  SEQUENCE {
		bitSTORM-HP-160BridgePrioTagFilterIndex  Integer32,
		bitSTORM-HP-160BridgePrioTagInputBridgePort  InterfaceIndex,
		bitSTORM-HP-160BridgePrioTagOutgoingVlanPriority  Integer32,
		bitSTORM-HP-160BridgePrioTagIncomingVlanPriority  Integer32,
		bitSTORM-HP-160BridgePrioTagFilterRowStatus  RowStatus
		}


	bitSTORM-HP-160BridgePrioTagFilterIndex	OBJECT-TYPE	
		SYNTAX			Integer32  ( 1 .. 4095  ) 
		MAX-ACCESS		read-only
		STATUS			current
		DESCRIPTION		""
		::=  {  bitSTORM-HP-160CfgBridgePrioTagFilterEntry  1  }


	bitSTORM-HP-160BridgePrioTagInputBridgePort	OBJECT-TYPE	
		SYNTAX			InterfaceIndex
		MAX-ACCESS		read-create
		STATUS			current
		DESCRIPTION		""
		::=  {  bitSTORM-HP-160CfgBridgePrioTagFilterEntry  2  }


	bitSTORM-HP-160BridgePrioTagOutgoingVlanPriority	OBJECT-TYPE	
		SYNTAX			Integer32  ( 0 .. 7  ) 
		MAX-ACCESS		read-create
		STATUS			current
		DESCRIPTION		""
		DEFVAL			{ 0 }
		::=  {  bitSTORM-HP-160CfgBridgePrioTagFilterEntry  3  }


	bitSTORM-HP-160BridgePrioTagIncomingVlanPriority	OBJECT-TYPE	
		SYNTAX			Integer32  ( 0 .. 7  ) 
		MAX-ACCESS		read-create
		STATUS			current
		DESCRIPTION		""
		DEFVAL			{ 0 }
		::=  {  bitSTORM-HP-160CfgBridgePrioTagFilterEntry  4  }


	bitSTORM-HP-160BridgePrioTagFilterRowStatus	OBJECT-TYPE	
		SYNTAX			RowStatus
		MAX-ACCESS		read-create
		STATUS			current
		DESCRIPTION		""
		DEFVAL			{ createAndGo }
		::=  {  bitSTORM-HP-160CfgBridgePrioTagFilterEntry  5  }



		

	bitSTORM-HP-160CfgIgmpSourceGroupIp	OBJECT-TYPE
		SYNTAX			IpAddress
		MAX-ACCESS		read-write
		STATUS			current
		DESCRIPTION		""
		::=  {  bitSTORM-HP-160CfgIgmpSource  1  }

	bitSTORM-HP-160CfgIgmpSourceGroupVlan	OBJECT-TYPE	
		SYNTAX			Integer32  ( 1 .. 4094  )   --960803
		MAX-ACCESS		read-write
		STATUS			current
		DESCRIPTION		""
		::=  {  bitSTORM-HP-160CfgIgmpSource  2  }




	bitSTORM-HP-160TrapAlmSystemHousekeep1	NOTIFICATION-TYPE
		STATUS			current
		DESCRIPTION		"DSLAM system housekeeping1 trap."
		::=  {  bitSTORM-HP-160SystemAlarmTrap  1  }

	bitSTORM-HP-160TrapAlmSystemHousekeep2	NOTIFICATION-TYPE
		STATUS			current
		DESCRIPTION		"DSLAM system housekeeping2 trap."
		::=  {  bitSTORM-HP-160SystemAlarmTrap  2  }

	bitSTORM-HP-160TrapAlmSystemHousekeep3	NOTIFICATION-TYPE
		STATUS			current
		DESCRIPTION		"DSLAM system housekeeping3 trap."
		::=  {  bitSTORM-HP-160SystemAlarmTrap  3  }

	bitSTORM-HP-160TrapAlmSystemHousekeep4	NOTIFICATION-TYPE
		STATUS			current
		DESCRIPTION		"DSLAM system housekeeping4 trap."
		::=  {  bitSTORM-HP-160SystemAlarmTrap  4  }

	bitSTORM-HP-160TrapAlmSystemFanFailure	NOTIFICATION-TYPE
		STATUS			current
		DESCRIPTION		"DSLAM fan failure alarm trap."
		::=  {  bitSTORM-HP-160SystemAlarmTrap  5  }

	bitSTORM-HP-160TrapAlmSystemSelfTestTestFail	NOTIFICATION-TYPE
		STATUS			current
		DESCRIPTION		"DSLAM system module test fail trap."
		::=  {  bitSTORM-HP-160SystemAlarmTrap  6  }

	bitSTORM-HP-160TrapAlmSystemAboveTemperature	NOTIFICATION-TYPE
		STATUS			current
		DESCRIPTION		"The current temperature exceeds bitSTORM-HP-160SysTemperatureUpShfThreshold."
		::=  {  bitSTORM-HP-160SystemAlarmTrap  7  }

	bitSTORM-HP-160TrapAlmSystemBelowTemperature	NOTIFICATION-TYPE
		STATUS			current
		DESCRIPTION		"The current temperature descends below to bitSTORM-HP-160SysTemperatureDwShfThreshold."
		::=  {  bitSTORM-HP-160SystemAlarmTrap  8  }


bitSTORM-HP-160TrapAlmVdslLOF   NOTIFICATION-TYPE
    OBJECTS {
                ifIndex
            }
    STATUS             current
    DESCRIPTION  "Loss of frame of the DSLAM VDSL interface."
   ::= { bitSTORM-HP-160VDSLAlarmTrap 1 }

bitSTORM-HP-160TrapAlmVdslLOS   NOTIFICATION-TYPE
    OBJECTS {
                ifIndex
            }
    STATUS             current
    DESCRIPTION  "Loss of signal of the DSLAM VDSL interface."
   ::= { bitSTORM-HP-160VDSLAlarmTrap 2 }

bitSTORM-HP-160TrapAlmVdslLOSQ   NOTIFICATION-TYPE
    OBJECTS {
                ifIndex
            }
    STATUS             current
    DESCRIPTION  "Loss of signal quality of the DSLAM VDSL interface."
   ::= { bitSTORM-HP-160VDSLAlarmTrap 3 }

bitSTORM-HP-160TrapAlmVdslLOL   NOTIFICATION-TYPE
    OBJECTS {
                ifIndex
            }
    STATUS             current
    DESCRIPTION  "Loss of link of the DSLAM VDSL interface."
   ::= { bitSTORM-HP-160VDSLAlarmTrap 4 }

bitSTORM-HP-160TrapAlmVdslInitFailure   NOTIFICATION-TYPE
    OBJECTS {
                ifIndex
            }
    STATUS             current
    DESCRIPTION  "VDSL Init Failure."
   ::= { bitSTORM-HP-160VDSLAlarmTrap 5 }



bitSTORM-HP-160TrapAlmVdslESE   NOTIFICATION-TYPE
    OBJECTS {
                ifIndex
            }
    STATUS             current
    DESCRIPTION  "VDSL Excessive Severely Errored Seconds of the VDSL interface."
   ::= { bitSTORM-HP-160VDSLAlarmTrap 8 }

bitSTORM-HP-160TrapAlmVdslNCDSlow   NOTIFICATION-TYPE
    OBJECTS {
                ifIndex
            }
    STATUS             current
    DESCRIPTION  "VDSL No Cell Delination on the slow channel"
   ::= { bitSTORM-HP-160VDSLAlarmTrap 9 }

bitSTORM-HP-160TrapAlmVdslLCDSlow   NOTIFICATION-TYPE
    OBJECTS {
                ifIndex
            }
    STATUS             current
    DESCRIPTION  "VDSL Loss of Cell Delination on the slow channel"
   ::= { bitSTORM-HP-160VDSLAlarmTrap 10 }
   
bitSTORM-HP-160TrapAlmVdslNCDFast   NOTIFICATION-TYPE
    OBJECTS {
                ifIndex
            }
    STATUS             current
    DESCRIPTION  "VDSL No Cell Delination on the fast channel"
   ::= { bitSTORM-HP-160VDSLAlarmTrap 11 }

bitSTORM-HP-160TrapAlmVdslLCDFast   NOTIFICATION-TYPE
    OBJECTS {
                ifIndex
            }
    STATUS             current
    DESCRIPTION  "VDSL Loss of Cell Delination on the fast channel"
   ::= { bitSTORM-HP-160VDSLAlarmTrap 12 }

bitSTORM-HP-160TrapAlmVdslLOFFE   NOTIFICATION-TYPE
    OBJECTS {
                ifIndex
            }
    STATUS             current
    DESCRIPTION  "Loss of frame in the downstream direction."
   ::= { bitSTORM-HP-160VDSLAlarmTrap 13 }

bitSTORM-HP-160TrapAlmVdslLOSFE   NOTIFICATION-TYPE
    OBJECTS {
                ifIndex
            }
    STATUS             current
    DESCRIPTION  "Loss of signal in the downstream direction."
   ::= { bitSTORM-HP-160VDSLAlarmTrap 14 }

bitSTORM-HP-160TrapAlmVdslLPRFE   NOTIFICATION-TYPE
    OBJECTS {
                ifIndex
            }
    STATUS             current
    DESCRIPTION  "Loss of power in the downstream direction."
   ::= { bitSTORM-HP-160VDSLAlarmTrap 15 }

bitSTORM-HP-160TrapAlmVdslLOSQFE   NOTIFICATION-TYPE
    OBJECTS {
                ifIndex
            }
    STATUS             current
    DESCRIPTION  "Loss of signal quality in the downstream direction."
   ::= { bitSTORM-HP-160VDSLAlarmTrap 16 }

bitSTORM-HP-160TrapAlmVdslNoPeerVtuPresentFE   NOTIFICATION-TYPE
    OBJECTS {
                ifIndex
            }
    STATUS             current
    DESCRIPTION  "VDSL No Peer Vtu Present in the downstream direction."
   ::= { bitSTORM-HP-160VDSLAlarmTrap 17 }

bitSTORM-HP-160TrapAlmVdslESEFE   NOTIFICATION-TYPE
    OBJECTS {
                ifIndex
            }
    STATUS             current
    DESCRIPTION  "VDSL Excessive Severely Errored Seconds in the downstream direction."
   ::= { bitSTORM-HP-160VDSLAlarmTrap 18 }

bitSTORM-HP-160TrapAlmVdslNCDSlowFE   NOTIFICATION-TYPE
    OBJECTS {
                ifIndex
            }
    STATUS             current
    DESCRIPTION  "VDSL FE No Cell Delination on the slow channel"
   ::= { bitSTORM-HP-160VDSLAlarmTrap 19 }

bitSTORM-HP-160TrapAlmVdslLCDSlowFE   NOTIFICATION-TYPE
    OBJECTS {
                ifIndex
            }
    STATUS             current
    DESCRIPTION  "VDSL FE Loss of Cell Delination on the slow channel"
   ::= { bitSTORM-HP-160VDSLAlarmTrap 20 }
   
bitSTORM-HP-160TrapAlmVdslNCDFastFE   NOTIFICATION-TYPE
    OBJECTS {
                ifIndex
            }
    STATUS             current
    DESCRIPTION  "VDSL FE No Cell Delination on the fast channel"
   ::= { bitSTORM-HP-160VDSLAlarmTrap 21 }

bitSTORM-HP-160TrapAlmVdslLCDFastFE   NOTIFICATION-TYPE
    OBJECTS {
                ifIndex
            }
    STATUS             current
    DESCRIPTION  "VDSL FE Loss of Cell Delination on the fast channel"
   ::= { bitSTORM-HP-160VDSLAlarmTrap 22 }


END
