-- This file is corresponding to Release 6.1.2.100 from 2001/09/26 00:00:00
-- (C)opyright 1991-1999 BinTec Communications AG, All Rights Reserved
--  $RCSfile: mibdhcp,v $ 
-- $Revision: 1.6 $ 

BIANCA-BRICK-DHCP-MIB DEFINITIONS ::= BEGIN
 
        IMPORTS
            IpAddress, Counter
                FROM RFC1155-SMI
 
            OBJECT-TYPE
                FROM RFC-1212;

    org		OBJECT IDENTIFIER ::= { iso 3 }
    dod		OBJECT IDENTIFIER ::= { org 6 }
    internet	OBJECT IDENTIFIER ::= { dod 1 }
    private	OBJECT IDENTIFIER ::= { internet 4 }
    enterprises	OBJECT IDENTIFIER ::= { private 1 }
    bintec 	OBJECT IDENTIFIER ::= { enterprises 272 }
    bibo	OBJECT IDENTIFIER ::= { bintec 4 }
    biboip	OBJECT IDENTIFIER
	::= { bibo 5 }

	PhysAddress ::= OCTET STRING
	Date ::= INTEGER

-- DHCP MIB
	ipDhcpTable OBJECT-TYPE
	    SYNTAX SEQUENCE OF IpDhcpEntry
	    ACCESS not-accessible
	    STATUS mandatory
	    DESCRIPTION
		""
	::= { biboip 8 }

	ipDhcpEntry OBJECT-TYPE
	    SYNTAX IpDhcpEntry
	    ACCESS not-accessible
	    STATUS mandatory
	    DESCRIPTION
		""
	    INDEX { ipDhcpIfIndex }
	::= { ipDhcpTable 1 }

	IpDhcpEntry ::=
	    SEQUENCE {
		ipDhcpIfIndex	INTEGER,
		ipDhcpState	INTEGER,
		ipDhcpFirst	IpAddress,
		ipDhcpRange	INTEGER,
		ipDhcpLease	INTEGER,
		ipDhcpPhys	PhysAddress,
		ipDhcpNodeType	INTEGER,
		ipDhcpGateway	IpAddress
	    }

	ipDhcpIfIndex OBJECT-TYPE
	    SYNTAX INTEGER
	    ACCESS read-write
	    STATUS mandatory
	    DESCRIPTION
		"Index of interface where this range of IP addresses
		 will be assigned to DHCP clients"
	::= { ipDhcpEntry 1 }

	ipDhcpState OBJECT-TYPE
	    SYNTAX INTEGER { on(1), delete(2) }
	    ACCESS read-write
	    STATUS mandatory
	    DESCRIPTION
		""
	::= { ipDhcpEntry 2 }

	ipDhcpFirst OBJECT-TYPE
	    SYNTAX IpAddress
	    ACCESS read-write
	    STATUS mandatory
	    DESCRIPTION
		"First address of this range. There must exist a route
		to this address via this interface"
	::= { ipDhcpEntry 3 }

	ipDhcpRange OBJECT-TYPE
	    SYNTAX INTEGER
	    ACCESS read-write
	    STATUS mandatory
	    DESCRIPTION
		"Number of IP addresses that will be assigned starting
		 from DhcpFirst. A range of 0 will disable this entry"
	::= { ipDhcpEntry 4 }

	ipDhcpLease OBJECT-TYPE
	    SYNTAX INTEGER
	    ACCESS read-write
	    STATUS mandatory
	    DESCRIPTION
		"amount of time (in minutes) a DHCP client can use an
		IP address assigned from this address range"
	::= { ipDhcpEntry 5 }

	ipDhcpPhys OBJECT-TYPE
	    SYNTAX PhysAddress
	    ACCESS read-write
	    STATUS mandatory
	    DESCRIPTION
		"MAC address of host this single address should be assigned
		to. If ipDhcpPhys is not empty or different from 0:0:0:0:0:0,
		ipDhcpRange must be 1"
	::= { ipDhcpEntry 6 }

	ipDhcpNodeType OBJECT-TYPE
	    SYNTAX  INTEGER {
		none(1),	-- don't include in DHCP response
		bnode(2),	-- Broadcast node
		pnode(3),	-- Point-to-Point node
		mnode(4),	-- Mixed node
		hnode(5)	-- Hybrid node, not in RFC 1001
	    }
	    ACCESS read-write
	    STATUS mandatory
	    DESCRIPTION
		"The NetBIOS end-node type according RFC 1001"
	::= { ipDhcpEntry 7 }

	ipDhcpGateway OBJECT-TYPE
	    SYNTAX IpAddress
	    ACCESS read-write
	    STATUS mandatory
	    DESCRIPTION
		"The Gateway which is told the clients upon requests. 
		 If this object equals 0.0.0.0 and DHCP client and
		 server share the same network, the DHCP servers own
		 address is returned upon request. If DHCP client and
		 server do not share the same network, the address of
		 the dhcp relay agent forwarding the request is returned."
	::= { ipDhcpEntry 8 }


	ipDhcpInUseTable OBJECT-TYPE
	    SYNTAX SEQUENCE OF IpDhcpInUseEntry
	    ACCESS not-accessible
	    STATUS mandatory
	    DESCRIPTION
		""
	::= { biboip 9 }

	ipDhcpInUseEntry OBJECT-TYPE
	    SYNTAX IpDhcpEntry
	    ACCESS not-accessible
	    STATUS mandatory
	    DESCRIPTION
		""
	    INDEX { ipDhcpInUseAddress }
	    ::= { ipDhcpInUseTable 1 }

	IpDhcpInUseEntry ::= 
	    SEQUENCE {
		ipDhcpInUseAddress IpAddress,
		ipDhcpInUsePhys PhysAddress,
		ipDhcpInUseExpires Date
	    }
	
	ipDhcpInUseAddress OBJECT-TYPE
	    SYNTAX IpAddress
	    ACCESS read-only
	    STATUS mandatory
	    DESCRIPTION
		"assigned IP address"
	::= { ipDhcpInUseEntry 1 }

	ipDhcpInUsePhys OBJECT-TYPE
	    SYNTAX PhysAddress
	    ACCESS read-only
	    STATUS mandatory
	    DESCRIPTION
		"MAC address of host"
	::= { ipDhcpInUseEntry 2 }

	ipDhcpInUseExpires OBJECT-TYPE
	    SYNTAX Date
	    ACCESS read-only
	    STATUS mandatory
	    DESCRIPTION
		"End of Lease time. From then on, the host is not
		 allowed to use this IP address any longer"
	::= { ipDhcpInUseEntry 3 }

END
