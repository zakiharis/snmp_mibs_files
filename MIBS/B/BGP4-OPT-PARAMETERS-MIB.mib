-- extracted from draft-jhaas-bgp4-mib-opt-00.txt
-- at Sat Feb 24 06:04:17 2001

      BGP4-OPT-PARAMETERS-MIB DEFINITIONS ::= BEGIN

      IMPORTS
          MODULE-IDENTITY, OBJECT-TYPE, NOTIFICATION-TYPE,
              Integer32, Counter32, Gauge32, mib-2
              FROM SNMPv2-SMI

          bgp, bgpPeerRemoteAddr FROM BGP4-MIB

          TruthValue, AutonomousType FROM SNMPv2-TC

          MODULE-COMPLIANCE, OBJECT-GROUP, NOTIFICATION-GROUP
              FROM SNMPv2-CONF;


      bgp4OptParametersMIB MODULE-IDENTITY
          LAST-UPDATED "200102230000Z"
          ORGANIZATION "IETF IDR Working Group"
          CONTACT-INFO
              "E-Mail: idr@merit.net

               Editor:  Susan Hares
                        517 W. William Street
                        Ann Arbor, MI  48103-4943
                        Tel: +1 734 936 2095
                        Fax: +1 734 615-3241
                        E-mail: skh@nexthop.com

               Authors: Jeffrey Haas
                        NextHop Technologies
                        517 W. William Street
                        Ann Arbor, MI  48103-4943
                        Tel: +1 734 936 2095
                        Fax: +1 734 615-3241
                        E-mail: jhaas@nexthop.com"

          DESCRIPTION
              "The extension of the MIB module for BGP-4 for
               optional parameters."
          REVISION    "200102230000Z"
          DESCRIPTION
              "Initial proposal.
               Definition of MIB extension for the following
               optional exetnsions to BGP-4"
          REVISION    "200102230000Z"

          DESCRIPTION
              "RFC 1771 - Border Gateway Protocol, Version 4
               RFC 2385 - TCP MD5 Authentication
               RFC 2842 - Capabilities Advertisement with BGP-4"
          ::= { bgp 9 }

      -- bgpAuthenticationTable        { bgp4OptParametersMIB 1 }
      -- bgpCapabilitySupportAvailable { bgp4OptParametersMIB 2 }
      -- bgpSupportedCapabilities      { bgp4OptParametersMIB 3 }
      -- bgpPeerCapabilitiesTable      { bgp4OptParametersMIB 4 }
      -- bgpProtocolExtensions         { bgp4OptParametersMIB 5 }


      bgpAuthenticationTable OBJECT-TYPE
          SYNTAX     SEQUENCE OF BgpAuthenticationPeerEntry
          MAX-ACCESS not-accessible
          STATUS     current
          DESCRIPTION
              "The BGP-4 Authentication Table contains information
               about BGP Authentication Options on a per-peer basis."
          REFERENCE
              "RFC 1771 - Border Gateway Protocol, Version 4"
          ::= { bgp4OptParametersMIB 1 }

      bgpAuthenticationPeerEntry OBJECT-TYPE
          SYNTAX     BgpAuthenticationEntry
          MAX-ACCESS not-accessible
          STATUS     current
          DESCRIPTION
              "Information about Authentication on a per-peer basis."
          INDEX {
              bgpPeerRemoteAddr,
              bgpAuthenticationDirection
              }
          ::= { bgpAuthenticationTable 1 }

      bgpAuthenticationEntry OBJECT-TYPE
          SYNTAX     BgpAuthenticationEntry
          MAX-ACCESS not-accessible
          STATUS     current
          DESCRIPTION
              "Information about BGP-4 Authentication."
          ::= { bgpAuthenticationPeerEntry 2 }

      BgpAuthenticationEntry ::= SEQUENCE {
          bgpAuthenticationDirection    Integer32,
          bgpAuthenticationCode         Integer32,
          bgpAuthenticationDataLength   Integer32,
          bgpAuthenticationDataContents OCTET STRING
      }

      bgpAuthenticationDirection OBJECT-TYPE
          SYNTAX Integer32 {
              sent     (1), -- Authorization is being sent
              received (2) -- Authorization is being received
              }
          MAX-ACCESS not-accessible
          STATUS     current
          DESCRIPTION
              "This variable indicates whether authentication
               information is either being sent by the BGP
               speaker or has been been received by the BGP
               speaker.  It also serves as the index into the
               table of authentication information for the
               direction of authentication."
          ::= { bgpAuthenticationEntry 1 }

      bgpAuthenticationCode OBJECT-TYPE
          SYNTAX     Integer32 (-1 | 0..255)
          MAX-ACCESS read-write
          STATUS     current
          DESCRIPTION
              "This is the AuthenticationCode used.
               This value is set to -1 if Authentication is
               not present."
          REFERENCE
              "RFC 1771, sec. 4.2.a"
          ::= { bgpAuthenticationEntry 2 }

      bgpAuthenticationDataLength OBJECT-TYPE
          SYNTAX     Integer32 (-1 | 0..252)
          MAX-ACCESS read-write
          STATUS     current
          DESCRIPTION
              "This value is derived from the optional
               parameter length minus one (the size of
               bgpAuthenticationCode).  This value may be no
               larger than 252 due to overhead.  This value
               is set to -1 if Authentication is not present."
          ::= { bgpAuthenticationEntry 3 }

      bgpAuthenticationDataContents OBJECT-TYPE
          SYNTAX     OCTET STRING (SIZE (1..252))
          MAX-ACCESS read-write
          STATUS     current
          DESCRIPTION
              "This is the Authentication payload.  The
               semantics of this variable are interpreted
               according to the authentication code."
          ::= { bgpAuthenticationEntry 4 }

      bgpCapabilitySupportAvailable OBJECT-TYPE
          SYNTAX     TruthValue
          MAX-ACCESS read-write
          STATUS     current
          DESCRIPTION
              "This variable determines whether BGP-4
               capabilities are supported in this
               implementation.  This variable may be set to
               false to disable capability support."
          ::= { bgp4OptParametersMIB 2 }

      bgpSupportedCapabilities OBJECT-TYPE
          SYNTAX     OCTET STRING (SIZE(0..32)) -- 256 bit vector
          MAX-ACCESS read-only
          STATUS     current
          DESCRIPTION
              "Vector of BGP-4 capabilities that are
               supported in this implementation.  Capabilities
               are identified via the string of bits within
               this object.  The first octet contains bits
               0 to 7, the second octet contains bits 8 to 15
               and so on.  If a bit, i, is present and set,
               then the capability (i+1) is supported.

               When capabilities are not supported, all bits
               must be zero."
          ::= { bgp4OptParametersMIB 3 }

      bgpPeerCapabilitiesTable OBJECT-TYPE
          SYNTAX     SEQUENCE OF BgpPeerCapabilitiesEntry
          MAX-ACCESS not-accessible
          STATUS     current
          DESCRIPTION
              "This table contains contains the capabilities
               that are supported for a given peer."
          ::= { bgp4OptParametersMIB 4 }

      BgpPeerCapabilitiesEntry ::= SEQUENCE {
          bgpPeerCapabilitiesAnnounced
              OCTET STRING,
          bgpPeerCapabilitiesReceived
              OCTET STRING
      }

      bgpPeerCapabilitiesEntry OBJECT-TYPE
          SYNTAX     BgpPeerCapabilitiesEntry
          MAX-ACCESS not-accessible
          STATUS     current
          DESCRIPTION
              "These entries are keyed by a BGP-4 peer's remote
               address and port combination over which the
               peering session has been established."
          AUGMENTS { bgpPeerTable }
          ::= { bgpPeerCapabilitiesTable 2 }

      bgpPeerCapabilitiesAnnounced OBJECT-TYPE
          SYNTAX     OCTET STRING (SIZE (0..32))
          MAX-ACCESS read-only
          STATUS     current
          DESCRIPTION
              "This bit vector identifies which capabilities
               have been announced to a BGP-4 speaker.

               Capabilities are identified via the string of
               bits within this object.  The first octet
               contains bits 0 to 7, the second octet contains
               bits 8 to 15 and so on.  If a bit, i, is present
               and set, then the capability (i+1) is supported.

               When capabilities are not supported, all bits
               must be zero."
      ::= { bgpPeerCapabilitiesEntry 1 }


      bgpPeerCapabilitiesReceived OBJECT-TYPE
          SYNTAX     OCTET STRING (SIZE (0..32))
          MAX-ACCESS read-only
          STATUS     current
          DESCRIPTION
              "This bit vector identifies which capabilities have
                been announced by the remote BGP-4 speaker.

               Capabilities are identified via the string of bits
               within this object.  The first octet contains bits 0
               to 7, the second octet contains bits 8 to 15 and so
               on.  If a bit, i, is present and set, then the
               capability (i+1) is supported.

               When capabilities are not supported, all bits must
               be zero."
          ::= { bgpPeerCapabilitiesEntry 2 }


      bgpProtocolExtensions OBJECT-TYPE
          SYNTAX     AutonomousType
          MAX-ACCESS read-only
          STATUS     current
          DESCRIPTION
              "Registration point for MIB Modules for BGP
               Protocol Extensions.

               The Capabilities Advertisement RFC delineates
               IANA registered capability code numbers, 0-127
               and private use capability code numbers, 128-255.

               The first sub-identifier will be the enterprise
               number of the registering entity.  This is used
               to remove the ambiguity of the private use
               portion of the capability code assignments.  For
               IANA registered capability codes 0-127, the first
               sub-identifier will be 0.

               The second sub-identifier will be the capability
               code for the advertised capability.

               For example, the MPBGP-MIB would be assigned as
               { bgpProtocolStandardExtensions 0 1 } since it
               has been assigned capability code number 1 and
               is an IETF assigned (IANA registered) capability
               extension."
          REFERENCE
              "RFC 2842 - Capabilities Advertisement with BGP-4"
          ::= { bgp4OptParametersMIB 5 }


      END
