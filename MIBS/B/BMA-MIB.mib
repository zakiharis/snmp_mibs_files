-- extracted from draft-ietf-ipoib-baseboard-mgmt-agent-mib-03.txt
-- at Wed Sep 14 06:35:49 2005

BMA-MIB DEFINITIONS ::= BEGIN 
    
IMPORTS  
   MODULE-IDENTITY, OBJECT-TYPE,                
   NOTIFICATION-TYPE, Integer32                  FROM SNMPv2-SMI  
   TruthValue, DisplayString, DateAndTime        FROM SNMPv2-TC  
   MODULE-COMPLIANCE, OBJECT-GROUP,  
   NOTIFICATION-GROUP                            FROM SNMPv2-CONF  
   IbDataPort, infinibandMIB                     FROM IB-TC-MIB;
  
ibBmaMIB MODULE-IDENTITY  
   LAST-UPDATED    "200509011200Z"   -- September 1, 2005 12:00:00 GMT
   ORGANIZATION    "IETF IP Over IB (IPOIB) Working Group"
   CONTACT-INFO  
       "Sean Harnedy (sharnedy@mangrovesystems.com)
        Mangrove Systems, Inc."
   DESCRIPTION  
      "Copyright (C) The Internet Society (2005).  The initial 
       version of this MIB module was published in RFC XXXX; for
       full legal notices see the RFC itself.  Supplementary 
       information may be available on 
       http://www.ietf.org/copyrights/ianamib.html.

       This module contains managed object definitions for 
       the Baseboard Management Agent instrumentation for an 
       InfiniBand Baseboard Management Agent (BMA)."  
   REVISION
      "200509011200Z"  -- 1 September 2005 12:00:00 GMT
   DESCRIPTION  
      "Initial version published as part of RFC XXXX."
   ::= { infinibandMIB 5 }
    
--**************************************************************** 
--  Object Indentifiers for the IPOIB BMA MIB  
--**************************************************************** 

ibBmaObjects         OBJECT IDENTIFIER ::= { ibBmaMIB 1 }  
ibBmaConformance     OBJECT IDENTIFIER ::= { ibBmaMIB 2 }  
--**************************************************************** 
-- BMA Baseboard Management Unit Info Group
--
-- DESCRIPTION: This group contains variables that describe
--    information about the BMA BMU implementation.
--**************************************************************** 

ibBmaBmuInfo        OBJECT IDENTIFIER ::= { ibBmaObjects 1 } 

ibBmaBaseboardManagedUnitType OBJECT-TYPE 
   SYNTAX INTEGER 
          { 
          ibModule(1), 
          nonModule(2), 
          managedChassis(3)
          } 
   MAX-ACCESS read-only 
   STATUS current 
   DESCRIPTION 
      "The Baseboard Managed Unit (BMU) that contains the BMA is one
       of three basic types.  If the BMU contains an interface to the
       InfiniBand Management Link (IB-ML) it is called an IB-Module 
       and returns ibModule(1).  If the BMU does not contain the IB-ML, 
       it is called a non-Module and returns nonModule(2).  If the BMU
       is part of a managed chassis and contains the Chassis Management
       Entity (CME) it will return managedChassis(3)."
   REFERENCE
      "InfiniBand Architecture Release 1.0.a. Vol. 1. Section 16.2 
       Baseboard Management; and Vol. 2. Chapter 12 Hardware 
       Management."
   ::= { ibBmaBmuInfo 1 } 

ibBmaIsIBMLSupported OBJECT-TYPE 
   SYNTAX TruthValue 
   MAX-ACCESS read-only 
   STATUS current 
   DESCRIPTION  
      "Flag that indicates whether direct access to IB-ML is supported."
   REFERENCE
      "InfiniBand Architecture Release 1.0.a. Vol. 1. Section 16.2.3.1;
       Table 205 Baseboard Management ClassPortInfo:Capability Mask."
   ::= { ibBmaBmuInfo 2 } 

ibBmaIBMLImplementation OBJECT-TYPE 
   SYNTAX INTEGER 
               { 
               ibMlPhysical(1), 
               ibMlVirtual(2), 
               unknown(3)
               } 
   MAX-ACCESS read-only 
   STATUS current 
   DESCRIPTION  
      "Indicates whether the IB-ML is a physical or virtual 
       implementation.  This object is only meaningful if 
       ibBmaIsIBMLSupported has a value of true(1). If the 
       IB-ML implementation type is not known, the unknown(3)
       value is returned."
   REFERENCE
      "InfiniBand Architecture Release 1.0.a. Vol. 1.
       Section 16.2.3.1; Section 13.2.3.2.2 Virtual IB-ML Vol. 2."
   ::= { ibBmaBmuInfo 3 } 

--**************************************************************** 
-- BMA Baseboard Key (B_Key) Info Group
--
-- DESCRIPTION: This group contains variables that describe
--    information about the Baseboard management keys.
--**************************************************************** 

ibBmaBKeyInfo OBJECT IDENTIFIER ::= { ibBmaObjects 2 } 

ibBmaIsBKeyNVRAM OBJECT-TYPE 
   SYNTAX TruthValue 
   MAX-ACCESS read-only 
   STATUS current 
   DESCRIPTION  
      "Flag that indicates whether the Baseboard Management
       key (B_Key) is being stored in NVRAM."
   REFERENCE
      "InfiniBand Architecture Release 1.0.a. Vol. 1.
       Section 16.2.3.1; Table 205 Baseboard Management 
       ClassPortInfo:Capability Mask."
   ::= { ibBmaBKeyInfo 1 } 

ibBmaBKeyValue OBJECT-TYPE 
   SYNTAX OCTET STRING (SIZE(64)) 
   MAX-ACCESS read-only 
   STATUS current 
   DESCRIPTION  
      "The eight-byte Baseboard Management key that is used in all
       BM MADs sent and received by all valid Baseboard Managers.
       If the value is all zeroes, B_Key checking is not done by
       the BMA. Each BMA in a node has one B_Key."
   REFERENCE
      "InfiniBand Architecture Release 1.0.a. Vol. 1.
       Section 16.2.3.3; Table 208 BKeyInfo; BKeyInfo:B_Key."
   ::= { ibBmaBKeyInfo 2 } 

ibBmaBKeyProtectBit OBJECT-TYPE
   SYNTAX TruthValue 
   MAX-ACCESS read-only 
   STATUS current 
   DESCRIPTION  
      "Flag that controls B_Key prototection levels at the BMA. 
       If the ibBmaBKeyValue is zero, no protection is provided
       for any ibBmaBKeyProtectBit value. If this value is false(2),
       protection is provided, but any BM can read this BMA's
       B_Key value (i.e., ibBmaBKeyValue). If this value is true(1),
       protection is provided depending on the value of the
       B_Key lease period (ibBmaBKeyLeasePeriod). If the lease
       period is non-zero, the BMA does not allow anyone to read
       the B_Key until the lease period has expired. If the lease
       period is zero, the BMA does not allow the B_Key in the node
       to be read by other BMs."
   REFERENCE
      "InfiniBand Architecture Release 1.0.a. Vol. 1.
       Section 16.2.4.6; Table 211 Protection Levels."
   ::= { ibBmaBKeyInfo 3 } 

ibBmaBKeyLeasePeriod OBJECT-TYPE
   SYNTAX Integer32(0..65535) 
   UNITS "seconds"
   MAX-ACCESS read-only 
   STATUS current 
   DESCRIPTION  
      "Specifies the timer value of the B_Key lease period (in 
       seconds). The lease period indicates how long the B_Key
       Protection bit is to remain non-zero after a BMSet(BKeyInfo)
       MAD that fails the B_Key authentication check is dropped.
       When the value is 0, the lease period shall never expire
       (i.e., infinite)."
   REFERENCE
      "InfiniBand Architecture Release 1.0.a. Vol. 1.
       Section 16.2.3.3; Table 208 BKeyInfo; BKeyInfo:B_KeyLeasePeriod."
   ::= { ibBmaBKeyInfo 4 } 

ibBmaBKeyViolations OBJECT-TYPE
   SYNTAX Integer32(0..65535) 
   MAX-ACCESS read-only 
   STATUS current 
   DESCRIPTION  
      "Counts the number of MAD packets that have been received at 
       this node since power-on or reset that have been dropped due 
       to a failed B_Key check. Note, if this counter is not implemented
       by the node, the value 65535 shall be returned." 
   REFERENCE
      "InfiniBand Architecture Release 1.0.a. Vol. 1.
       Section 16.2.3.3; Table 208 BKeyInfo; BKeyInfo:B_KeyViolations."
   ::= { ibBmaBKeyInfo 5 } 

--**************************************************************** 
-- Vital Product Data (VPD)
--
--    There are 9 Info Groups (Record Types) associated 
--    with the VPD:
--       o Module Information
--       o Chassis Information
--       o FRU Information
--       o Module Power Information
--       o Port Connection Information
--       o CME Information
--       o OEM Information
--       o Buddy Information
--       o Asset Tag Information
--
--**************************************************************** 

ibBmaVpd OBJECT IDENTIFIER ::= { ibBmaObjects 3 } 

--**************************************************************** 
-- BMA Module Info Group
--
-- DESCRIPTION: This group contains variables that describe
--    the Module class and the number of InfiniBand and IB-ML
--    links exiting the Module. Non-Modules can also utilize this
--    information to describe their link and IB-ML connection
--    support.
--**************************************************************** 

ibBmaModuleInfo OBJECT IDENTIFIER ::= { ibBmaVpd 1 } 

ibBmaModuleInfoTable OBJECT-TYPE
   SYNTAX SEQUENCE OF IbBmaModuleInfoEntry
   MAX-ACCESS not-accessible
   STATUS current
   DESCRIPTION
      "This table contains objects that describe the Module class 
       and the number of InfiniBand and IB-ML links exiting the 
       Module. Non-Modules can also utilize this information to 
       describe their link and IB-ML connection support."
   ::= { ibBmaModuleInfo 1 }

ibBmaModuleInfoEntry OBJECT-TYPE
   SYNTAX IbBmaModuleInfoEntry
   MAX-ACCESS not-accessible
   STATUS current
   DESCRIPTION
      "The column definitions for the Module Info table."
   INDEX { ibBmaModuleInfoIndex }
   ::= { ibBmaModuleInfoTable 1 }

IbBmaModuleInfoEntry ::= SEQUENCE {
   ibBmaModuleInfoIndex Integer32,
   ibBmaModInfoModGuid OCTET STRING,
   ibBmaModInfoModType INTEGER,
   ibBmaModInfoModClass INTEGER,
   ibBmaModInfoNodeCount Integer32,
   ibBmaModInfoLinkCount Integer32,
   ibBmaModInfoBckplaneLinkCnt Integer32,
   ibBmaModInfoIbmlCount Integer32,
   ibBmaModInfoBckPlaneIbmlCnt Integer32,
   ibBmaModInfoModuleSize OCTET STRING,
   ibBmaModInfoFormFactor INTEGER
}

ibBmaModuleInfoIndex OBJECT-TYPE
   SYNTAX Integer32(1..255)
   MAX-ACCESS not-accessible
   STATUS current
   DESCRIPTION
      "Index into the Module Info table."
   ::= { ibBmaModuleInfoEntry 1 } 

ibBmaModInfoModGuid OBJECT-TYPE
   SYNTAX OCTET STRING (SIZE(8)) 
   MAX-ACCESS read-only 
   STATUS current 
   DESCRIPTION 
      "The GUID (EUI-64 ID) assigned to this module."
   REFERENCE
      "InfiniBand Architecture Release 1.0.a. Vol. 2.
       Section 13.7.6 ModuleInfo Record. Table 105 ModuleInfo 
       Record."
   ::= { ibBmaModuleInfoEntry 2 } 

ibBmaModInfoModType OBJECT-TYPE
   SYNTAX INTEGER 
               { 
               notInfiniBandModule(1), 
               infiniBandModule(2), 
               other(3) 
               } 
   MAX-ACCESS read-only 
   STATUS current 
   DESCRIPTION  
      "InfiniBand module type."
   REFERENCE
      "InfiniBand Architecture Release 1.0.a. Vol. 2.
       Section 13.7.6 ModuleInfo Record. Table 105 ModuleInfo Record."
   ::= { ibBmaModuleInfoEntry 3 } 

ibBmaModInfoModClass OBJECT-TYPE
   SYNTAX INTEGER 
               { 
               tca(1), 
               hca(2), 
               switch(3), 
               router(4), 
               oneXrepeater(5), 
               fourXrepeater(6), 
               twelveXrepeater(7), 
               other(8)
               } 
   MAX-ACCESS read-only 
   STATUS current 
   DESCRIPTION  
      "InfiniBand module class."
   REFERENCE
      "InfiniBand Architecture Release 1.0.a. Vol. 2.
       Section 13.7.6 ModuleInfo Record. Table 105 ModuleInfo Record."
   ::= { ibBmaModuleInfoEntry 4 } 

ibBmaModInfoNodeCount OBJECT-TYPE
   SYNTAX Integer32(0..255) 
   MAX-ACCESS read-only 
   STATUS current 
   DESCRIPTION  
      "Number of InfiniBand nodes on this module with unique NodeGUIDs."
   REFERENCE
      "InfiniBand Architecture Release 1.0.a. Vol. 2.
       Section 13.7.6 ModuleInfo Record. Table 105 ModuleInfo Record."
   ::= { ibBmaModuleInfoEntry 5 } 

ibBmaModInfoLinkCount OBJECT-TYPE
   SYNTAX Integer32(0..255) 
   MAX-ACCESS read-only 
   STATUS current 
   DESCRIPTION  
      "Number of InfiniBand links on this module with unique PortGuids
       (i.e., NodeGUID plus Port Number)."
   REFERENCE
      "InfiniBand Architecture Release 1.0.a. Vol. 2.
       Section 13.7.6 ModuleInfo Record. Table 105 ModuleInfo Record."
   ::= { ibBmaModuleInfoEntry 6 } 

ibBmaModInfoBckplaneLinkCnt OBJECT-TYPE
   SYNTAX Integer32(0..255)
   MAX-ACCESS read-only 
   STATUS current 
   DESCRIPTION  
      "Number of InfiniBand links exiting this module through its
       backplane connectors. If the module is not an InfiniBand
       module, this count is the number of InfiniBand links that
       exit the module."
   REFERENCE
      "InfiniBand Architecture Release 1.0.a. Vol. 2.
       Section 13.7.6 ModuleInfo Record. Table 105 ModuleInfo Record."
   ::= { ibBmaModuleInfoEntry 7 } 

ibBmaModInfoIbmlCount OBJECT-TYPE
   SYNTAX Integer32(0..255)
   MAX-ACCESS read-only 
   STATUS current 
   DESCRIPTION  
      "Number of IB-ML interfaces on this module."
   REFERENCE
      "InfiniBand Architecture Release 1.0.a. Vol. 2.
       Section 13.7.6 ModuleInfo Record. Table 105 ModuleInfo Record."
   ::= { ibBmaModuleInfoEntry 8 } 

ibBmaModInfoBckPlaneIbmlCnt OBJECT-TYPE
   SYNTAX Integer32(0..255)
   MAX-ACCESS read-only 
   STATUS current 
   DESCRIPTION  
      "Number of IB-MLs exiting this module through its
       backplane connectors. If the module is not an 
       InfiniBand module, this count is the number of IB-MLs 
       that exit the module."
   REFERENCE
      "InfiniBand Architecture Release 1.0.a. Vol. 2.
       Section 13.7.6 ModuleInfo Record. Table 105 ModuleInfo Record."
   ::= { ibBmaModuleInfoEntry 9 } 

ibBmaModInfoModuleSize OBJECT-TYPE
   SYNTAX OCTET STRING (SIZE (8))
   MAX-ACCESS read-only 
   STATUS current 
   DESCRIPTION  
      "Eight-byte bit map for the volumetric information for standard
       form factors (in millimeters)."
   REFERENCE
      "InfiniBand Architecture Release 1.0.a. Vol. 2.
       Section 13.7.6 ModuleInfo Record."
   ::= { ibBmaModuleInfoEntry 10 } 

ibBmaModInfoFormFactor OBJECT-TYPE
   SYNTAX INTEGER 
               { 
               unspecified(1), 
               nonRemovable(2),
               standard(3), 
               standardWide(4), 
               tall(5), 
               tallWide(6), 
               pci(7), 
               lowProfilePci(8), 
               compactPci(9), 
               vme(10), 
               internalMezzanineBoard(11), 
               cardEdgeBoard(12), 
               deviceBay(13), 
               otherRemovable(14)
               } 
   MAX-ACCESS read-only 
   STATUS current 
   DESCRIPTION  
      "The Module Form Factor."
   REFERENCE
      "InfiniBand Architecture Release 1.0.a. Vol. 2.
       Section 13.7.6 ModuleInfo Record."
   ::= { ibBmaModuleInfoEntry 11 } 

--**************************************************************** 
-- BMA Chassis Info Group
--
-- DESCRIPTION: This group contains variables that describe
--    the InfiniBand chassis and slot-specific information for the
--    chassis VPD that can be accessed from an InfiniBand Module 
--    or a CME.
--**************************************************************** 

ibBmaChassisInfo        OBJECT IDENTIFIER ::= { ibBmaVpd 2 } 

ibBmaChasInfoChassisGuid OBJECT-TYPE
   SYNTAX OCTET STRING (SIZE(8)) 
   MAX-ACCESS read-only 
   STATUS current 
   DESCRIPTION 
      "The GUID assigned to this chassis."
   REFERENCE
      "InfiniBand Architecture Release 1.0.a. Vol. 2.
       Section 13.7.7 ChassisInfo Record iand Table 106."
   ::= { ibBmaChassisInfo 1 } 

ibBmaChasInfoSlotCount OBJECT-TYPE
   SYNTAX      Integer32(1..254)
   MAX-ACCESS read-only 
   STATUS      current 
   DESCRIPTION 
      "Total number of InfiniBand module slots in this chassis."
   REFERENCE
      "InfiniBand Architecture Release 1.0.a. Vol. 2.
       Section 13.7.7 ChassisInfo Record and Table 106."
   ::= { ibBmaChassisInfo 2 } 

ibBmaChasInfoSlotTable OBJECT-TYPE
   SYNTAX      SEQUENCE OF IbBmaChasInfoSlotEntry
   MAX-ACCESS not-accessible
   STATUS      current
   DESCRIPTION
      "This table contains objects that describe the Chassis
       and slot-specific information for Chassis VPD accessed
       from an InfiniBand Module or a CME."
   ::= { ibBmaChassisInfo 3 } 

ibBmaChasInfoSlotEntry OBJECT-TYPE
   SYNTAX      IbBmaChasInfoSlotEntry
   MAX-ACCESS not-accessible
   STATUS      current
   DESCRIPTION
      "The column definitions for the Chassis Info table."
   INDEX { ibBmaChasInfoSlotIndex }
   ::= { ibBmaChasInfoSlotTable 1 } 

IbBmaChasInfoSlotEntry ::= SEQUENCE {
   ibBmaChasInfoSlotIndex Integer32,
   ibBmaChasInfoAssignedSlotNum Integer32,
   ibBmaChasInfoSlotConnStatus INTEGER,
   ibBmaChasInfoCmeAccess INTEGER,
   ibBmaChasInfoProxyAccess INTEGER,
   ibBmaChasInfoLockDrivesCtr INTEGER,
   ibBmaChasInfoMechLockPresent INTEGER
}

ibBmaChasInfoSlotIndex OBJECT-TYPE
   SYNTAX Integer32(1..254) 
   MAX-ACCESS not-accessible 
   STATUS current 
   DESCRIPTION
      "Chassis slot index."
   ::= { ibBmaChasInfoSlotEntry 1 } 

ibBmaChasInfoAssignedSlotNum OBJECT-TYPE
   SYNTAX Integer32(1..255)
   MAX-ACCESS read-only 
   STATUS current 
   DESCRIPTION
      "Slot number assigned to the CME and the Chassis
       containing the CME. If the slot number is unspecified
       or occupied by a non-Module, the value returned
       will be 0xFF(255)."
   REFERENCE
      "InfiniBand Architecture Release 1.0.a. Vol. 2.
       Section 13.7.7 ChassisInfo Record and Table 106."
   ::= { ibBmaChasInfoSlotEntry 2 } 

ibBmaChasInfoSlotConnStatus OBJECT-TYPE
   SYNTAX INTEGER
               {
               notImplemented(1),
               oneConnectToStandardSlot(2),
               oneConnectToTallSlot(3),
               twoConnectToTallSlot(4)
               }
   MAX-ACCESS read-only 
   STATUS current 
   DESCRIPTION
      "Chassis slot connector status."
   REFERENCE
      "InfiniBand Architecture Release 1.0.a. Vol. 2.
       Section 13.7.7 ChassisInfo Record and Table 106."
   ::= { ibBmaChasInfoSlotEntry 3 } 

ibBmaChasInfoCmeAccess OBJECT-TYPE
   SYNTAX INTEGER
               {
               unspecified(1),
               accessViaPriPort(2),
               notAccessible(3),
               reserved(4)
               }
   MAX-ACCESS read-only 
   STATUS current 
   DESCRIPTION
      "Chassis CME access."
   REFERENCE
      "InfiniBand Architecture Release 1.0.a. Vol. 2.
       Section 13.7.7 ChassisInfo Record and Table 106."
   ::= { ibBmaChasInfoSlotEntry 4 } 

ibBmaChasInfoProxyAccess OBJECT-TYPE
   SYNTAX INTEGER 
               { 
               noProxyAccess(1),  
               hasProxyAccess(2)
               }
   MAX-ACCESS read-only 
   STATUS current 
   DESCRIPTION
      "Chassis proxy access."
   REFERENCE
      "InfiniBand Architecture Release 1.0.a. Vol. 2.
       Section 13.7.7 ChassisInfo Record and Table 106."
   ::= { ibBmaChasInfoSlotEntry 5 } 

ibBmaChasInfoLockDrivesCtr OBJECT-TYPE
   SYNTAX INTEGER 
               { 
               unspecified(1),       -- non-Module application 
               lockDrivesCmeCtr(2), 
               lockReleaseForCmeCtr(3),   
               reserved(4)           -- other
               }
   MAX-ACCESS read-only 
   STATUS current 
   DESCRIPTION  
      "Indicates whether the lock (if present) keeps CME_CTR
       deasserted until the lock is released. The value
       lockDrivesCmeCtr(2) is used if the CME uses only the
       state of the lock to drive the CME_CTR. The value of
       lockReleaseFromCmeCtr(3) indicates that the CME_CTR will
       not be asserted unless the lock is released. Also, the CME 
       has other criteria that can also cause the CME_CTR to be 
       kept deasserted."
   REFERENCE
      "InfiniBand Architecture Release 1.0.a. Vol. 2.
       Section 13.7.7 ChassisInfo Record and Table 106."
   ::= { ibBmaChasInfoSlotEntry 6 } 

ibBmaChasInfoMechLockPresent OBJECT-TYPE
   SYNTAX INTEGER 
            { 
            unspecified(1), -- non-Module application 
            hasLock(2),     -- mechnical lock present
            noLock(3),      -- no mechnical lock on slot
            reserved(4)     -- other
            }
   MAX-ACCESS read-only 
   STATUS current 
   DESCRIPTION  
      "Indicates whether there is a mechnical lock associated with this
       slot.  A mechnical lock physically prevents the removal of the
       Module from the slot.  The implementation can be mechnical
       or electro-mechanical."
   REFERENCE
      "InfiniBand Architecture Release 1.0.a. Vol. 2.
       Section 13.7.7 ChassisInfo Record and Table 106."
   ::= { ibBmaChasInfoSlotEntry 7 } 

--**************************************************************** 
-- BMA Field Replaceable Unit (FRU) Info Group
--
-- DESCRIPTION: This group provides FRU information. This information
--    can help a user identify and inventory the FRU units that
--    make up a given Module, system, or subsystem. The FRU information
--    is presented in a table because there can be more than one FRU
--    info record within the managed device.
--**************************************************************** 

ibBmaFruInfo OBJECT IDENTIFIER ::= { ibBmaVpd 3 } 

ibBmaFruInfoTable OBJECT-TYPE
   SYNTAX SEQUENCE OF IbBmaFruInfoEntry
   MAX-ACCESS not-accessible
   STATUS current
   DESCRIPTION
      "This table contains objects that describe the FRU
       records present in the managed device."
   ::= { ibBmaFruInfo 1 } 

ibBmaFruInfoEntry OBJECT-TYPE
   SYNTAX IbBmaFruInfoEntry
   MAX-ACCESS not-accessible
   STATUS current
   DESCRIPTION
      "The column definitions for the FRU Info table."
   INDEX { ibBmaFruInfoIndex }
   ::= { ibBmaFruInfoTable 1 } 

IbBmaFruInfoEntry ::= SEQUENCE {
   ibBmaFruInfoIndex Integer32,
   ibBmaFruInfoType INTEGER,
   ibBmaFruInfoGuidType INTEGER,
   ibBmaFruInfoGuidValue OCTET STRING,
   ibBmaFruInfoSerialNumber OCTET STRING,
   ibBmaFruInfoPartNumber OCTET STRING,
   ibBmaFruInfoModelName OCTET STRING,
   ibBmaFruInfoVersion OCTET STRING,
   ibBmaFruInfoManufacturerName OCTET STRING,
   ibBmaFruInfoProductName OCTET STRING,
   ibBmaFruInfoManufacturerID OCTET STRING,
   ibBmaFruInfoManDateAndTime DateAndTime
}

ibBmaFruInfoIndex OBJECT-TYPE
   SYNTAX Integer32(1..254) 
   MAX-ACCESS not-accessible 
   STATUS current 
   DESCRIPTION
      "FRU Info index."
   ::= { ibBmaFruInfoEntry 1 } 

ibBmaFruInfoType OBJECT-TYPE
   SYNTAX INTEGER 
             { 
             unspecified(1), 
             infinibandModule(2), 
             infinibandModBackplane(3), 
             infinibandSwitchMod(4), 
             mainChassis(5), 
             platformSystem(6), 
             standaloneProduct(7), 
             boardOrCard(8), 
             powerConverterSuppyMod(9), 
             otherModAssembly(10), 
             coolingModule(11), 
             subChassis(12), 
             processorModule(13), 
             memoryModule(14), 
             memoryCard(15), 
             oem(16) 
             }
   MAX-ACCESS read-only 
   STATUS current 
   DESCRIPTION 
      "The Field Replaceable Unit (FRU) type."
   REFERENCE
      "InfiniBand Architecture Release 1.0.a. Vol. 2. Section
       13.7.8 FRUInfo Record. Table 107 FRUInfo Record."
   ::= { ibBmaFruInfoEntry 2 } 

ibBmaFruInfoGuidType OBJECT-TYPE
   SYNTAX INTEGER 
           { 
           none(1),    -- none specified; GUID value is 0
           guid64(2),  -- EUI-64 (8 bytes)
           guid48(3),  -- EUI-48 (6 bytes)
           guid16(4),  -- SMBIOS/IPMI/OSF/WFM/MSFT GUID/UUID (16 bytes)
           guid8(5)    -- SMBus 2.0 UDID (8 bytes)
           }
   MAX-ACCESS read-only 
   STATUS current 
   DESCRIPTION 
      "The FRU GUID type."
   REFERENCE
      "InfiniBand Architecture Release 1.0.a. Vol. 2.
       Section 13.7.8 FRUInfo Record. Table 107 FRUInfo
       Record."
   ::= { ibBmaFruInfoEntry 3 } 

ibBmaFruInfoGuidValue OBJECT-TYPE
   SYNTAX OCTET STRING (SIZE(16)) 
   MAX-ACCESS read-only 
   STATUS current 
   DESCRIPTION 
      "The GUID assigned to this FRU. Needs to hold the longest possible
       GUID type (guid16(4))."
   REFERENCE
      "InfiniBand Architecture Release 1.0.a. Vol. 2.
       Section 13.7.8 FRUInfo Record. Table 107 FRUInfo
       Record."
   ::= { ibBmaFruInfoEntry 4 } 

ibBmaFruInfoSerialNumber OBJECT-TYPE
   SYNTAX OCTET STRING (SIZE(8))
   MAX-ACCESS read-only 
   STATUS current 
   DESCRIPTION  
      "The FRU serial number."
   REFERENCE
      "InfiniBand Architecture Release 1.0.a. Vol. 2.
       Section 13.7.8 FRUInfo Record. Table 107 FRUInfo
       Record."
   ::= { ibBmaFruInfoEntry 5 } 

ibBmaFruInfoPartNumber OBJECT-TYPE
   SYNTAX OCTET STRING (SIZE(8))
   MAX-ACCESS read-only 
   STATUS current 
   DESCRIPTION  
      "The FRU Part Number."
   REFERENCE
      "InfiniBand Architecture Release 1.0.a. Vol. 2.
       Section 13.7.8 FRUInfo Record. Table 107 FRUInfo
       Record."
   ::= { ibBmaFruInfoEntry 6 } 

ibBmaFruInfoModelName OBJECT-TYPE
   SYNTAX OCTET STRING (SIZE(8))
   MAX-ACCESS read-only 
   STATUS current 
   DESCRIPTION  
      "The model name is assigned by the FRU manufacturer."
   REFERENCE
      "InfiniBand Architecture Release 1.0.a. Vol. 2.
       Section 13.7.8 FRUInfo Record. Table 107 FRUInfo
       Record."
   ::= { ibBmaFruInfoEntry 7 } 

ibBmaFruInfoVersion OBJECT-TYPE
   SYNTAX OCTET STRING (SIZE(8))
   MAX-ACCESS read-only 
   STATUS current 
   DESCRIPTION  
       "The FRU version is assigned by the FRU manufacturer."
   REFERENCE
      "InfiniBand Architecture Release 1.0.a. Vol. 2.
       Section 13.7.8 FRUInfo Record. Table 107 FRUInfo
       Record."
   ::= { ibBmaFruInfoEntry 8 } 

ibBmaFruInfoManufacturerName OBJECT-TYPE
   SYNTAX OCTET STRING (SIZE(8))
   MAX-ACCESS read-only 
   STATUS current 
   DESCRIPTION  
      "The FRU Manufacturer Name."
   REFERENCE
      "InfiniBand Architecture Release 1.0.a. Vol. 2.
       Section 13.7.8 FRUInfo Record. Table 107 FRUInfo
       Record."
   ::= { ibBmaFruInfoEntry 9 } 

ibBmaFruInfoProductName OBJECT-TYPE
   SYNTAX OCTET STRING (SIZE(8))
   MAX-ACCESS read-only 
   STATUS current 
   DESCRIPTION  
      "The FRU Product name."
   REFERENCE
      "InfiniBand Architecture Release 1.0.a. Vol. 2.
       Section 13.7.8 FRUInfo Record. Table 107 FRUInfo
       Record."
   ::= { ibBmaFruInfoEntry 10 } 

ibBmaFruInfoManufacturerID OBJECT-TYPE
   SYNTAX OCTET STRING (SIZE(8))
   MAX-ACCESS read-only 
   STATUS current 
   DESCRIPTION  
      "The FRU Manufacturer ID."

   REFERENCE
      "InfiniBand Architecture Release 1.0.a. Vol. 2.
       Section 13.7.8 FRUInfo Record. Table 107 FRUInfo
       Record."
   ::= { ibBmaFruInfoEntry 11 } 

ibBmaFruInfoManDateAndTime OBJECT-TYPE
   SYNTAX DateAndTime
   MAX-ACCESS read-only 
   STATUS current 
   DESCRIPTION  
      "Manufacture date and time."
   REFERENCE
      "InfiniBand Architecture Release 1.0.a. Vol. 2.
       Section 13.7.8 FRUInfo Record. Table 107 FRUInfo
       Record."
   ::= { ibBmaFruInfoEntry 12 } 

--**************************************************************** 
-- BMA Port Connection Info Group
--
-- DESCRIPTION: This group provides information about the entity to
--    which the port connects. 
--**************************************************************** 

ibBmaPortConnectInfo OBJECT IDENTIFIER ::= { ibBmaVpd 4 } 

ibBmaPortConNumConnection OBJECT-TYPE
   SYNTAX Integer32(1..254)
   MAX-ACCESS read-only 
   STATUS current 
   DESCRIPTION
      "Number of port connections."
   REFERENCE
      "InfiniBand Architecture Release 1.0.a. Vol. 2.
       Section 13.7.9 PortConnectionInfo Record. Table 108
       PortConnectionInfoRecord."
   ::= { ibBmaPortConnectInfo 1 } 

ibBmaPortConnectTable OBJECT-TYPE
   SYNTAX SEQUENCE OF IbBmaPortConnectEntry
   MAX-ACCESS not-accessible
   STATUS current
   DESCRIPTION
      "This table contains objects that describe the Port
       Connections present in the managed device."
   ::= { ibBmaPortConnectInfo 2 } 

ibBmaPortConnectEntry OBJECT-TYPE
   SYNTAX IbBmaPortConnectEntry
   MAX-ACCESS not-accessible
   STATUS current
   DESCRIPTION
      "The column definitions for the Port Connection table."
   INDEX { ibBmaPortConnectIndex }
   ::= { ibBmaPortConnectTable 1 } 

IbBmaPortConnectEntry ::= SEQUENCE {
   ibBmaPortConnectIndex Integer32,
   ibBmaPortConInternalCon INTEGER,
   ibBmaPortConMediaClass INTEGER,
   ibBmaPortConConClass INTEGER
}

ibBmaPortConnectIndex OBJECT-TYPE
   SYNTAX Integer32(1..254)
   MAX-ACCESS not-accessible 
   STATUS current 
   DESCRIPTION
      "Index for the Port Connection table."
   ::= { ibBmaPortConnectEntry 1 } 

ibBmaPortConInternalCon OBJECT-TYPE
   SYNTAX INTEGER
            {
            unspecified(1),
            terminateWithoutGoing(2),
            terminateAfterGoing(3),
            noInternelConnection(4)
            }
   MAX-ACCESS read-only 
   STATUS current 
   DESCRIPTION
      "Internal connection type."
   REFERENCE
      "InfiniBand Architecture Release 1.0.a. Vol. 2.
       Section 13.7.9 PortConnectionInfo Record. Table 108
       PortConnectionInfoRecord."
   ::= { ibBmaPortConnectEntry 2 } 

ibBmaPortConMediaClass OBJECT-TYPE
   SYNTAX INTEGER
            {
            unspecified(1),
            copper(2),
            fiber(3),
            pcb(4),
            repeaterThenCopper(5),
            repeaterThenFiber(6),
            repeaterThenNode(7),
            reserved(8)
            }
   MAX-ACCESS read-only
   STATUS current 
   DESCRIPTION
      "Connection Media Class."

   REFERENCE
      "InfiniBand Architecture Release 1.0.a. Vol. 2.
       Section 13.7.9 PortConnectionInfo Record. Table 108
       PortConnectionInfoRecord."
   ::= { ibBmaPortConnectEntry 3 } 

ibBmaPortConConClass OBJECT-TYPE
   SYNTAX INTEGER
            {
            unspecified(1),
            nonSpecifyRemovable(2),
            backplaneSide(3),
            moduleSide(4),
            nonRemovable(5),
            noInfo(6),
            reserved(7)
            }
   MAX-ACCESS read-only
   STATUS current 
   DESCRIPTION
      "Connection Class."
   REFERENCE
      "InfiniBand Architecture Release 1.0.a. Vol. 2.
       Section 13.7.9 PortConnectionInfo Record. Table 108
       PortConnectionInfoRecord."
   ::= { ibBmaPortConnectEntry 4 } 

--**************************************************************** 
-- BMA Module Power Info Group
--
-- DESCRIPTION: This group provides information about the power
--    consumption, startup characteristics, and power management
--    capabilities for a Module.
--**************************************************************** 

ibBmaModPowerInfo OBJECT IDENTIFIER ::= { ibBmaVpd 5 } 

ibBmaOperThermalPower OBJECT-TYPE
   SYNTAX Integer32(0..131071)
   MAX-ACCESS read-only
   STATUS current 
   DESCRIPTION
      "Maximum amount of power dissipated under normal operation
       including any vendor supplied exerciser over any sliding
       60 second window expressed in mW. If this value is 
       unspecified, a 0 should be returned."
   REFERENCE
      "InfiniBand Architecture Release 1.0.a. Vol. 2.
       Section 13.7.10 ModulePowerInfo Record. Table 109
       ModulePowerInfoRecord."
   ::= { ibBmaModPowerInfo 1 }

ibBmaOperCurrent OBJECT-TYPE
   SYNTAX Integer32(0..16383)
   MAX-ACCESS read-only
   STATUS current 
   DESCRIPTION
      "Maximum amount of current drawn under normal operation
       including any vendor supplied exerciser across the 
       range of VBulk (expressed in mA). If this value is
       unspecified, a 0 should be returned."
   REFERENCE
      "InfiniBand Architecture Release 1.0.a. Vol. 2.
       Section 13.7.10 ModulePowerInfo Record. Table 109
       ModulePowerInfoRecord."
   ::= { ibBmaModPowerInfo 2 }

ibBmaIdleCurrent OBJECT-TYPE
   SYNTAX Integer32(0..16383)
   MAX-ACCESS read-only
   STATUS current 
   DESCRIPTION
      "Amount of current that a fully initialized device 
       draws when waiting for functional requests (in mA).
       If this value is unspecified, a 0 will be returned."
   REFERENCE
      "InfiniBand Architecture Release 1.0.a. Vol. 2.
       Section 13.7.10 ModulePowerInfo Record. Table 109
       ModulePowerInfoRecord."
   ::= { ibBmaModPowerInfo 3 }

ibBmaInitCurrent OBJECT-TYPE
   SYNTAX Integer32(0..16383)
   MAX-ACCESS read-only
   STATUS current 
   DESCRIPTION
      "Amount of current drawn during Modules Built-in
       self test or self-initialization execution across the
       range of VBulk (in mA). If this value is unspecified,
       a 0 will be returned."
   REFERENCE
      "InfiniBand Architecture Release 1.0.a. Vol. 2.
       Section 13.7.10 ModulePowerInfo Record. Table 109
       ModulePowerInfoRecord."
   ::= { ibBmaModPowerInfo 4 }

ibBmaInitTime OBJECT-TYPE
   SYNTAX Integer32(0..65535)
   MAX-ACCESS read-only
   STATUS current 
   DESCRIPTION
      "Amount of time (in 10's of ms) from the end of Module
       Reset to the end of BIST and/or module self-initialization
       complete under non-fault conditions. The module must be
       ready for normal operation at the conclusion of this time,
       excluding any external software driven initialization. 
       If the value is unspecified, a 0 will be returned."
   REFERENCE
      "InfiniBand Architecture Release 1.0.a. Vol. 2.
       Section 13.7.10 ModulePowerInfo Record. Table 109
       ModulePowerInfoRecord."
   ::= { ibBmaModPowerInfo 5 }

ibBmaIsMStandbySupported OBJECT-TYPE
   SYNTAX TruthValue
   MAX-ACCESS read-only
   STATUS current 
   DESCRIPTION
      "Capability flag to indicate if MStandby is supported."
   REFERENCE
      "InfiniBand Architecture Release 1.0.a. Vol. 2.
       Section 13.7.10 ModulePowerInfo Record. Table 109
       ModulePowerInfoRecord."
   ::= { ibBmaModPowerInfo 6 }

ibBmaIsPowerMgmtSupported OBJECT-TYPE
   SYNTAX TruthValue
   MAX-ACCESS read-only
   STATUS current 
   DESCRIPTION
      "Capability flag to indicate if power management is
       supported."
   REFERENCE
      "InfiniBand Architecture Release 1.0.a. Vol. 2.
       Section 13.7.10 ModulePowerInfo Record. Table 109
       ModulePowerInfoRecord."
   ::= { ibBmaModPowerInfo 7 }

ibBmaIsUSleepSupported OBJECT-TYPE
   SYNTAX TruthValue
   MAX-ACCESS read-only
   STATUS current 
   DESCRIPTION
      "Capability flag to indicate if USleep is supported."
   REFERENCE
      "InfiniBand Architecture Release 1.0.a. Vol. 2.
       Section 13.7.10 ModulePowerInfo Record. Table 109
       ModulePowerInfoRecord."
   ::= { ibBmaModPowerInfo 8 }

ibBmaIsUStandbySupported OBJECT-TYPE
   SYNTAX TruthValue
   MAX-ACCESS read-only
   STATUS current 
   DESCRIPTION
      "Capability flag to indicate if UStandby is supported."
   REFERENCE
      "InfiniBand Architecture Release 1.0.a. Vol. 2.
       Section 13.7.10 ModulePowerInfo Record. Table 109
       ModulePowerInfoRecord."
   ::= { ibBmaModPowerInfo 9 }

ibBmaPowerClass OBJECT-TYPE
   SYNTAX INTEGER
            {
            unspecified(1),
            powerClass1(2),
            powerClass2(3),
            other(4)
            }
   MAX-ACCESS read-only
   STATUS current 
   DESCRIPTION
      "Power class."
   REFERENCE
      "InfiniBand Architecture Release 1.0.a. Vol. 2.
       Section 13.7.10 ModulePowerInfo Record. Table 109
       ModulePowerInfoRecord."
   ::= { ibBmaModPowerInfo 10 }

ibBmaRedundantPower OBJECT-TYPE
   SYNTAX INTEGER
               {
               unspecified(1),
               noRedundancy(2),
               redundancy(3),
               reserved(4)
               }
   MAX-ACCESS read-only
   STATUS current 
   DESCRIPTION
      "Redundant power converter capability."
   REFERENCE
      "InfiniBand Architecture Release 1.0.a. Vol. 2.
       Section 13.7.10 ModulePowerInfo Record. Table 109
       ModulePowerInfoRecord."
   ::= { ibBmaModPowerInfo 11 }

--**************************************************************** 
-- IOC Power Management Info Group
--
--   DESCRIPTION: This group describes the power management 
--      capabilities of the IOCs assoicated with an IOUnit. If a
--      Module contains multiple IOUnits and several IOCs, the
--      information about all such IOCs appear sequentially in 
--      the IOCPMInfo record.
--**************************************************************** 

ibBmaPowerMgmtInfo OBJECT IDENTIFIER ::= { ibBmaVpd 6 } 

ibBmaPowerMgmtIocCount OBJECT-TYPE
   SYNTAX Integer32(1..255)
   MAX-ACCESS read-only
   STATUS current 
   DESCRIPTION
      "Number of IOC capabilities."
   REFERENCE
      "InfiniBand Architecture Release 1.0.a. Vol. 2.
       Section 13.7.11 IOCOMInfo Record. Table 110
       IOCPMInfo Record."
   ::= { ibBmaPowerMgmtInfo 1 }

ibBmaPowerMgmtIocTable OBJECT-TYPE
   SYNTAX SEQUENCE OF IbBmaPowerMgmtIocEntry
   MAX-ACCESS not-accessible
   STATUS current
   DESCRIPTION
      "This table contains objects that describe the Power
       Management for each IOC."
   ::= { ibBmaPowerMgmtInfo 2 }

ibBmaPowerMgmtIocEntry OBJECT-TYPE
   SYNTAX IbBmaPowerMgmtIocEntry
   MAX-ACCESS not-accessible
   STATUS current
   DESCRIPTION
      "The column definitions for the Power Managment IOC table."
   INDEX { ibBmaPowerMgmtIocIndex }
   ::= { ibBmaPowerMgmtIocTable 1 } 

IbBmaPowerMgmtIocEntry ::= SEQUENCE {
   ibBmaPowerMgmtIocIndex Integer32,
   ibBmaPMIsIDozeSupported TruthValue,
   ibBmaPMIsINapSupported TruthValue,
   ibBmaPMIsISleepSupported TruthValue,
   ibBmaPMIsIStandbySupported TruthValue,
   ibBmaPMWREIsIDozeSupported TruthValue,
   ibBmaPMWREIsINapSupported TruthValue,
   ibBmaPMWREIsISleepSupported TruthValue,
   ibBmaPMWREIsIStandbySupported TruthValue,
   ibBmaPwrMgtIDozeCurrent Integer32, 
   ibBmaPwrMgtINapCurrent Integer32,
   ibBmaPwrMgtISleepCurrent Integer32,
   ibBmaPwrMgtIStandbyCurrent Integer32
}

ibBmaPowerMgmtIocIndex OBJECT-TYPE
   SYNTAX Integer32(1..254)
   MAX-ACCESS not-accessible 
   STATUS current 
   DESCRIPTION
      "Index for the Power Management IOC table."
   ::= { ibBmaPowerMgmtIocEntry 1 } 

ibBmaPMIsIDozeSupported OBJECT-TYPE
   SYNTAX TruthValue
   MAX-ACCESS read-only
   STATUS current 
   DESCRIPTION
      "Flag for Is I Doze supported."
   REFERENCE
      "InfiniBand Architecture Release 1.0.a. Vol. 2.
       Section 13.7.11 IOCOMInfo Record. Table 110
       IOCPMInfo Record."
   ::= { ibBmaPowerMgmtIocEntry 2 } 

ibBmaPMIsINapSupported OBJECT-TYPE
   SYNTAX TruthValue
   MAX-ACCESS read-only
   STATUS current 
   DESCRIPTION
      "Flag for Is I Nap supported."
   REFERENCE
      "InfiniBand Architecture Release 1.0.a. Vol. 2.
       Section 13.7.11 IOCOMInfo Record. Table 110
       IOCPMInfo Record."
   ::= { ibBmaPowerMgmtIocEntry 3 } 

ibBmaPMIsISleepSupported OBJECT-TYPE
   SYNTAX TruthValue
   MAX-ACCESS read-only
   STATUS current 
   DESCRIPTION
      "Flag for Is I Sleep supported."
   REFERENCE
      "InfiniBand Architecture Release 1.0.a. Vol. 2.
       Section 13.7.11 IOCOMInfo Record. Table 110
       IOCPMInfo Record."
   ::= { ibBmaPowerMgmtIocEntry 4 } 

ibBmaPMIsIStandbySupported OBJECT-TYPE
   SYNTAX TruthValue
   MAX-ACCESS read-only
   STATUS current 
   DESCRIPTION
      "Flag for Is I Standby supported."
   REFERENCE
      "InfiniBand Architecture Release 1.0.a. Vol. 2.
       Section 13.7.11 IOCOMInfo Record. Table 110
       IOCPMInfo Record."
   ::= { ibBmaPowerMgmtIocEntry 5 } 

ibBmaPMWREIsIDozeSupported OBJECT-TYPE
   SYNTAX TruthValue
   MAX-ACCESS read-only
   STATUS current 
   DESCRIPTION
      "Flag for Is WRE I Doze supported."

   REFERENCE
      "InfiniBand Architecture Release 1.0.a. Vol. 2.
       Section 13.7.11 IOCOMInfo Record. Table 110
       IOCPMInfo Record."
   ::= { ibBmaPowerMgmtIocEntry 6 } 

ibBmaPMWREIsINapSupported OBJECT-TYPE
   SYNTAX TruthValue
   MAX-ACCESS read-only
   STATUS current 
   DESCRIPTION
      "Flag for Is WRE I Nap supported."
   REFERENCE
      "InfiniBand Architecture Release 1.0.a. Vol. 2.
       Section 13.7.11 IOCOMInfo Record. Table 110
       IOCPMInfo Record."
   ::= { ibBmaPowerMgmtIocEntry 7 } 

ibBmaPMWREIsISleepSupported OBJECT-TYPE
   SYNTAX TruthValue
   MAX-ACCESS read-only
   STATUS current 
   DESCRIPTION
      "Flag for Is WRE I Sleep supported."
   REFERENCE
      "InfiniBand Architecture Release 1.0.a. Vol. 2.
       Section 13.7.11 IOCOMInfo Record. Table 110
       IOCPMInfo Record."
   ::= { ibBmaPowerMgmtIocEntry 8 } 

ibBmaPMWREIsIStandbySupported OBJECT-TYPE
   SYNTAX TruthValue
   MAX-ACCESS read-only
   STATUS current 
   DESCRIPTION
      "Flag for Is WRE I Standby supported."
   REFERENCE
      "InfiniBand Architecture Release 1.0.a. Vol. 2.
       Section 13.7.11 IOCOMInfo Record. Table 110
       IOCPMInfo Record."
   ::= { ibBmaPowerMgmtIocEntry 9 } 

ibBmaPwrMgtIDozeCurrent OBJECT-TYPE
   SYNTAX Integer32(0..16384)
   MAX-ACCESS read-only
   STATUS current 
   DESCRIPTION
      "The amount of total current drawn from the Bulk Power
       while in I-Doze PM state. The range is from 0 to 16,384
       milliAmps."
   REFERENCE
      "InfiniBand Architecture Release 1.0.a. Vol. 2.
       Section 13.7.11 IOCOMInfo Record. Table 110
       IOCPMInfo Record."
   ::= { ibBmaPowerMgmtIocEntry 10 } 

ibBmaPwrMgtINapCurrent OBJECT-TYPE
   SYNTAX Integer32(0..16384)
   MAX-ACCESS read-only
   STATUS current 
   DESCRIPTION
      "The amount of total current drawn from the Bulk Power
       while in I-Nap PM state. The range is from 0 to 16,384
       milliAmps."
   REFERENCE
      "InfiniBand Architecture Release 1.0.a. Vol. 2.
       Section 13.7.11 IOCOMInfo Record. Table 110
       IOCPMInfo Record."
   ::= { ibBmaPowerMgmtIocEntry 11 } 

ibBmaPwrMgtISleepCurrent OBJECT-TYPE
   SYNTAX Integer32(0..16384)
   MAX-ACCESS read-only
   STATUS current 
   DESCRIPTION
      "The amount of total current drawn from the Bulk Power
       while in I-Sleep PM state. The range is from 0 to 16,384
       milliAmps."
   REFERENCE
      "InfiniBand Architecture Release 1.0.a. Vol. 2.
       Section 13.7.11 IOCOMInfo Record. Table 110
       IOCPMInfo Record."
   ::= { ibBmaPowerMgmtIocEntry 12 } 

ibBmaPwrMgtIStandbyCurrent OBJECT-TYPE
   SYNTAX Integer32(0..16384)
   MAX-ACCESS read-only
   STATUS current 
   DESCRIPTION
      "The amount of total current drawn from the Auxilliary Power
       while in I-Standby PM state. The Bulk Power drawn is defined
       to be 0 amps. The range is from 0 to 16,384 milliAmps."
   REFERENCE
      "InfiniBand Architecture Release 1.0.a. Vol. 2.
       Section 13.7.11 IOCOMInfo Record. Table 110
       IOCPMInfo Record."
   ::= { ibBmaPowerMgmtIocEntry 13 } 

--**************************************************************** 
-- CME Info Group
--
--   DESCRIPTION: This group contains additional information 
--      about the CME.
--**************************************************************** 

ibBmaCmeInfo OBJECT IDENTIFIER ::= { ibBmaVpd 7 } 
ibBmaCmeGuidType OBJECT-TYPE
   SYNTAX INTEGER 
           { 
           none(1),   -- none specified; GUID value is 0
           guid64(2), -- EUI-64 (8 bytes)
           guid48(3), -- EUI-48 (6 bytes)
           guid16(4), -- SMBIOS/IPMI/OSF/WFM/MSFT GUID/UUID (16 bytes)
           guid8(5)   -- SMBus 2.0 UDID (8 bytes)
           }
   MAX-ACCESS read-only 
   STATUS current 
   DESCRIPTION 
      "The CME GUID type."
   REFERENCE
      "InfiniBand Architecture Release 1.0.a. Vol. 2.
       Section 13.7.12; Table 111 CmeInfo Record."
   ::= { ibBmaCmeInfo 1 } 

ibBmaCmeGuidValue OBJECT-TYPE
   SYNTAX OCTET STRING (SIZE(16)) 
   MAX-ACCESS read-only 
   STATUS current 
   DESCRIPTION 
      "The GUID assigned to this CME. Needs to hold the longest 
       possible GUID type (guid16(4))."
   REFERENCE
      "InfiniBand Architecture Release 1.0.a. Vol. 2.
       Section 13.7.12; Table 111 CmeInfo Record."
   ::= { ibBmaCmeInfo 2 } 

ibBmaCmeFirmMinorRev OBJECT-TYPE
   SYNTAX OCTET STRING (SIZE(1)) 
   MAX-ACCESS read-only 
   STATUS current 
   DESCRIPTION 
      "The minor revision of the CME firmware."
   REFERENCE
      "InfiniBand Architecture Release 1.0.a. Vol. 2.
       Section 13.7.12; Table 111 CmeInfo Record."
   ::= { ibBmaCmeInfo 3 } 

ibBmaCmeFirmMajorRev OBJECT-TYPE
   SYNTAX OCTET STRING (SIZE(1)) 
   MAX-ACCESS read-only 
   STATUS current 
   DESCRIPTION 
      "The major revision of the CME firmware."
   REFERENCE
      "InfiniBand Architecture Release 1.0.a. Vol. 2.
       Section 13.7.12; Table 111 CmeInfo Record."
   ::= { ibBmaCmeInfo 4 } 

ibBmaCmeSlotNumbers OBJECT-TYPE
   SYNTAX OCTET STRING (SIZE(32))
   MAX-ACCESS read-only
   STATUS current
   DESCRIPTION
      "A 256 bit mask representing IB ports for which the CME provides
       IB-ML access. The mask allows slot numbers to be non-sequential.
       Slot numbers must be in the range 1 to 254. 0 is assigned to the
       CME and its containing Chassis via CME."
   REFERENCE
      "InfiniBand Architecture Release 1.0.a. Vol. 2. Section 13.7.12;
       Table 111 CmeInfo Record."
   ::= { ibBmaCmeInfo 5 } 

--**************************************************************** 
-- OEM Info Group
--
--   DESCRIPTION: This group contains OEM records of OEM-specified data.
--**************************************************************** 

ibBmaOemInfo OBJECT IDENTIFIER ::= { ibBmaVpd 8 } 

ibBmaOemTable OBJECT-TYPE
   SYNTAX SEQUENCE OF IbBmaOemEntry
   MAX-ACCESS not-accessible
   STATUS current
   DESCRIPTION
      "This table contains objects that describe the OEM
       entries."
   ::= { ibBmaOemInfo 1 }

ibBmaOemEntry OBJECT-TYPE
   SYNTAX IbBmaOemEntry
   MAX-ACCESS not-accessible
   STATUS current
   DESCRIPTION
      "The column definitions for the OEM table."
   INDEX { ibBmaOemIndex }
   ::= { ibBmaOemTable 1 } 

IbBmaOemEntry ::= SEQUENCE {
   ibBmaOemIndex Integer32,
   ibBmaOemIdType INTEGER,
   ibBmaOemIdValue OCTET STRING,
   ibBmaOemDataLength Integer32,
   ibBmaOemDataBuf OCTET STRING
}

ibBmaOemIndex OBJECT-TYPE
   SYNTAX Integer32(1..254)
   MAX-ACCESS not-accessible 
   STATUS current 
   DESCRIPTION
      "Index for the OEM table."
   ::= { ibBmaOemEntry 1 } 

ibBmaOemIdType OBJECT-TYPE
   SYNTAX INTEGER 
           { 
           other(1),                -- reserved
           companyId(2),            -- company ID
           enterpriseNumBased(3)    -- enterprise number based ID
           }
   MAX-ACCESS read-only
   STATUS current 
   DESCRIPTION
      "The OEM ID type."
   ::= { ibBmaOemEntry 2 } 

ibBmaOemIdValue OBJECT-TYPE
   SYNTAX OCTET STRING (SIZE(3))
   MAX-ACCESS read-only
   STATUS current 
   DESCRIPTION
      "The OEM ID value."
   ::= { ibBmaOemEntry 3 } 

ibBmaOemDataLength OBJECT-TYPE
   SYNTAX Integer32(0..255)
   MAX-ACCESS read-only
   STATUS current 
   DESCRIPTION
      "The OEM Data field length."
   ::= { ibBmaOemEntry 4 } 

ibBmaOemDataBuf OBJECT-TYPE
   SYNTAX OCTET STRING (SIZE(255))
   MAX-ACCESS read-only
   STATUS current 
   DESCRIPTION
      "The OEM Data buffer."
   ::= { ibBmaOemEntry 5 } 

--**************************************************************** 
-- Buddy Info Group
--
--   DESCRIPTION: This group contains the Buddy count and the Node
--      GUIDs of the InfiniBand nodes (and other entities) that 
--      belong to the same enclosure. 
--**************************************************************** 

ibBmaBuddyInfo OBJECT IDENTIFIER ::= { ibBmaVpd 9 } 

ibBmaBuddyCount OBJECT-TYPE
   SYNTAX Integer32(1..65535) 
   MAX-ACCESS read-only
   STATUS current 
   DESCRIPTION  
      "The Buddy count. This is the number of InfiniBand nodes,
       excluding this node, that belong to the same enclosure as
       the node reporting this record. If no other node belongs to
       the same enclosure, the value will be 0 and there will be
       no entries in the ibBmaBuddyTable."
   REFERENCE
      "InfiniBand Architecture Release 1.0.a. Vol. 2.
       Section 13.7.14; Table 113 BuddyInfo Record."
   ::= { ibBmaBuddyInfo 1 } 

ibBmaBuddyTable OBJECT-TYPE
   SYNTAX SEQUENCE OF IbBmaBuddyEntry
   MAX-ACCESS not-accessible  
   STATUS current 
   DESCRIPTION
      "A table containing BMA Buddy Record information." 
   ::= { ibBmaBuddyInfo 2 } 

ibBmaBuddyEntry OBJECT-TYPE
   SYNTAX IbBmaBuddyEntry
   MAX-ACCESS not-accessible  
   STATUS current 
   DESCRIPTION
      "A conceptual row of the ibBmaBuddyTable containing
       information about a particular Buddy table entry." 
   INDEX { ibBmaBuddyIndex }
   ::= { ibBmaBuddyTable 1 } 

IbBmaBuddyEntry ::= SEQUENCE {
   ibBmaBuddyIndex Integer32,
   ibBmaBuddyGuidType INTEGER,
   ibBmaBuddyGuidValue OCTET STRING
   }

ibBmaBuddyIndex OBJECT-TYPE
   SYNTAX Integer32(1..65535) 
   MAX-ACCESS not-accessible 
   STATUS current 
   DESCRIPTION  
      "Index that identifies this Buddy table entry."
   ::= { ibBmaBuddyEntry 1 }

ibBmaBuddyGuidType OBJECT-TYPE
   SYNTAX INTEGER 
           { 
           none(1),   -- none specified; GUID value is 0
           guid64(2), -- EUI-64 (8 bytes)
           guid48(3), -- EUI-48 (6 bytes)
           guid16(4), -- SMBIOS/IPMI/OSF/WFM/MSFT GUID/UUID (16 bytes)
           guid8(5)   -- SMBus 2.0 UDID (8 bytes)
           }
   MAX-ACCESS read-only 
   STATUS current 
   DESCRIPTION 
      "The Buddy node GUID type."
   REFERENCE
      "InfiniBand Architecture Release 1.0.a. Vol. 2.
       Section 13.7.14; Table 113 BuddyInfo Record."
   ::= { ibBmaBuddyEntry 2 } 

ibBmaBuddyGuidValue OBJECT-TYPE
   SYNTAX OCTET STRING (SIZE(16)) 
   MAX-ACCESS read-only 
   STATUS current 
   DESCRIPTION 
      "The GUID assigned to this node. Needs to hold the longest 
       possible GUID type (guid16(4))."
   REFERENCE
      "InfiniBand Architecture Release 1.0.a. Vol. 2.
       Section 13.7.14; Table 113 BuddyInfo Record."
   ::= { ibBmaBuddyEntry 3 } 

--**************************************************************** 
-- BMA Asset Tag Info Group
--
-- DESCRIPTION: This group provides information about the Asset
--    Tags.
--**************************************************************** 

ibBmaAssetTagInfo OBJECT IDENTIFIER ::= { ibBmaVpd 10 } 

ibBmaAssetTagTable OBJECT-TYPE
   SYNTAX SEQUENCE OF IbBmaAssetTagEntry
   MAX-ACCESS not-accessible  
   STATUS current 
   DESCRIPTION
      "A table containing BMA Asset Tag information." 
   ::= { ibBmaAssetTagInfo 1 } 

ibBmaAssetTagEntry OBJECT-TYPE
   SYNTAX IbBmaAssetTagEntry
   MAX-ACCESS not-accessible  
   STATUS current 
   DESCRIPTION
      "A conceptual row of the ibBmaAssetTagTable containing
       information about a particular Asset Tag entry." 
   INDEX { ibBmaAssetTagIndex }
   ::= { ibBmaAssetTagTable 1 } 

IbBmaAssetTagEntry ::= SEQUENCE {
   ibBmaAssetTagIndex Integer32,
   ibBmaAssetTagFruHandle Integer32,
   ibBmaAssetTagLength Integer32,
   ibBmaAssetTagValue OCTET STRING
   }

ibBmaAssetTagIndex OBJECT-TYPE
   SYNTAX Integer32(1..65535) 
   MAX-ACCESS not-accessible 
   STATUS current 
   DESCRIPTION  
      "Index that identifies this Asset Tag table entry."
   ::= { ibBmaAssetTagEntry 1 }

ibBmaAssetTagFruHandle OBJECT-TYPE
   SYNTAX Integer32(1..255)
   MAX-ACCESS read-only
   STATUS current
   DESCRIPTION
      "The FRU handle."
   REFERENCE
      "InfiniBand Architecture Release 1.0.a. Vol. 2.
       Section 13.7.15; Table 114 AssetTagRecord."
   ::= { ibBmaAssetTagEntry 2 }

ibBmaAssetTagLength OBJECT-TYPE
   SYNTAX Integer32(1..255)
   MAX-ACCESS read-only 
   STATUS current
   DESCRIPTION
      "The length of the ibBmaAssetTagValue object."
   REFERENCE
      "InfiniBand Architecture Release 1.0.a. Vol. 2.
       Section 13.7.15; Table 114 AssetTagRecord."
   ::= { ibBmaAssetTagEntry 3 }

ibBmaAssetTagValue OBJECT-TYPE
   SYNTAX OCTET STRING (SIZE(255))
   MAX-ACCESS read-only
   STATUS current
   DESCRIPTION
      "The Asset Tag."
   REFERENCE
      "InfiniBand Architecture Release 1.0.a. Vol. 2.
       Section 13.7.15; Table 114 AssetTagRecord."
   ::= { ibBmaAssetTagEntry 4 }

--**************************************************************** 
-- Module Conformance Statement 
--
-- DESCRIPTION: The module conformance statement includes the
--    compliance statements and the units of conformance
--    section.
--**************************************************************** 
ibBmaCompliances OBJECT IDENTIFIER ::= { ibBmaConformance 1 }

ibBmaGroups OBJECT IDENTIFIER ::= { ibBmaConformance 2 }
--**************************************************************** 
-- Compliance Statements 
--**************************************************************** 

ibBmaBasicNodeCompliance MODULE-COMPLIANCE
   STATUS current
   DESCRIPTION
      "The basic node implementation requirements for agents that
       support the IPOIB BMA MIB."
   MODULE -- this module
       MANDATORY-GROUPS { 
                        ibBmaBmuInfoGroup
                        }
   ::= { ibBmaCompliances 1 }

ibBmaFullNodeCompliance MODULE-COMPLIANCE
   STATUS current
   DESCRIPTION
      "The full node implementation requirements for agents that
       support the IPOIB BMA MIB."
   MODULE -- this module
       MANDATORY-GROUPS { 
                        ibBmaBmuInfoGroup,
                        ibBmaBKeyInfoGroup,
                        ibBmaModuleInfoGroup,
                        ibBmaChassisInfoGroup,
                        ibBmaFruInfoGroup,
                        ibBmaPortConnectInfoGroup,
                        ibBmaModPowerInfoGroup,
                        ibBmaPowerMgmtInfoGroup,
                        ibBmaCmeInfoGroup,
                        ibBmaOemInfoGroup,
                        ibBmaBuddyInfoGroup,
                        ibBmaAssetTagInfoGroup
                        }
   ::= { ibBmaCompliances 2 }

--**************************************************************** 
-- Units Of Conformance 
--**************************************************************** 

ibBmaBmuInfoGroup OBJECT-GROUP
   OBJECTS  {
       ibBmaBaseboardManagedUnitType,
       ibBmaIsIBMLSupported,
       ibBmaIBMLImplementation
   }
   STATUS current
   DESCRIPTION
      "The ibBmaBmuInfoGroup defines the MIB objects that describe
        information about the Baseboard Management Unit (BMU)."
   ::= { ibBmaGroups 1 }

ibBmaBKeyInfoGroup OBJECT-GROUP
   OBJECTS  {
       ibBmaIsBKeyNVRAM, 
       ibBmaBKeyValue,
       ibBmaBKeyProtectBit, 
       ibBmaBKeyLeasePeriod,
       ibBmaBKeyViolations 
   }
   STATUS current
   DESCRIPTION
      "The ibBmaBKeyInfo Group defines the MIB objects that describe
       information about the Baseboard Management keys (B_Keys)."
   ::= { ibBmaGroups 2 }

ibBmaModuleInfoGroup OBJECT-GROUP
   OBJECTS  {
       ibBmaModInfoModGuid,
       ibBmaModInfoModType,
       ibBmaModInfoModClass,
       ibBmaModInfoNodeCount,
       ibBmaModInfoLinkCount,
       ibBmaModInfoBckplaneLinkCnt,
       ibBmaModInfoIbmlCount,
       ibBmaModInfoBckPlaneIbmlCnt,
       ibBmaModInfoModuleSize,
       ibBmaModInfoFormFactor
   }
   STATUS current
   DESCRIPTION
      "The ibBmaModuleInfo Group defines the MIB objects that describe
       information about the module."
   ::= { ibBmaGroups 3 }

ibBmaChassisInfoGroup OBJECT-GROUP
   OBJECTS  {
       ibBmaChasInfoChassisGuid,
       ibBmaChasInfoSlotCount,
       ibBmaChasInfoAssignedSlotNum,
       ibBmaChasInfoSlotConnStatus,
       ibBmaChasInfoCmeAccess,
       ibBmaChasInfoProxyAccess,
       ibBmaChasInfoLockDrivesCtr,
       ibBmaChasInfoMechLockPresent
   }
   STATUS current
   DESCRIPTION
      "The ibBmaChassisInfo Group defines the MIB objects that describe
       information about a managed chassis."
   ::= { ibBmaGroups 4 }

ibBmaFruInfoGroup OBJECT-GROUP
   OBJECTS  {
       ibBmaFruInfoType,
       ibBmaFruInfoGuidType,
       ibBmaFruInfoGuidValue,
       ibBmaFruInfoSerialNumber,
       ibBmaFruInfoPartNumber,
       ibBmaFruInfoModelName,
       ibBmaFruInfoVersion,
       ibBmaFruInfoManufacturerName,
       ibBmaFruInfoProductName,
       ibBmaFruInfoManufacturerID,
       ibBmaFruInfoManDateAndTime
   }
   STATUS current
   DESCRIPTION
      "The ibBmaFruInfo Group defines the MIB objects that describe
       information about the Fru attributes."
   ::= { ibBmaGroups 5 }

ibBmaPortConnectInfoGroup OBJECT-GROUP
   OBJECTS  {
       ibBmaPortConNumConnection,
          ibBmaPortConInternalCon,
          ibBmaPortConMediaClass,
          ibBmaPortConConClass
   }
   STATUS current
   DESCRIPTION
      "The ibBmaPortConnectInfo Group defines the MIB objects that 
       describe information about the port connections."
   ::= { ibBmaGroups 6 }

ibBmaModPowerInfoGroup OBJECT-GROUP
   OBJECTS  {
       ibBmaOperThermalPower,
       ibBmaOperCurrent,
       ibBmaIdleCurrent,
       ibBmaInitCurrent,
       ibBmaInitTime,
       ibBmaIsMStandbySupported,
       ibBmaIsPowerMgmtSupported,
       ibBmaIsUSleepSupported,
       ibBmaIsUStandbySupported,
       ibBmaPowerClass,
       ibBmaRedundantPower
   }
   STATUS current
   DESCRIPTION
      "The ibBmaModPowerInfo Group defines the MIB objects that 
       describe information about the power attributes of the module."
   ::= { ibBmaGroups 7 }

ibBmaPowerMgmtInfoGroup OBJECT-GROUP
   OBJECTS  {
       ibBmaPowerMgmtIocCount,
       ibBmaPMIsIDozeSupported,
       ibBmaPMIsINapSupported,
       ibBmaPMIsISleepSupported,
       ibBmaPMIsIStandbySupported,
       ibBmaPMWREIsIDozeSupported,
       ibBmaPMWREIsINapSupported,
       ibBmaPMWREIsISleepSupported,
       ibBmaPMWREIsIStandbySupported,
       ibBmaPwrMgtIDozeCurrent,
       ibBmaPwrMgtINapCurrent,
       ibBmaPwrMgtISleepCurrent,
       ibBmaPwrMgtIStandbyCurrent
   }
   STATUS current
   DESCRIPTION
      "The ibBmaPowerMgmtInfo Group defines the MIB objects that 
       describe information about power management."
   ::= { ibBmaGroups 8 }

ibBmaCmeInfoGroup OBJECT-GROUP
   OBJECTS  {
       ibBmaCmeGuidType,
       ibBmaCmeGuidValue,
       ibBmaCmeFirmMinorRev,
       ibBmaCmeFirmMajorRev,
       ibBmaCmeSlotNumbers 
   }
   STATUS current
   DESCRIPTION
      "The ibBmaCmeInfo Group defines the MIB objects that describe
       information about the CME."
   ::= { ibBmaGroups 9 }

ibBmaOemInfoGroup OBJECT-GROUP
   OBJECTS  {
       ibBmaOemIdType,
       ibBmaOemIdValue,
       ibBmaOemDataLength,
       ibBmaOemDataBuf
   }
   STATUS current
   DESCRIPTION
      "The ibBmaOemInfo Group defines the MIB objects that describe
       information about OEM data."
   ::= { ibBmaGroups 10 }

ibBmaBuddyInfoGroup OBJECT-GROUP
   OBJECTS  {
       ibBmaBuddyCount,
       ibBmaBuddyGuidType,
       ibBmaBuddyGuidValue
   }
   STATUS current
   DESCRIPTION
      "The ibBmaBuddyInfo Group defines the MIB objects that describe
       information about the Buddy Info."
   ::= { ibBmaGroups 11 }

ibBmaAssetTagInfoGroup OBJECT-GROUP
   OBJECTS  {
       ibBmaAssetTagFruHandle,
       ibBmaAssetTagLength,
       ibBmaAssetTagValue
   }
   STATUS current
   DESCRIPTION
      "The ibBmaAssetTagInfo Group defines the MIB objects that 
       describe information about the asset tags."
   ::= { ibBmaGroups 12 }

END 

--    
--    Copyright (C) The Internet Society (2005).  This document is
--    subject to the rights, licenses and restrictions contained in BCP
--    78, and except as set forth therein, the authors retain all their
--    rights.
--    
--    This document and translations of it may be copied and
--    furnished to others, and derivative works that comment on
--    or otherwise explain it or assist in its implementation may
--    be prepared, copied, published and distributed, in whole or
--    in part, without restriction of any kind, provided that the
--    above copyright notice and this paragraph are included on
--    all such copies and derivative works.  However, this document
--    itself may not be modified in any way, such as by removing the
--    copyright notice or references to the Internet Society or other 
--    Internet organizations, except as needed for the purpose of 
--    developing Internet standards in which case the procedures for 
--    copyrights defined in the Internet Standards process must be 
--    followed, or as required to translate it into languages other 
--    than English.
--    
--    The limited permissions granted above are perpetual and
--    will not be revoked by the Internet Society or its
--    successors or assigns. 
-- 
--    This document and the information contained herein are provided
--    on an "AS IS" basis and THE CONTRIBUTOR, THE ORGANIZATION HE/SHE
--    REPRESENTS OR IS SPONSORED BY (IF ANY), THE INTERNET SOCIETY AND
--    THE INTERNET ENGINEERING TASK FORCE DISCLAIM ALL WARRANTIES,
--    EXPRESS OR IMPLIED, INCLUDING BUT NOT LIMITED TO ANY WARRANTY THAT
--    THE USE OF THE INFORMATION HEREIN WILL NOT INFRINGE ANY RIGHTS OR
--    ANY IMPLIED WARRANTIES OF MERCHANTABILITY OR FITNESS FOR A
--    PARTICULAR PURPOSE.
