BTI7800-INVENTORY-MIB DEFINITIONS ::= BEGIN
IMPORTS
    enterprises, MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
;

bTI7800-INVENTORY-MIB MODULE-IDENTITY
    LAST-UPDATED "201412230000Z"
    ORGANIZATION "@ORGANIZATION"
    CONTACT-INFO "@CONTACT-INFO"
    DESCRIPTION "This module provides object definitions for system
inventory and provisioned equipment on a BTI7800"
    REVISION "201412230000Z"
    DESCRIPTION "@REVISION-DESCRIPTION"
    ::= { enterprises 18070 2 9 3 2 }

UnsignedByte ::= TEXTUAL-CONVENTION
    DISPLAY-HINT "d"
    STATUS      current
    DESCRIPTION "xs:unsignedByte"
    SYNTAX      Unsigned32 (0 .. 255)

UnsignedShort ::= TEXTUAL-CONVENTION
    DISPLAY-HINT "d"
    STATUS      current
    DESCRIPTION "xs:unsignedShort"
    SYNTAX      Unsigned32 (0 .. 65535)

ConfdString ::= TEXTUAL-CONVENTION
    DISPLAY-HINT "1t"
    STATUS      current
    DESCRIPTION "xs: and confd: types mapped to strings"
    SYNTAX      OCTET STRING

InetAddressIP ::= TEXTUAL-CONVENTION
    STATUS      current
    DESCRIPTION "confd:inetAddressIP"
    SYNTAX      OCTET STRING (SIZE (4|16))

String ::= TEXTUAL-CONVENTION
    DISPLAY-HINT "1t"
    STATUS      current
    DESCRIPTION "xs:string"
    SYNTAX      OCTET STRING

BicIndexT ::= TEXTUAL-CONVENTION
    DISPLAY-HINT "d"
    STATUS      current
    DESCRIPTION "BIC identifier"
    SYNTAX      Unsigned32 (1 .. 2)

FanIndexT ::= TEXTUAL-CONVENTION
    DISPLAY-HINT "d"
    STATUS      current
    DESCRIPTION "Fan identifier"
    SYNTAX      Unsigned32 (1 .. 6)

PemIndexT ::= TEXTUAL-CONVENTION
    DISPLAY-HINT "d"
    STATUS      current
    DESCRIPTION "PEM identifier"
    SYNTAX      Unsigned32 (1 .. 4)

CmmIndexT ::= TEXTUAL-CONVENTION
    DISPLAY-HINT "d"
    STATUS      current
    DESCRIPTION "CMM identifier"
    SYNTAX      Unsigned32 (1 .. 2)

PortIndexT ::= TEXTUAL-CONVENTION
    DISPLAY-HINT "d"
    STATUS      current
    DESCRIPTION "Port identifier on a BIC"
    SYNTAX      Unsigned32 (1 .. 12)

ModuleIndexT ::= TEXTUAL-CONVENTION
    DISPLAY-HINT "d"
    STATUS      current
    DESCRIPTION "Module (payload card) identifier"
    SYNTAX      Unsigned32 (1 .. 14)

ChassisIndexT ::= TEXTUAL-CONVENTION
    DISPLAY-HINT "d"
    STATUS      current
    DESCRIPTION "Chassis identifier"
    SYNTAX      Unsigned32 (1 .. 16)

inventory-chassisTable OBJECT-TYPE
    SYNTAX      SEQUENCE OF Inventory-chassisEntry
    MAX-ACCESS  not-accessible
    STATUS      current
    DESCRIPTION ""
    ::= { bTI7800-INVENTORY-MIB 1 }

inventory-chassisEntry OBJECT-TYPE
    SYNTAX      Inventory-chassisEntry
    MAX-ACCESS  not-accessible
    STATUS      current
    DESCRIPTION ""
    INDEX { inventory-chassisChassisNum }
        ::= { inventory-chassisTable 1 }

Inventory-chassisEntry ::=
    SEQUENCE {
        inventory-chassisChassisNum ChassisIndexT,
        inventory-chassisName String,
        inventory-chassisPEC String,
        inventory-chassisRevision UnsignedShort,
        inventory-chassisSerialNumber String,
        inventory-chassisManufactureDate DateAndTime,
        inventory-chassisVendor String
    }

inventory-chassisChassisNum OBJECT-TYPE
    SYNTAX      ChassisIndexT
    MAX-ACCESS  not-accessible
    STATUS      current
    DESCRIPTION "Chassis identifier"
    ::= { inventory-chassisEntry 1 }

inventory-chassisName OBJECT-TYPE
    SYNTAX      String
    MAX-ACCESS  read-only
    STATUS      current
    DESCRIPTION "Entity name"
    ::= { inventory-chassisEntry 2 }

inventory-chassisPEC OBJECT-TYPE
    SYNTAX      String
    MAX-ACCESS  read-only
    STATUS      current
    DESCRIPTION "Product Equipment Code assigned by BTI"
    ::= { inventory-chassisEntry 3 }

inventory-chassisRevision OBJECT-TYPE
    SYNTAX      UnsignedShort
    MAX-ACCESS  read-only
    STATUS      current
    DESCRIPTION "Hardware revision number"
    ::= { inventory-chassisEntry 4 }

inventory-chassisSerialNumber OBJECT-TYPE
    SYNTAX      String
    MAX-ACCESS  read-only
    STATUS      current
    DESCRIPTION "Serial number"
    ::= { inventory-chassisEntry 5 }

inventory-chassisManufactureDate OBJECT-TYPE
    SYNTAX      DateAndTime
    MAX-ACCESS  read-only
    STATUS      current
    DESCRIPTION "Manufacturing date"
    ::= { inventory-chassisEntry 6 }

inventory-chassisVendor OBJECT-TYPE
    SYNTAX      String
    MAX-ACCESS  read-only
    STATUS      current
    DESCRIPTION "Vendor name"
    ::= { inventory-chassisEntry 7 }

inventory-fanTable OBJECT-TYPE
    SYNTAX      SEQUENCE OF Inventory-fanEntry
    MAX-ACCESS  not-accessible
    STATUS      current
    DESCRIPTION ""
    ::= { bTI7800-INVENTORY-MIB 2 }

inventory-fanEntry OBJECT-TYPE
    SYNTAX      Inventory-fanEntry
    MAX-ACCESS  not-accessible
    STATUS      current
    DESCRIPTION ""
    INDEX { inventory-fanChassisNum, inventory-fanSlotNum }
        ::= { inventory-fanTable 1 }

Inventory-fanEntry ::=
    SEQUENCE {
        inventory-fanChassisNum ChassisIndexT,
        inventory-fanSlotNum FanIndexT,
        inventory-fanName String,
        inventory-fanPEC String,
        inventory-fanRevision UnsignedShort,
        inventory-fanSerialNumber String,
        inventory-fanManufactureDate DateAndTime,
        inventory-fanVendor String
    }

inventory-fanChassisNum OBJECT-TYPE
    SYNTAX      ChassisIndexT
    MAX-ACCESS  not-accessible
    STATUS      current
    DESCRIPTION "Chassis identifier"
    ::= { inventory-fanEntry 1 }

inventory-fanSlotNum OBJECT-TYPE
    SYNTAX      FanIndexT
    MAX-ACCESS  not-accessible
    STATUS      current
    DESCRIPTION "Fan identifier"
    ::= { inventory-fanEntry 2 }

inventory-fanName OBJECT-TYPE
    SYNTAX      String
    MAX-ACCESS  read-only
    STATUS      current
    DESCRIPTION "Entity name"
    ::= { inventory-fanEntry 3 }

inventory-fanPEC OBJECT-TYPE
    SYNTAX      String
    MAX-ACCESS  read-only
    STATUS      current
    DESCRIPTION "Product Equipment Code assigned by BTI"
    ::= { inventory-fanEntry 4 }

inventory-fanRevision OBJECT-TYPE
    SYNTAX      UnsignedShort
    MAX-ACCESS  read-only
    STATUS      current
    DESCRIPTION "Hardware revision number"
    ::= { inventory-fanEntry 5 }

inventory-fanSerialNumber OBJECT-TYPE
    SYNTAX      String
    MAX-ACCESS  read-only
    STATUS      current
    DESCRIPTION "Serial number"
    ::= { inventory-fanEntry 6 }

inventory-fanManufactureDate OBJECT-TYPE
    SYNTAX      DateAndTime
    MAX-ACCESS  read-only
    STATUS      current
    DESCRIPTION "Manufacturing date"
    ::= { inventory-fanEntry 7 }

inventory-fanVendor OBJECT-TYPE
    SYNTAX      String
    MAX-ACCESS  read-only
    STATUS      current
    DESCRIPTION "Vendor name"
    ::= { inventory-fanEntry 8 }

inventory-pemTable OBJECT-TYPE
    SYNTAX      SEQUENCE OF Inventory-pemEntry
    MAX-ACCESS  not-accessible
    STATUS      current
    DESCRIPTION ""
    ::= { bTI7800-INVENTORY-MIB 3 }

inventory-pemEntry OBJECT-TYPE
    SYNTAX      Inventory-pemEntry
    MAX-ACCESS  not-accessible
    STATUS      current
    DESCRIPTION ""
    INDEX { inventory-pemChassisNum, inventory-pemSlotNum }
        ::= { inventory-pemTable 1 }

Inventory-pemEntry ::=
    SEQUENCE {
        inventory-pemChassisNum ChassisIndexT,
        inventory-pemSlotNum PemIndexT,
        inventory-pemName String,
        inventory-pemPEC String,
        inventory-pemRevision UnsignedShort,
        inventory-pemSerialNumber String,
        inventory-pemManufactureDate DateAndTime,
        inventory-pemVendor String
    }

inventory-pemChassisNum OBJECT-TYPE
    SYNTAX      ChassisIndexT
    MAX-ACCESS  not-accessible
    STATUS      current
    DESCRIPTION "Chassis identifier"
    ::= { inventory-pemEntry 1 }

inventory-pemSlotNum OBJECT-TYPE
    SYNTAX      PemIndexT
    MAX-ACCESS  not-accessible
    STATUS      current
    DESCRIPTION "PEM identifier"
    ::= { inventory-pemEntry 2 }

inventory-pemName OBJECT-TYPE
    SYNTAX      String
    MAX-ACCESS  read-only
    STATUS      current
    DESCRIPTION "Entity name"
    ::= { inventory-pemEntry 3 }

inventory-pemPEC OBJECT-TYPE
    SYNTAX      String
    MAX-ACCESS  read-only
    STATUS      current
    DESCRIPTION "Product Equipment Code assigned by BTI"
    ::= { inventory-pemEntry 4 }

inventory-pemRevision OBJECT-TYPE
    SYNTAX      UnsignedShort
    MAX-ACCESS  read-only
    STATUS      current
    DESCRIPTION "Hardware revision number"
    ::= { inventory-pemEntry 5 }

inventory-pemSerialNumber OBJECT-TYPE
    SYNTAX      String
    MAX-ACCESS  read-only
    STATUS      current
    DESCRIPTION "Serial number"
    ::= { inventory-pemEntry 6 }

inventory-pemManufactureDate OBJECT-TYPE
    SYNTAX      DateAndTime
    MAX-ACCESS  read-only
    STATUS      current
    DESCRIPTION "Manufacturing date"
    ::= { inventory-pemEntry 7 }

inventory-pemVendor OBJECT-TYPE
    SYNTAX      String
    MAX-ACCESS  read-only
    STATUS      current
    DESCRIPTION "Vendor name"
    ::= { inventory-pemEntry 8 }

inventory-cmmTable OBJECT-TYPE
    SYNTAX      SEQUENCE OF Inventory-cmmEntry
    MAX-ACCESS  not-accessible
    STATUS      current
    DESCRIPTION ""
    ::= { bTI7800-INVENTORY-MIB 4 }

inventory-cmmEntry OBJECT-TYPE
    SYNTAX      Inventory-cmmEntry
    MAX-ACCESS  not-accessible
    STATUS      current
    DESCRIPTION ""
    INDEX { inventory-cmmChassisNum, inventory-cmmSlotNum }
        ::= { inventory-cmmTable 1 }

Inventory-cmmEntry ::=
    SEQUENCE {
        inventory-cmmChassisNum ChassisIndexT,
        inventory-cmmSlotNum CmmIndexT,
        inventory-cmmName String,
        inventory-cmmPEC String,
        inventory-cmmRevision UnsignedShort,
        inventory-cmmSerialNumber String,
        inventory-cmmManufactureDate DateAndTime,
        inventory-cmmVendor String
    }

inventory-cmmChassisNum OBJECT-TYPE
    SYNTAX      ChassisIndexT
    MAX-ACCESS  not-accessible
    STATUS      current
    DESCRIPTION "Chassis identifier"
    ::= { inventory-cmmEntry 1 }

inventory-cmmSlotNum OBJECT-TYPE
    SYNTAX      CmmIndexT
    MAX-ACCESS  not-accessible
    STATUS      current
    DESCRIPTION "CMM identifier"
    ::= { inventory-cmmEntry 2 }

inventory-cmmName OBJECT-TYPE
    SYNTAX      String
    MAX-ACCESS  read-only
    STATUS      current
    DESCRIPTION "Entity name"
    ::= { inventory-cmmEntry 3 }

inventory-cmmPEC OBJECT-TYPE
    SYNTAX      String
    MAX-ACCESS  read-only
    STATUS      current
    DESCRIPTION "Product Equipment Code assigned by BTI"
    ::= { inventory-cmmEntry 4 }

inventory-cmmRevision OBJECT-TYPE
    SYNTAX      UnsignedShort
    MAX-ACCESS  read-only
    STATUS      current
    DESCRIPTION "Hardware revision number"
    ::= { inventory-cmmEntry 5 }

inventory-cmmSerialNumber OBJECT-TYPE
    SYNTAX      String
    MAX-ACCESS  read-only
    STATUS      current
    DESCRIPTION "Serial number"
    ::= { inventory-cmmEntry 6 }

inventory-cmmManufactureDate OBJECT-TYPE
    SYNTAX      DateAndTime
    MAX-ACCESS  read-only
    STATUS      current
    DESCRIPTION "Manufacturing date"
    ::= { inventory-cmmEntry 7 }

inventory-cmmVendor OBJECT-TYPE
    SYNTAX      String
    MAX-ACCESS  read-only
    STATUS      current
    DESCRIPTION "Vendor name"
    ::= { inventory-cmmEntry 8 }

inventory-moduleTable OBJECT-TYPE
    SYNTAX      SEQUENCE OF Inventory-moduleEntry
    MAX-ACCESS  not-accessible
    STATUS      current
    DESCRIPTION ""
    ::= { bTI7800-INVENTORY-MIB 5 }

inventory-moduleEntry OBJECT-TYPE
    SYNTAX      Inventory-moduleEntry
    MAX-ACCESS  not-accessible
    STATUS      current
    DESCRIPTION ""
    INDEX { inventory-moduleChassisNum, inventory-moduleSlotNum }
        ::= { inventory-moduleTable 1 }

Inventory-moduleEntry ::=
    SEQUENCE {
        inventory-moduleChassisNum ChassisIndexT,
        inventory-moduleSlotNum ModuleIndexT,
        inventory-moduleName String,
        inventory-modulePEC String,
        inventory-moduleRevision UnsignedShort,
        inventory-moduleSerialNumber String,
        inventory-moduleManufactureDate DateAndTime,
        inventory-moduleVendor String
    }

inventory-moduleChassisNum OBJECT-TYPE
    SYNTAX      ChassisIndexT
    MAX-ACCESS  not-accessible
    STATUS      current
    DESCRIPTION "Chassis identifier"
    ::= { inventory-moduleEntry 1 }

inventory-moduleSlotNum OBJECT-TYPE
    SYNTAX      ModuleIndexT
    MAX-ACCESS  not-accessible
    STATUS      current
    DESCRIPTION "Module identifier"
    ::= { inventory-moduleEntry 2 }

inventory-moduleName OBJECT-TYPE
    SYNTAX      String
    MAX-ACCESS  read-only
    STATUS      current
    DESCRIPTION "Entity name"
    ::= { inventory-moduleEntry 3 }

inventory-modulePEC OBJECT-TYPE
    SYNTAX      String
    MAX-ACCESS  read-only
    STATUS      current
    DESCRIPTION "Product Equipment Code assigned by BTI"
    ::= { inventory-moduleEntry 4 }

inventory-moduleRevision OBJECT-TYPE
    SYNTAX      UnsignedShort
    MAX-ACCESS  read-only
    STATUS      current
    DESCRIPTION "Hardware revision number"
    ::= { inventory-moduleEntry 5 }

inventory-moduleSerialNumber OBJECT-TYPE
    SYNTAX      String
    MAX-ACCESS  read-only
    STATUS      current
    DESCRIPTION "Serial number"
    ::= { inventory-moduleEntry 6 }

inventory-moduleManufactureDate OBJECT-TYPE
    SYNTAX      DateAndTime
    MAX-ACCESS  read-only
    STATUS      current
    DESCRIPTION "Manufacturing date"
    ::= { inventory-moduleEntry 7 }

inventory-moduleVendor OBJECT-TYPE
    SYNTAX      String
    MAX-ACCESS  read-only
    STATUS      current
    DESCRIPTION "Vendor name"
    ::= { inventory-moduleEntry 8 }

inventory-bicTable OBJECT-TYPE
    SYNTAX      SEQUENCE OF Inventory-bicEntry
    MAX-ACCESS  not-accessible
    STATUS      current
    DESCRIPTION ""
    ::= { bTI7800-INVENTORY-MIB 6 }

inventory-bicEntry OBJECT-TYPE
    SYNTAX      Inventory-bicEntry
    MAX-ACCESS  not-accessible
    STATUS      current
    DESCRIPTION ""
    INDEX { inventory-bicChassisNum, inventory-bicSlotNum, inventory-bicSubslotNum }
        ::= { inventory-bicTable 1 }

Inventory-bicEntry ::=
    SEQUENCE {
        inventory-bicChassisNum ChassisIndexT,
        inventory-bicSlotNum ModuleIndexT,
        inventory-bicSubslotNum BicIndexT,
        inventory-bicName String,
        inventory-bicPEC String,
        inventory-bicRevision UnsignedShort,
        inventory-bicSerialNumber String,
        inventory-bicManufactureDate DateAndTime,
        inventory-bicVendor String
    }

inventory-bicChassisNum OBJECT-TYPE
    SYNTAX      ChassisIndexT
    MAX-ACCESS  not-accessible
    STATUS      current
    DESCRIPTION "Chassis identifier"
    ::= { inventory-bicEntry 1 }

inventory-bicSlotNum OBJECT-TYPE
    SYNTAX      ModuleIndexT
    MAX-ACCESS  not-accessible
    STATUS      current
    DESCRIPTION "Module identifier"
    ::= { inventory-bicEntry 2 }

inventory-bicSubslotNum OBJECT-TYPE
    SYNTAX      BicIndexT
    MAX-ACCESS  not-accessible
    STATUS      current
    DESCRIPTION "Subslot identifier"
    ::= { inventory-bicEntry 3 }

inventory-bicName OBJECT-TYPE
    SYNTAX      String
    MAX-ACCESS  read-only
    STATUS      current
    DESCRIPTION "Entity name"
    ::= { inventory-bicEntry 4 }

inventory-bicPEC OBJECT-TYPE
    SYNTAX      String
    MAX-ACCESS  read-only
    STATUS      current
    DESCRIPTION "Product Equipment Code assigned by BTI"
    ::= { inventory-bicEntry 5 }

inventory-bicRevision OBJECT-TYPE
    SYNTAX      UnsignedShort
    MAX-ACCESS  read-only
    STATUS      current
    DESCRIPTION "Hardware revision number"
    ::= { inventory-bicEntry 6 }

inventory-bicSerialNumber OBJECT-TYPE
    SYNTAX      String
    MAX-ACCESS  read-only
    STATUS      current
    DESCRIPTION "Serial number"
    ::= { inventory-bicEntry 7 }

inventory-bicManufactureDate OBJECT-TYPE
    SYNTAX      DateAndTime
    MAX-ACCESS  read-only
    STATUS      current
    DESCRIPTION "Manufacturing date"
    ::= { inventory-bicEntry 8 }

inventory-bicVendor OBJECT-TYPE
    SYNTAX      String
    MAX-ACCESS  read-only
    STATUS      current
    DESCRIPTION "Vendor name"
    ::= { inventory-bicEntry 9 }

inventory-xcvrTable OBJECT-TYPE
    SYNTAX      SEQUENCE OF Inventory-xcvrEntry
    MAX-ACCESS  not-accessible
    STATUS      current
    DESCRIPTION ""
    ::= { bTI7800-INVENTORY-MIB 7 }

inventory-xcvrEntry OBJECT-TYPE
    SYNTAX      Inventory-xcvrEntry
    MAX-ACCESS  not-accessible
    STATUS      current
    DESCRIPTION ""
    INDEX { inventory-xcvrChassisNum, inventory-xcvrSlotNum, inventory-xcvrSubslotNum, inventory-xcvrPortNum }
        ::= { inventory-xcvrTable 1 }

Inventory-xcvrEntry ::=
    SEQUENCE {
        inventory-xcvrChassisNum ChassisIndexT,
        inventory-xcvrSlotNum ModuleIndexT,
        inventory-xcvrSubslotNum BicIndexT,
        inventory-xcvrPortNum PortIndexT,
        inventory-xcvrName String,
        inventory-xcvrPEC String,
        inventory-xcvrRevision UnsignedShort,
        inventory-xcvrSerialNumber String,
        inventory-xcvrManufactureDate DateAndTime,
        inventory-xcvrVendor String,
        inventory-xcvrVendorPartNum String,
        inventory-xcvrType INTEGER
    }

inventory-xcvrChassisNum OBJECT-TYPE
    SYNTAX      ChassisIndexT
    MAX-ACCESS  not-accessible
    STATUS      current
    DESCRIPTION "Chassis identifier"
    ::= { inventory-xcvrEntry 1 }

inventory-xcvrSlotNum OBJECT-TYPE
    SYNTAX      ModuleIndexT
    MAX-ACCESS  not-accessible
    STATUS      current
    DESCRIPTION "Module identifier"
    ::= { inventory-xcvrEntry 2 }

inventory-xcvrSubslotNum OBJECT-TYPE
    SYNTAX      BicIndexT
    MAX-ACCESS  not-accessible
    STATUS      current
    DESCRIPTION "Subslot identifier"
    ::= { inventory-xcvrEntry 3 }

inventory-xcvrPortNum OBJECT-TYPE
    SYNTAX      PortIndexT
    MAX-ACCESS  not-accessible
    STATUS      current
    DESCRIPTION "Port identifier"
    ::= { inventory-xcvrEntry 4 }

inventory-xcvrName OBJECT-TYPE
    SYNTAX      String
    MAX-ACCESS  read-only
    STATUS      current
    DESCRIPTION "Entity name"
    ::= { inventory-xcvrEntry 5 }

inventory-xcvrPEC OBJECT-TYPE
    SYNTAX      String
    MAX-ACCESS  read-only
    STATUS      current
    DESCRIPTION "Product Equipment Code assigned by BTI"
    ::= { inventory-xcvrEntry 6 }

inventory-xcvrRevision OBJECT-TYPE
    SYNTAX      UnsignedShort
    MAX-ACCESS  read-only
    STATUS      current
    DESCRIPTION "Hardware revision number"
    ::= { inventory-xcvrEntry 7 }

inventory-xcvrSerialNumber OBJECT-TYPE
    SYNTAX      String
    MAX-ACCESS  read-only
    STATUS      current
    DESCRIPTION "Serial number"
    ::= { inventory-xcvrEntry 8 }

inventory-xcvrManufactureDate OBJECT-TYPE
    SYNTAX      DateAndTime
    MAX-ACCESS  read-only
    STATUS      current
    DESCRIPTION "Manufacturing date"
    ::= { inventory-xcvrEntry 9 }

inventory-xcvrVendor OBJECT-TYPE
    SYNTAX      String
    MAX-ACCESS  read-only
    STATUS      current
    DESCRIPTION "Vendor name"
    ::= { inventory-xcvrEntry 10 }

inventory-xcvrVendorPartNum OBJECT-TYPE
    SYNTAX      String
    MAX-ACCESS  read-only
    STATUS      current
    DESCRIPTION "Transceiver part number assigned by the vendor"
    ::= { inventory-xcvrEntry 11 }

inventory-xcvrType OBJECT-TYPE
    SYNTAX      INTEGER {unknown(0),sfp(1),sfpPlus(2),cfp(3),msa(4),qsfp(5),qsfp28(6),msa400(7)}
    MAX-ACCESS  read-only
    STATUS      current
    DESCRIPTION "Transceiver type"
    ::= { inventory-xcvrEntry 12 }

inventory-preampTable OBJECT-TYPE
    SYNTAX      SEQUENCE OF Inventory-preampEntry
    MAX-ACCESS  not-accessible
    STATUS      current
    DESCRIPTION ""
    ::= { bTI7800-INVENTORY-MIB 8 }

inventory-preampEntry OBJECT-TYPE
    SYNTAX      Inventory-preampEntry
    MAX-ACCESS  not-accessible
    STATUS      current
    DESCRIPTION ""
    INDEX { inventory-preampChassisNum, inventory-preampSlotNum, inventory-preampSubslotNum }
        ::= { inventory-preampTable 1 }

Inventory-preampEntry ::=
    SEQUENCE {
        inventory-preampChassisNum ChassisIndexT,
        inventory-preampSlotNum ModuleIndexT,
        inventory-preampSubslotNum BicIndexT,
        inventory-preampName String,
        inventory-preampPEC String,
        inventory-preampRevision UnsignedShort,
        inventory-preampSerialNumber String,
        inventory-preampManufactureDate DateAndTime,
        inventory-preampVendor String
    }

inventory-preampChassisNum OBJECT-TYPE
    SYNTAX      ChassisIndexT
    MAX-ACCESS  not-accessible
    STATUS      current
    DESCRIPTION "Chassis identifier"
    ::= { inventory-preampEntry 1 }

inventory-preampSlotNum OBJECT-TYPE
    SYNTAX      ModuleIndexT
    MAX-ACCESS  not-accessible
    STATUS      current
    DESCRIPTION "Module identifier"
    ::= { inventory-preampEntry 2 }

inventory-preampSubslotNum OBJECT-TYPE
    SYNTAX      BicIndexT
    MAX-ACCESS  not-accessible
    STATUS      current
    DESCRIPTION "Subslot identifier"
    ::= { inventory-preampEntry 3 }

inventory-preampName OBJECT-TYPE
    SYNTAX      String
    MAX-ACCESS  read-only
    STATUS      current
    DESCRIPTION "Entity name"
    ::= { inventory-preampEntry 4 }

inventory-preampPEC OBJECT-TYPE
    SYNTAX      String
    MAX-ACCESS  read-only
    STATUS      current
    DESCRIPTION "Product Equipment Code assigned by BTI"
    ::= { inventory-preampEntry 5 }

inventory-preampRevision OBJECT-TYPE
    SYNTAX      UnsignedShort
    MAX-ACCESS  read-only
    STATUS      current
    DESCRIPTION "Hardware revision number"
    ::= { inventory-preampEntry 6 }

inventory-preampSerialNumber OBJECT-TYPE
    SYNTAX      String
    MAX-ACCESS  read-only
    STATUS      current
    DESCRIPTION "Serial number"
    ::= { inventory-preampEntry 7 }

inventory-preampManufactureDate OBJECT-TYPE
    SYNTAX      DateAndTime
    MAX-ACCESS  read-only
    STATUS      current
    DESCRIPTION "Manufacturing date"
    ::= { inventory-preampEntry 8 }

inventory-preampVendor OBJECT-TYPE
    SYNTAX      String
    MAX-ACCESS  read-only
    STATUS      current
    DESCRIPTION "Vendor name"
    ::= { inventory-preampEntry 9 }

inventory-eslTable OBJECT-TYPE
    SYNTAX      SEQUENCE OF Inventory-eslEntry
    MAX-ACCESS  not-accessible
    STATUS      current
    DESCRIPTION ""
    ::= { bTI7800-INVENTORY-MIB 9 }

inventory-eslEntry OBJECT-TYPE
    SYNTAX      Inventory-eslEntry
    MAX-ACCESS  not-accessible
    STATUS      current
    DESCRIPTION ""
    INDEX { inventory-eslChassisNum, inventory-eslSlotNum }
        ::= { inventory-eslTable 1 }

Inventory-eslEntry ::=
    SEQUENCE {
        inventory-eslChassisNum ChassisIndexT,
        inventory-eslSlotNum UnsignedByte,
        inventory-eslName String,
        inventory-eslPEC String,
        inventory-eslRevision UnsignedShort,
        inventory-eslSerialNumber String,
        inventory-eslManufactureDate DateAndTime,
        inventory-eslVendor String
    }

inventory-eslChassisNum OBJECT-TYPE
    SYNTAX      ChassisIndexT
    MAX-ACCESS  not-accessible
    STATUS      current
    DESCRIPTION "Chassis identifier"
    ::= { inventory-eslEntry 1 }

inventory-eslSlotNum OBJECT-TYPE
    SYNTAX      UnsignedByte
    MAX-ACCESS  not-accessible
    STATUS      current
    DESCRIPTION "ESL identifier"
    ::= { inventory-eslEntry 2 }

inventory-eslName OBJECT-TYPE
    SYNTAX      String
    MAX-ACCESS  read-only
    STATUS      current
    DESCRIPTION "Entity name"
    ::= { inventory-eslEntry 3 }

inventory-eslPEC OBJECT-TYPE
    SYNTAX      String
    MAX-ACCESS  read-only
    STATUS      current
    DESCRIPTION "Product Equipment Code assigned by BTI"
    ::= { inventory-eslEntry 4 }

inventory-eslRevision OBJECT-TYPE
    SYNTAX      UnsignedShort
    MAX-ACCESS  read-only
    STATUS      current
    DESCRIPTION "Hardware revision number"
    ::= { inventory-eslEntry 5 }

inventory-eslSerialNumber OBJECT-TYPE
    SYNTAX      String
    MAX-ACCESS  read-only
    STATUS      current
    DESCRIPTION "Serial number"
    ::= { inventory-eslEntry 6 }

inventory-eslManufactureDate OBJECT-TYPE
    SYNTAX      DateAndTime
    MAX-ACCESS  read-only
    STATUS      current
    DESCRIPTION "Manufacturing date"
    ::= { inventory-eslEntry 7 }

inventory-eslVendor OBJECT-TYPE
    SYNTAX      String
    MAX-ACCESS  read-only
    STATUS      current
    DESCRIPTION "Vendor name"
    ::= { inventory-eslEntry 8 }

END
