-- extracted from draft-richardson-bgp4-communities-mib-00.txt
-- at Sat Feb 24 06:04:17 2001

    BGP-COMMUNITIES-MIB DEFINITIONS ::= BEGIN


        IMPORTS
            MODULE-IDENTITY, OBJECT-TYPE, NOTIFICATION-TYPE,
            IpAddress, mib-2
                FROM SNMPv2-SMI
            MODULE-COMPLIANCE, OBJECT-GROUP, NOTIFICATION-GROUP
                FROM SNMPv2-CONF
	    bgp
		FROM BGP4-MIB;

        bgpCommunities MODULE-IDENTITY
            LAST-UPDATED "200102230000Z"
            ORGANIZATION "IETF IDR Working Group"
            CONTACT-INFO "E-mail:  idr@merit.net

			  Mathew Richardson (Author)
			  E-mail: mrr@nexthop.com
			  Shane Wright (Author)
			  E-mail: swright@nexthop.com
                          517 W. William Street
                          Ann Arbor, MI 48103-4943
                          Tel: +1 734 973-2200
                          Fax: +1 734 615-3241

                          Susan Hares  (Editor)
                          517 W. William Street
                          Ann Arbor, MI 48103-4943
                          Tel: +1 734 973-2200
                          Fax: +1 734 615-3241
                          E-mail: skh@nexthop.com"

            DESCRIPTION
                    "Extension of the MIB module for BGP-4 to include
		     information about the communities attribute defined
		     in BGP Communities."
            REVISION    "200102230000Z"
	    DESCRIPTION
		    "RFC 1997 - BGP Communities Attribute"
		
            ::= { bgp 10 }


        bgp4CommTable OBJECT-TYPE
            SYNTAX     SEQUENCE OF Bgp4CommEntry
            MAX-ACCESS not-accessible
            STATUS     current
            DESCRIPTION
		    "The BGP-4 Communities Table contains information about
		     the communities received with a route."
            ::= { bgpCommunities 1 }


        bgp4CommEntry OBJECT-TYPE
            SYNTAX     Bgp4CommEntry
            MAX-ACCESS not-accessible
            STATUS     current
            DESCRIPTION ""
	    AUGMENTS	{ bgp4PathAttrTable }
	    ::= { bgp4CommTable 1 }


        Bgp4CommEntry ::= SEQUENCE {
	    bgp4PathAttrComm
		 OCTET STRING
        }

	bgp4PathAttrComm OBJECT-TYPE
	    SYNTAX	OCTET STRING (SIZE(0..4096))
	    MAX-ACCESS	read-only
	    STATUS	current
	    DESCRIPTION
		    "A list of 4-octet long values, each representing a
		     community.  Size zero (0) indicates the absence of
		     such attributes.  Octets beyond the maximum size, if
		     any, are not recorded by this object.  There are certain
		     4-octet long values that carry additional semantics."
	    REFERENCE
		    "RFC 1997 - BGP Communities Attribute"
	    ::= { bgp4CommEntry 1 }

    END

-- 
-- 
--    Copyright (C) The Internet Society (1999).  All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
-- 
--    The limited permissions granted above are perpetual and will not be
--    revoked by the Internet Society or its successors or assigns.
-- 
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
-- 
-- Expires August 2001
