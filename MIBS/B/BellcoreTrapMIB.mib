BellcoreTrapMIB DEFINITIONS ::= BEGIN

          IMPORTS
              enterprises
                  FROM RFC1155-SMI
              TRAP-TYPE
                  FROM RFC-1215;



          -- Bellcore Enterprise-specific traps for use
          -- with SNMP-based Network Management.

          -- This is the Bellcore Trap MIB trap module.

          bellcore    OBJECT IDENTIFIER ::= { enterprises 148 }


          fyiTrap TRAP-TYPE
             ENTERPRISE  bellcore
             DESCRIPTION
                "This trap signifies an event
                 related to the contents of
                 the VarBindList."
             ::= 13



          END
