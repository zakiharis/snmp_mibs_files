-- extracted from draft-richardson-bgp4-ext-comm-mib-00.txt
-- at Sat Feb 24 06:04:17 2001

    BGP4-EXT-COMM-MIB DEFINITIONS ::= BEGIN


        IMPORTS
            MODULE-IDENTITY, OBJECT-TYPE, NOTIFICATION-TYPE,
            mib-2
                FROM SNMPv2-SMI
            MODULE-COMPLIANCE, OBJECT-GROUP, NOTIFICATION-GROUP
                FROM SNMPv2-CONF
	    bgp
		FROM BGP4-MIB;

        bgpExtComm MODULE-IDENTITY
            LAST-UPDATED "200102230000Z"
            ORGANIZATION "IETF IDR Working Group"
            CONTACT-INFO "E-mail:  idr@merit.net

			  Mathew Richardson (Author)
			  E-mail: mrr@nexthop.com
			  Shane Wright (Author)
			  E-mail: swright@nexthop.com
                          517 W. William Street
                          Ann Arbor, MI 48103-4943
                          Tel: +1 734 973-2200
                          Fax: +1 734 615-3241

                          Susan Hares  (Editor)
                          517 W. William Street
                          Ann Arbor, MI 48103-4943
                          Tel: +1 734 933-2200
                          Fax: +1 734 615-3241
                          E-mail: skh@nexthop.com"

            DESCRIPTION
                    "Extension of the MIB module for BGP-4 to include
		     information about the Extended Communities attribute
		     associated with incoming routes."
            REVISION    "200102230000Z"
	    DESCRIPTION
		    "BGP-EXTCOMM - BGP Extended Communities Attribute"
		
            ::= { bgp 13 }


        bgp4ExtCommTable OBJECT-TYPE
            SYNTAX     SEQUENCE OF Bgp4ExtCommEntry
            MAX-ACCESS not-accessible
            STATUS     current
            DESCRIPTION
                    "BGP Extended Communities Table.  This table contains
		     information on the Extended Communities [BGP-EXTCOMM]
		     learned with incoming routes."
	    REFERENCE
		    "RFC 1771 - Border Gateway Protocol version 4 (BGP4)"
            ::= { bgpExtComm 1 }


        bgp4ExtCommEntry OBJECT-TYPE
            SYNTAX     Bgp4ExtCommEntry
            MAX-ACCESS not-accessible
            STATUS     current
            DESCRIPTION
                    "Information about the Extended Communities [BGP-EXTCOMM]
		     learned with a route."
	    AUGMENTS	{ bgp4PathAttrTable }
	    ::= { bgp4ExtCommTable 1 }


        Bgp4ExtCommEntry ::= SEQUENCE {
	    bgp4PathAttrExtComm
		 OCTET STRING
        }

	bgp4PathAttrExtComm OBJECT-TYPE
	    SYNTAX	OCTET STRING (SIZE(0..4096))
	    MAX-ACCESS	read-only
	    STATUS	current
	    DESCRIPTION
		    "A sequence of values each eight octets long, and each
		     representing an extended community that was received
		     with the route.  The values of each of the individual
		     octets may have semantic meaning.  A length of zero (0)
		     indicates the absence of this attribute."
	    REFERENCE
		    "BGP-EXTCOMM - BGP Extended Communities Attribute"
	    ::= { bgp4ExtCommEntry 1 }

    END

-- 
-- 
--    Copyright (C) The Internet Society (1999).  All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
-- 
--    The limited permissions granted above are perpetual and will not be
--    revoked by the Internet Society or its successors or assigns.
-- 
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
-- 
-- Expires August 2001
