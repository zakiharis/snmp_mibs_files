--
-- WS-SW-SMI.my
-- MIB generated by MG-SOFT Visual MIB Builder Version 6.0  Build 88
-- Tuesday, June 03, 2008 at 13:21:01
--

	WS-SW-SMI DEFINITIONS ::= BEGIN
 
		IMPORTS
			MODULE-IDENTITY			
				FROM SNMPv2-SMI			
			wsSw			
				FROM WS-SMI;
	
	
		-- 1.3.6.1.4.1.388.14.2.1
		wsSwMIB MODULE-IDENTITY 
			LAST-UPDATED "200806021100Z"		-- June 02, 2008 at 11:00 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Description."
			REVISION "200806021104Z"		-- June 02, 2008 at 11:04 GMT
			DESCRIPTION 
				"02a05
				
				Added wsSwMacName."
			REVISION "200606081136Z"		-- June 08, 2006 at 11:36 GMT
			DESCRIPTION 
				"02a04"
			REVISION "200605241634Z"		-- May 24, 2006 at 16:34 GMT
			DESCRIPTION 
				"02a03"
			REVISION "200605091425Z"		-- May 09, 2006 at 14:25 GMT
			DESCRIPTION 
				"02a02"
			REVISION "200604271519Z"		-- April 27, 2006 at 15:19 GMT
			DESCRIPTION 
				"02a01"
			REVISION "200603021057Z"		-- March 02, 2006 at 10:57 GMT
			DESCRIPTION 
				"01a09"
			REVISION "200511011342Z"		-- November 01, 2005 at 13:42 GMT
			DESCRIPTION 
				"01a08"
			REVISION "200509201547Z"		-- September 20, 2005 at 15:47 GMT
			DESCRIPTION 
				"01a07"
			REVISION "200509191125Z"		-- September 19, 2005 at 11:25 GMT
			DESCRIPTION 
				"01a06"
			REVISION "200508031134Z"		-- August 03, 2005 at 11:34 GMT
			DESCRIPTION 
				"01a05"
			REVISION "200505311714Z"		-- May 31, 2005 at 17:14 GMT
			DESCRIPTION 
				"01a04"
			REVISION "200505181428Z"		-- May 18, 2005 at 14:28 GMT
			DESCRIPTION 
				"01a03"
			REVISION "200505121402Z"		-- May 12, 2005 at 14:02 GMT
			DESCRIPTION 
				"01a02"
			REVISION "200505051100Z"		-- May 05, 2005 at 11:00 GMT
			DESCRIPTION 
				"01a01"
			::= { wsSw 1 }

		
	
--
-- Node definitions
--
	
		-- 1.3.6.1.4.1.388.14.2.2
		wsSwDNS OBJECT IDENTIFIER ::= { wsSw 2 }

		
		-- 1.3.6.1.4.1.388.14.2.3
		wsSwDHCP OBJECT IDENTIFIER ::= { wsSw 3 }

		
		-- 1.3.6.1.4.1.388.14.2.4
		wsSwIf OBJECT IDENTIFIER ::= { wsSw 4 }

		
		-- 1.3.6.1.4.1.388.14.2.5
		wsSwIp OBJECT IDENTIFIER ::= { wsSw 5 }

		
		-- 1.3.6.1.4.1.388.14.2.6
		wsSwSnmpSave OBJECT IDENTIFIER ::= { wsSw 6 }

		
		-- 1.3.6.1.4.1.388.14.2.7
		wsSwArp OBJECT IDENTIFIER ::= { wsSw 7 }

		
		-- 1.3.6.1.4.1.388.14.2.8
		wsSwGre OBJECT IDENTIFIER ::= { wsSw 8 }

		
		-- 1.3.6.1.4.1.388.14.2.9
		wsSwMobility OBJECT IDENTIFIER ::= { wsSw 9 }

		
		-- 1.3.6.1.4.1.388.14.2.10
		wsSwMacName OBJECT IDENTIFIER ::= { wsSw 10 }

		
		-- 1.3.6.1.4.1.388.14.2.11
		wsSwAcl OBJECT IDENTIFIER ::= { wsSw 11 }

		
		-- 1.3.6.1.4.1.388.14.2.12
		wsSwNtp OBJECT IDENTIFIER ::= { wsSw 12 }

		
		-- 1.3.6.1.4.1.388.14.2.13
		wsSwRadius OBJECT IDENTIFIER ::= { wsSw 13 }

		
		-- 1.3.6.1.4.1.388.14.2.13
		wsSwRadius OBJECT IDENTIFIER ::= { wsSw 13 }

		
		-- 1.3.6.1.4.1.388.14.2.16
		wsSwFirewall OBJECT IDENTIFIER ::= { wsSw 16 }

		
		-- 1.3.6.1.4.1.388.14.2.17
		wsSwIgmpSnoop OBJECT IDENTIFIER ::= { wsSw 17 }

		
		-- 1.3.6.1.4.1.388.14.2.20
		wsSwRoleFirewall OBJECT IDENTIFIER ::= { wsSw 20 }

		
		-- 1.3.6.1.4.1.388.14.2.80
		wsSwGuestRadius OBJECT IDENTIFIER ::= { wsSw 80 }

		
		-- 1.3.6.1.4.1.388.14.2.100
		wsSwVlan OBJECT IDENTIFIER ::= { wsSw 100 }

		
	
	END

--
-- WS-SW-SMI.my
--
