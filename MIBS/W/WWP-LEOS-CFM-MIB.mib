-- This file was included in WWP MIB release 04-10-01-0027

 --
 -- WWP-LEOS-CFM-MIB.my
 --     

 WWP-LEOS-CFM-MIB DEFINITIONS ::= BEGIN

 IMPORTS                
   TimeTicks, Integer32, Unsigned32, Gauge32, Counter32, Counter64, OBJECT-TYPE, MODULE-IDENTITY, NOTIFICATION-TYPE                       
        FROM SNMPv2-SMI                 
   DisplayString, MacAddress, TEXTUAL-CONVENTION, RowStatus , TruthValue                
        FROM SNMPv2-TC
   sysName
        FROM RFC1213-MIB                                                        
   wwpModulesLeos           
        FROM WWP-SMI;
        
 wwpLeosCfmMIB MODULE-IDENTITY
            LAST-UPDATED "201204110000Z"
            ORGANIZATION "Ciena, Inc"
            CONTACT-INFO
                    "Mib Meister
                     115 North Sullivan Road
                     Spokane Valley, WA 99037
                     USA
                     Phone:  +1 509 242 9000
                     Email:  support@ciena.com"    
             DESCRIPTION
                "Connectivity Fault Management (CFM) MIB for configuration and monitoring CFM"

             REVISION "201204110000Z"
             DESCRIPTION
                "Expanded value ranges for Delay fields to allow setting of the 'default' value (-1 for threshold,
                0 for msgcount). Merged 6.x changes back into 4.x MIB to make them identical. Cleaned up history section
                to conform to standard - REVISION comes before DESCRIPTION"

             REVISION "201202030000Z"
             DESCRIPTION
                "Added new objects wwpLeosCfmServiceAccelerated,wwpLeosCfmRemoteMEPAccelerated and wwpLeosCfmExtMEPAccelerated.
                 Added a new table for query for port OAM capability."

             REVISION "201107260000Z"                
             DESCRIPTION
                "Added new objects wwpLeosCfmRemoteMEPServiceClear,wwpLeosCfmRemoteMEPServiceStatisticsClear"

             REVISION "201105310000Z"    
             DESCRIPTION
            	"Deprecated objects wwpLeosCfmLBMDefaultCount,wwpLeosCfmLBMDefaultInterval,wwpLeosCfmLBMDefaultTimeout,
            	wwpLeosCfmFrameClassifierMode under wwpLeosCfmGlobal.
            	Added objects wwpLeosCfmGlobalLBMDefaultCount,wwpLeosCfmGlobalLBMDefaultInterval,wwpLeosCfmGlobalLBMDefaultTimeout,
            	wwpLeosCfmGlobalFrameClassifierMode under wwpLeosCfmGlobal.
            	Deprecated wwpLeosCfmServiceDefaultMEPType,wwpLeosCfmServiceMAID,wwpLeosCfmServiceMdIndex,wwpLeosCfmServiceMaintAssocNameType,
            	wwpLeosCfmServiceMaintAssocName under WwpLeosCfmServiceEntry.
            	Added wwpLeosCfmServiceY1731,wwpLeosCfmServiceCCMTxState,wwpLeosCfmServiceRMEPAging,wwpLeosCfmServiceMulticastDa,
            	wwpLeosCfmServiceChargedAgainstGlobalFrameBudget,wwpLeosCfmServiceCfmDefaultMEPType,wwpLeosCfmServiceCfmMAID,
            	wwpLeosCfmServiceCfmMdIndex,wwpLeosCfmServiceCfmMaintAssocNameType,wwpLeosCfmServiceCfmMaintAssocName,
            	wwpLeosCfmServiceCfmControlModuleFrameBudget under WwpLeosCfmService.
            	Added wwpLeosCfmLinkTraceMsgServiceName,wwpLeosCfmLinkTraceMsgSubPortName,wwpLeosCfmLinkTraceMsgVsIndex,
            	wwpLeosCfmLinkTraceMsgTotalTxLtm,wwpLeosCfmLinkTraceMsgTotalRxLtr under wwpLeosCfmLinkTraceMsg.
            	Added wwpLeosCfmLinkTraceMsgReplyIngressMacAddr,wwpLeosCfmLinkTraceMsgReplyEgressMacAddr under 
            	WwpLeosCfmLinkTraceMsgReplyEntry.
            	Added wwpLeosCfmMEPDMMMinDelay,wwpLeosCfmMEPDMMMaxDelay,wwpLeosCfmMEPDMMMinJitter,wwpLeosCfmMEPDMMMaxJitter,
            	wwpLeosCfmMEPServiceName,wwpLeosCfmMEPSubPortName,wwpLeosCfmMEPVsPbtName,wwpLeosCfmMEPLogicalPortName,
            	wwpLeosCfmMEPSubPortIndex,wwpLeosCfmMEPEncapsulation,wwpLeosCfmMEPLeadPortBayIndex,wwpLeosCfmMEPLeadPortShelfIndex,
            	wwpLeosCfmMEPLeadPortModuleIndex,wwpLeosCfmMEPPBTBvid,wwpLeosCfmMEPPBTEtype,wwpLeosCfmMEPNumLbmTxmt, wwpLeosCfmMEPNumLbmReceived,
            	wwpLeosCfmMEPNumLoopbackRepliesReceived,wwpLeosCfmMEPNumLTRepliesTxmt, wwpLeosCfmMEPNumLTRepliesReceived,
            	wwpLeosCfmMEPNumUnexpectedLTRepliesReceived,wwpLeosCfmMEPNumCCMReceived under wwpLeosCfmMEPEntry.
            	Deprecated wwpLeosCfmRemoteMEPHoldState under wwpLeosCfmRemoteMEP.
            	Added wwpLeosCfmRemoteMEPMinDelay,wwpLeosCfmRemoteMEPMaxDelay,wwpLeosCfmRemoteMEPMinJitter,wwpLeosCfmRemoteMEPMaxJitter,
            	wwpLeosCfmRemoteCfmMEPHoldState,wwpLeosCfmRemoteMEPSubPortName,wwpLeosCfmRemoteMEPServiceName ,wwpLeosCfmRemoteMEPBayIndex,
            	wwpLeosCfmRemoteMEPShelfIndex,wwpLeosCfmRemoteMEPModuleIndex ,wwpLeosCfmRemoteMEPPreviousBayIndex,
            	wwpLeosCfmRemoteMEPPreviousShelfIndex ,wwpLeosCfmRemoteMEPPreviousModuleIndex,wwpLeosCfmRemoteMEPLastPortStatus,
            	wwpLeosCfmRemoteMEPLastInterfaceStatus,wwpLeosCfmRemoteMEPLastSeqNum, wwpLeosCfmRemoteMEPCCMSeqErrors,
            	wwpLeosCfmRemoteMEPCCMLevel,wwpLeosCfmRemoteMEPDeleteAll under wwpLeosCfmRemoteMEPEntry.
            	Deprecated the table wwpLeosCfmPortStackTable .
            	Added wwpLeosCfmServiceVsPbtName under  WwpLeosCfmServiceFaultEntry.
            	Added wwpLeosCfmDelayMsgMaxDelayThreshold, wwpLeosCfmDelayMsgMaxJitterThreshold under wwpLeosCfmDelayMsgEntry.
            	Added wwpLeosCfmExtMEPDMMMinDelay,wwpLeosCfmExtMEPDMMMaxDelay,wwpLeosCfmExtMEPDMMMinJitter,wwpLeosCfmExtMEPDMMMaxJitter 
            	under wwpLeosCfmExtMEPEntry.
            	Added wwpLeosCfmExtMEPLastStatsDMMMinDelay,wwpLeosCfmExtMEPLastStatsDMMMaxDelay,wwpLeosCfmExtMEPLastStatsDMMMinJitter,
            	wwpLeosCfmExtMEPLastStatsDMMMaxJitter under wwpLeosCfmExtMEPLastStatsEntry.
            	Added wwpLeosCfmExtDelayMsgMaxDelayThreshold,wwpLeosCfmExtDelayMsgMaxJitterThreshold under wwpLeosCfmExtDelayMsgEntry.
            	Added new tables wwpLeosCfmGlobalFrameBudgetTable,wwpLeosCfmServiceFrameBudgetTable,wwpLeosCfmExtPortStackTable,
                wwpLeosCfmExtMEPDelayHistoryTable,wwpLeosTceCfmMipTable,wwpLeosTceCfmMipCCMDbTable,wwpLeosTceCfmLoopbackMsgTable,
                wwpLeosTceCfmPortStackTable,wwpLeosTceCfmMEPTable,wwpLeosTceCfmDelayMsgTable,wwpLeosTceCfmFrameLossMsgTable.
                Added new notifications wwpLeosCfmFaultTrapSet,wwpLeosCfmFaultTrapClear,wwpLeosCfmDmmTrap,wwpLeosCfmLmmTrap." 
                  
            REVISION "201101310000Z"  
            DESCRIPTION
            	"Deprecated object wwpLeosCfmPbtFaultTrap."   

            REVISION "201007150000Z"       
            DESCRIPTION
               "Added wwpLeosCfmLBMDefaultCount, wwpLeosCfmLBMDefaultInterval, wwpLeosCfmLBMDefaultTimeout,
               and wwpLeosCfmFrameClassifierMode under wwpLeosCfmGlobal.
               Added wwpLeosCfmTotalRxDropBlockedOppositeMep under wwpLeosCfmGlobalStats.
               Added wwpLeosCfmServiceMAID, wwpLeosCfmServiceMdIndex, wwpLeosCfmServiceMaintAssocNameType,
               and wwpLeosCfmServiceMaintAssocName under WwpLeosCfmServiceEntry.
               Added wwpLeosCfmLoopbackMsgDefaultInterval and wwpLeosCfmLoopbackMsgDefaultTimeout
               under WwpLeosCfmLoopbackMsgEntry.
               Added wwpLeosCfmMaintenanceDomainMdFormat, wwpLeosCfmMaintenanceDomainMdName, and
               wwpLeosCfmMaintenanceDomainStatus under WwpLeosCfmMaintenanceDomainEntry.
               Added wwpLeosCfmExtLoopbackMsgInterval, wwpLeosCfmExtLoopbackMsgTimeout,
               and wwpLeosCfmExtLoopbackMsgLoss under WwpLeosCfmExtLoopbackMsgEntry.
               Added wwpLeosCfmExtMEPBlockOppositeFaultCurrent, wwpLeosCfmExtMEPBlockOppositeFaultThreshold,
               and wwpLeosCfmExtMEPBlockOppositeFaultTime under WwpLeosCfmExtMEPEntry.
               Added wwpLeosCfmExtMEPStatsInvalidBlockedOppositeMep under WwpLeosCfmExtMEPStatsEntry.
               Added wwpLeosCfmBlockOppositeMEPSetTrap and wwpLeosCfmBlockOppositeMEPClearTrap under
               wwpLeosCfmNotifMIBNotification."
 
            REVISION "200911160000Z"
            DESCRIPTION
               "Added wwpLeosCfmExtMEPLMMMissingSequence under wwpLeosCfmExtMEPEntry"

            REVISION "200909041700Z"
            DESCRIPTION 
               "Added wwpLeosCfmExtMipTable under wwpLeosCfmExtMIBObj"

            REVISION "200908061900Z"
            DESCRIPTION 
               "Added wwpLeosCfmRemoteMEPBadSequence under wwpLeosCfmRemoteMEPEntry"

            REVISION "200907301900Z"
            DESCRIPTION
               "Added wwpLeosCfmL2LoopDetectState, wwpLeosCfmDot1adStrict, wwpLeosCfmMipLevelEnforcement and wwpLeosCfmMipCcmDbState
               under wwpLeosGlobal
               Added wwpLeosCfmServiceDefaultMEPType under wwpLeosCfmServiceEntry.
               Added wwpLeosCfmRemoteMEPCCMComment under wwpLeosCfmRemoteMEPEntry.
               Added wwpLeosCfmExtMEPLMMBadSequence and wwpLeosCfmExtMEPCCMComment under wwpLeosCfmExtMEPEntry.
               Added wwpLeosCfmExtMEPLastStatsFrameLossBadSequence under wwpLeosCfmExtMEPLastStatsEntry.
               Added wwpLeosCfmExtFrameLossMsgSeqThreshold under wwpLeosCfmExtFrameLossMsgEntry.
               Added wwpLeosCfmBadSequenceFaultTrap under wwpLeosCfmNotifMIBNotification."

            REVISION    "200811141700Z" 
            DESCRIPTION
               "Added wwpLeosCfmExtInterfaceStackTable under wwpLeosCfmExtMIBObj
               Added wwpLeosCfmExtMepCfmServiceName, wwpLeosCfmExtMepInterfaceName, wwpLeosCfmExtMepServiceInstanceName,
               wwpLeosCfmExtMepLogicalPortName to wwpLeosCfmExtMepEntryTable
               Added wwpLeosCfmFaultTrapSet and wwpLeosCfmFaultTrapClear Notifications"

            REVISION    "200810231700Z"
            DESCRIPTION
               "Added wwpLeosCfmExtLoopback, wwpLeosCfmExtMEP, wwpLeosCfmExtLinkTrace, 
               wwpLeosCfmExtDelay and wwpLeosCfmExtFrameLoss tables under wwpLeosCfmExtMIBObj.
               Added wwpLeosCfmServiceRemoteMepDiscovery under wwpLeosCfmServiceTableEntry.
               Added wwpLeosCfmRemoteMEPHoldState and wwpLeosCfmRemoteMEPRowStatus."
     
            REVISION    "200710241700Z"  
            DESCRIPTION
               "changed the properties on the WwpLeosCfmServiceFaultTable to read
               only"  

            REVISION    "200604181700Z"
            DESCRIPTION
               "Initial creation."
            ::= { wwpModulesLeos 35 }

 --
 -- Node definitions
 --        
 --wwpLeosCfmMIBObjects            
 wwpLeosCfmMIBObjects OBJECT IDENTIFIER ::= { wwpLeosCfmMIB 1 }

 wwpLeosCfmGlobal OBJECT IDENTIFIER ::= { wwpLeosCfmMIBObjects 1 }  
 
 wwpLeosCfmService OBJECT IDENTIFIER ::= { wwpLeosCfmMIBObjects 2 }

 wwpLeosCfmMIP OBJECT IDENTIFIER ::= { wwpLeosCfmMIBObjects 3 }        

 wwpLeosCfmLinkTrace OBJECT IDENTIFIER ::= { wwpLeosCfmMIBObjects 4 }        

 wwpLeosCfmLoopback OBJECT IDENTIFIER ::= { wwpLeosCfmMIBObjects 5 }

 wwpLeosCfmMaintenance OBJECT IDENTIFIER ::= { wwpLeosCfmMIBObjects 6 }

 wwpLeosCfmMEP OBJECT IDENTIFIER ::= { wwpLeosCfmMIBObjects 7 }                                                         

 wwpLeosCfmRemoteMEP OBJECT IDENTIFIER ::= { wwpLeosCfmMIBObjects 8 }

 wwpLeosCfmStack OBJECT IDENTIFIER ::= { wwpLeosCfmMIBObjects 9 }

 wwpLeosCfmMipCCMDb OBJECT IDENTIFIER ::= { wwpLeosCfmMIBObjects 10 }  

 wwpLeosCfmFaultNotif OBJECT IDENTIFIER ::= { wwpLeosCfmMIBObjects 11 }  

 wwpLeosCfmDelay OBJECT IDENTIFIER ::= { wwpLeosCfmMIBObjects 12 }  

 wwpLeosCfmFrameLoss OBJECT IDENTIFIER ::= { wwpLeosCfmMIBObjects 13 } 

 wwpLeosCfmRemoteMEPCCMLoss OBJECT IDENTIFIER ::= { wwpLeosCfmMIBObjects 14 }   
              
 wwpLeosCfmExtStack OBJECT IDENTIFIER ::= { wwpLeosCfmMIBObjects 15 }
 
 wwpLeosCfmServiceFrameBudget	OBJECT IDENTIFIER ::= { wwpLeosCfmMIBObjects 16}

 wwpLeosCfmExtMIBObj OBJECT IDENTIFIER ::= { wwpLeosCfmMIBObjects 21 }
 
 --wwpLeosCfmGlobal
 wwpLeosCfmGlobalFrameBudget OBJECT IDENTIFIER ::= { wwpLeosCfmGlobal 24 }
 
 wwpLeosCfmGlobalStats OBJECT IDENTIFIER ::= {wwpLeosCfmGlobal 25}    
 
 --wwpLeosCfmGlobalStats
 wwpLeosCfmGlobalCCMStats OBJECT IDENTIFIER ::= { wwpLeosCfmGlobalStats 26}

 wwpLeosCfmGlobalLoopbackStats OBJECT IDENTIFIER ::= { wwpLeosCfmGlobalStats 27}

 wwpLeosCfmGlobalLinkTraceStats OBJECT IDENTIFIER ::= { wwpLeosCfmGlobalStats 28}

 wwpLeosCfmGlobalDelayMeasurementStats OBJECT IDENTIFIER ::= { wwpLeosCfmGlobalStats 29 }

 wwpLeosCfmGlobalLossMeasurementStats OBJECT IDENTIFIER ::= { wwpLeosCfmGlobalStats 30}
 
 
 --wwpLeosCfmExtMIBObj
 wwpLeosCfmExtLoopback OBJECT IDENTIFIER ::= { wwpLeosCfmExtMIBObj 3 }

 wwpLeosCfmExtMEP OBJECT IDENTIFIER ::= { wwpLeosCfmExtMIBObj 7 } 

 wwpLeosCfmExtLinkTrace OBJECT IDENTIFIER ::= { wwpLeosCfmExtMIBObj 8 }

 wwpLeosCfmExtDelay OBJECT IDENTIFIER ::= { wwpLeosCfmExtMIBObj 12 }

 wwpLeosCfmExtFrameLoss OBJECT IDENTIFIER ::= { wwpLeosCfmExtMIBObj 13 }

 wwpLeosCfmExtInterfaceStack OBJECT IDENTIFIER ::= { wwpLeosCfmExtMIBObj 14 }  

 wwpLeosCfmExtMIP OBJECT IDENTIFIER ::= { wwpLeosCfmExtMIBObj 15 }

 wwpLeosCfmExtInterfaceMIP OBJECT IDENTIFIER ::= { wwpLeosCfmExtMIBObj 16 }

 wwpLeosCfmExtOamPort OBJECT IDENTIFIER ::= { wwpLeosCfmExtMIBObj 17 }


 -- Notifications 
  
 wwpLeosCfmNotifMIBNotificationPrefix  OBJECT IDENTIFIER ::= { wwpLeosCfmMIB 2 } 
 
 wwpLeosCfmNotifMIBNotification       OBJECT IDENTIFIER ::=  { wwpLeosCfmNotifMIBNotificationPrefix 0 }
 
  -- Conformance information  
 wwpLeosCfmMIBConformance OBJECT IDENTIFIER ::= { wwpLeosCfmMIB 3 } 
 wwpLeosCfmMIBCompliances OBJECT IDENTIFIER ::= { wwpLeosCfmMIBConformance 1 }                
 wwpLeosCfmMIBGroups      OBJECT IDENTIFIER ::= { wwpLeosCfmMIBConformance 2 }
              
 CfmMAID ::= TEXTUAL-CONVENTION
    DISPLAY-HINT "1x:"
    STATUS      current
    DESCRIPTION 
             "Binary data representing the md name and ma name."
    SYNTAX      OCTET STRING(SIZE(1..48))

 CfmDisplayString ::= TEXTUAL-CONVENTION
    DISPLAY-HINT "1x:"
    STATUS      current
    DESCRIPTION
            "Represents the cfm display string."
    SYNTAX      OCTET STRING (SIZE(1..2))
    
 EthType ::= TEXTUAL-CONVENTION
    DISPLAY-HINT "1x:"
    STATUS      current
    DESCRIPTION
        "Represents the ethernet type."
    SYNTAX      OCTET STRING (SIZE(1..2))
    
 SendState ::= TEXTUAL-CONVENTION
    STATUS      current
    DESCRIPTION
        "Represents the action for the row. 
         Send (1): the message with the corresponding parameters
         is to be sent to the Target host
         Clear (2): Clears the counters of the particular entry
         Cancel (3)"
    SYNTAX      INTEGER {
                   send(1),
                   clear(2),
                   cancel(3),
                   none(99)
                }

 Dot1agCfmMaintDomainNameType ::= TEXTUAL-CONVENTION
    STATUS      current
    DESCRIPTION
        "A value that represents a type (and thereby the format)
         of a Dot1agCfmMaintDomainName. The value can be one of
         the following:

         ieeeReserved(0)   Reserved for definition by IEEE 802.1
                           recommend to not use zero unless
                           absolutely needed.
          none(1)           No format specified, usually because
                            there is not (yet) a Maintenance
                            Domain Name. In this case, a zero
                            length OCTET STRING for the Domain
                            Name field is acceptable.
          dnsLikeName(2)    Domain Name like string, globally unique
                           text string derived from a DNS name.
          macAddrAndUint(3) MAC address + 2-octet (unsigned) integer.
          charString(4)     RFC2579 DisplayString, except that the
                            character codes 0-31 (decimal) are not
                            used.
          ieeeReserved(xx)  Reserved for definition by IEEE 802.1
                            xx values can be [5..31] and [64..255]
          ituReserved(xx)   Reserved for definition by ITU-T Y.1731
                            xx values range from [32..63]
         "
    REFERENCE
         "802.1ag clause 21.6.5, Table 21-19"
    SYNTAX      INTEGER {
                   none              (1),
                   dnsLikeName       (2),
                   macAddressAndUint (3),
                   charString        (4)
                }

 Dot1agCfmMaintDomainName ::= TEXTUAL-CONVENTION
    STATUS      current
    DESCRIPTION
        "Denotes a generic Maintenance Domain Name."
    REFERENCE
        "802.1ag clause 21.6.5"
    SYNTAX OCTET STRING (SIZE(1..43))

 Dot1agCfmMaintAssocNameType ::= TEXTUAL-CONVENTION
    STATUS      current
    DESCRIPTION
         "A value that represents a type (and thereby the format)
          of a Dot1agCfmMaintAssocName. The value can be one of
          the following:

          ieeeReserved(0)  Reserved for definition by IEEE 802.1
                           recommend to not use zero unless
                           absolutely needed.
          primaryVid(1)    Primary VLAN ID.
                           12 bits represented in a 2-octet integer:
                           - 4 least significant bits of the first
                             byte contains the 4 most significant
                             bits of the 12 bits primary VID
                           - second byte contains the 8 least
                             significant bits of the primary VID

                                0 1 2 3 4 5 6 7 8
                                +-+-+-+-+-+-+-+-+
                                |0 0 0 0| (MSB) |
                                +-+-+-+-+-+-+-+-+
                                |  VID   LSB    |
                                +-+-+-+-+-+-+-+-+

          charString(2)    RFC2579 DisplayString, except that the
                           character codes 0-31 (decimal) are not
                           used. (1..45) octets
                           unsignedInt16 (3) 2-octet integer/big endian
          rfc2865VpnId(4)  RFC 2685 VPN ID
                           3 octet VPN authority Organizationally
                           Unique Identifier followed by 4 octet VPN
                           index identifying VPN according to the OUI:

                                0 1 2 3 4 5 6 7 8
                                +-+-+-+-+-+-+-+-+
                                | VPN OUI (MSB) |
                                +-+-+-+-+-+-+-+-+
                                |   VPN OUI     |
                                +-+-+-+-+-+-+-+-+
                                | VPN OUI (LSB) |
                                +-+-+-+-+-+-+-+-+
                                |VPN Index (MSB)|
                                +-+-+-+-+-+-+-+-+
                                |  VPN Index    |
                                +-+-+-+-+-+-+-+-+
                                |  VPN Index    |
                                +-+-+-+-+-+-+-+-+
                                |VPN Index (LSB)|
                                +-+-+-+-+-+-+-+-+

          ieeeReserved(xx) Reserved for definition by IEEE 802.1
                           xx values can be [5..31] and [64..255]
          ituReserved(xx)  Reserved for definition by ITU-T Y.1731
                           xx values range from [32..63]
         "
    REFERENCE
         "802.1ag clause 21.6.5.4, Table 21-20"
    SYNTAX     INTEGER {
                  primaryVid    (1),
                  charString    (2),
                  unsignedInt16 (3),
                  rfc2865VpnId  (4),
                  iccBased      (32)
               }

 Dot1agCfmMaintAssocName ::= TEXTUAL-CONVENTION
    STATUS      current
    DESCRIPTION
         "Denotes a generic Maintenance Association Name. It is the
          part of the Maintenance Association Identifier which is
          unique within the Maintenance Domain Name and is appended
          to the Maintenance Domain Name to form the Maintenance
          Association Identifier (MAID).
         "
    REFERENCE
         "802.1ag clauses 21.6.5.4, 21.6.5.5, 21.6.5.6"
    SYNTAX      OCTET STRING (SIZE(1..45))

--
--Global Attributes
--
 wwpLeosCfmState OBJECT-TYPE
    SYNTAX      INTEGER {
                                disabled(1),
                                enabled(2)
                        }
    MAX-ACCESS  read-write
    STATUS      current
    DESCRIPTION
        "This object allows to globally configure CFM state."
    ::= { wwpLeosCfmGlobal 1 } 
  
 wwpLeosCfmEtherType  OBJECT-TYPE
    SYNTAX      EthType
    MAX-ACCESS  read-write
    STATUS      current
    DESCRIPTION
        "This object specifies the Ethernet type value for CFM frames."    
    ::= { wwpLeosCfmGlobal 2 }
    
 wwpLeosCfmMEPHoldTime OBJECT-TYPE
    SYNTAX      Integer32
    MAX-ACCESS  read-write
    STATUS      current
    DESCRIPTION
        "This object specifies the Time in ms to hold a MEP in an inactive state."
    ::= { wwpLeosCfmGlobal 3 }                                                  
 
 wwpLeosCfmCcmAvailable OBJECT-TYPE
    SYNTAX      Counter32
    MAX-ACCESS  read-only
    STATUS      current
    DESCRIPTION
        "This object specifies the current CCM available."
    ::= { wwpLeosCfmGlobal 4 } 
    
 wwpLeosCfmY1731EtherType  OBJECT-TYPE
    SYNTAX      EthType
    MAX-ACCESS  read-write
    STATUS      current
    DESCRIPTION
        "This object specifies the Optional Alternate Ethernet type for Y.1731 frames."    
    ::= { wwpLeosCfmGlobal 5 } 
 
  wwpLeosCfmL2LoopDetectState OBJECT-TYPE
    SYNTAX      INTEGER {
                                off(1),
                                on(2)
                        }
    MAX-ACCESS  read-write
    STATUS      current
    DESCRIPTION
        "This object allows to globally configure CFM's Layer 2 Loop
        detection state.  Frames received by the switch that have a
        Source MAC of the the switch will be discarded."
    ::= { wwpLeosCfmGlobal 6 } 
 
 
 wwpLeosCfmDot1adStrict OBJECT-TYPE
   SYNTAX INTEGER {
   					on(1), 
 					off(2)
 		   } 
   MAX-ACCESS   read-write 
   STATUS 	current
   DESCRIPTION
   		"Controls  compliance of processing 802.1ad encapsulated CFM frames in accordance with the 8021.ag standard. 
   		When on (1) CFM frames containing more than one VLAN tag are forwarded as normal data frames, bypassing processing  by MEPs and MIPs.  
   		When off (2) CFM frames with multiple VLAN tags are subject to normal CFM processing."
   ::= { wwpLeosCfmGlobal 7}
  
  wwpLeosCfmMipLevelEnforcement OBJECT-TYPE  
   SYNTAX INTEGER {
   					on(1), 
 					off(2)
 		   } 
   MAX-ACCESS   read-write 
   STATUS 	 current
   DESCRIPTION
    	"Controls enforcement of a MIPs associated MD Level.  
         When on (1) a MIP will only  process CFM messages received at its level.  
         When off (2) a MIP will process frames received at any level."
   ::= {wwpLeosCfmGlobal 8}
   
  wwpLeosCfmMipCcmDbState OBJECT-TYPE
    SYNTAX INTEGER {
                        enable(1),
                        disable(2)
                   }
    MAX-ACCESS   read-write 
    STATUS       current
    DESCRIPTION
                "The administrative state of the MIP CCM Database.  
                 A MIP only records CCMs in the MIP CCM Database when this object is set to enable (1)."
    ::= {wwpLeosCfmGlobal 9}

  --deprecated
  wwpLeosCfmLBMDefaultCount OBJECT-TYPE
    SYNTAX      Integer32
    MAX-ACCESS  read-write
    STATUS      deprecated
    DESCRIPTION
        "The global default loopback message count."
    ::= { wwpLeosCfmGlobal 10 }  
 
   --deprecated
  wwpLeosCfmLBMDefaultInterval OBJECT-TYPE
    SYNTAX      Integer32
    MAX-ACCESS  read-write
    STATUS      deprecated
    DESCRIPTION
        "The global default loopback message interval."
    ::= { wwpLeosCfmGlobal 11 } 

  --deprecated
  wwpLeosCfmLBMDefaultTimeout OBJECT-TYPE
    SYNTAX      Integer32
    MAX-ACCESS  read-write
    STATUS      deprecated
    DESCRIPTION
        "The global default loopback message timeout."
    ::= { wwpLeosCfmGlobal 12 }   

  --deprecated
 wwpLeosCfmFrameClassifierMode OBJECT-TYPE
    SYNTAX INTEGER {
                        etype(1),
                        etypeMd(2)
                   }
    MAX-ACCESS  read-write 
    STATUS      deprecated
    DESCRIPTION
        "Configures the hardware frame classification mode used to detect CFM
        and Y.1731 frames that should be sent to the CPU for processing.  Changing
        this mode will cause a reboot of the device."
    ::= {wwpLeosCfmGlobal 13}  
 
 --Deprecated OIDs 14,15 in 5305 MIB   
  wwpLeosCfmGlobalLBMDefaultCount OBJECT-TYPE
    SYNTAX      Integer32
    MAX-ACCESS  read-write
    STATUS      current
    DESCRIPTION
        "The global default loopback message count."
    ::= { wwpLeosCfmGlobal 16 }  
   
  wwpLeosCfmGlobalLBMDefaultInterval OBJECT-TYPE
    SYNTAX      Integer32
    MAX-ACCESS  read-write
    STATUS      current
    DESCRIPTION
        "The global default loopback message interval."
    ::= { wwpLeosCfmGlobal 17 } 
    
  wwpLeosCfmGlobalLBMDefaultTimeout OBJECT-TYPE
    SYNTAX      Integer32
    MAX-ACCESS  read-write
    STATUS      current
    DESCRIPTION
        "The global default loopback message timeout."
    ::= { wwpLeosCfmGlobal 18 }   

 wwpLeosCfmGlobalFrameClassifierMode OBJECT-TYPE
    SYNTAX INTEGER {
                        etype(1),
                        etypeMd(2)
                   }
    MAX-ACCESS  read-write 
    STATUS      current
    DESCRIPTION
        "Configures the hardware frame classification mode used to detect CFM
        and Y.1731 frames that should be sent to the CPU for processing.  Changing
        this mode will cause a reboot of the device."
    ::= {wwpLeosCfmGlobal 19} 
 
 --
 -- wwpLeosCfmGlobalStats
 --
  wwpLeosCfmStatsTotalTx OBJECT-TYPE
 	SYNTAX		Counter64
 	MAX-ACCESS	read-only
 	STATUS		current
 	DESCRIPTION	
 		"The number of frames sent."
 	::= { wwpLeosCfmGlobalStats 1 }
   
 wwpLeosCfmStatsTotalRx OBJECT-TYPE
 	SYNTAX		Counter64
 	MAX-ACCESS	read-only
 	STATUS		current
 	DESCRIPTION	
 		"The number of frames received."
 	::= { wwpLeosCfmGlobalStats 2 }

 wwpLeosCfmStatsTxFloodedFrames OBJECT-TYPE
 	SYNTAX		Counter64
 	MAX-ACCESS	read-only
 	STATUS		current
 	DESCRIPTION	
 		"The number of Flooded frames sent."
 	::= { wwpLeosCfmGlobalStats 3 }
 
 wwpLeosCfmStatsTxFloodedIgnoredStpState  OBJECT-TYPE
 	SYNTAX		Counter64
 	MAX-ACCESS	read-only
 	STATUS		current
 	DESCRIPTION	
 		"The number of flooded ignored frames sent."
 	::= { wwpLeosCfmGlobalStats 4 }
 
 wwpLeosCfmStatsRxTotalValidFrames OBJECT-TYPE
 	SYNTAX		Counter64
 	MAX-ACCESS	read-only
 	STATUS		current
 	DESCRIPTION	
 		"The number of valid frames received."
 	::= { wwpLeosCfmGlobalStats 5 }
 
 wwpLeosCfmStatsRxTotalNotValidatedFrames OBJECT-TYPE
 	SYNTAX		Counter64
 	MAX-ACCESS	read-only
 	STATUS		current
 	DESCRIPTION	
 		"The number of not validated frames received."
 	::= { wwpLeosCfmGlobalStats 6 }
 
 wwpLeosCfmStatsRxTotalInValidFrames OBJECT-TYPE
 	SYNTAX		Counter64
 	MAX-ACCESS	read-only
 	STATUS		current
 	DESCRIPTION	
 		"The number of invalid frames received."
 	::= { wwpLeosCfmGlobalStats 7 }                         
 
 wwpLeosCfmTotalRxInvalidMessageOverflow OBJECT-TYPE
 	SYNTAX		Counter64
 	MAX-ACCESS	read-only
 	STATUS		current
 	DESCRIPTION	
 		"The number of invalid message overflow frames received."
 	::= { wwpLeosCfmGlobalStats 8 }
 
 wwpLeosCfmTotalRxInvalidPortStatusTLV OBJECT-TYPE
 	SYNTAX		Counter64
 	MAX-ACCESS	read-only
 	STATUS		current
 	DESCRIPTION	
 		"The number of invalid port status TLV received."
 	::= { wwpLeosCfmGlobalStats 9 }                                
 	
 wwpLeosCfmTotalRxInvalidInterfaceStatusTLV OBJECT-TYPE
 	SYNTAX		Counter64
 	MAX-ACCESS	read-only
 	STATUS		current
 	DESCRIPTION	
 		"The number of invalid interface status TLV received."
 	::= { wwpLeosCfmGlobalStats 10 }                 
 	
 wwpLeosCfmTotalRxInvalidSenderIDTLV OBJECT-TYPE
 	SYNTAX		Counter64
 	MAX-ACCESS	read-only
 	STATUS		current
 	DESCRIPTION	
 		"The number of invalid sender ID TLV received."
 	::= { wwpLeosCfmGlobalStats 11 }                 
 
  wwpLeosCfmRxAdminDisableDropped OBJECT-TYPE
  	SYNTAX Counter64
  	MAX-ACCESS read-only
  	STATUS current
  	DESCRIPTION 
  		"The number of frames dropped when in admin disable mode."
  	::= { wwpLeosCfmGlobalStats 12 }
  
  wwpLesoCfmRxInvalidEtypeDropped OBJECT-TYPE
  	SYNTAX Counter64
  	MAX-ACCESS read-only
  	STATUS current
  	DESCRIPTION 
  		"The number of frames dropped when in admin disable mode."
  	::= { wwpLeosCfmGlobalStats 13 }
  
  wwpLeosCfmRxInvalidOpCodeDropped OBJECT-TYPE
  	SYNTAX Counter64
  	MAX-ACCESS read-only
  	STATUS current
  	DESCRIPTION 
  		"The number of received Invalid Opcode frames dropped."
  	::= { wwpLeosCfmGlobalStats 14 }
  	
  wwpLeosCfmRxSTPStateNotForwardingDropped OBJECT-TYPE
  	SYNTAX Counter64
  	MAX-ACCESS read-only
  	STATUS current
  	DESCRIPTION 
  		"The number of frames dropped when system is not in STP forwarding mode."
  	::= { wwpLeosCfmGlobalStats 15 } 
  
  wwpLeosCfmGlobalStatsClear	OBJECT-TYPE
  	SYNTAX INTEGER {
  			clear(1),
  			none(2)
  		}
  	MAX-ACCESS read-write
  	STATUS current
  	DESCRIPTION
  		"Setting this object to clear will clear statistics globally 
  		(Global Stats, Service Stats and Mep Stats). 
  		This object cannot be set to none."
  	::= { wwpLeosCfmGlobalStats 16 } 
  
  wwpLeosCfmGlobalLoopbackMsgStatsClear OBJECT-TYPE
  	SYNTAX INTEGER {
  			clear(1),
  			none(2)
  		}
  	MAX-ACCESS read-write
  	STATUS current
  	DESCRIPTION 
  		"Setting this object to clear will clear Loopback Statistics 
  		globally(Global stats, Service Stats and Mep Stats)."
  	::= { wwpLeosCfmGlobalStats 17 }  
  
  wwpLeosCfmGlobalLinkTraceMsgStatsClear  OBJECT-TYPE
  	SYNTAX INTEGER {
  			clear(1),
  			none(2)
  		}
  	MAX-ACCESS read-write
  	STATUS current
  	DESCRIPTION 
  		"Setting this object to clear will clear Link Trace Statistics 
  		globally(Global stats, Service Stats and Mep Stats)."
  	::= { wwpLeosCfmGlobalStats 18 } 
  
  wwpLeosCfmGlobalDelayMeasurementMsgStatsClear  OBJECT-TYPE
  	SYNTAX INTEGER {
  			clear(1),
  			none(2)
  		}
  	MAX-ACCESS read-write
  	STATUS current
  	DESCRIPTION 
  		"Setting this object to clear will clear Delay Measurement 
  		Statistics globally(Global stats, Service Stats and Mep Stats)."
  	::= { wwpLeosCfmGlobalStats 19 } 
  
  
  wwpLeosCfmGlobalLossMeasurementMsgStatsClear  OBJECT-TYPE
  	SYNTAX INTEGER {
  			clear(1),
  			none(2)
  		}
  	MAX-ACCESS read-write
  	STATUS current
  	DESCRIPTION 
  		"Setting this object to clear will clear Loss Measurement 
  		Statistics globally(Global stats, Service Stats and Mep Stats)."
  	::= { wwpLeosCfmGlobalStats 20 } 

  wwpLeosCfmTotalRxDropBlockedOppositeMep OBJECT-TYPE
  	SYNTAX Counter64
  	MAX-ACCESS read-only
  	STATUS current
  	DESCRIPTION 
  		"The number of received Blocked by Opposite Mep frames dropped."
  	::= { wwpLeosCfmGlobalStats 21 }
 
--
--wwpLeosCfmGlobalCCMStats
--  	
  wwpLeosCfmTotalTxCCM OBJECT-TYPE
  	SYNTAX Counter64
  	MAX-ACCESS read-only
  	STATUS current
  	DESCRIPTION 
  		"The total number of CCM frames sent."
  	::= { wwpLeosCfmGlobalCCMStats  1 }
  
  wwpLeosCfmTotalTxCCMFlooded OBJECT-TYPE
  	SYNTAX Counter64
  	MAX-ACCESS read-only
  	STATUS current
  	DESCRIPTION 
  		"The total number of flooded CCM frames sent."
  	::= { wwpLeosCfmGlobalCCMStats  2 }
  
  wwpLeosCfmTotalRxValidCCM OBJECT-TYPE
  	SYNTAX Counter64
  	MAX-ACCESS read-only
  	STATUS current
  	DESCRIPTION 
  		"The number of valid frames received."
  	::= { wwpLeosCfmGlobalCCMStats  3 }
  
  wwpLeosCfmTotalRxCCMInSequence OBJECT-TYPE
  	SYNTAX Counter64
  	MAX-ACCESS read-only
  	STATUS current
  	DESCRIPTION 
  		"The number of CCM frames received in sequence."
  	::= { wwpLeosCfmGlobalCCMStats  4 }
  
  wwpLeosCfmTotalRxCCMSequenceError OBJECT-TYPE
  	SYNTAX Counter64
  	MAX-ACCESS read-only
  	STATUS current
  	DESCRIPTION 
  		"The number of errored CCM frames received in sequence."
  	::= { wwpLeosCfmGlobalCCMStats  5 }
   
   wwpLeosCfmTotalCCMRxMDLevelXcon OBJECT-TYPE
  	SYNTAX Counter64
  	MAX-ACCESS read-only
  	STATUS current
  	DESCRIPTION 
  		"The number of MD Level CFM frames received."
  	::= { wwpLeosCfmGlobalCCMStats  6 }  
  	
  	wwpLeosCfmTotalCCMRxMAIDXcon OBJECT-TYPE
  	SYNTAX Counter64
  	MAX-ACCESS read-only
  	STATUS current
  	DESCRIPTION 
  		"The number of MAID Xcon CFM frames received."
  	::= { wwpLeosCfmGlobalCCMStats  7 } 
  
   wwpLeosCfmTotalRxCCMErrorOnMepId OBJECT-TYPE
  	SYNTAX Counter64
  	MAX-ACCESS read-only
  	STATUS current
  	DESCRIPTION 
  		"The number of frames dropped when in admin disable mode."
  	::= { wwpLeosCfmGlobalCCMStats  8 }
  
   wwpLeosCfmTotalRxCCMIntervalError OBJECT-TYPE
   	SYNTAX Counter64
  	MAX-ACCESS read-only
  	STATUS current
  	DESCRIPTION 
  		"The number of interval error frames received."
  	::= { wwpLeosCfmGlobalCCMStats  9 }
    
    wwpLeosCfmTotalRxInvalidCCM OBJECT-TYPE
    	SYNTAX Counter64
    	MAX-ACCESS read-only
    	STATUS current
    	DESCRIPTION
    		"The number of invalid CCM frames received."
        ::= { wwpLeosCfmGlobalCCMStats  10 } 
 
 --
 --wwpLeosCfmGlobalLoopbackStats
 --   
    wwpLeosCfmTotalTxLBM OBJECT-TYPE
    	SYNTAX Counter64
    	MAX-ACCESS read-only
    	STATUS current
    	DESCRIPTION
    		"The number of Loopback messages sent."
        ::= { wwpLeosCfmGlobalLoopbackStats  1 }
      
     wwpLeosCfmTotalTxLBR OBJECT-TYPE
     	SYNTAX Counter64
    	MAX-ACCESS read-only
    	STATUS current
    	DESCRIPTION
    		"The total number of Loopback Replies frames sent."
        ::= { wwpLeosCfmGlobalLoopbackStats  2 }
        
      wwpLeosCfmTotalRxInOderLBR OBJECT-TYPE
      	SYNTAX Counter64
    	MAX-ACCESS read-only
    	STATUS current
    	DESCRIPTION
    		"The total number of  In order LBR frames received."
        ::= { wwpLeosCfmGlobalLoopbackStats  3 } 
       
   wwpLeosCfmTotalRxOOOLBR OBJECT-TYPE
       	SYNTAX Counter64
    	MAX-ACCESS read-only
    	STATUS current
    	DESCRIPTION
    		"The number of Out of Order LBR frames received."
        ::= { wwpLeosCfmGlobalLoopbackStats  4 }
    
    wwpLeosCfmTotalRxContentMismatchLBR  OBJECT-TYPE
       	SYNTAX Counter64
    	MAX-ACCESS read-only
    	STATUS current
    	DESCRIPTION
    		"The number of Content Mismatch LBR frames received."
        ::= { wwpLeosCfmGlobalLoopbackStats  5 }         
     
     wwpLeosCfmTotalRxUnexpectedLBR  OBJECT-TYPE
       	SYNTAX Counter64
    	MAX-ACCESS read-only
    	STATUS current
    	DESCRIPTION
    		"The number of unexpected LBR frames received."
        ::= { wwpLeosCfmGlobalLoopbackStats  6 }
        
     wwpLeosCfmTotalRxInvalidLBR  OBJECT-TYPE
       	SYNTAX Counter64
    	MAX-ACCESS read-only
    	STATUS current
    	DESCRIPTION
    		"The number of invalid LBR frames received."
        ::= { wwpLeosCfmGlobalLoopbackStats  7 }
      
      wwpLeosCfmTotalRxvalidLBM OBJECT-TYPE
       	SYNTAX Counter64
    	MAX-ACCESS read-only
    	STATUS current
    	DESCRIPTION
    		"The number of valid LBM frames received."
        ::= { wwpLeosCfmGlobalLoopbackStats  8 }

      wwpLeosCfmTotalRxInvalidLBM OBJECT-TYPE
       	SYNTAX Counter64
    	MAX-ACCESS read-only
    	STATUS current
    	DESCRIPTION
    		"The number of invalid LBM frames received."
        ::= { wwpLeosCfmGlobalLoopbackStats  9 }
  
 --
 --wwpLeosCfmGlobalLinkTraceStats
 --      
      wwpLeosCfmTotalTxLTM OBJECT-TYPE
       	SYNTAX Counter64
    	MAX-ACCESS read-only
    	STATUS current
    	DESCRIPTION
    		"The number of LTM frames sent."
        ::= { wwpLeosCfmGlobalLinkTraceStats  1 }
      
      wwpLeosCfmTotalTxLTR OBJECT-TYPE
       	SYNTAX Counter64
    	MAX-ACCESS read-only
    	STATUS current
    	DESCRIPTION
    		"The total number of LTR frames sent."
        ::= { wwpLeosCfmGlobalLinkTraceStats  2 }
       
       wwpLeosCfmTotalRxValidLTM  OBJECT-TYPE
       	  SYNTAX Counter64
       	  MAX-ACCESS read-only 
       	  STATUS current
    	  DESCRIPTION
    		"The total number of LTM frames received."
        ::= { wwpLeosCfmGlobalLinkTraceStats  3 }
       
       wwpLeosCfmTotalRxValidLTR OBJECT-TYPE
       	SYNTAX Counter64
       	MAX-ACCESS read-only
       	STATUS current
    	DESCRIPTION
    		"The total number of Valid LTR frames received."
        ::= { wwpLeosCfmGlobalLinkTraceStats  4 }   
        
       wwpLeosCfmTotalRxUnexpectedLTR  OBJECT-TYPE
       	SYNTAX Counter64
       	MAX-ACCESS read-only
       	STATUS current
    	DESCRIPTION
    		"The total number of unexpected LTR frames received."
        ::= { wwpLeosCfmGlobalLinkTraceStats  5 }                                                
        
      wwpLeosCfmTotalRxInvalidLTR OBJECT-TYPE
      	SYNTAX Counter64
       	MAX-ACCESS read-only
       	STATUS current
    	DESCRIPTION
    		"The total number of Invalid LTR frames received."
        ::= { wwpLeosCfmGlobalLinkTraceStats  6 }
      
       wwpLeosCfmInvalidLTRRelayAction   OBJECT-TYPE
       	SYNTAX Counter64
       	MAX-ACCESS read-only
       	STATUS current
    	DESCRIPTION
    		"The total number of Invalid LTR Action."
        ::= { wwpLeosCfmGlobalLinkTraceStats  7 }

      wwpLeosCfmTotalRxInvalidLTM OBJECT-TYPE
       	SYNTAX Counter64
       	MAX-ACCESS read-only
       	STATUS current
    	DESCRIPTION
    		"The total number of Invalid LTM frames received."
        ::= { wwpLeosCfmGlobalLinkTraceStats  8 }
       
       wwpLeosCfmRxUnresolvedLTM  OBJECT-TYPE
       	SYNTAX Counter64
       	MAX-ACCESS read-only
       	STATUS current
    	DESCRIPTION
    		"The total number of Unresolved LTM frames received."
        ::= { wwpLeosCfmGlobalLinkTraceStats  9 }
   
 --
 --wwpLeosCfmGlobalDelayMeasurementStats
 --       
        wwpLeosCfmTotalTxDMM OBJECT-TYPE
        	SYNTAX Counter64
        	MAX-ACCESS  read-only
        	STATUS current
        	DESCRIPTION
        		"The total number of Delay Measurements messages sent."
        	::= {wwpLeosCfmGlobalDelayMeasurementStats  1 }
        
        wwpLeosCfmTotalTxDMR OBJECT-TYPE
        	SYNTAX Counter64
        	MAX-ACCESS  read-only
        	STATUS current
        	DESCRIPTION
        		"The total number of Delay Measurements Reply sent."
        	::= {wwpLeosCfmGlobalDelayMeasurementStats  2 }
        
        wwpLeosCfmTotalRxDMM  OBJECT-TYPE
        	SYNTAX Counter64
        	MAX-ACCESS  read-only
        	STATUS current
        	DESCRIPTION
        		"The total number of Delay Measurements Messages received."
        	::= {wwpLeosCfmGlobalDelayMeasurementStats  3 }
        
        wwpLeosCfmTotalRxDMR  OBJECT-TYPE
        	SYNTAX Counter64
        	MAX-ACCESS  read-only
        	STATUS current
        	DESCRIPTION
        		"The total number of Delay Measurements Reply received."
        	::= {wwpLeosCfmGlobalDelayMeasurementStats  4 }  
--
-- wwpLeosCfmGlobalLossMeasurementStats
--        
        wwpLeosCfmTotalTxLMM  OBJECT-TYPE
        	SYNTAX Counter64
        	MAX-ACCESS  read-only
        	STATUS current
        	DESCRIPTION
        		"The total number of Loss Measurements messages sent."
        	::= {wwpLeosCfmGlobalLossMeasurementStats  1 }  
       
       wwpLeosCfmTotalTxLMR OBJECT-TYPE
        	SYNTAX Counter64
        	MAX-ACCESS  read-only
        	STATUS current
        	DESCRIPTION
        		"The total number of Loss Measurements Reply frames sent."
        	::= {wwpLeosCfmGlobalLossMeasurementStats 2 }  
        
       wwpLeosCfmTotalRxLMM OBJECT-TYPE
       		SYNTAX Counter64
       		MAX-ACCESS read-only
       		STATUS current
       		DESCRIPTION
       			"The total number of LMM received."
       	 	::= { wwpLeosCfmGlobalLossMeasurementStats  3 }
       	
       	wwpLeosCfmTotalRxLMR  OBJECT-TYPE
       		SYNTAX Counter64
       		MAX-ACCESS read-only
       		STATUS current
       		DESCRIPTION
       			"The total number of LMR received."
       	 	::= { wwpLeosCfmGlobalLossMeasurementStats  4 }
 
--
-- wwpLeosCfmGlobalFrameBudgetTable
--  
  wwpLeosCfmGlobalControlModuleFrameBudget OBJECT-TYPE
  	  SYNTAX    Counter32
  	  MAX-ACCESS read-only
  	  STATUS 	   current
  	  DESCRIPTION
  		"Control Module Frame Budget .
  		Not applicable to 6.x"
  	::= { wwpLeosCfmGlobalFrameBudget 1 }
     	
  wwpLeosCfmGlobalFrameBudgetTable OBJECT-TYPE
  	SYNTAX SEQUENCE OF WwpLeosCfmGlobalFrameBudgetEntry
  	MAX-ACCESS not-accessible
  	STATUS current
  	DESCRIPTION
  		"Global Frame Budget Table"
  	::= { wwpLeosCfmGlobalFrameBudget 2 }  
  	
  wwpLeosCfmGlobalFrameBudgetEntry OBJECT-TYPE
  	SYNTAX WwpLeosCfmGlobalFrameBudgetEntry
  	MAX-ACCESS  not-accessible
    STATUS      current
    DESCRIPTION
           "An entry (conceptual row) in the wwpLeosCfmServiceTable.
            Not applicable to 6.x"
    INDEX {wwpLeosCfmGlobalFrameBudgetSlotIndex}
     ::= { wwpLeosCfmGlobalFrameBudgetTable 1 }
   
   WwpLeosCfmGlobalFrameBudgetEntry ::= SEQUENCE {
   		wwpLeosCfmGlobalFrameBudgetSlotIndex	Unsigned32,
   		wwpLeosCfmGlobalFrameBudgetValue		Counter32
   	}
 	wwpLeosCfmGlobalFrameBudgetSlotIndex	OBJECT-TYPE
 		SYNTAX 	    Unsigned32
 		MAX-ACCESS  not-accessible
 		STATUS 		current
 		DESCRIPTION
 			"Slot Index"
 		::= {    wwpLeosCfmGlobalFrameBudgetEntry 1}
 	
 	wwpLeosCfmGlobalFrameBudgetValue OBJECT-TYPE
 		SYNTAX Counter32
 		UNITS  "frames/sec"
 		MAX-ACCESS 	read-only
 		STATUS 	current
 		DESCRIPTION
 			"Frame budget value"
 		::= { wwpLeosCfmGlobalFrameBudgetEntry 2}
  	

 --
 -- CFM Service Table
 --                          
 wwpLeosCfmServiceTable OBJECT-TYPE
     SYNTAX     SEQUENCE OF WwpLeosCfmServiceEntry
     MAX-ACCESS not-accessible
     STATUS     current
     DESCRIPTION
            "The (conceptual) table listing the configuration 
            parameters for the CFM Service Table.          
            To create an entry in this table the following criteria 
            must be followed:                                  
            wwpLeosCfmServiceType must be specified.
            wwpLeosCfmServiceValue must be specified.
            wwpLeosCfmServiceName must be specified.
            wwpLeosCfmServiceStatus must be set to createAndGo.
            "  
     ::= { wwpLeosCfmService 1 }
                
 wwpLeosCfmServiceEntry OBJECT-TYPE
     SYNTAX      WwpLeosCfmServiceEntry
     MAX-ACCESS  not-accessible
     STATUS      current
     DESCRIPTION
           "An entry (conceptual row) in the wwpLeosCfmServiceTable."
     INDEX {wwpLeosCfmServiceIndex}
     ::= { wwpLeosCfmServiceTable 1 }
        
 WwpLeosCfmServiceEntry ::=  SEQUENCE {               
     wwpLeosCfmServiceIndex                             Unsigned32,
     wwpLeosCfmServiceType                              INTEGER,
     wwpLeosCfmServiceValue                             INTEGER,     
     wwpLeosCfmServiceAdminState                        INTEGER,
     wwpLeosCfmServiceOperState                         INTEGER,
     wwpLeosCfmServiceAlarmTime                         INTEGER,
     wwpLeosCfmServiceCCMInterval                       INTEGER,
     wwpLeosCfmServiceName                              DisplayString,
     wwpLeosCfmServiceMdLevel                           INTEGER,
     wwpLeosCfmServiceResetTime                         INTEGER,
     wwpLeosCfmServiceLastFaultCCM                      CfmDisplayString,     
     wwpLeosCfmServiceRMEPFailureFlag                   TruthValue,
     wwpLeosCfmServiceCCMErrorFlag                      TruthValue,
     wwpLeosCfmServiceCrossConnectErrorFlag             TruthValue,     
     wwpLeosCfmServiceNumMEP                            Counter32,
     wwpLeosCfmServiceNumRemoteMEP                      Counter32,
     wwpLeosCfmServiceNumActiveMEP                      Counter32,
     wwpLeosCfmServiceStatus                            RowStatus,
     wwpLeosCfmServiceNextMepId                         Unsigned32,
     wwpLeosCfmServiceAlarmPriority                     Unsigned32,
     wwpLeosCfmServiceNumCCMForFault                    Unsigned32,
     wwpLeosCfmServiceDMMInterval                       INTEGER,
     wwpLeosCfmServiceLMMInterval                       INTEGER,
     wwpLeosCfmServiceCCMLossStatsState                 INTEGER,
     wwpLeosCfmServiceCCMLossBucketInterval             INTEGER,
     wwpLeosCfmServiceRemoteMepDiscovery                INTEGER,
     wwpLeosCfmServiceTlvSenderIdType                   INTEGER,
     wwpLeosCfmServiceRMEPHoldTime                      Unsigned32,
     wwpLeosCfmServicePortStatusFlag                    TruthValue,
     wwpLeosCfmServiceRDIFlag                           TruthValue,
     wwpLeosCfmServiceInstabilityFlag                   TruthValue,   
     wwpLeosCfmServiceDefaultMEPType                    INTEGER,                      --deprecated
     wwpLeosCfmServiceMAID                              CfmMAID,            		  --deprecated
     wwpLeosCfmServiceMdIndex                           Unsigned32,                   --deprecated
     wwpLeosCfmServiceMaintAssocNameType                Dot1agCfmMaintAssocNameType,  --deprecated
     wwpLeosCfmServiceMaintAssocName                    Dot1agCfmMaintAssocName,      --deprecated
     wwpLeosCfmServiceCfmMAID                           CfmMAID, 
     wwpLeosCfmServiceCfmMdIndex                        Unsigned32,   
     wwpLeosCfmServiceCfmMaintAssocNameType             Dot1agCfmMaintAssocNameType,
     wwpLeosCfmServiceCfmMaintAssocName                 Dot1agCfmMaintAssocName,
     wwpLeosCfmServiceCfmDefaultMEPType   		INTEGER,
     wwpLeosCfmServiceY1731                             TruthValue,   
     wwpLeosCfmServiceAccelerated			TruthValue,
     wwpLeosCfmServiceCCMTxState                        INTEGER,
     wwpLeosCfmServiceRMEPAging                         TruthValue,
     wwpLeosCfmServiceMulticastDa                       TruthValue,
     wwpLeosCfmServiceChargedAgainstGlobalFrameBudget	TruthValue,
     wwpLeosCfmServiceCfmControlModuleFrameBudget       Counter32
   }

 wwpLeosCfmServiceIndex OBJECT-TYPE
     SYNTAX      Unsigned32 (1..65535) 
     MAX-ACCESS  read-create
     STATUS      current
     DESCRIPTION
             "A unique identifier for CFM service entry."
     ::= { wwpLeosCfmServiceEntry 1 }

 wwpLeosCfmServiceType OBJECT-TYPE
     SYNTAX      INTEGER {
                                mplsVs(1),
                                ethVs(2),
                                vlan(3),
                                pbtTunnel(4),
                                vs(5),
                                other(9)                                 
                                }
     MAX-ACCESS  read-create
     STATUS      current
     DESCRIPTION
             "This object is used to specify the service type.
              Interpretation of wwpLeosCfmServiceValue depends on the value of this MIB object.
              This MIB object along with wwpLeosCfmServiceValue must be unique for each entry in this table"
     ::= { wwpLeosCfmServiceEntry 2 } 
                
 wwpLeosCfmServiceValue OBJECT-TYPE
     SYNTAX       INTEGER (1..65535)
     MAX-ACCESS   read-create
     STATUS       current
     DESCRIPTION
             "This object is used to specify the service value.
              Interpretation of this object depends on the value of wwpLeosCfmServiceType.
              This MIB object along with wwpLeosCfmServiceType must be unique for each entry in this table"
     ::= { wwpLeosCfmServiceEntry 3 }
 
 wwpLeosCfmServiceAdminState OBJECT-TYPE
     SYNTAX       INTEGER  {
                                disabled(1),
                                enabled(2)
                          }
     MAX-ACCESS   read-write
     STATUS       current
     DESCRIPTION
             "This object specifies the admin state of CFM for this service type."
     DEFVAL {enabled}
     ::= { wwpLeosCfmServiceEntry 4 }
 
 wwpLeosCfmServiceOperState OBJECT-TYPE
     SYNTAX       INTEGER  {
                                disabled(1),
                                enabled(2)
                          }
     MAX-ACCESS   read-only
     STATUS       current
     DESCRIPTION
             "The operational state of CFM for this service type."
     ::= { wwpLeosCfmServiceEntry 5 }
 
 wwpLeosCfmServiceAlarmTime OBJECT-TYPE
     SYNTAX       INTEGER (1..60000)
     MAX-ACCESS   read-write
     STATUS       current
     DESCRIPTION
             "This MIB object allows to set the time interval that a service fault detected 
              by wwpLeosCfmServiceType must be present prior to triggering a fault alarm."
     --UNITS    {msec}
     ::= { wwpLeosCfmServiceEntry 6 }
     
 wwpLeosCfmServiceCCMInterval OBJECT-TYPE
     SYNTAX       INTEGER (0..7)
     MAX-ACCESS   read-write
     STATUS       current
     DESCRIPTION
             "This MIB object allows to set the CCM transmission interval index for the service specified by wwpLeosCfmServiceType.  
              This determines the frequency at which CCMs are transmitted.  The length of the interval increases exponentially 
              with the index value.  Setting the interval to 0 disables CCM transmission from all MEPs in the MA."
     ::= { wwpLeosCfmServiceEntry 7 }

 wwpLeosCfmServiceName OBJECT-TYPE
     SYNTAX       DisplayString (SIZE(1..31))
     MAX-ACCESS   read-create
     STATUS       current
     DESCRIPTION
             "This MIB object allows to set the CFM service name."
     ::= { wwpLeosCfmServiceEntry 9 }        

wwpLeosCfmServiceMdLevel OBJECT-TYPE
     SYNTAX       INTEGER (0..7)
     MAX-ACCESS   read-create
     STATUS       current
     DESCRIPTION
             "This MIB object sets the CFM service level which associates it with a Maintenance Domain."
     ::= { wwpLeosCfmServiceEntry 10 }        

wwpLeosCfmServiceResetTime OBJECT-TYPE
     SYNTAX       INTEGER (10..36000)
     MAX-ACCESS   read-write
     STATUS       current
     DESCRIPTION
             "This MIB object set the time interval during which no service faults can be detected
              before the service will reset a fault alarm."
     ::= { wwpLeosCfmServiceEntry 11 }           

wwpLeosCfmServiceLastFaultCCM OBJECT-TYPE
     SYNTAX       CfmDisplayString
     MAX-ACCESS   read-only
     STATUS       current
     DESCRIPTION
             "This MIB object shows last received CCM fault."
     ::= { wwpLeosCfmServiceEntry 12 }            

 wwpLeosCfmServiceRMEPFailureFlag OBJECT-TYPE
     SYNTAX       TruthValue
     MAX-ACCESS   read-only
     STATUS       current
     DESCRIPTION
             "This MIB object shows the RMEP failure flag."
     ::= { wwpLeosCfmServiceEntry 13 }        

wwpLeosCfmServiceCCMErrorFlag OBJECT-TYPE
     SYNTAX       TruthValue
     MAX-ACCESS   read-only
     STATUS       current
     DESCRIPTION
             "This MIB object shows the CCM Error flag."
     ::= { wwpLeosCfmServiceEntry 14 }        

wwpLeosCfmServiceCrossConnectErrorFlag OBJECT-TYPE
     SYNTAX       TruthValue
     MAX-ACCESS   read-only
     STATUS       current
     DESCRIPTION
             "This MIB object shows the cross-connect Error flag."
     ::= { wwpLeosCfmServiceEntry 15 }                 
 
wwpLeosCfmServiceNumMEP OBJECT-TYPE
     SYNTAX       Counter32
     MAX-ACCESS   read-only
     STATUS       current
     DESCRIPTION
             "This MIB object shows Number of MEPs."
     ::= { wwpLeosCfmServiceEntry 16 }        
 
wwpLeosCfmServiceNumRemoteMEP OBJECT-TYPE
     SYNTAX       Counter32
     MAX-ACCESS   read-only
     STATUS       current
     DESCRIPTION
             "This MIB object shows the Number of Remote MEPs."
     ::= { wwpLeosCfmServiceEntry 17 }        
 
 wwpLeosCfmServiceNumActiveMEP OBJECT-TYPE
     SYNTAX       Counter32
     MAX-ACCESS   read-only
     STATUS       current
     DESCRIPTION
             "This MIB object shows the Number of active MEPs."
     ::= { wwpLeosCfmServiceEntry 18 }         
         
 wwpLeosCfmServiceStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this object to 'destroy'."
     ::= { wwpLeosCfmServiceEntry 19 }  
     
 wwpLeosCfmServiceNextMepId OBJECT-TYPE
     SYNTAX      Unsigned32 (1..8191) 
     MAX-ACCESS  read-create
     STATUS      current
     DESCRIPTION
             "This mib object specifies the next MEP Id for given service."
     ::= { wwpLeosCfmServiceEntry 20 }
     
  wwpLeosCfmServiceAlarmPriority OBJECT-TYPE
     SYNTAX      Unsigned32 (1..5) 
     MAX-ACCESS  read-write
     STATUS      current
     DESCRIPTION
             "This mib object specifies the alarm priority for given service."
     DEFVAL		{3}
     ::= { wwpLeosCfmServiceEntry 21 } 
     
  wwpLeosCfmServiceNumCCMForFault OBJECT-TYPE
     SYNTAX      Unsigned32 (1..255) 
     MAX-ACCESS  read-write
     STATUS      current
     DESCRIPTION
             "The number of CCM frames that must go undelivered 
              for the service to be declared as operationally down."
     DEFVAL      {3}
     ::= { wwpLeosCfmServiceEntry 22 }  
     
 wwpLeosCfmServiceDMMInterval OBJECT-TYPE
     SYNTAX       INTEGER (1..7)
     MAX-ACCESS   read-write
     STATUS       current
     DESCRIPTION
             "This MIB object allows to set the DMM transmission interval index for the service specified by wwpLeosCfmServiceType.  
              This determines the frequency at which DMMs are transmitted.  The length of the interval increases exponentially 
              with the index value."
     ::= { wwpLeosCfmServiceEntry 23 }
     
 wwpLeosCfmServiceLMMInterval OBJECT-TYPE
     SYNTAX       INTEGER (1..7)
     MAX-ACCESS   read-write
     STATUS       current
     DESCRIPTION
             "This MIB object allows to set the LMM transmission interval index for the service specified by wwpLeosCfmServiceType.  
              This determines the frequency at which LMMs are transmitted.  The length of the interval increases exponentially 
              with the index value."
     ::= { wwpLeosCfmServiceEntry 24 }
 
 wwpLeosCfmServiceCCMLossStatsState OBJECT-TYPE
     SYNTAX       INTEGER  {
                                disabled(1),
                                enabled(2)
                          }
     MAX-ACCESS   read-write
     STATUS       current
     DESCRIPTION
             "This object specifies the operational state of CCM loss accounting
             for RMEPs learned by this service type."
     DEFVAL {enabled}
     ::= { wwpLeosCfmServiceEntry 25 } 
     
 wwpLeosCfmServiceCCMLossBucketInterval OBJECT-TYPE
     SYNTAX       INTEGER (1..60)
     MAX-ACCESS   read-write
     STATUS       current
     DESCRIPTION
             "This object specifies the interval in minutes that each of the 96
             CCM loss history buckets spans.  The default is 15 minutes, which
             means the default history covers 24 hours."
     ::= { wwpLeosCfmServiceEntry 26 }
  
 wwpLeosCfmServiceRemoteMepDiscovery OBJECT-TYPE
     SYNTAX      INTEGER { 
                    disabled(1),
                    enabled(2)
                 }
     MAX-ACCESS read-write
     STATUS current
     DESCRIPTION
             "This object specifies whether remote meps should be discovered automatically.
              if this object is set to enable it will cause remote meps to be discovered 
              automatically and if set to disable will not discover rempote meps."
     ::= { wwpLeosCfmServiceEntry 27 }   
 
 wwpLeosCfmServiceY1731 OBJECT-TYPE
     SYNTAX       TruthValue
     MAX-ACCESS   read-write
     STATUS       current
     DESCRIPTION
             "Specifies if y1731 is enabled for the service."
     ::= { wwpLeosCfmServiceEntry 28 }
      
  wwpLeosCfmServiceAccelerated OBJECT-TYPE
     SYNTAX       TruthValue
     MAX-ACCESS   read-create
     STATUS       current
     DESCRIPTION
             "Specifies if the service is supported in hardware ."
     ::= { wwpLeosCfmServiceEntry 49 }

 wwpLeosCfmServiceTlvSenderIdType OBJECT-TYPE
     SYNTAX      INTEGER {
                    none(1),
                    chassis(2),
                    manage(3),
                    chassisManage(4)
                 } 
     MAX-ACCESS  read-create
     STATUS      current
     DESCRIPTION
             "This mib object specifies the Sender Id Tlv Type."
     DEFVAL		{chassis}
     ::= { wwpLeosCfmServiceEntry 50 }
   
  wwpLeosCfmServiceRMEPHoldTime OBJECT-TYPE
     SYNTAX      Unsigned32 (0..3600000)
     MAX-ACCESS  read-create
     STATUS      current
     DESCRIPTION
             "This mib object specifies the Remote MEP hold time in milliseconds."
     DEFVAL		{2500}
     ::= { wwpLeosCfmServiceEntry 51 }

  wwpLeosCfmServiceCCMTxState OBJECT-TYPE
     SYNTAX      INTEGER {
                    disabled(1),
                    enabled(2)
                 }
     MAX-ACCESS  read-create
     STATUS      current
     DESCRIPTION
             "This mib object specifies the admin state of the CCM Tx."
     DEFVAL		{enabled}
     ::= { wwpLeosCfmServiceEntry 52 }

 wwpLeosCfmServicePortStatusFlag OBJECT-TYPE
     SYNTAX       TruthValue
     MAX-ACCESS   read-only
     STATUS       current
     DESCRIPTION
             "This mib object shows the Port Status defect flag."
     ::= { wwpLeosCfmServiceEntry 53 }        

 wwpLeosCfmServiceRDIFlag OBJECT-TYPE
     SYNTAX       TruthValue
     MAX-ACCESS   read-only
     STATUS       current
     DESCRIPTION
             "This mib object shows the RDI defect flag."
     ::= { wwpLeosCfmServiceEntry 54 }        

 wwpLeosCfmServiceInstabilityFlag OBJECT-TYPE
     SYNTAX       TruthValue
     MAX-ACCESS   read-only
     STATUS       current
     DESCRIPTION
             "This mib object shows the Instability defect flag."
     ::= { wwpLeosCfmServiceEntry 55 } 

  wwpLeosCfmServiceRMEPAging OBJECT-TYPE
     SYNTAX       TruthValue
     MAX-ACCESS   read-create
     STATUS       current
     DESCRIPTION
             "Controls automatic Remote MEP aging for the service."
     ::= { wwpLeosCfmServiceEntry 56 }

 --deprecated
 wwpLeosCfmServiceDefaultMEPType OBJECT-TYPE
     SYNTAX      INTEGER {
                            up(1),
                            down(2)                                 
                         }
     MAX-ACCESS  read-create
     STATUS      deprecated
     DESCRIPTION
             "This object is used to specify the type of all MEP's created for
              the service. Services of type PBT must specify a MEP type of 'down'."
     ::= { wwpLeosCfmServiceEntry 57 }

 --deprecated
 wwpLeosCfmServiceMAID OBJECT-TYPE
     SYNTAX      CfmMAID
     MAX-ACCESS  read-only
     STATUS      deprecated
     DESCRIPTION 
             "The MAID send by CCM's associated with the service."
     ::= { wwpLeosCfmServiceEntry 58 }

 --deprecated
wwpLeosCfmServiceMdIndex OBJECT-TYPE
     SYNTAX      Unsigned32
     MAX-ACCESS  read-write
     STATUS      deprecated
     DESCRIPTION
             "The unique index in the Maint Domain table."
     ::= { wwpLeosCfmServiceEntry 59 }

 --deprecated
wwpLeosCfmServiceMaintAssocNameType OBJECT-TYPE
     SYNTAX      Dot1agCfmMaintAssocNameType
     MAX-ACCESS  read-write
     STATUS      deprecated
     DESCRIPTION
             "The type (and thereby format) of the Maintenance Association Name."
     REFERENCE
             "802.1ag clauses 21.6.5.4"
     ::= { wwpLeosCfmServiceEntry 60 }
 
  --deprecated
 wwpLeosCfmServiceMaintAssocName OBJECT-TYPE
     SYNTAX Dot1agCfmMaintAssocName
     MAX-ACCESS read-write
     STATUS deprecated
     DESCRIPTION
             "The Short Maintenance Association name. The type/format of
              this object is determined by the value of the
              dot1agCfmMaNetNameType object."
     REFERENCE
             "802.1ag clauses 21.6.5.6, and Table 21-20"
     ::= { wwpLeosCfmServiceEntry 61 }    
  
  --  OIDs 62,63,64 deprecated in 5305 donot use these OIDs
   wwpLeosCfmServiceMulticastDa OBJECT-TYPE
     SYNTAX       TruthValue
     MAX-ACCESS   read-write
     STATUS       current
     DESCRIPTION
             "Specifies if multicast DA mode is enabled for the service."
     ::= { wwpLeosCfmServiceEntry 65 }
 
   --  OIDs 66,67,68,69 deprecated in 5305 donot use these OIDs
   wwpLeosCfmServiceChargedAgainstGlobalFrameBudget OBJECT-TYPE
  	SYNTAX       TruthValue
    MAX-ACCESS   read-only
    STATUS       current
    DESCRIPTION
             "This MIB object reflects if this service is charged against
             the global frame budget."
     ::= { wwpLeosCfmServiceEntry 71 }

  wwpLeosCfmServiceCfmDefaultMEPType OBJECT-TYPE
     SYNTAX      INTEGER {
                            up(1),
                            down(2)                                 
                         }
     MAX-ACCESS  read-create
     STATUS      current
     DESCRIPTION
             "This object is used to specify the type of all MEP's created for
              the service. Services of type PBT must specify a MEP type of 'down'."
     ::= { wwpLeosCfmServiceEntry 72 }
     
  wwpLeosCfmServiceCfmMAID OBJECT-TYPE
     SYNTAX      CfmMAID
     MAX-ACCESS  read-only
     STATUS      current
     DESCRIPTION 
             "The MAID send by CCM's associated with the service."
     ::= { wwpLeosCfmServiceEntry 73 } 
     
  wwpLeosCfmServiceCfmMdIndex OBJECT-TYPE
     SYNTAX      Unsigned32
     MAX-ACCESS  read-write
     STATUS      current
     DESCRIPTION
             "The unique index in the Maint Domain table."
     ::= { wwpLeosCfmServiceEntry 74 } 
     
 wwpLeosCfmServiceCfmMaintAssocNameType OBJECT-TYPE
     SYNTAX      Dot1agCfmMaintAssocNameType
     MAX-ACCESS  read-write
     STATUS      current
     DESCRIPTION
             "The type (and thereby format) of the Maintenance Association Name."
     REFERENCE
             "802.1ag clauses 21.6.5.4"
     ::= { wwpLeosCfmServiceEntry 75 }  
     
   wwpLeosCfmServiceCfmMaintAssocName OBJECT-TYPE
     SYNTAX Dot1agCfmMaintAssocName
     MAX-ACCESS read-write
     STATUS current
     DESCRIPTION
             "The Short Maintenance Association name. The type/format of
              this object is determined by the value of the
              dot1agCfmMaNetNameType object."
     REFERENCE
             "802.1ag clauses 21.6.5.6, and Table 21-20"
     ::= { wwpLeosCfmServiceEntry 76 }  
 
   wwpLeosCfmServiceCfmControlModuleFrameBudget  OBJECT-TYPE
  	 SYNTAX       Counter32
     MAX-ACCESS   read-only
     STATUS       current
     DESCRIPTION
             "Cfm Frame budget for control module for the given service."
     ::= { wwpLeosCfmServiceEntry 77 }  
 
 
  --
 -- CFM Service Frame Budget Table
 --                           
 wwpLeosCfmServiceFrameBudgetTable OBJECT-TYPE
     SYNTAX     SEQUENCE OF WwpLeosCfmServiceFrameBudgetEntry
     MAX-ACCESS not-accessible
     STATUS     current
     DESCRIPTION
            "The (conceptual) table listing the config 
            parameters for the CFM service frame budget table."  
     ::= { wwpLeosCfmServiceFrameBudget 1 }
                
 wwpLeosCfmServiceFrameBudgetEntry OBJECT-TYPE
     SYNTAX      WwpLeosCfmServiceFrameBudgetEntry
     MAX-ACCESS  not-accessible
     STATUS      current
     DESCRIPTION
           "An entry (conceptual row) in the wwpLeosCfmServiceFrameBudgetTable."
     INDEX {wwpLeosCfmServiceIndex, wwpLeosCfmSlotIndex}
     ::= { wwpLeosCfmServiceFrameBudgetTable 1 }
        
 WwpLeosCfmServiceFrameBudgetEntry ::=  SEQUENCE {           
              
     wwpLeosCfmSlotIndex                        INTEGER,
     wwpLeosCfmServiceFrameBudgetSlot			 Counter32
     }

  wwpLeosCfmSlotIndex  OBJECT-TYPE
     SYNTAX       INTEGER(0..8) 
     MAX-ACCESS   not-accessible
     STATUS       current
     DESCRIPTION
             "This object identifies the slot number."
     ::= { wwpLeosCfmServiceFrameBudgetEntry 1 } 
  
  wwpLeosCfmServiceFrameBudgetSlot   OBJECT-TYPE
  	 SYNTAX       Counter32
  	 UNITS 		  "frames/sec"
     MAX-ACCESS   read-only
     STATUS       current
     DESCRIPTION
             "This object specifies the CFM frame budget for the slot for the given service."
     ::= { wwpLeosCfmServiceFrameBudgetEntry 2 } 
  
 --
 -- CFM MIP Table
 --                          
 wwpLeosCfmMipTable OBJECT-TYPE
     SYNTAX     SEQUENCE OF WwpLeosCfmMipEntry
     MAX-ACCESS not-accessible
     STATUS     current
     DESCRIPTION
            "The (conceptual) table listing the configuration 
            parameters for the CFM MIP Table. 
            This table is not applicable if wwpLeosCfmServiceType is set to pbtTunnel. 
            Any Get/Set/Walk will return error." 
     ::= { wwpLeosCfmMIP 1 }
                
 wwpLeosCfmMipEntry OBJECT-TYPE
     SYNTAX      WwpLeosCfmMipEntry
     MAX-ACCESS  not-accessible
     STATUS      current
     DESCRIPTION
           "An entry (conceptual row) in the wwpLeosCfmMipTable."
     INDEX {wwpLeosCfmMipVid, wwpLeosCfmMipPort}
     ::= { wwpLeosCfmMipTable 1 }
                
 WwpLeosCfmMipEntry ::=  SEQUENCE { 
     wwpLeosCfmMipVid                     	INTEGER,
     wwpLeosCfmMipPort                    	INTEGER,
     wwpLeosCfmMipLevel                   	INTEGER,
     wwpLeosCfmMipStatus                  	RowStatus
 }

 wwpLeosCfmMipVid OBJECT-TYPE
     SYNTAX      INTEGER (0..24576)
     MAX-ACCESS  read-only
     STATUS      current
     DESCRIPTION
             "This object is used as index in the table and is used to specify the 
              VLAN service type for which intermediate maintenance points can be created."
     ::= { wwpLeosCfmMipEntry 1 }
 
 wwpLeosCfmMipPort OBJECT-TYPE
     SYNTAX      INTEGER (1..65535)
     MAX-ACCESS  read-only
     STATUS      current
     DESCRIPTION
             "This object is used as index in the table and is used to specify the 
              port."
     ::= { wwpLeosCfmMipEntry 2 }
                    
 wwpLeosCfmMipLevel OBJECT-TYPE
     SYNTAX       INTEGER (0..7)
     MAX-ACCESS   read-create
     STATUS       current
     DESCRIPTION
             "This object is used to specify the level attribute."
     ::= { wwpLeosCfmMipEntry 3 }

 wwpLeosCfmMipStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set it to 'destroy'."
     ::= { wwpLeosCfmMipEntry 4 }
 
 --
 --  Link Trace Message table
 --  
 wwpLeosCfmLinkTraceMsgTable OBJECT-TYPE
     SYNTAX     SEQUENCE OF WwpLeosCfmLinkTraceMsgEntry
     MAX-ACCESS not-accessible
     STATUS     current
     DESCRIPTION
            "The (conceptual) table listing the configuration 
            parameters for the LinkTraceMsg.
            Not applicable to 6.x"  
     ::= { wwpLeosCfmLinkTrace 1 }
                
 wwpLeosCfmLinkTraceMsgEntry OBJECT-TYPE
     SYNTAX      WwpLeosCfmLinkTraceMsgEntry
     MAX-ACCESS  not-accessible
     STATUS      current
     DESCRIPTION
           "An entry (conceptual row) in the wwpLeosCfmLinkTraceMsgTable."
     INDEX {wwpLeosCfmServiceIndex, wwpLeosCfmLinkTraceMsgPortId}
     ::= { wwpLeosCfmLinkTraceMsgTable 1 }
                
 WwpLeosCfmLinkTraceMsgEntry ::=  SEQUENCE { 
     wwpLeosCfmLinkTraceMsgPortId             	INTEGER,
     wwpLeosCfmLinkTraceMsgTargetMEPID        	INTEGER,
     wwpLeosCfmLinkTraceMsgTargetMacAddr      	MacAddress,
     wwpLeosCfmLinkTraceMsgTTL                	INTEGER,
     wwpLeosCfmLinkTraceMsgSequenceNumber       Integer32,
     wwpLeosCfmLinkTraceMsgRowStatus          	RowStatus,
     wwpLeosCfmLinkTraceMsgPriority             INTEGER,
     wwpLeosCfmLinkTraceMsgServiceName          DisplayString,
     wwpLeosCfmLinkTraceMsgSubPortName          DisplayString,
     wwpLeosCfmLinkTraceMsgVsIndex              Unsigned32,
     wwpLeosCfmLinkTraceMsgTotalTxLtm           Unsigned32,
     wwpLeosCfmLinkTraceMsgTotalRxLtr           Unsigned32   
 }

 wwpLeosCfmLinkTraceMsgPortId OBJECT-TYPE
     SYNTAX       INTEGER (1..65535)
     MAX-ACCESS   not-accessible
     STATUS       current
     DESCRIPTION
             "This object is used to specify the port."
     ::= { wwpLeosCfmLinkTraceMsgEntry 1 }
 
 wwpLeosCfmLinkTraceMsgTargetMEPID OBJECT-TYPE
     SYNTAX       INTEGER (1..8191)
     MAX-ACCESS   read-create
     STATUS       current
     DESCRIPTION
             "This object is used to specify the target MEPID.
              This object should only be set if wwpLeosCfmLinkTraceMsgTargetMacAddr is not specified else 
              error will be returned."
     ::= { wwpLeosCfmLinkTraceMsgEntry 2 }
     
 wwpLeosCfmLinkTraceMsgTargetMacAddr OBJECT-TYPE
     SYNTAX       MacAddress
     MAX-ACCESS   read-create
     STATUS       current
     DESCRIPTION
             "This object is used to specify the target MacAddress to be used when sending link LinkMsg.
              This object should only be set if wwpLeosCfmLinkTraceMsgTargetMEPID is not specified else 
              error will be returned."
     ::= { wwpLeosCfmLinkTraceMsgEntry 3 }
     
 wwpLeosCfmLinkTraceMsgTTL OBJECT-TYPE
     SYNTAX       INTEGER (1..255)
     MAX-ACCESS   read-create
     STATUS       current
     DESCRIPTION
             "This object is used to specify the TTL to be used when sending link LinkTraceMsg."
     ::= { wwpLeosCfmLinkTraceMsgEntry 4 }
 
 wwpLeosCfmLinkTraceMsgSequenceNumber OBJECT-TYPE
     SYNTAX       Integer32
     MAX-ACCESS   read-only
     STATUS       current
     DESCRIPTION
             "This object is used to specify the sequence number in the linkTraceMsg."
     ::= { wwpLeosCfmLinkTraceMsgEntry 5 }

 wwpLeosCfmLinkTraceMsgRowStatus OBJECT-TYPE
     SYNTAX       RowStatus
     MAX-ACCESS   read-create
     STATUS       current
     DESCRIPTION
             "Used to manage the creation and deletion of the 
              conceptual rows in this table.

              To create a row in this table, a manager must
              set this object to 'createAndGo'. To delete a row in this
              table, set this to 'destroy'."
     ::= { wwpLeosCfmLinkTraceMsgEntry 6 }

  wwpLeosCfmLinkTraceMsgPriority OBJECT-TYPE
     SYNTAX      INTEGER (0..7) 
     MAX-ACCESS  read-create
     STATUS      current
     DESCRIPTION
             "This object is used to specify the priority to be used 
              when sending LinkTraceMsg. "
     DEFVAL {7}
     ::= { wwpLeosCfmLinkTraceMsgEntry 7 } 
     
  wwpLeosCfmLinkTraceMsgServiceName OBJECT-TYPE
     SYNTAX      DisplayString (SIZE(1..31))
     MAX-ACCESS  read-only
     STATUS      current
     DESCRIPTION
             "This object is used to specify the service to be used when
              sending LinkTraceMsg."
     ::= { wwpLeosCfmLinkTraceMsgEntry 50 }

 wwpLeosCfmLinkTraceMsgSubPortName OBJECT-TYPE
     SYNTAX      DisplayString (SIZE(0..31))
     MAX-ACCESS  read-only
     STATUS      current
     DESCRIPTION
             "This object represents the sub-port name where the LinkTraceMsg
              was sent."
     ::= { wwpLeosCfmLinkTraceMsgEntry 52 }

 wwpLeosCfmLinkTraceMsgVsIndex OBJECT-TYPE
     SYNTAX      Unsigned32 
     MAX-ACCESS  read-only
     STATUS      current
     DESCRIPTION
             "This object represents the virtual switch where the LinkTraceMsg was sent."
     ::= { wwpLeosCfmLinkTraceMsgEntry 53 }

 wwpLeosCfmLinkTraceMsgTotalTxLtm OBJECT-TYPE
     SYNTAX      Unsigned32
     MAX-ACCESS  read-only
     STATUS      current
     DESCRIPTION
             "This object represents the total LinkTraceMsg were sent."
     ::= { wwpLeosCfmLinkTraceMsgEntry 54 }

 wwpLeosCfmLinkTraceMsgTotalRxLtr OBJECT-TYPE
     SYNTAX      Unsigned32
     MAX-ACCESS  read-only
     STATUS      current
     DESCRIPTION
             "This object represents the total LinkTraceMsg were received
              from the LinkTraceResponse."
     ::= { wwpLeosCfmLinkTraceMsgEntry 55 }

  
 --
 --  Link Trace Message Reply table
 --  
 wwpLeosCfmLinkTraceMsgReplyTable OBJECT-TYPE
     SYNTAX     SEQUENCE OF WwpLeosCfmLinkTraceMsgReplyEntry
     MAX-ACCESS not-accessible
     STATUS     current
     DESCRIPTION
            "The (conceptual) table listing the display 
            parameters for the LinkTrace Msg Reply."
     ::= { wwpLeosCfmLinkTrace 2 }
                
  wwpLeosCfmLinkTraceMsgReplyEntry OBJECT-TYPE
     SYNTAX      WwpLeosCfmLinkTraceMsgReplyEntry
     MAX-ACCESS  not-accessible
     STATUS      current
     DESCRIPTION
           "An entry (conceptual row) in the wwpLeosCfmLinkTraceMsgReplyTable."  

     INDEX {wwpLeosCfmServiceIndex, wwpLeosCfmLinkTraceMsgPortId, wwpLeosCfmLinkTraceMsgReplyTTL, wwpLeosCfmLinkTraceMsgReplyTTLIndex}
     ::= { wwpLeosCfmLinkTraceMsgReplyTable 1 }
                
  WwpLeosCfmLinkTraceMsgReplyEntry ::=  SEQUENCE {           
         wwpLeosCfmLinkTraceMsgReplyTTL                      	Integer32,
         wwpLeosCfmLinkTraceMsgReplyTTLIndex                    Unsigned32,
         wwpLeosCfmLinkTraceMsgReplySequenceNumber              Integer32,
         wwpLeosCfmLinkTraceMsgReplyMPMacAddr                   MacAddress,
         wwpLeosCfmLinkTraceMsgReplyMEPID                       Integer32,
         wwpLeosCfmLinkTraceMsgReplyTargetMacAddr               MacAddress,
         wwpLeosCfmLinkTraceMsgReplyRelayAction                 INTEGER,
         wwpLeosCfmLinkTraceMsgReplyIngressPort                 INTEGER,
         wwpLeosCfmLinkTraceMsgReplyIngressAction               INTEGER,
         wwpLeosCfmLinkTraceMsgReplyEgressPort                  INTEGER,
         wwpLeosCfmLinkTraceMsgReplyEgressAction                INTEGER,
         wwpLeosCfmLinkTraceMsgReplyIngressPortStr				DisplayString,
         wwpLeosCfmLinkTraceMsgReplyEgressPortStr				DisplayString,                
         wwpLeosCfmLinkTraceMsgReplyIngressMacAddr              MacAddress,
         wwpLeosCfmLinkTraceMsgReplyEgressMacAddr               MacAddress
  }
  
  wwpLeosCfmLinkTraceMsgReplyTTL OBJECT-TYPE
     SYNTAX       Integer32 (0..255)
     MAX-ACCESS   read-only
     STATUS       current
     DESCRIPTION
             "This object is used to specify the ttl of the received LinkTrace msg reply."
     ::= { wwpLeosCfmLinkTraceMsgReplyEntry 1 }
     
  wwpLeosCfmLinkTraceMsgReplyTTLIndex OBJECT-TYPE
     SYNTAX       Unsigned32 (1..24576)
     MAX-ACCESS   read-only
     STATUS       current
     DESCRIPTION
             "This object provides an additional index when multiple LinkTrace messages are received with the same TTL."
     ::= { wwpLeosCfmLinkTraceMsgReplyEntry 2 }
  
  wwpLeosCfmLinkTraceMsgReplySequenceNumber OBJECT-TYPE
     SYNTAX       Integer32
     MAX-ACCESS   read-only
     STATUS       current
     DESCRIPTION
             "This object is used to specify the sequence number of the received LinkTrace msg reply."
     ::= { wwpLeosCfmLinkTraceMsgReplyEntry 3 }

  wwpLeosCfmLinkTraceMsgReplyMPMacAddr OBJECT-TYPE
     SYNTAX       MacAddress
     MAX-ACCESS   read-only
     STATUS       current
     DESCRIPTION
             "This object is used to specify the mac address of the MP of received LinkTrace msg reply."
     ::= { wwpLeosCfmLinkTraceMsgReplyEntry 4 }

  wwpLeosCfmLinkTraceMsgReplyMEPID OBJECT-TYPE
     SYNTAX       Integer32
     MAX-ACCESS   read-only
     STATUS       current
     DESCRIPTION
             "This object is used to specify the MEP ID of the received LinkTrace msg reply."
     ::= { wwpLeosCfmLinkTraceMsgReplyEntry 5 }

  wwpLeosCfmLinkTraceMsgReplyTargetMacAddr OBJECT-TYPE
     SYNTAX       MacAddress
     MAX-ACCESS   read-only
     STATUS       current
     DESCRIPTION
             "This object is used to specify the Target Mac address of the received LinkTrace msg reply."
     ::= { wwpLeosCfmLinkTraceMsgReplyEntry 6 }
     
  wwpLeosCfmLinkTraceMsgReplyRelayAction OBJECT-TYPE
     SYNTAX       INTEGER   {
                                        invalid(1), 
                                        unknown(2),
                                        fdb(3),
                                        mpdb(4),
                                        noLearn(5),
                                        hit(6)
                            }     
     MAX-ACCESS   read-only
     STATUS       current
     DESCRIPTION
             "This object is used to specify the message reply relay action."
     ::= { wwpLeosCfmLinkTraceMsgReplyEntry 7 }
  
  wwpLeosCfmLinkTraceMsgReplyIngressPort  OBJECT-TYPE
     SYNTAX       INTEGER  (1..65535)
     MAX-ACCESS   read-only
     STATUS       obsolete
     DESCRIPTION
             "This object is used to specify the message reply ingress port."
     ::= { wwpLeosCfmLinkTraceMsgReplyEntry 8 }
 
  wwpLeosCfmLinkTraceMsgReplyIngressAction  OBJECT-TYPE
     SYNTAX       INTEGER  {
                                        ok(1),
                                        blocked(2),
                                        vid(3),
                                        down(4),
                                        none(5)
                           }
     MAX-ACCESS   read-only
     STATUS       current
     DESCRIPTION
             "This object is used to specify the message reply ingress action."
     ::= { wwpLeosCfmLinkTraceMsgReplyEntry 9 }
 
  wwpLeosCfmLinkTraceMsgReplyEgressPort  OBJECT-TYPE
     SYNTAX       INTEGER  (1..65535)
     MAX-ACCESS   read-only
     STATUS       obsolete
     DESCRIPTION
             "This object is used to specify the message reply egress port."
     ::= { wwpLeosCfmLinkTraceMsgReplyEntry 10 }
  
  wwpLeosCfmLinkTraceMsgReplyEgressAction  OBJECT-TYPE
     SYNTAX       INTEGER  {
                                none(1),
                                ttl(2),
                                down(3),
                                blocked(4),
                                vid(5),
                                ok(6)
                                }
     MAX-ACCESS   read-only
     STATUS       current
     DESCRIPTION
             "This object is used to specify the message reply egress action."
     ::= { wwpLeosCfmLinkTraceMsgReplyEntry 11 }
  
  wwpLeosCfmLinkTraceMsgReplyIngressPortStr OBJECT-TYPE
     SYNTAX       DisplayString (SIZE(1..8))
     MAX-ACCESS   read-only
     STATUS       current
     DESCRIPTION
             "This mib object is used to specify the message reply ingress port."
     ::= { wwpLeosCfmLinkTraceMsgReplyEntry 12 }        
 
 wwpLeosCfmLinkTraceMsgReplyEgressPortStr OBJECT-TYPE
     SYNTAX       DisplayString (SIZE(1..8))
     MAX-ACCESS   read-only
     STATUS       current
     DESCRIPTION
             "This mib object is used to specify the message reply egress port."
     ::= { wwpLeosCfmLinkTraceMsgReplyEntry 13 }        

  wwpLeosCfmLinkTraceMsgReplyIngressMacAddr OBJECT-TYPE
     SYNTAX       MacAddress
     MAX-ACCESS   read-only
     STATUS       current
     DESCRIPTION
             "This object is used to specify the message reply ingress mac address."
     ::= { wwpLeosCfmLinkTraceMsgReplyEntry 50 }
     
  wwpLeosCfmLinkTraceMsgReplyEgressMacAddr OBJECT-TYPE
     SYNTAX       MacAddress
     MAX-ACCESS   read-only
     STATUS       current
     DESCRIPTION
             "This object is used to specify the message reply egress mac address."
     ::= { wwpLeosCfmLinkTraceMsgReplyEntry 51 }
 
  --
  -- Loopback Msg table
  -- 
  wwpLeosCfmLoopbackMsgTable OBJECT-TYPE
     SYNTAX     SEQUENCE OF WwpLeosCfmLoopbackMsgEntry
     MAX-ACCESS not-accessible
     STATUS     current
     DESCRIPTION
            "The (conceptual) table listing the configuration 
            parameters for the LoopbackMsg."  
     ::= { wwpLeosCfmLoopback 1 }
                
 wwpLeosCfmLoopbackMsgEntry OBJECT-TYPE
     SYNTAX      WwpLeosCfmLoopbackMsgEntry
     MAX-ACCESS  not-accessible
     STATUS      current
     DESCRIPTION
           "An entry (conceptual row) in the wwpLeosCfmLoopbackMsgTable."
     INDEX {wwpLeosCfmServiceIndex, wwpLeosCfmLoopbackMsgPortId}
     ::= { wwpLeosCfmLoopbackMsgTable 1 }
                
 WwpLeosCfmLoopbackMsgEntry ::=  SEQUENCE { 
     wwpLeosCfmLoopbackMsgPortId                  INTEGER,
     wwpLeosCfmLoopbackMsgTargetMEPID             Unsigned32,
     wwpLeosCfmLoopbackMsgTargetMacAddr           MacAddress,
     wwpLeosCfmLoopbackMsgCount                   INTEGER,
     wwpLeosCfmLoopbackMsgData                    DisplayString,
     wwpLeosCfmLoopbackMsgPriority                INTEGER,     
     wwpLeosCfmLoopbackMsgDefaultInterval         INTEGER,
     wwpLeosCfmLoopbackMsgDefaultTimeout          INTEGER,
     wwpLeosCfmLoopbackMsgRowStatus               RowStatus     
 }

 wwpLeosCfmLoopbackMsgPortId OBJECT-TYPE
     SYNTAX       INTEGER (1..65535)
     MAX-ACCESS   read-only
     STATUS       current
     DESCRIPTION
             "This object is used to specify the port."
     ::= { wwpLeosCfmLoopbackMsgEntry 1 }
 
 wwpLeosCfmLoopbackMsgTargetMEPID OBJECT-TYPE
     SYNTAX       Unsigned32 (1..8191)
     MAX-ACCESS   read-create
     STATUS       current
     DESCRIPTION
             "This object is used to specify the MEPID.
              This object should only be set if wwpLeosCfmLoopbackMsgTargetMacAddr is not specified else 
              error will be returned."
     ::= { wwpLeosCfmLoopbackMsgEntry 2 }
     
 wwpLeosCfmLoopbackMsgTargetMacAddr OBJECT-TYPE
     SYNTAX       MacAddress
     MAX-ACCESS   read-create
     STATUS       current
     DESCRIPTION
             "This object is used to specify the MacAddress to be used when sending link LoopbackMsg.
              This object should only be set if wwpLeosCfmLoopbackMsgTargetMEPID is not specified else 
              error will be returned."
     ::= { wwpLeosCfmLoopbackMsgEntry 3 }
     
 wwpLeosCfmLoopbackMsgCount OBJECT-TYPE
     SYNTAX       INTEGER (1..20) 
     MAX-ACCESS   read-create
     STATUS       current
     DESCRIPTION
             "This object is used to specify the LoopbackMsg count to be used when sending link LoopbackMsg.
              "
     ::= { wwpLeosCfmLoopbackMsgEntry 4 }
 
 wwpLeosCfmLoopbackMsgData OBJECT-TYPE
     SYNTAX       DisplayString  (SIZE(1..127))
     MAX-ACCESS   read-create
     STATUS       current
     DESCRIPTION                    
             "This object is used to specify the LoopbackMsg data to be used when sending link LoopbackMsg.
              "
     ::= { wwpLeosCfmLoopbackMsgEntry 5 }

 wwpLeosCfmLoopbackMsgPriority OBJECT-TYPE
     SYNTAX       INTEGER (0..7)
     MAX-ACCESS   read-create
     STATUS       current
     DESCRIPTION
             "This object is used to specify the LoopbackMsg priority to be used when sending link LoopbackMsg.
              "
     ::= { wwpLeosCfmLoopbackMsgEntry 6 }
 
 wwpLeosCfmLoopbackMsgRowStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this to 'destroy'."
     ::= { wwpLeosCfmLoopbackMsgEntry 7 }
 
 wwpLeosCfmLoopbackMsgDefaultInterval OBJECT-TYPE
     SYNTAX       INTEGER (10..60000)
     MAX-ACCESS   read-create
     STATUS       current
     DESCRIPTION
             "The global default LoopbackMsg interval to be used when sending link LoopbackMsg
              "
     ::= { wwpLeosCfmLoopbackMsgEntry 8 }
     
 wwpLeosCfmLoopbackMsgDefaultTimeout OBJECT-TYPE
     SYNTAX       INTEGER (2000..10000)
     MAX-ACCESS   read-create
     STATUS       current
     DESCRIPTION
             "The global default LoopbackMsg timeout to be used when sending link LoopbackMsg
              "
     ::= { wwpLeosCfmLoopbackMsgEntry 9 }

 
  --
  --  CFM Maintainence Domain Table 
  --                                   
 wwpLeosCfmMaintenanceDomainTable OBJECT-TYPE
     SYNTAX     SEQUENCE OF WwpLeosCfmMaintenanceDomainEntry
     MAX-ACCESS not-accessible
     STATUS     current
     DESCRIPTION
            "The (conceptual) table listing the configuration 
            parameters for the CFM Maintenance Domain Table."  
     ::= { wwpLeosCfmMaintenance 1 }
                
 wwpLeosCfmMaintenanceDomainEntry OBJECT-TYPE
     SYNTAX      WwpLeosCfmMaintenanceDomainEntry
     MAX-ACCESS  not-accessible
     STATUS      current
     DESCRIPTION
           "An entry (conceptual row) in the wwpLeosCfmMaintenanceDomainTable."
     INDEX {wwpLeosCfmMaintenanceDomainIndex }
     ::= { wwpLeosCfmMaintenanceDomainTable 1 }
                
 WwpLeosCfmMaintenanceDomainEntry ::=  SEQUENCE { 
     wwpLeosCfmMaintenanceDomainIndex                   Unsigned32,
     wwpLeosCfmMaintenanceDomainLevel                   INTEGER,
     wwpLeosCfmMaintenanceDomainName                    DisplayString,
     wwpLeosCfmMaintenanceDomainServiceCount            Unsigned32,
     wwpLeosCfmMaintenanceDomainMdFormat                Dot1agCfmMaintDomainNameType,
     wwpLeosCfmMaintenanceDomainMdName                  Dot1agCfmMaintDomainName,
     wwpLeosCfmMaintenanceDomainStatus                  RowStatus
 }
 
 wwpLeosCfmMaintenanceDomainIndex OBJECT-TYPE
     SYNTAX      Unsigned32
     MAX-ACCESS  read-only
     STATUS      current
     DESCRIPTION
             "This object specfies the unique index in the table."
     ::= { wwpLeosCfmMaintenanceDomainEntry 1 }
     
 wwpLeosCfmMaintenanceDomainLevel OBJECT-TYPE
     SYNTAX      INTEGER (0..7)
     MAX-ACCESS  read-write
     STATUS      current
     DESCRIPTION
             "This object specfies the domain level."
     ::= { wwpLeosCfmMaintenanceDomainEntry 2 }
 
 wwpLeosCfmMaintenanceDomainName OBJECT-TYPE
     SYNTAX      DisplayString (SIZE(1..31))
     MAX-ACCESS  read-write
     STATUS      current
     DESCRIPTION
             "The domain name which can be modified."
     ::= { wwpLeosCfmMaintenanceDomainEntry 3 }
  
 wwpLeosCfmMaintenanceDomainServiceCount OBJECT-TYPE
     SYNTAX      Unsigned32
     MAX-ACCESS  read-only
     STATUS      current
     DESCRIPTION
             "This object specfies number of cfm services  mapped to this domain."
     ::= { wwpLeosCfmMaintenanceDomainEntry 4 }

 wwpLeosCfmMaintenanceDomainMdFormat OBJECT-TYPE
     SYNTAX      Dot1agCfmMaintDomainNameType
     MAX-ACCESS  read-write
     STATUS      current
     DESCRIPTION
             "The type (and thereby format) of the Maintenance Domain Name."
     REFERENCE
             "802.1ag clause 21.6.5.1"
     DEFVAL { charString }
     ::= { wwpLeosCfmMaintenanceDomainEntry 5 }

 wwpLeosCfmMaintenanceDomainMdName OBJECT-TYPE
     SYNTAX      Dot1agCfmMaintDomainName
     MAX-ACCESS  read-write
     STATUS      current
     DESCRIPTION
             "The Maintenance Domain name. The type/format of this object
              is determined by the value of the wwpLeosCfmMaintenanceDomainMdFormat object."
     REFERENCE
             "802.1ag clauses 3.24, 12.14.5, and 21.6.5.3"
        ::= { wwpLeosCfmMaintenanceDomainEntry 6 }

 wwpLeosCfmMaintenanceDomainStatus OBJECT-TYPE
     SYNTAX       RowStatus
     MAX-ACCESS   read-create
     STATUS       current
     DESCRIPTION
             "Used to manage the creation and deletion of the conceptual rows in this table.

             To create a row in this table, a manager must set this object to 'createAndGo'
             and specify, at a minimum, the wwpLeosCfmMaintenanceDomainLevel and
             wwpLeosCfmMaintenanceDomainName objects.
             
             During a create/set operation, if a non-default MdFormat is required, both the
             wwpLeosCfmMaintenanceDomainMdFormat and wwpLeosCfmMaintenanceDomainMdName objects
             must also be specified.
             
             To delete a row in this table, set this object to 'destroy'."
     ::= { wwpLeosCfmMaintenanceDomainEntry 7 }
                                                    
  --
  --  CFM MEP Table 
  --                                   
 wwpLeosCfmMEPTable OBJECT-TYPE
     SYNTAX     SEQUENCE OF WwpLeosCfmMEPEntry
     MAX-ACCESS not-accessible
     STATUS     current
     DESCRIPTION
            "The (conceptual) table listing the configuration 
            parameters for the CFM MEP table."  
     ::= { wwpLeosCfmMEP 1 }
                
 wwpLeosCfmMEPEntry OBJECT-TYPE
     SYNTAX      WwpLeosCfmMEPEntry
     MAX-ACCESS  not-accessible
     STATUS      current
     DESCRIPTION
           "An entry (conceptual row) in the wwpLeosCfmMEPTable."
     INDEX {wwpLeosCfmServiceIndex, wwpLeosCfmMEPPort}
     ::= { wwpLeosCfmMEPTable 1 }
                
 WwpLeosCfmMEPEntry ::=  SEQUENCE { 
     wwpLeosCfmMEPPort                                          INTEGER,        
     wwpLeosCfmMEPAdminState                                    INTEGER,        
     wwpLeosCfmMEPOperState                                     INTEGER,        
     wwpLeosCfmMEPDirection                                     INTEGER,
     wwpLeosCfmMEPCCMState            							INTEGER,
     wwpLeosCfmMEPCCMPriority         							INTEGER,
     wwpLeosCfmMEPLTMPriority         							INTEGER,  
     wwpLeosCfmMEPId											Unsigned32,
     wwpLeosCfmMEPMacAddr                                       MacAddress,
     wwpLeosCfmMEPNextLbmSeqNumber                              Counter32,
     wwpLeosCfmMEPRxValidInOrderLoopbackReply       			Counter32,
     wwpLeosCfmMEPRxValidOutOrderLoopbackReply          		Counter32,
     wwpLeosCfmMEPNextLTMSeqNumber                              Counter32,
     wwpLeosCfmMEPNumLoopbackRepliesTxmt                		Counter32,
     wwpLeosCfmMEPNumLTMReceived                                Counter32,
     wwpLeosCfmMEPNumLTMTxmt                                    Counter32,
     wwpLeosCfmMEPNumCCMTxmt                                    Counter32,     
     wwpLeosCfmMEPRowStatus                                     RowStatus,
     wwpLeosCfmMEPNumDMMSent									Counter32,
     wwpLeosCfmMEPDMMDelay										Counter32,
     wwpLeosCfmMEPDMMJitter										Counter32,
     wwpLeosCfmMEPNumLMMSent									Counter32,
     wwpLeosCfmMEPLMMFrameLossNear								Counter32,
     wwpLeosCfmMEPLMMFrameLossFar								Counter32,
     wwpLeosCfmMEPNumLMRReceived								Counter32,
     wwpLeosCfmMEPNumDMRReceived								Counter32,
     wwpLeosCfmMEPDMMMinDelay									Counter32,
     wwpLeosCfmMEPDMMMaxDelay									Counter32,
     wwpLeosCfmMEPDMMMinJitter									Counter32,
     wwpLeosCfmMEPDMMMaxJitter									Counter32,
     wwpLeosCfmMEPServiceName                                   DisplayString,
     wwpLeosCfmMEPSubPortName                                   DisplayString,
     wwpLeosCfmMEPVsPbtName                                     DisplayString,
     wwpLeosCfmMEPLogicalPortName                               DisplayString,
     wwpLeosCfmMEPSubPortIndex                                  Unsigned32,
     wwpLeosCfmMEPEncapsulation                                 INTEGER,
     wwpLeosCfmMEPLeadPortBayIndex                              Unsigned32,
     wwpLeosCfmMEPLeadPortShelfIndex                            Unsigned32,
     wwpLeosCfmMEPLeadPortModuleIndex                           Unsigned32,
     wwpLeosCfmMEPPBTBvid                                       Unsigned32,
     wwpLeosCfmMEPPBTEtype                                      Unsigned32,
     wwpLeosCfmMEPNumLbmTxmt                                    Counter32,
     wwpLeosCfmMEPNumLbmReceived                                Counter32,
     wwpLeosCfmMEPNumLoopbackRepliesReceived                    Counter32,
     wwpLeosCfmMEPNumLTRepliesTxmt                              Counter32,
     wwpLeosCfmMEPNumLTRepliesReceived                          Counter32,
     wwpLeosCfmMEPNumUnexpectedLTRepliesReceived                Counter32,
     wwpLeosCfmMEPNumCCMReceived                                Counter32
 }

 wwpLeosCfmMEPPort OBJECT-TYPE
     SYNTAX      INTEGER (1..65535)
     MAX-ACCESS  read-only
     STATUS      current
     DESCRIPTION
             "This object is used as index in the table and is used to specify the port id."
     ::= { wwpLeosCfmMEPEntry 1 }
 
 wwpLeosCfmMEPAdminState OBJECT-TYPE
     SYNTAX      INTEGER   {
                                disabled(1),
                                enabled(2)  
                          }
     MAX-ACCESS  read-write
     STATUS      current
     DESCRIPTION
             "This object is used to specify the admin state of CFM MEP."
     ::= { wwpLeosCfmMEPEntry 2 }
 
 wwpLeosCfmMEPOperState OBJECT-TYPE
     SYNTAX      INTEGER   {
                                disabled(1),
                                enabled(2)  
                          }
     MAX-ACCESS  read-only
     STATUS      obsolete
     DESCRIPTION
             "This object is obsolete and should not be used."
     ::= { wwpLeosCfmMEPEntry 3 }
     
 wwpLeosCfmMEPDirection OBJECT-TYPE
     SYNTAX      INTEGER {
                                up(1),
                                down(2)
                         }
     MAX-ACCESS  read-create
     STATUS      current
     DESCRIPTION
             "This object is used to specify the MEP direction of the service.
              This object can only be set if wwpLeosCfmServiceIndex is of type vlan."
     ::= { wwpLeosCfmMEPEntry 4 } 
 
 wwpLeosCfmMEPCCMState OBJECT-TYPE
     SYNTAX       INTEGER {
                                on(1),
                                off(2)
                                }
     MAX-ACCESS   read-write
     STATUS       current
     DESCRIPTION
             "This object specifies the CCM transmission for the service specified by wwpLeosCfmServiceType."
     ::= { wwpLeosCfmMEPEntry 5 }
     
 wwpLeosCfmMEPCCMPriority OBJECT-TYPE
     SYNTAX       INTEGER (0..7)
     MAX-ACCESS   read-write
     STATUS       current
     DESCRIPTION
             "This object specified the priority of CCM messages transmitted."
     ::= { wwpLeosCfmMEPEntry 6 }
     
 wwpLeosCfmMEPLTMPriority OBJECT-TYPE
     SYNTAX      INTEGER (0..7)
     MAX-ACCESS  read-write
     STATUS      obsolete
     DESCRIPTION
             "This object specifies the priority received on the given service and port."
     ::= { wwpLeosCfmMEPEntry 7 }
 
 wwpLeosCfmMEPId OBJECT-TYPE
     SYNTAX      Unsigned32 (1..8191)
     MAX-ACCESS  read-create
     STATUS      current
     DESCRIPTION
             "This object specifies the mep id for the given service and port."
     ::= { wwpLeosCfmMEPEntry 8 }
     
 wwpLeosCfmMEPMacAddr OBJECT-TYPE
     SYNTAX      MacAddress
     MAX-ACCESS  read-only
     STATUS      current
     DESCRIPTION
             "This object specifies the mac address received on the given service and port.."
     ::= { wwpLeosCfmMEPEntry 9 }
     
 wwpLeosCfmMEPNextLbmSeqNumber OBJECT-TYPE
     SYNTAX      Counter32 
     MAX-ACCESS  read-only
     STATUS      current
     DESCRIPTION
             "This object specifies the next lbm sequence number received on the given service and port."
     ::= { wwpLeosCfmMEPEntry 10 }
     
 wwpLeosCfmMEPRxValidInOrderLoopbackReply OBJECT-TYPE
     SYNTAX      Counter32
     MAX-ACCESS  read-only
     STATUS      current
     DESCRIPTION
             "The total valid in order loopback replies received on the given service and port."
     ::= { wwpLeosCfmMEPEntry 11 }
     
 wwpLeosCfmMEPRxValidOutOrderLoopbackReply OBJECT-TYPE
     SYNTAX      Counter32
     MAX-ACCESS  read-only
     STATUS      current
     DESCRIPTION
             "This object specifies the total valid out of order loopback replies received on the given service and port."
     ::= { wwpLeosCfmMEPEntry 12 }
     
 wwpLeosCfmMEPNextLTMSeqNumber OBJECT-TYPE
     SYNTAX      Counter32 
     MAX-ACCESS  read-only
     STATUS      current
     DESCRIPTION
             "This object specifies the next LTM serquence number received on the given service and port."
     ::= { wwpLeosCfmMEPEntry 13 }
     
 wwpLeosCfmMEPNumLoopbackRepliesTxmt OBJECT-TYPE
     SYNTAX      Counter32
     MAX-ACCESS  read-only
     STATUS      current
     DESCRIPTION
             "This object specifies the flags total loopback replies transmitted on the given service and port."
     ::= { wwpLeosCfmMEPEntry 14 }
     
 wwpLeosCfmMEPNumLTMReceived OBJECT-TYPE
     SYNTAX      Counter32
     MAX-ACCESS  read-only
     STATUS      current
     DESCRIPTION
             "This object specifies the total LTM messages received on the given service and port."
     ::= { wwpLeosCfmMEPEntry 15 }
     
 wwpLeosCfmMEPNumLTMTxmt OBJECT-TYPE
     SYNTAX      Counter32
     MAX-ACCESS  read-only
     STATUS      current
     DESCRIPTION
             "The total LTM transmitted on the given service and port."
     ::= { wwpLeosCfmMEPEntry 16 }
     
 wwpLeosCfmMEPNumCCMTxmt OBJECT-TYPE
     SYNTAX      Counter32
     MAX-ACCESS  read-only
     STATUS      current
     DESCRIPTION
             "This object specifies the total CCM messages transmitted on the given service and port."
     ::= { wwpLeosCfmMEPEntry 17 }     
     
 wwpLeosCfmMEPRowStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this to 'destroy'."
     ::= { wwpLeosCfmMEPEntry 18 }  
     
  wwpLeosCfmMEPNumDMMSent OBJECT-TYPE
     SYNTAX      Counter32
     MAX-ACCESS  read-only
     STATUS      current
     DESCRIPTION
             "This object specifies the total delay measurement messages
             transmitted on the given service and port."
     ::= { wwpLeosCfmMEPEntry 19 } 
     
 wwpLeosCfmMEPDMMDelay OBJECT-TYPE
     SYNTAX      Counter32
     MAX-ACCESS  read-only
     STATUS      current
     DESCRIPTION
             "This object specifies the average delay in microseconds
             measured during the last DMM performance test on the given service and port."
     ::= { wwpLeosCfmMEPEntry 20 } 
     
 wwpLeosCfmMEPDMMJitter OBJECT-TYPE
     SYNTAX      Counter32
     MAX-ACCESS  read-only
     STATUS      current
     DESCRIPTION
             "This object specifies the average jitter in microseconds
             measured during the last DMM performance test on the given service and port."
     ::= { wwpLeosCfmMEPEntry 21 }
 
 wwpLeosCfmMEPNumLMMSent OBJECT-TYPE
     SYNTAX      Counter32
     MAX-ACCESS  read-only
     STATUS      current
     DESCRIPTION
             "The total frame loss measurement messages transmitted 
             during the last test performed on the given service and port."
     ::= { wwpLeosCfmMEPEntry 22 } 
     
 wwpLeosCfmMEPLMMFrameLossNear OBJECT-TYPE
     SYNTAX      Counter32
     MAX-ACCESS  read-only
     STATUS      current
     DESCRIPTION
             "This object specifies the number of lost frames on the near side
             measured during the last LMM performance test on the given service and port."
     ::= { wwpLeosCfmMEPEntry 23 } 
     
 wwpLeosCfmMEPLMMFrameLossFar OBJECT-TYPE
     SYNTAX      Counter32
     MAX-ACCESS  read-only
     STATUS      current
     DESCRIPTION
             "This object specifies the number of lost frames on the far side
             measured during the last LMM performance test on the given service and port."
     ::= { wwpLeosCfmMEPEntry 24 }
     
 wwpLeosCfmMEPNumLMRReceived OBJECT-TYPE
 	SYNTAX		Counter32
 	MAX-ACCESS	read-only
 	STATUS		current
 	DESCRIPTION
 			"This object specifies the total number of frame loss measurement
 			replies received during the last test performed on the given service
 			and port.  If this count is zero, the near and far frame loss counts
 			are probably invalid as connectivity to the device being tested was
 			not available."
 	::= { wwpLeosCfmMEPEntry 25 }  
 	 
 wwpLeosCfmMEPNumDMRReceived OBJECT-TYPE
 	SYNTAX		Counter32
 	MAX-ACCESS	read-only
 	STATUS		current
 	DESCRIPTION
 			"This object specifies the total number of delay measurement
 			replies received during the last test performed on the given service
 			and port.  If this count is not equal to the number of delay
 			measurement frames sent, the jitter and delay are probably invalid
 			as connectivity to the device being tested was not stable."
 	::= { wwpLeosCfmMEPEntry 26 }

 wwpLeosCfmMEPDMMMinDelay OBJECT-TYPE
     SYNTAX      Counter32
     MAX-ACCESS  read-only
     STATUS      current
     DESCRIPTION
             "The minimum delay in microseconds measured during 
             the last DMM performance test on the given service and port."
     ::= { wwpLeosCfmMEPEntry 27 }
      
 wwpLeosCfmMEPDMMMaxDelay OBJECT-TYPE
     SYNTAX      Counter32
     MAX-ACCESS  read-only
     STATUS      current
     DESCRIPTION
             "The maximum delay in microseconds measured during 
             the last DMM performance test on the given service and port."
     ::= { wwpLeosCfmMEPEntry 28 } 
     
 wwpLeosCfmMEPDMMMinJitter OBJECT-TYPE
     SYNTAX      Counter32
     MAX-ACCESS  read-only
     STATUS      current
     DESCRIPTION
             "The minimum jitter in microseconds measured during 
             the last DMM performance test on the given service and port."
     ::= { wwpLeosCfmMEPEntry 29 }

wwpLeosCfmMEPDMMMaxJitter OBJECT-TYPE
     SYNTAX      Counter32
     MAX-ACCESS  read-only
     STATUS      current
     DESCRIPTION
             "The maximum jitter in microseconds measured during 
             the last DMM performance test on the given service and port."
     ::= { wwpLeosCfmMEPEntry 30 }
 	
 wwpLeosCfmMEPServiceName OBJECT-TYPE
     SYNTAX      DisplayString (SIZE(0..31))
     MAX-ACCESS  read-only
     STATUS      current
     DESCRIPTION
             "This object is used to specify the service name assigned to this port."
     ::= { wwpLeosCfmMEPEntry 50 }
  
 wwpLeosCfmMEPSubPortName OBJECT-TYPE
     SYNTAX      DisplayString (SIZE(0..31))
     MAX-ACCESS  read-only
     STATUS      current
     DESCRIPTION
             "This object represents the sub-port name assigned to the given service and port." 
     ::= { wwpLeosCfmMEPEntry 51 }

 wwpLeosCfmMEPVsPbtName OBJECT-TYPE
     SYNTAX      DisplayString (SIZE(0..31))
     MAX-ACCESS  read-only
     STATUS      current
     DESCRIPTION
             "This object represents the virtual switch or Pbt tunnel assigned to the given service and port." 
     ::= { wwpLeosCfmMEPEntry 52 }

 wwpLeosCfmMEPLogicalPortName OBJECT-TYPE
     SYNTAX      DisplayString (SIZE(0..31))
     MAX-ACCESS  read-only
     STATUS      current
     DESCRIPTION
             "This object represents the logical port name assigned to the given service and port." 
     ::= { wwpLeosCfmMEPEntry 53 }

 wwpLeosCfmMEPSubPortIndex OBJECT-TYPE
     SYNTAX      Unsigned32
     MAX-ACCESS  read-only
     STATUS      current
     DESCRIPTION
             "This object is used to specify the CFM sub-port index."
     ::= { wwpLeosCfmMEPEntry 54 }

 wwpLeosCfmMEPEncapsulation OBJECT-TYPE
     SYNTAX      INTEGER {
                                ieee802dot1d(1),
                                pbtCfmEncap(2)
                         }
     MAX-ACCESS  read-only
     STATUS      current
     DESCRIPTION
             "This object is used to specify the encapsulation applied to the service and port."
     ::= { wwpLeosCfmMEPEntry 55 } 
 
 wwpLeosCfmMEPLeadPortBayIndex OBJECT-TYPE
     SYNTAX          Unsigned32 (1..1)
     MAX-ACCESS      read-only
     STATUS          current
     DESCRIPTION
           "This object is used as to specify the agent bay that MEP is in."               
     ::= { wwpLeosCfmMEPEntry 56 }

 wwpLeosCfmMEPLeadPortShelfIndex OBJECT-TYPE
     SYNTAX          Unsigned32 (1..1)
     MAX-ACCESS      read-only
     STATUS          current
     DESCRIPTION
           "This object is used as to specify the agent shelf that MEP is in."               
     ::= { wwpLeosCfmMEPEntry 57 }

 wwpLeosCfmMEPLeadPortModuleIndex OBJECT-TYPE
     SYNTAX          Unsigned32 (1..7 | 255)
     MAX-ACCESS      read-only
     STATUS          current
     DESCRIPTION
           "This object is used as to specify the agent module that MEP is in.
            Index = 255 is reserved for Lag ports and this this object cannot be set to 255
            in this table."               
     ::= { wwpLeosCfmMEPEntry 58 }
     
 wwpLeosCfmMEPPBTBvid OBJECT-TYPE
     SYNTAX          Unsigned32 (1..8191)
     MAX-ACCESS      read-only
     STATUS          current
     DESCRIPTION
             "This object specifies the BVID assigned to the given service and port."
     ::= { wwpLeosCfmMEPEntry 59 }

 wwpLeosCfmMEPPBTEtype OBJECT-TYPE
     SYNTAX          Unsigned32 (1..8191)
     MAX-ACCESS      read-only
     STATUS          current
     DESCRIPTION
             "This object specifies the E-type assigned to the given service and port."
     ::= { wwpLeosCfmMEPEntry 60 }

 wwpLeosCfmMEPNumLbmTxmt OBJECT-TYPE
     SYNTAX      Counter32
     MAX-ACCESS  read-only
     STATUS      current
     DESCRIPTION
             "This object specifies the total loopback messages transmitted on the 
              given service and port."
     ::= { wwpLeosCfmMEPEntry 61 }
     
 wwpLeosCfmMEPNumLbmReceived OBJECT-TYPE
     SYNTAX      Counter32
     MAX-ACCESS  read-only
     STATUS      current
     DESCRIPTION
             "This object specifies the total loopback messages received on the 
              given service and port."
     ::= { wwpLeosCfmMEPEntry 62 }

 wwpLeosCfmMEPNumLoopbackRepliesReceived OBJECT-TYPE
     SYNTAX      Counter32
     MAX-ACCESS  read-only
     STATUS      current
     DESCRIPTION
             "This object specifies the total loopback replies received on the 
              given service and port."
     ::= { wwpLeosCfmMEPEntry 63 }

 wwpLeosCfmMEPNumLTRepliesTxmt OBJECT-TYPE
     SYNTAX      Counter32
     MAX-ACCESS  read-only
     STATUS      current
     DESCRIPTION
             "This object specifies the total link trace replies transmitted on the 
              given service and port."
     ::= { wwpLeosCfmMEPEntry 64 }

 wwpLeosCfmMEPNumLTRepliesReceived OBJECT-TYPE
     SYNTAX      Counter32
     MAX-ACCESS  read-only
     STATUS      current
     DESCRIPTION
             "This object specifies the total link trace replies received on the 
              given service and port."
     ::= { wwpLeosCfmMEPEntry 65 }

 wwpLeosCfmMEPNumUnexpectedLTRepliesReceived OBJECT-TYPE
     SYNTAX      Counter32
     MAX-ACCESS  read-only
     STATUS      current
     DESCRIPTION
             "This object specifies the total unexpected link trace replies received on the 
              given service and port."
     ::= { wwpLeosCfmMEPEntry 66 }

 wwpLeosCfmMEPNumCCMReceived OBJECT-TYPE
     SYNTAX      Counter32
     MAX-ACCESS  read-only
     STATUS      current
     DESCRIPTION
             "This object specifies the total CCM messages received on the given service and port."
     ::= { wwpLeosCfmMEPEntry 67 }

  --
  --  CFM Remote MEP Table
  --                                   
 wwpLeosCfmRemoteMEPTable OBJECT-TYPE
     SYNTAX     SEQUENCE OF WwpLeosCfmRemoteMEPEntry
     MAX-ACCESS not-accessible
     STATUS     current
     DESCRIPTION
            "The (conceptual) table listing the display 
             parameters for the Remote MEP table."  
     ::= { wwpLeosCfmRemoteMEP 1 }
                
 wwpLeosCfmRemoteMEPEntry OBJECT-TYPE
     SYNTAX      WwpLeosCfmRemoteMEPEntry
     MAX-ACCESS  not-accessible
     STATUS      current
     DESCRIPTION
           "An entry (conceptual row) in the wwpLeosCfmRemoteMEPTable."
     INDEX {wwpLeosCfmServiceIndex, wwpLeosCfmRemoteMEPID}
     ::= { wwpLeosCfmRemoteMEPTable 1 }
                
 WwpLeosCfmRemoteMEPEntry ::=  SEQUENCE { 
     wwpLeosCfmRemoteMEPID                              Unsigned32,
     wwpLeosCfmRemoteMEPAdminState                  	INTEGER,     
     wwpLeosCfmRemoteMEPOperState                       INTEGER,
     wwpLeosCfmRemoteMEPTime                            TimeTicks,
     wwpLeosCfmRemoteMEPMacAddr                         MacAddress,
     wwpLeosCfmRemoteMEPKLastMacStatus      			TruthValue,
     wwpLeosCfmRemoteMEPFailureFlag                     TruthValue,
     wwpLeosCfmRemoteMEPCCMErrorFlag            		TruthValue,
     wwpLeosCfmRemoteMEPRDIErrorFlag            		TruthValue,
     wwpLeosCfmRemoteMEPNumCCMRx         				Counter32,
     wwpLeosCfmRemoteMEPNumDMMSent						Counter32,
     wwpLeosCfmRemoteMEPDelay							Counter32,
     wwpLeosCfmRemoteMEPJitter							Counter32,
     wwpLeosCfmRemoteMEPNumLMMSent						Counter32,
     wwpLeosCfmRemoteMEPFrameLossNear					Counter32,
     wwpLeosCfmRemoteMEPFrameLossFar					Counter32,
     wwpLeosCfmRemoteMEPNumLMRReceived					Counter32,
     wwpLeosCfmRemoteMEPNumCCMLost						Counter32,
     wwpLeosCfmRemoteMEPNumDMRReceived					Counter32, 
     wwpLeosCfmRemoteMEPHoldState						INTEGER,   --deprecated
     wwpLeosCfmRemoteMEPCCMComment						DisplayString,   
     wwpLeosCfmRemoteMEPBadSequence                     Counter32,
     wwpLeosCfmRemoteMEPMinDelay						Counter32,
     wwpLeosCfmRemoteMEPMaxDelay						Counter32,
     wwpLeosCfmRemoteMEPMinJitter						Counter32,
     wwpLeosCfmRemoteMEPMaxJitter						Counter32,
     wwpLeosCfmRemoteMEPSubPortName                     DisplayString,
     wwpLeosCfmRemoteMEPServiceName                     DisplayString,
     wwpLeosCfmRemoteMEPBayIndex                        Unsigned32,
     wwpLeosCfmRemoteMEPShelfIndex                      Unsigned32,
     wwpLeosCfmRemoteMEPModuleIndex                     Unsigned32,
     wwpLeosCfmRemoteMEPPreviousBayIndex                Unsigned32,
     wwpLeosCfmRemoteMEPPreviousShelfIndex              Unsigned32,
     wwpLeosCfmRemoteMEPPreviousModuleIndex             Unsigned32,
     wwpLeosCfmRemoteMEPLastPortStatus                  INTEGER,
     wwpLeosCfmRemoteMEPLastInterfaceStatus             INTEGER,
     wwpLeosCfmRemoteMEPLastSeqNum                      Unsigned32,
     wwpLeosCfmRemoteMEPCCMSeqErrors                    Unsigned32,
     wwpLeosCfmRemoteMEPCCMLevel                        INTEGER,
     wwpLeosCfmRemoteCfmMEPHoldState                    INTEGER,
     wwpLeosCfmRemoteMEPServiceClear                    TruthValue,
     wwpLeosCfmRemoteMEPServiceStatisticsClear          TruthValue,  
     wwpLeosCfmRemoteMEPAccelerated			TruthValue,
     wwpLeosCfmRemoteMEPRowStatus                       RowStatus
 }

 wwpLeosCfmRemoteMEPID OBJECT-TYPE
     SYNTAX      Unsigned32 (1..100)
     MAX-ACCESS  read-only
     STATUS      current
     DESCRIPTION
             "This object is used as index in the table and is used to specify the MEPID."
     ::= { wwpLeosCfmRemoteMEPEntry 1 }
  
  wwpLeosCfmRemoteMEPAdminState OBJECT-TYPE
     SYNTAX      INTEGER  {
                                disabled(1),
                                enabled(2)
                          }
     MAX-ACCESS  read-write
     STATUS      current
     DESCRIPTION
             "The administrative state of the Remote MEP State Machine."
     ::= { wwpLeosCfmRemoteMEPEntry 2 }
     
  wwpLeosCfmRemoteMEPOperState OBJECT-TYPE
     SYNTAX      INTEGER  {
                                disabled(1),
                                enabled(2),
                                hold(3),
                                holdLocked(4)
                          }
     MAX-ACCESS  read-only
     STATUS      current
     DESCRIPTION
             "The operational state of the Remote MEP State Machine.
             disabled represents that remote mep is admin disabled.
             enabled represents that remote mep is operationally enabled
             hold represents that remote mep is admin enabled but currently in operational hold state
             holdLocked represents that remote mep is locked in hold state."
     ::= { wwpLeosCfmRemoteMEPEntry 3 }
  
 wwpLeosCfmRemoteMEPTime OBJECT-TYPE
     SYNTAX      TimeTicks 
     MAX-ACCESS  read-only
     STATUS      current
     DESCRIPTION
             "This object is used to specify the time at which the Remote MEP State Machine last 
              entered RMEP_FAILED or RMEP_OK states."
     ::= { wwpLeosCfmRemoteMEPEntry 4 }
 
 wwpLeosCfmRemoteMEPMacAddr OBJECT-TYPE
     SYNTAX      MacAddress 
     MAX-ACCESS  read-create
     STATUS      current
     DESCRIPTION
             "This object is used to specify the MAC address of the remote MEP."
     ::= { wwpLeosCfmRemoteMEPEntry 5 }
 
 wwpLeosCfmRemoteMEPKLastMacStatus OBJECT-TYPE
     SYNTAX      TruthValue 
     MAX-ACCESS  read-only
     STATUS      current
     DESCRIPTION
             "This object is used to specify the last MAC status received."
     ::= { wwpLeosCfmRemoteMEPEntry 6 }
 
 wwpLeosCfmRemoteMEPFailureFlag OBJECT-TYPE
     SYNTAX      TruthValue 
     MAX-ACCESS  read-only
     STATUS      current
     DESCRIPTION
             "This object is used to specify the Remote MEP failure flag."
     ::= { wwpLeosCfmRemoteMEPEntry  7 }
 
 wwpLeosCfmRemoteMEPCCMErrorFlag OBJECT-TYPE
     SYNTAX      TruthValue 
     MAX-ACCESS  read-only
     STATUS      current
     DESCRIPTION
             "This object is used to specify the MEP CCM error flag."
     ::= { wwpLeosCfmRemoteMEPEntry 8 }
 
 wwpLeosCfmRemoteMEPRDIErrorFlag OBJECT-TYPE
     SYNTAX      TruthValue 
     MAX-ACCESS  read-only
     STATUS      current
     DESCRIPTION
             "This object is used to specify the MEP RDI error flag."
     ::= { wwpLeosCfmRemoteMEPEntry 9 }
 
 wwpLeosCfmRemoteMEPNumCCMRx     OBJECT-TYPE
     SYNTAX      Counter32
     MAX-ACCESS  read-only
     STATUS      current
     DESCRIPTION
             "This object is used to show the number of MEP CCM frames received."
     ::= { wwpLeosCfmRemoteMEPEntry 10 }  
     
 wwpLeosCfmRemoteMEPNumDMMSent	OBJECT-TYPE
 	SYNTAX		Counter32
 	MAX-ACCESS	read-only
 	STATUS		current
 	DESCRIPTION
 	      "The number of DMM frames sent."
 	::= { wwpLeosCfmRemoteMEPEntry 11 }
 	
 wwpLeosCfmRemoteMEPDelay		OBJECT-TYPE
	SYNTAX		Counter32
 	MAX-ACCESS	read-only
 	STATUS		current
 	DESCRIPTION
 			"This object is used to show the average Delay in microseconds
 			during the last Delay Measurement test."
    ::= { wwpLeosCfmRemoteMEPEntry 12 }
 
 wwpLeosCfmRemoteMEPJitter		OBJECT-TYPE
	SYNTAX		Counter32
 	MAX-ACCESS	read-only
 	STATUS		current
 	DESCRIPTION
 			"This object is used to show the average Jitter in microseconds
 			during the last Delay Measurement test."
    ::= { wwpLeosCfmRemoteMEPEntry 13 }

 wwpLeosCfmRemoteMEPNumLMMSent	OBJECT-TYPE
 	SYNTAX		Counter32
 	MAX-ACCESS	read-only
 	STATUS		current
 	DESCRIPTION
 			"This object is used to show the number of LMM frames sent."
    ::= { wwpLeosCfmRemoteMEPEntry 14 }
 	
 wwpLeosCfmRemoteMEPFrameLossNear	OBJECT-TYPE
	SYNTAX		Counter32
 	MAX-ACCESS	read-only
 	STATUS		current
 	DESCRIPTION
 			"This object is used to show the near side Frame Loss
 			during the last Frame Loss Measurement test."
    ::= { wwpLeosCfmRemoteMEPEntry 15 }
 
 wwpLeosCfmRemoteMEPFrameLossFar	OBJECT-TYPE
	SYNTAX		Counter32
 	MAX-ACCESS	read-only
 	STATUS		current
 	DESCRIPTION
 			"This object is used to show the far side Frame Loss
 			during the last Frame Loss Measurement test."
    ::= { wwpLeosCfmRemoteMEPEntry 16 }
 
 wwpLeosCfmRemoteMEPNumLMRReceived	OBJECT-TYPE
 	SYNTAX		Counter32
 	MAX-ACCESS	read-only
 	STATUS		current
 	DESCRIPTION
 			"This object is used to show the number of LMR frames received."
 	::= { wwpLeosCfmRemoteMEPEntry 17 }
 	
 wwpLeosCfmRemoteMEPNumCCMLost     OBJECT-TYPE
     SYNTAX      Counter32
     MAX-ACCESS  read-only
     STATUS      current
     DESCRIPTION
             "This object is used to show the number of MEP CCM frames lost,
             as calculated by watching for CCM sequence errors."
     ::= { wwpLeosCfmRemoteMEPEntry 18 }
       
 wwpLeosCfmRemoteMEPNumDMRReceived	OBJECT-TYPE
 	SYNTAX		Counter32
 	MAX-ACCESS	read-only
 	STATUS		current
 	DESCRIPTION
 			"This object is used to show the number of DMR frames received."
 	::= { wwpLeosCfmRemoteMEPEntry 19 }

--deprecated
wwpLeosCfmRemoteMEPHoldState OBJECT-TYPE
    SYNTAX INTEGER
    		{ 
    		disabled(1),
    		enabled(2),
    		locked(3)
    		}
    MAX-ACCESS read-create
    STATUS deprecated
    DESCRIPTION
    	"This object is used to set the remote MEP Hold State"
    ::= { wwpLeosCfmRemoteMEPEntry 20 }
 
 wwpLeosCfmRemoteMEPRowStatus 	OBJECT-TYPE
   SYNTAX RowStatus
   MAX-ACCESS read-create
   STATUS current
   DESCRIPTION
   		"This object is used to create entries in remote mep table"
   ::= { wwpLeosCfmRemoteMEPEntry 21 } 
 
 wwpLeosCfmRemoteMEPCCMComment OBJECT-TYPE
    SYNTAX       DisplayString (SIZE(1..32))
    MAX-ACCESS   read-only
    STATUS       current
    DESCRIPTION
             "This mib object contains the CCM Comment, if available,
             that was sent by the remote Ciena device."
     ::= { wwpLeosCfmRemoteMEPEntry 22 }
     
 wwpLeosCfmRemoteMEPBadSequence OBJECT-TYPE
    SYNTAX       Counter32
    MAX-ACCESS   read-only
    STATUS       current
    DESCRIPTION
             "This mib object contains the number of LMR frames received 
              with bad sequence number, for a given service and remote mep."
     ::= { wwpLeosCfmRemoteMEPEntry 23 }
  	
 wwpLeosCfmRemoteMEPMinDelay		OBJECT-TYPE
	SYNTAX		Counter32
 	MAX-ACCESS	read-only
 	STATUS		current
 	DESCRIPTION
 		"The minimum Delay in microseconds
 		during the last Delay Measurement test."
 	::= { wwpLeosCfmRemoteMEPEntry 24 }
 	
 wwpLeosCfmRemoteMEPMaxDelay		OBJECT-TYPE
	SYNTAX		Counter32
 	MAX-ACCESS	read-only
 	STATUS		current
 	DESCRIPTION
 		"The maximum Delay in microseconds
 		during the last Delay Measurement test."
 	::= { wwpLeosCfmRemoteMEPEntry 25 }
 
 wwpLeosCfmRemoteMEPMinJitter		OBJECT-TYPE
	SYNTAX		Counter32
 	MAX-ACCESS	read-only
 	STATUS		current
 	DESCRIPTION
 		"The minimum jitter in microseconds
 		during the last Delay Measurement test."
 	::= { wwpLeosCfmRemoteMEPEntry 26 }
 
 wwpLeosCfmRemoteMEPMaxJitter		OBJECT-TYPE
	SYNTAX		Counter32
 	MAX-ACCESS	read-only
 	STATUS		current
 	DESCRIPTION
 		"The maximum jitter in microseconds
 		during the last Delay Measurement test."
 	::= { wwpLeosCfmRemoteMEPEntry 27 }
 
 wwpLeosCfmRemoteCfmMEPHoldState OBJECT-TYPE
     SYNTAX      INTEGER  {
                                disable(1),
                                enable(2),
                                lock(3)
                                }
     MAX-ACCESS  read-create
     STATUS      current
     DESCRIPTION
             "Hold-state for the remote-mep entry."
     ::= { wwpLeosCfmRemoteMEPEntry 28 }
 
  wwpLeosCfmRemoteMEPServiceClear OBJECT-TYPE
     SYNTAX      TruthValue
     MAX-ACCESS  read-create
     STATUS      current
     DESCRIPTION
             "Setting this object to true causes the remote MEP for this service
              to be re-initialized ."
     ::= { wwpLeosCfmRemoteMEPEntry 29 }
  
  wwpLeosCfmRemoteMEPServiceStatisticsClear OBJECT-TYPE
     SYNTAX      TruthValue
     MAX-ACCESS  read-create
     STATUS      current
     DESCRIPTION
             "Setting this object to true resets the statistics for the remote MEP
              for this service."
     ::= { wwpLeosCfmRemoteMEPEntry 30 }
 
  wwpLeosCfmRemoteMEPAccelerated OBJECT-TYPE
     SYNTAX      TruthValue
     MAX-ACCESS  read-only
     STATUS      current
     DESCRIPTION
             "Specifies if the remote-mep is monitored in the hardware."
     ::= { wwpLeosCfmRemoteMEPEntry 49 }
                                 
 wwpLeosCfmRemoteMEPSubPortName   OBJECT-TYPE
     SYNTAX          DisplayString (SIZE(0..31))
     MAX-ACCESS      read-only
     STATUS          current
     DESCRIPTION
           "The object indicates the unique index for the module."               
     ::= { wwpLeosCfmRemoteMEPEntry 50 }

 wwpLeosCfmRemoteMEPServiceName OBJECT-TYPE
     SYNTAX      DisplayString (SIZE(0..31))
     MAX-ACCESS  read-only
     STATUS      current
     DESCRIPTION
             "This object is used to specify the Service name."
     ::= { wwpLeosCfmRemoteMEPEntry 51 }
  
 wwpLeosCfmRemoteMEPBayIndex          OBJECT-TYPE
     SYNTAX          Unsigned32 (1..1)
     MAX-ACCESS      read-only
     STATUS          current
     DESCRIPTION
           "This object is used as to specify the agent bay that MEP is in."               
     ::= { wwpLeosCfmRemoteMEPEntry 52 }

 wwpLeosCfmRemoteMEPShelfIndex          OBJECT-TYPE
     SYNTAX          Unsigned32 (1..1)
     MAX-ACCESS      read-only
     STATUS          current
     DESCRIPTION
           "This object is used as to specify the agent shelf that MEP is in."               
     ::= { wwpLeosCfmRemoteMEPEntry 53 }

 wwpLeosCfmRemoteMEPModuleIndex          OBJECT-TYPE
     SYNTAX          Unsigned32 (1..7 | 255)
     MAX-ACCESS      read-only
     STATUS          current
     DESCRIPTION
           "This object is used as to specify the agent module that MEP is in.
            Index = 255 is reserved for Lag ports and this this object cannot be set to 255
            in this table."               
     ::= { wwpLeosCfmRemoteMEPEntry 54 }
     
 wwpLeosCfmRemoteMEPPreviousBayIndex    OBJECT-TYPE
     SYNTAX          Unsigned32 (1..1)
     MAX-ACCESS      read-only
     STATUS          current
     DESCRIPTION
           "This object is used as to specify the agent bay that MEP was previously in."               
     ::= { wwpLeosCfmRemoteMEPEntry 55 }
     
 wwpLeosCfmRemoteMEPPreviousShelfIndex  OBJECT-TYPE
     SYNTAX          Unsigned32 (1..1)
     MAX-ACCESS      read-only
     STATUS          current
     DESCRIPTION
           "This object is used as to specify the agent shelf that MEP was previously in."               
     ::= { wwpLeosCfmRemoteMEPEntry 56 }

 wwpLeosCfmRemoteMEPPreviousModuleIndex  OBJECT-TYPE
     SYNTAX          Unsigned32 (1..7 | 255)
     MAX-ACCESS      read-only
     STATUS          current
     DESCRIPTION
           "This object is used as to specify the agent module that MEP was previously in.
            Index = 255 is reserved for Lag ports and this this object cannot be set to 255
            in this table."               
     ::= { wwpLeosCfmRemoteMEPEntry 57 }
          
 wwpLeosCfmRemoteMEPLastPortStatus OBJECT-TYPE
     SYNTAX      INTEGER {
                   unknown(1),
                   none(2),
                   blocked(3),
                   up(4)
                 }
     MAX-ACCESS  read-only
     STATUS      current
     DESCRIPTION
             "This object is used as to specify the remote MEP last port status."
     ::= { wwpLeosCfmRemoteMEPEntry 58 }

 wwpLeosCfmRemoteMEPLastInterfaceStatus OBJECT-TYPE
     SYNTAX      INTEGER {
                   none(1),
                   up(2),
                   down(3),
                   testing(4),
                   dormant(5),
                   lowerLayerDown(6),
                   notPresent(7)
                 }
     MAX-ACCESS  read-only
     STATUS      current
     DESCRIPTION
             "This object is used as to specify the remote MEP interface status."
     ::= { wwpLeosCfmRemoteMEPEntry 59 }

 wwpLeosCfmRemoteMEPLastSeqNum     OBJECT-TYPE
     SYNTAX      Unsigned32
     MAX-ACCESS  read-only
     STATUS      current
     DESCRIPTION
             "This object is used to show the tbd."
     ::= { wwpLeosCfmRemoteMEPEntry 60 }

 wwpLeosCfmRemoteMEPCCMSeqErrors     OBJECT-TYPE
     SYNTAX      Unsigned32
     MAX-ACCESS  read-only
     STATUS      current
     DESCRIPTION
             "This object is used to show the number of MEP CCM frames sequence errors."
     ::= { wwpLeosCfmRemoteMEPEntry 61 }

 wwpLeosCfmRemoteMEPCCMLevel OBJECT-TYPE
     SYNTAX      INTEGER (1..256)
     MAX-ACCESS  read-only
     STATUS      current
     DESCRIPTION
             "This object is used as to specify the CCM level."
     ::= { wwpLeosCfmRemoteMEPEntry 62 } 
     
  --OID 63 is deprecated in 5305 MIB, OID 64 is removed in the 5305 MIB
  wwpLeosCfmRemoteMEPDeleteAll OBJECT-TYPE
     SYNTAX      TruthValue 
     MAX-ACCESS  read-write
     STATUS      current
     DESCRIPTION
             "Setting this object to true will delete all remote meps.
              This object will always return false."
     ::= { wwpLeosCfmRemoteMEP 65 }
  
  --
  --  CFM Port Stack Table
  --                                   
 wwpLeosCfmPortStackTable OBJECT-TYPE
     SYNTAX     SEQUENCE OF WwpLeosCfmPortStackEntry
     MAX-ACCESS not-accessible
     STATUS     deprecated
     DESCRIPTION
            "The (conceptual) table listing the display 
             parameters for the CFM port stack table."  
     ::= { wwpLeosCfmStack 1 }
                
 wwpLeosCfmPortStackEntry OBJECT-TYPE
     SYNTAX      WwpLeosCfmPortStackEntry
     MAX-ACCESS  not-accessible
     STATUS      deprecated
     DESCRIPTION
           "An entry (conceptual row) in the wwpLeosCfmPortStackTable."
     INDEX {wwpLeosCfmPortStackPort, wwpLeosCfmPortStackVid, wwpLeosCfmPortStackType, wwpLeosCfmPortStackLevel}
     ::= { wwpLeosCfmPortStackTable 1 }
                
 WwpLeosCfmPortStackEntry ::=  SEQUENCE {
     wwpLeosCfmPortStackPort        INTEGER, 
     wwpLeosCfmPortStackVid         INTEGER, 
     wwpLeosCfmPortStackType        INTEGER,
     wwpLeosCfmPortStackLevel       Unsigned32,
     wwpLeosCfmPortStackMEPId       INTEGER
 }
 
 wwpLeosCfmPortStackPort OBJECT-TYPE
     SYNTAX      INTEGER (1..65535)
     MAX-ACCESS  read-only
     STATUS      deprecated
     DESCRIPTION
             "This object is used as index in the table and is used to specify the port id."
     ::= { wwpLeosCfmPortStackEntry 1 }

 wwpLeosCfmPortStackVid OBJECT-TYPE
     SYNTAX      INTEGER (1..24576)
     MAX-ACCESS  read-only
     STATUS      deprecated
     DESCRIPTION
             "This object is used as index in the table and is used to show the VLAN."
     ::= { wwpLeosCfmPortStackEntry 2 }

 wwpLeosCfmPortStackType OBJECT-TYPE
     SYNTAX      INTEGER  {
                                        mepUp(1),
                                        mepDown(2),
                                        mip(3)
                                }
     MAX-ACCESS  read-only
     STATUS      deprecated
     DESCRIPTION
             "This object is used as index in the table and is used to show the type of Maintenance Point."
     ::= { wwpLeosCfmPortStackEntry 3 }
                          
  wwpLeosCfmPortStackLevel OBJECT-TYPE
     SYNTAX      Unsigned32 (0..7)
     MAX-ACCESS  read-only
     STATUS      deprecated
     DESCRIPTION
             "This object is used as index in the table and is used to show the level of stack."
     ::= { wwpLeosCfmPortStackEntry 4 }

   wwpLeosCfmPortStackMEPId OBJECT-TYPE
     SYNTAX      INTEGER (1..100)
     MAX-ACCESS  read-only
     STATUS      deprecated
     DESCRIPTION
             "The MEP ID."
     ::= { wwpLeosCfmPortStackEntry 5 }
 
  --
  --  CFM Port Stack Table
  --                                   
 wwpLeosCfmExtPortStackTable OBJECT-TYPE
     SYNTAX     SEQUENCE OF WwpLeosCfmExtPortStackEntry
     MAX-ACCESS not-accessible
     STATUS     current
     DESCRIPTION
            "The (conceptual) table listing the display 
             parameters for the CFM port stack table."  
     ::= { wwpLeosCfmExtStack 1 } 
     
 wwpLeosCfmExtPortStackEntry OBJECT-TYPE
     SYNTAX      WwpLeosCfmExtPortStackEntry
     MAX-ACCESS  not-accessible
     STATUS      current
     DESCRIPTION
           "An entry (conceptual row) in the wwpLeosCfmPortStackTable."
     INDEX {wwpLeosCfmExtPortStackVid, wwpLeosCfmExtPortStackPort, wwpLeosCfmExtPortStackType, wwpLeosCfmExtPortStackLevel}
     ::= { wwpLeosCfmExtPortStackTable 1 } 
     
 WwpLeosCfmExtPortStackEntry ::=  SEQUENCE {
     wwpLeosCfmExtPortStackVid         INTEGER, 
	 wwpLeosCfmExtPortStackPort        INTEGER, 
     wwpLeosCfmExtPortStackType        INTEGER,
     wwpLeosCfmExtPortStackLevel       Unsigned32,
     wwpLeosCfmExtPortStackMEPId       INTEGER
 }
 wwpLeosCfmExtPortStackVid OBJECT-TYPE
     SYNTAX      INTEGER (1..24576)
     MAX-ACCESS  read-only
     STATUS      current
     DESCRIPTION
             "This object is used as index in the table and is used to show the VLAN."
     ::= { wwpLeosCfmExtPortStackEntry 1 }
     
  wwpLeosCfmExtPortStackPort OBJECT-TYPE
     SYNTAX      INTEGER (1..65535)
     MAX-ACCESS  read-only
     STATUS      current
     DESCRIPTION
             "This object is used as index in the table and is used to specify the port id."
     ::= { wwpLeosCfmExtPortStackEntry 2 } 
     
 wwpLeosCfmExtPortStackType OBJECT-TYPE
     SYNTAX      INTEGER  {
                                        mepUp(1),
                                        mepDown(2),
                                        mip(3)
                                }
     MAX-ACCESS  read-only
     STATUS      current
     DESCRIPTION
             "This object is used as index in the table and is used to show the type of Maintenance Point."
     ::= { wwpLeosCfmExtPortStackEntry 3 }    
     
  wwpLeosCfmExtPortStackLevel OBJECT-TYPE
     SYNTAX      Unsigned32 (0..7)
     MAX-ACCESS  read-only
     STATUS      current
     DESCRIPTION
             "This object is used as index in the table and is used to show the level of stack."
     ::= { wwpLeosCfmExtPortStackEntry 4 }
     
   wwpLeosCfmExtPortStackMEPId OBJECT-TYPE
     SYNTAX      INTEGER (1..100)
     MAX-ACCESS  read-only
     STATUS      current
     DESCRIPTION
             "The MEP ID."
     ::= { wwpLeosCfmExtPortStackEntry 5 }
 
  --
  --  CFM Mip CCM Db Table
  --                                   
 wwpLeosCfmMipCCMDbTable OBJECT-TYPE
     SYNTAX     SEQUENCE OF WwpLeosCfmMipCCMDbEntry
     MAX-ACCESS not-accessible
     STATUS     current
     DESCRIPTION
            "The (conceptual) table listing the display 
             parameters for the MIP CCM Db table."  
     ::= { wwpLeosCfmMipCCMDb 1 }
                
 wwpLeosCfmMipCCMDbEntry OBJECT-TYPE
     SYNTAX      WwpLeosCfmMipCCMDbEntry
     MAX-ACCESS  not-accessible
     STATUS      current
     DESCRIPTION
           "An entry (conceptual row) in the wwpLeosCfmMipCCMDbTable."
     INDEX { wwpLeosCfmMipCCMDbIndex }
     ::= { wwpLeosCfmMipCCMDbTable 1 }
                
 WwpLeosCfmMipCCMDbEntry ::=  SEQUENCE {                      
        wwpLeosCfmMipCCMDbIndex                           Unsigned32,
        wwpLeosCfmMipCCMDbVid                             Unsigned32,
        wwpLeosCfmMipCCMDbMacAddr                         MacAddress,
        wwpLeosCfmMaintenanceDomainIndex                  Unsigned32,
        wwpLeosCfmMipCCMDbPort                            INTEGER,
        wwpLeosCfmMipCCMDbMEPID                           INTEGER,
        wwpLeosCfmMipCCMdbNumCCMRx                        Counter32,
        wwpLeosCfmMipCCMDbTime                            TimeTicks,
        wwpLeosCfmMipCCMDbLastMacStatus                   TruthValue,
        wwpLeosCfmMipCCMDbRDIErrorFlag                    TruthValue
 }                                    
 
 wwpLeosCfmMipCCMDbIndex OBJECT-TYPE
     SYNTAX      Unsigned32 (1..24576)
     MAX-ACCESS  read-only
     STATUS      current
     DESCRIPTION
             "This object shows the CCM DB vlan."
     ::= { wwpLeosCfmMipCCMDbEntry 1 }
      
 wwpLeosCfmMipCCMDbVid OBJECT-TYPE
     SYNTAX      Unsigned32 (1..24576)
     MAX-ACCESS  read-only
     STATUS      current
     DESCRIPTION
             "This object shows the CCM DB vlan."
     ::= { wwpLeosCfmMipCCMDbEntry 2 }
 
 wwpLeosCfmMipCCMDbMacAddr OBJECT-TYPE
     SYNTAX      MacAddress
     MAX-ACCESS  read-only
     STATUS      current
     DESCRIPTION
             "This object shows the mac address."
     ::= { wwpLeosCfmMipCCMDbEntry 3 }
 
 wwpLeosCfmMipCCMDbPort OBJECT-TYPE
     SYNTAX      INTEGER (1..65535)
     MAX-ACCESS  read-only
     STATUS      current
     DESCRIPTION
             "This object shows the CCM DB port."
     ::= { wwpLeosCfmMipCCMDbEntry 4 }         
     
 wwpLeosCfmMipCCMDbMEPID OBJECT-TYPE
     SYNTAX      INTEGER (1..8191)
     MAX-ACCESS  read-only
     STATUS      current
     DESCRIPTION
             "This object shows the CCM DB MEP ID."
     ::= { wwpLeosCfmMipCCMDbEntry 5 }        
     
 wwpLeosCfmMipCCMdbNumCCMRx OBJECT-TYPE
     SYNTAX      Counter32
     MAX-ACCESS  read-only
     STATUS      current
     DESCRIPTION
             "This object shows the number of CCM DB packets received."
     ::= { wwpLeosCfmMipCCMDbEntry 6 } 
     
 wwpLeosCfmMipCCMDbTime OBJECT-TYPE
     SYNTAX      TimeTicks
     MAX-ACCESS  read-only
     STATUS      current
     DESCRIPTION
             "This object shows the CCM DB time."
     ::= { wwpLeosCfmMipCCMDbEntry 7 } 
     
 wwpLeosCfmMipCCMDbLastMacStatus OBJECT-TYPE
     SYNTAX      TruthValue
     MAX-ACCESS  read-only
     STATUS      current
     DESCRIPTION
             "This object shows the CCM DB last mac status."
     ::= { wwpLeosCfmMipCCMDbEntry 8 }
     
  wwpLeosCfmMipCCMDbRDIErrorFlag OBJECT-TYPE
     SYNTAX      TruthValue
     MAX-ACCESS  read-only
     STATUS      current
     DESCRIPTION
             "This object shows the CCM DB RDI error flag status."
     ::= { wwpLeosCfmMipCCMDbEntry 9 }
  
 --
 -- CFM Faults
 --  
 wwpLeosCfmServiceFaultTable OBJECT-TYPE
     SYNTAX     SEQUENCE OF WwpLeosCfmServiceFaultEntry
     MAX-ACCESS not-accessible
     STATUS     current
     DESCRIPTION
            "The (conceptual) table used for Fault Traps.
             The last CFM error that occurred is reported."  
     ::= { wwpLeosCfmService 2 }
                
 wwpLeosCfmServiceFaultEntry OBJECT-TYPE
     SYNTAX      WwpLeosCfmServiceFaultEntry
     MAX-ACCESS  not-accessible
     STATUS      current
     DESCRIPTION
           "An entry (conceptual row) in the wwpLeosCfmServiceFaultTable."
     INDEX { wwpLeosCfmServiceIndex }
     ::= { wwpLeosCfmServiceFaultTable 1 }
                
 WwpLeosCfmServiceFaultEntry ::=  SEQUENCE {                      
 	wwpLeosCfmServiceFaultTime    	TimeTicks,
 	wwpLeosCfmServiceFaultType		INTEGER,
 	wwpLeosCfmServiceFaultDesc		DisplayString,
 	wwpLeosCfmServiceFaultMep		INTEGER,
 	wwpLeosCfmServiceVlan			INTEGER,
    wwpLeosCfmServiceVsPbtName      DisplayString
 }
   
 wwpLeosCfmServiceFaultTime OBJECT-TYPE
     SYNTAX      TimeTicks 
     MAX-ACCESS  read-only
     STATUS      current
     DESCRIPTION
             "This object is used to specify the Time at which the fault occurred."
     ::= { wwpLeosCfmServiceFaultEntry 1 }
 
 wwpLeosCfmServiceFaultType OBJECT-TYPE
     SYNTAX      INTEGER  {         
     				none(1),
     				someRDIDefect(2),
     				someMACStatusDefect(3),
     				someRMEPCCMDefect(4),
     				errorCCMDefect(5),
     				xconCCMDefect(6),
     				instability(7)
     				}
     MAX-ACCESS  read-only
     STATUS      current
     DESCRIPTION
             "This object is used to specify the type of fault."
     ::= { wwpLeosCfmServiceFaultEntry 2 }

wwpLeosCfmServiceFaultDesc OBJECT-TYPE
     SYNTAX      DisplayString
     MAX-ACCESS  read-only
     STATUS      current
     DESCRIPTION
             "This object is used to specify the description of the fault."
     ::= { wwpLeosCfmServiceFaultEntry 3 }
 
wwpLeosCfmServiceFaultMep OBJECT-TYPE
     SYNTAX      INTEGER (1..8191)
     MAX-ACCESS  read-only
     STATUS      current
     DESCRIPTION
             "This object is used to specify the Mepid of MEP reporting the fault."
     ::= { wwpLeosCfmServiceFaultEntry 4 }
     
 wwpLeosCfmServiceVlan OBJECT-TYPE
     SYNTAX      INTEGER (1..65535)
     MAX-ACCESS  read-only
     STATUS      current
     DESCRIPTION
             "This object is used to specify the service VLAN."
     ::= { wwpLeosCfmServiceFaultEntry 5 } 

  wwpLeosCfmServiceVsPbtName OBJECT-TYPE
     SYNTAX      DisplayString (SIZE(0..31))
     MAX-ACCESS  read-only
     STATUS      current
     DESCRIPTION
             "This object represents the virtual switch or Pbt tunnel assigned to the given service." 
     ::= { wwpLeosCfmServiceFaultEntry 50 }
  
 --
 -- CFM SERVICE STATISTICS TABLE
 --
 wwpLeosCfmServiceStatisticsTable OBJECT-TYPE
     SYNTAX     SEQUENCE OF WwpLeosCfmServiceStatisticsEntry
     MAX-ACCESS not-accessible
     STATUS     current
     DESCRIPTION
            "The (conceptual) table listing the configuration 
            parameters for the CFM Service Table.
            
            To create an entry in this table, the following criteria must be met: 
                                   
            wwpLeosCfmServiceType must be specified.
            wwpLeosCfmServiceValue must be specified.
            wwpLeosCfmServiceName must be specified.
            wwpLeosCfmServiceStatus must be set to createAndGo.
            "  
     ::= { wwpLeosCfmService 3 }

 
 wwpLeosCfmServiceStatisticsEntry OBJECT-TYPE
     SYNTAX      WwpLeosCfmServiceStatisticsEntry
     MAX-ACCESS  not-accessible
     STATUS      current
     DESCRIPTION
           "An entry (conceptual row) in the wwpLeosCfmServiceTable."
     INDEX {wwpLeosCfmServiceIndex}
     ::= { wwpLeosCfmServiceStatisticsTable 1 }
 
 WwpLeosCfmServiceStatisticsEntry ::=  SEQUENCE {  
 	          wwpLeosCfmServiceRxTotalValidFrames 				Counter64,
 	          wwpLeosCfmServiceRxTotalInvalidFrames 			Counter64,
 	          wwpLeosCfmServiceInvalidMessageOverflow 			Counter64,
 	          wwpLeosCfmServiceInvalidPortStatusTLV  			Counter64,
 	          wwpLeosCfmServiceInvalidInterfaceStatusTLV 		Counter64,
 	          wwpLeosCfmServiceInvalidSenderIDTLV 				Counter64,
 	          wwpLeosCfmServiceTxTotalCCM 						Counter64,
 	          wwpLeosCfmServiceTotalRxValidCCM 					Counter64,
 	          wwpLeosCfmServiceTotalRxInSequenceCCM 			Counter64,
 	          wwpLeosCfmServiceTotalRxNotInSequenceCCM 			Counter64,
 	          wwpLeosCfmServiceTotalRxMDLevelXconCCM 			Counter64,
 	          wwpLeosCfmServiceTotalRxMAIDXconCCM    			Counter64, 
 	          wwpLeosCfmServiceTotalRxMEPIDErrorCCM  			Counter64,
 	          wwpLeosCfmServiceTotalRxCCMIntervalErrorCCM 		Counter64,
 	          wwpLeosCfmServiceTotalRxInvalidCCM     			Counter64,
 	          wwpLeosCfmServiceTotalTxLTM						Counter64,
 	          wwpLeosCfmServiceTotalTxLTR						Counter64,
 	          wwpLeosCfmServiceTotalRxValidLTR					Counter64,
 	          wwpLeosCfmServiceTotalRxUnexpectedLTR				Counter64,
 	          wwpLeosCfmServiceTotalRxInvalidLTR				Counter64,
 	          wwpLeosCfmServiceTotalRxInvalidRelayActionLTR     Counter64,
 	          wwpLeosCfmServiceTotalRxValidLTM					Counter64,
 	          wwpLeosCfmServiceTotalTxInvalidLTM				Counter64,
 	          wwpLeosCfmServiceTotalTxLBM						Counter64,
 	          wwpLeosCfmServiceTotalTxLBR						Counter64,
 	          wwpLeosCfmServiceTotalRxInorderLBR				Counter64,
 	          wwpLeosCfmServiceTotalRxOutOfOrderLBR				Counter64,
 	          wwpLeosCfmServiceTotalRxContentMismatchLBR		Counter64,
 	          wwpLeosCfmServiceTotalRxUnexpectedLBR				Counter64,
 	          wwpLeosCfmServiceTotalRxInvalidLBR 				Counter64,
 	          wwpLeosCfmServiceTotalRxValidLBM					Counter64,
 	          wwpLeosCfmServiceTotalRxInvalidLBM				Counter64,
 	          wwpLeosCfmServiceTotalTxDMM						Counter64, 
 	          wwpLeosCfmServiceTotalTxDMR						Counter64,
 	          wwpLeosCfmServiceTotalRxDMM						Counter64,
 	          wwpLeosCfmServiceTotalRxDMR						Counter64, 
 	          wwpLeosCfmServiceTotalTxLMM						Counter64,
 	          wwpLeosCfmServiceTotalTxLMR						Counter64,
 	          wwpLeosCfmServiceTotalRxLMM						Counter64,
 	          wwpLeosCfmServiceTotalRxLMR						Counter64,
 	          wwpLeosCfmServiceStatsClear						INTEGER
 }
 
 wwpLeosCfmServiceRxTotalValidFrames	OBJECT-TYPE
 	SYNTAX  Counter64 
 	MAX-ACCESS read-only
 	STATUS current
 	DESCRIPTION
 		"The total valid Frames received."
 	::= { wwpLeosCfmServiceStatisticsEntry 1 }
 
 wwpLeosCfmServiceRxTotalInvalidFrames	OBJECT-TYPE
 	SYNTAX Counter64
 	MAX-ACCESS read-only
 	STATUS current
 	DESCRIPTION
 		"The total invalid Frames received."
 	::= { wwpLeosCfmServiceStatisticsEntry 2 }
 
 wwpLeosCfmServiceInvalidMessageOverflow	OBJECT-TYPE
 	SYNTAX Counter64
 	MAX-ACCESS read-only
 	STATUS current
 	DESCRIPTION
 		"The total invalid message overflow Frames."
 	::= { wwpLeosCfmServiceStatisticsEntry 3 }
 
  wwpLeosCfmServiceInvalidPortStatusTLV		OBJECT-TYPE
  	SYNTAX Counter64
  	MAX-ACCESS read-only
 	STATUS current
 	DESCRIPTION
 		"The total invalid Port Status TLVs Frames."
 	::= { wwpLeosCfmServiceStatisticsEntry 4 }
    
  wwpLeosCfmServiceInvalidInterfaceStatusTLV   OBJECT-TYPE
  	SYNTAX Counter64
  	MAX-ACCESS read-only
 	STATUS current
 	DESCRIPTION
 		"The invalid interface Status TLVs Frames."
 	::= { wwpLeosCfmServiceStatisticsEntry 5 }
 
   wwpLeosCfmServiceInvalidSenderIDTLV	OBJECT-TYPE
   	SYNTAX Counter64
  	MAX-ACCESS read-only
 	STATUS current
 	DESCRIPTION
 		"The invalid SenderId TLV."
 	::= { wwpLeosCfmServiceStatisticsEntry 6 }
    
    wwpLeosCfmServiceTxTotalCCM		OBJECT-TYPE
    SYNTAX Counter64
    MAX-ACCESS read-only
 	STATUS current
 	DESCRIPTION
 		"The total CCM sent."
 	::= { wwpLeosCfmServiceStatisticsEntry 7 }        
 	
 	wwpLeosCfmServiceTotalRxValidCCM  OBJECT-TYPE
    SYNTAX Counter64
    MAX-ACCESS read-only
 	STATUS current
 	DESCRIPTION
 		"The total valid CCM received."
 	::= { wwpLeosCfmServiceStatisticsEntry 8 } 
 	
 	wwpLeosCfmServiceTotalRxInSequenceCCM	OBJECT-TYPE
 	SYNTAX Counter64
 	MAX-ACCESS read-only
 	STATUS current
 	DESCRIPTION
 		"The total CCM in sequence received."
 	::= { wwpLeosCfmServiceStatisticsEntry 9 }                         
 	
 	wwpLeosCfmServiceTotalRxNotInSequenceCCM  	OBJECT-TYPE
 		SYNTAX Counter64
 		 MAX-ACCESS read-only
 		STATUS current
 		DESCRIPTION
 		"The total CCM not in sequence received."
 	::= { wwpLeosCfmServiceStatisticsEntry 10 } 
 	
 	wwpLeosCfmServiceTotalRxMDLevelXconCCM		OBJECT-TYPE
 		SYNTAX Counter64
 		MAX-ACCESS read-only
 		STATUS current
 		DESCRIPTION
 		"The total MD Level Xcon CCM received."
 	::= { wwpLeosCfmServiceStatisticsEntry 11 } 		    
 	
 	wwpLeosCfmServiceTotalRxMAIDXconCCM		OBJECT-TYPE
 		SYNTAX Counter64
 		MAX-ACCESS read-only
 		STATUS current
 		DESCRIPTION
 		"The total MAID Xcon CCM received."
 	::= { wwpLeosCfmServiceStatisticsEntry 12 }    
 	
 	wwpLeosCfmServiceTotalRxMEPIDErrorCCM    OBJECT-TYPE
 		SYNTAX Counter64
 		MAX-ACCESS read-only
 		STATUS current
 		DESCRIPTION
 		"The total MEPID Error CCM received."
 	::= { wwpLeosCfmServiceStatisticsEntry 13 }            
 	
 	wwpLeosCfmServiceTotalRxCCMIntervalErrorCCM		OBJECT-TYPE
 		SYNTAX Counter64
 		MAX-ACCESS read-only
 		STATUS current
 		DESCRIPTION
 		"The total Interval Error CCM received."
 	::= { wwpLeosCfmServiceStatisticsEntry 14 }        
 	
 	wwpLeosCfmServiceTotalRxInvalidCCM		OBJECT-TYPE
 		SYNTAX Counter64
 		MAX-ACCESS read-only
 		STATUS current
 		DESCRIPTION
 		"The total Internal Error CCM received."
 	::= { wwpLeosCfmServiceStatisticsEntry 15 }  
 	
 	wwpLeosCfmServiceTotalTxLTM		OBJECT-TYPE
 		SYNTAX Counter64
 		MAX-ACCESS read-only
 		STATUS current
 		DESCRIPTION
 		"The total Internal Error CCM received."
 	::= { wwpLeosCfmServiceStatisticsEntry 16 }
 	
 	wwpLeosCfmServiceTotalTxLTR	 OBJECT-TYPE
 		SYNTAX Counter64
 		MAX-ACCESS read-only
 		STATUS current
 		DESCRIPTION
 		"The total Internal Error CCM received."
 	::= { wwpLeosCfmServiceStatisticsEntry 17 }
 	
 	wwpLeosCfmServiceTotalRxValidLTR OBJECT-TYPE
 		SYNTAX Counter64
 		MAX-ACCESS read-only
 		STATUS current
 		DESCRIPTION
 		"The valid LTR Received."
 	::= { wwpLeosCfmServiceStatisticsEntry 18 } 
 	
 	wwpLeosCfmServiceTotalRxUnexpectedLTR OBJECT-TYPE
 		SYNTAX Counter64
 		MAX-ACCESS read-only
 		STATUS current
 		DESCRIPTION
 		"The unexpected LTR received. "
 	::= { wwpLeosCfmServiceStatisticsEntry 19 }
 	
 	wwpLeosCfmServiceTotalRxInvalidLTR	OBJECT-TYPE
 		SYNTAX Counter64
 		MAX-ACCESS read-only
 		STATUS current
 		DESCRIPTION
 		"This object specifies invalid LTR received. "
 	::= { wwpLeosCfmServiceStatisticsEntry 20 }
 	
 	wwpLeosCfmServiceTotalRxInvalidRelayActionLTR OBJECT-TYPE
 		SYNTAX Counter64
 		MAX-ACCESS read-only
 		STATUS current
 		DESCRIPTION
 		"The total invalid relay action LTR received."
 	::= { wwpLeosCfmServiceStatisticsEntry 21 }
 	
 	wwpLeosCfmServiceTotalRxValidLTM  OBJECT-TYPE
 		SYNTAX Counter64
 		MAX-ACCESS read-only
 		STATUS current
 		DESCRIPTION
 		"The valid LTM received."
 	::= { wwpLeosCfmServiceStatisticsEntry 22 } 
 	
 	wwpLeosCfmServiceTotalTxInvalidLTM  OBJECT-TYPE
 		SYNTAX Counter64
 		MAX-ACCESS read-only
 		STATUS current
 		DESCRIPTION
 		"The total invalid LTM sent."
 	::= { wwpLeosCfmServiceStatisticsEntry 23 } 
 	
 	wwpLeosCfmServiceTotalTxLBM	 OBJECT-TYPE
 		SYNTAX Counter64
 		MAX-ACCESS read-only
 		STATUS current
 		DESCRIPTION
 		"The total LBM sent."
 	::= { wwpLeosCfmServiceStatisticsEntry 24 } 
 	
 	wwpLeosCfmServiceTotalTxLBR OBJECT-TYPE
 		SYNTAX Counter64
 		MAX-ACCESS read-only
 		STATUS current
 		DESCRIPTION
 		"The total LBR sent."
 	::= { wwpLeosCfmServiceStatisticsEntry 25 } 
 	
 	wwpLeosCfmServiceTotalRxInorderLBR OBJECT-TYPE
 		SYNTAX Counter64
 		MAX-ACCESS read-only
 		STATUS current
 		DESCRIPTION
 		"The total in order LBR received."
 	::= { wwpLeosCfmServiceStatisticsEntry 26 } 
 	
 	wwpLeosCfmServiceTotalRxOutOfOrderLBR  OBJECT-TYPE
 		SYNTAX Counter64
 		MAX-ACCESS read-only
 		STATUS current
 		DESCRIPTION
 		"The toal out of order LBR received."
 	::= { wwpLeosCfmServiceStatisticsEntry 27 }  
 	
 	wwpLeosCfmServiceTotalRxContentMismatchLBR OBJECT-TYPE
 		SYNTAX Counter64
 		MAX-ACCESS read-only
 		STATUS current
 		DESCRIPTION
 		"The total content mismatch LBR received."
 	::= { wwpLeosCfmServiceStatisticsEntry 28 }  
 	
 	wwpLeosCfmServiceTotalRxUnexpectedLBR  OBJECT-TYPE
 		SYNTAX Counter64
 		MAX-ACCESS read-only
 		STATUS current
 		DESCRIPTION
 		"The total unexpected LBR received."
 	::= { wwpLeosCfmServiceStatisticsEntry 29 } 
 	
 	wwpLeosCfmServiceTotalRxInvalidLBR	OBJECT-TYPE
 		SYNTAX Counter64
 		MAX-ACCESS read-only
 		STATUS current
 		DESCRIPTION
 		"The invalid LBR received."
 	::= { wwpLeosCfmServiceStatisticsEntry 30 } 
 	
 	wwpLeosCfmServiceTotalRxValidLBM OBJECT-TYPE
 		SYNTAX Counter64
 		MAX-ACCESS read-only
 		STATUS current
 		DESCRIPTION
 		"The valid LBM received."
 	::= { wwpLeosCfmServiceStatisticsEntry 31 }   
 	
 	wwpLeosCfmServiceTotalRxInvalidLBM	OBJECT-TYPE
 		SYNTAX Counter64
 		MAX-ACCESS read-only
 		STATUS current
 		DESCRIPTION
 		"The total invalid LBM received."
 	::= { wwpLeosCfmServiceStatisticsEntry 32 }    
 	

 	wwpLeosCfmServiceTotalTxDMM		OBJECT-TYPE
 		SYNTAX Counter64
 		MAX-ACCESS read-only
 		STATUS current
 		DESCRIPTION
 		 "The total DMM sent. "
 	::= { wwpLeosCfmServiceStatisticsEntry 33 }
 	
 	wwpLeosCfmServiceTotalTxDMR	OBJECT-TYPE
 		SYNTAX Counter64
 		MAX-ACCESS read-only
 		STATUS current
 		DESCRIPTION
 		"The total DMR sent."
 	::= { wwpLeosCfmServiceStatisticsEntry 34 }
 	
 	wwpLeosCfmServiceTotalRxDMM		OBJECT-TYPE
 		SYNTAX   Counter64
 		MAX-ACCESS read-only
 		STATUS current
 		DESCRIPTION
 		"The total DMM received."
 	::= { wwpLeosCfmServiceStatisticsEntry 35 } 
 	
 	wwpLeosCfmServiceTotalRxDMR		OBJECT-TYPE
 		SYNTAX   Counter64
 		MAX-ACCESS read-only
 		STATUS current
 		DESCRIPTION
 		"The total DMR received."
 	::= { wwpLeosCfmServiceStatisticsEntry 36 } 
	
	wwpLeosCfmServiceTotalTxLMM		OBJECT-TYPE
 		SYNTAX   Counter64
 		MAX-ACCESS read-only
 		STATUS current
 		DESCRIPTION
 		"The total LMM sent."
 	::= { wwpLeosCfmServiceStatisticsEntry 37 } 
 	
 	wwpLeosCfmServiceTotalTxLMR  OBJECT-TYPE
 		SYNTAX   Counter64
 		MAX-ACCESS read-only
 		STATUS current
 		DESCRIPTION
 		"The total LMR sent."
 	::= { wwpLeosCfmServiceStatisticsEntry 38 } 
	
	wwpLeosCfmServiceTotalRxLMM	OBJECT-TYPE
 		SYNTAX   Counter64
 		MAX-ACCESS read-only
 		STATUS current
 		DESCRIPTION
 		"The total LMM received."
 	::= { wwpLeosCfmServiceStatisticsEntry 39 } 
 	
 	wwpLeosCfmServiceTotalRxLMR  OBJECT-TYPE
 		SYNTAX   Counter64
 		MAX-ACCESS read-only
 		STATUS current
 		DESCRIPTION
 		"The total LMR received. "
 	::= { wwpLeosCfmServiceStatisticsEntry 40 }
  
   wwpLeosCfmServiceStatsClear OBJECT-TYPE
   	  SYNTAX INTEGER 
   	  		{
   	  			clear(1),
   	  			none(2)
   	  		}
   	  MAX-ACCESS read-write
   	  STATUS current
   	  DESCRIPTION 
   	  "Setting this object to clear will clear statististics for the given service index.
   	  			   This object can't be set to none"
   	  ::=   { wwpLeosCfmServiceStatisticsEntry 41 }

   wwpLeosCfmServiceClearStats OBJECT-TYPE
 	SYNTAX INTEGER {
 		clear(1),
 		none(2)
 		}
 	MAX-ACCESS read-write
 	STATUS current
 	DESCRIPTION "Setting this object to clear(1) will clear all service level statistics for all services 
 				in addition within each mep."
 	DEFVAL {none}
 	::= {wwpLeosCfmService 4}
                                                      
  --
  -- Delay Measurement Msg table
  -- 
  wwpLeosCfmDelayMsgTable OBJECT-TYPE
     SYNTAX     SEQUENCE OF WwpLeosCfmDelayMsgEntry
     MAX-ACCESS not-accessible
     STATUS     current
     DESCRIPTION
            "The (conceptual) table listing the configuration 
            parameters for the DelayMeasurementMsg."  
     ::= { wwpLeosCfmDelay 1 }
                
 wwpLeosCfmDelayMsgEntry OBJECT-TYPE
     SYNTAX      WwpLeosCfmDelayMsgEntry
     MAX-ACCESS  not-accessible
     STATUS      current
     DESCRIPTION
           "An entry (conceptual row) in the wwpLeosCfmDelayMsgTable."
     INDEX {wwpLeosCfmServiceIndex, wwpLeosCfmDelayMsgPortId}
     ::= { wwpLeosCfmDelayMsgTable 1 }
                
 WwpLeosCfmDelayMsgEntry ::=  SEQUENCE { 
     wwpLeosCfmDelayMsgPortId                  	INTEGER,
     wwpLeosCfmDelayMsgTargetMEPID              Unsigned32,
     wwpLeosCfmDelayMsgTargetMacAddr            MacAddress,
     wwpLeosCfmDelayMsgCount                   	INTEGER,
     wwpLeosCfmDelayMsgPriority                	INTEGER,
     wwpLeosCfmDelayMsgRowStatus               	RowStatus,
     wwpLeosCfmDelayMsgRepeat					INTEGER,
     wwpLeosCfmDelayMsgRepeatCount				INTEGER,
     wwpLeosCfmDelayMsgDelayThreshold			INTEGER,
     wwpLeosCfmDelayMsgJitterThreshold			INTEGER,
     wwpLeosCfmDelayMsgMaxDelayThreshold		INTEGER,
     wwpLeosCfmDelayMsgMaxJitterThreshold		INTEGER     
 }

 wwpLeosCfmDelayMsgPortId OBJECT-TYPE
     SYNTAX       INTEGER (1..65535)
     MAX-ACCESS   read-only
     STATUS       current
     DESCRIPTION
             "This object is used to specify the port."
     ::= { wwpLeosCfmDelayMsgEntry 1 }
 
 wwpLeosCfmDelayMsgTargetMEPID OBJECT-TYPE
     SYNTAX       Unsigned32 (1..8191)
     MAX-ACCESS   read-create
     STATUS       current
     DESCRIPTION
             "This object is used to specify the MEPID.
              This object should only be set if wwpLeosCfmDelayMsgTargetMacAddr is not specified else 
              error will be returned."
     ::= { wwpLeosCfmDelayMsgEntry 2 }
     
 wwpLeosCfmDelayMsgTargetMacAddr OBJECT-TYPE
     SYNTAX       MacAddress
     MAX-ACCESS   read-create
     STATUS       current
     DESCRIPTION
             "This object is used to specify the MacAddress to be used when sending link LoopbackMsg.
              This object should only be set if wwpLeosCfmDelayMsgTargetMEPID is not specified else 
              error will be returned."
     ::= { wwpLeosCfmDelayMsgEntry 3 }
     
 wwpLeosCfmDelayMsgCount OBJECT-TYPE
     SYNTAX       INTEGER (2..600) 
     MAX-ACCESS   read-create
     STATUS       current
     DESCRIPTION
             "This object is used to specify the DelayMeasurementMsg count to be used
              when sending link DelayMeasurementMsg."
     ::= { wwpLeosCfmDelayMsgEntry 4 }
 
 wwpLeosCfmDelayMsgPriority OBJECT-TYPE
     SYNTAX       INTEGER (0..7)
     MAX-ACCESS   read-create
     STATUS       current
     DESCRIPTION
             "This object is used to specify the DelayMeasurementMsg priority to be
             used when sending link DelayMeasurementMsg."
     ::= { wwpLeosCfmDelayMsgEntry 5 }
 
 wwpLeosCfmDelayMsgRowStatus OBJECT-TYPE
     SYNTAX       RowStatus
     MAX-ACCESS   read-create
     STATUS       current
     DESCRIPTION
             "Used to manage the creation and deletion of the 
             conceptual rows in this table.

             To create a row in this table, a manager must set this object to
             'createAndGo'. To delete a row in this table, set this to 'destroy'.
             If 'destroy' is used and either TargetMacAddr or TargetMEPID is
             specified, a cancel will be done for any repeating test on those items."
     ::= { wwpLeosCfmDelayMsgEntry 6 }  
     
 wwpLeosCfmDelayMsgRepeat OBJECT-TYPE
 	 SYNTAX			INTEGER {
 	 					enable(1),
 	 					disable(2)
 	 					}
 	 MAX-ACCESS		read-create
 	 STATUS			current
 	 DESCRIPTION
 	 		"Used to make the Delay Measurement test a repeating test."
 	 ::= { wwpLeosCfmDelayMsgEntry 7 } 
 	 
 wwpLeosCfmDelayMsgRepeatCount OBJECT-TYPE
 	SYNTAX			INTEGER (0..1440)
 	MAX-ACCESS		read-create
 	STATUS			current
 	DESCRIPTION
 			"The repeat time in minutes for the Delay Measurement test.
 			If zero is specified, the test runs continuously."
 	::= { wwpLeosCfmDelayMsgEntry 8 }  
 	
 wwpLeosCfmDelayMsgDelayThreshold OBJECT-TYPE
 	SYNTAX			INTEGER (-1..2147483647)
 	MAX-ACCESS		read-create
 	STATUS			current
 	DESCRIPTION
 			"The fault threshold for the Delay Measurement test, specified
 			in microseconds.  A value of -1 disables the generate of faults,
 			0 or greater will be compared to the average delay result of the
 			test and a fault will be generated if the threshold is exceeded."
 	::= { wwpLeosCfmDelayMsgEntry 9 }
 
 wwpLeosCfmDelayMsgJitterThreshold OBJECT-TYPE
 	SYNTAX			INTEGER (-1..2147483647)
 	MAX-ACCESS		read-create
 	STATUS			current
 	DESCRIPTION
 			"The fault threshold for the Jitter Measurement test, specified
 			in microseconds.  A value of -1 disables the generate of faults,
 			0 or greater will be compared to the average jitter result of the
 			test and a fault will be generated if the threshold is exceeded."
 	::= { wwpLeosCfmDelayMsgEntry 10 }
 	
 wwpLeosCfmDelayMsgMaxDelayThreshold OBJECT-TYPE
 	SYNTAX			INTEGER (-1..2147483647)
 	MAX-ACCESS		read-create
 	STATUS			current
 	DESCRIPTION
 			"The fault threshold for the Delay Measurement test, specified
 			in microseconds.  A value of -1 disables the generate of faults,
 			0 or greater will be compared to the maximum delay result of the
 			test and a fault will be generated if the threshold is exceeded."
 	::= { wwpLeosCfmDelayMsgEntry 11 }
 
 wwpLeosCfmDelayMsgMaxJitterThreshold OBJECT-TYPE
 	SYNTAX			INTEGER (-1..2147483647)
 	MAX-ACCESS		read-create
 	STATUS			current
 	DESCRIPTION
 			"The fault threshold for the Jitter Measurement test, specified
 			in microseconds.  A value of -1 disables the generate of faults,
 			0 or greater will be compared to the maximum jitter result of the
 			test and a fault will be generated if the threshold is exceeded."
 	::= { wwpLeosCfmDelayMsgEntry 12 }


 
  --
  -- Frame Loss Measurement Msg table
  -- 
  wwpLeosCfmFrameLossMsgTable OBJECT-TYPE
     SYNTAX     SEQUENCE OF WwpLeosCfmFrameLossMsgEntry
     MAX-ACCESS not-accessible
     STATUS     current
     DESCRIPTION
            "The (conceptual) table listing the configuration 
            parameters for the FrameLossMeasurementMsg."  
     ::= { wwpLeosCfmFrameLoss 1 }
                
 wwpLeosCfmFrameLossMsgEntry OBJECT-TYPE
     SYNTAX      WwpLeosCfmFrameLossMsgEntry
     MAX-ACCESS  not-accessible
     STATUS      current
     DESCRIPTION
           "An entry (conceptual row) in the wwpLeosCfmFrameLossMsgTable."
     INDEX {wwpLeosCfmServiceIndex, wwpLeosCfmFrameLossMsgPortId}
     ::= { wwpLeosCfmFrameLossMsgTable 1 }
                
 WwpLeosCfmFrameLossMsgEntry ::=  SEQUENCE { 
     wwpLeosCfmFrameLossMsgPortId                  	INTEGER,
     wwpLeosCfmFrameLossMsgTargetMEPID              Unsigned32,
     wwpLeosCfmFrameLossMsgTargetMacAddr            MacAddress,
     wwpLeosCfmFrameLossMsgCount                   	INTEGER,
     wwpLeosCfmFrameLossMsgPriority                	INTEGER,
     wwpLeosCfmFrameLossMsgRowStatus               	RowStatus,
     wwpLeosCfmFrameLossMsgRepeat					INTEGER,
     wwpLeosCfmFrameLossMsgRepeatCount				INTEGER,
     wwpLeosCfmFrameLossMsgFlnThreshold				INTEGER,
     wwpLeosCfmFrameLossMsgFlfThreshold				INTEGER
 }

 wwpLeosCfmFrameLossMsgPortId OBJECT-TYPE
     SYNTAX       INTEGER (1..65535)
     MAX-ACCESS   read-only
     STATUS       current
     DESCRIPTION
             "This object is used to specify the port."
     ::= { wwpLeosCfmFrameLossMsgEntry 1 }
 
 wwpLeosCfmFrameLossMsgTargetMEPID OBJECT-TYPE
     SYNTAX       Unsigned32 (1..8191)
     MAX-ACCESS   read-create
     STATUS       current
     DESCRIPTION
             "This object is used to specify the MEPID.
              This object should only be set if wwpLeosCfmFrameLossMsgTargetMacAddr is not specified else 
              error will be returned."
     ::= { wwpLeosCfmFrameLossMsgEntry 2 }
     
 wwpLeosCfmFrameLossMsgTargetMacAddr OBJECT-TYPE
     SYNTAX       MacAddress
     MAX-ACCESS   read-create
     STATUS       current
     DESCRIPTION
             "This object is used to specify the MacAddress to be used when sending link LoopbackMsg.
              This object should only be set if wwpLeosCfmFrameLossMsgTargetMEPID is not specified else 
              error will be returned."
     ::= { wwpLeosCfmFrameLossMsgEntry 3 }
     
 wwpLeosCfmFrameLossMsgCount OBJECT-TYPE
     SYNTAX       INTEGER (2..600) 
     MAX-ACCESS   read-create
     STATUS       current
     DESCRIPTION
             "This object is used to specify the FrameLossMeasurementMsg count to be used
              when sending link FrameLossMeasurementMsg."
     ::= { wwpLeosCfmFrameLossMsgEntry 4 }
 
 wwpLeosCfmFrameLossMsgPriority OBJECT-TYPE
     SYNTAX       INTEGER (0..7)
     MAX-ACCESS   read-create
     STATUS       current
     DESCRIPTION
             "This object is used to specify the FrameLossMeasurementMsg priority to be
             used when sending link FrameLossMeasurementMsg."
     ::= { wwpLeosCfmFrameLossMsgEntry 5 }
 
 wwpLeosCfmFrameLossMsgRowStatus OBJECT-TYPE
     SYNTAX       RowStatus
     MAX-ACCESS   read-create
     STATUS       current
     DESCRIPTION
             "Used to manage the creation and deletion of the 
             conceptual rows in this table.

             To create a row in this table, a manager must set this object to
             'createAndGo'. To delete a row in this table, set this to 'destroy'.
             If 'destroy' is used and either TargetMacAddr or TargetMEPID is
             specified, a cancel will be done for any repeating test on those items."
     ::= { wwpLeosCfmFrameLossMsgEntry 6 } 
     
 wwpLeosCfmFrameLossMsgRepeat OBJECT-TYPE
 	 SYNTAX			INTEGER {
 	 					enable(1),
 	 					disable(2)
 	 					}
 	 MAX-ACCESS		read-create
 	 STATUS			current
 	 DESCRIPTION
 	 		"Used to make the Frame Loss Measurement test a repeating test."
 	 ::= { wwpLeosCfmFrameLossMsgEntry 7 } 
 	 
 wwpLeosCfmFrameLossMsgRepeatCount OBJECT-TYPE
 	SYNTAX			INTEGER (0..1440)
 	MAX-ACCESS		read-create
 	STATUS			current
 	DESCRIPTION
 			"The repeat time in minutes for the Frame Loss Measurement test.
 			If zero is specified, the test runs continuously."
 	::= { wwpLeosCfmFrameLossMsgEntry 8 } 
 	
  wwpLeosCfmFrameLossMsgFlnThreshold OBJECT-TYPE
 	SYNTAX			INTEGER (-1..600)
 	MAX-ACCESS		read-create
 	STATUS			current
 	DESCRIPTION
 			"The fault threshold for the Frame Loss Measurement test.
 			A value of -1 disables the generate of faults, 0 or greater
 			will be compared to the frame loss near result of the
 			test and a fault will be generated if the threshold is exceeded."
 	::= { wwpLeosCfmFrameLossMsgEntry 9 }
 
 wwpLeosCfmFrameLossMsgFlfThreshold OBJECT-TYPE
 	SYNTAX			INTEGER (-1..600)
 	MAX-ACCESS		read-create
 	STATUS			current
 	DESCRIPTION
 			"The fault threshold for the Frame Loss Measurement test.
 			A value of -1 disables the generate of faults, 0 or greater
 			will be compared to the frame loss far result of the
 			test and a fault will be generated if the threshold is exceeded."
 	::= { wwpLeosCfmFrameLossMsgEntry 10 }
 
  --
  --  CFM Remote MEP CCM Loss Table
  --                                   
 wwpLeosCfmRemoteMEPCCMLossTable OBJECT-TYPE
     SYNTAX     SEQUENCE OF WwpLeosCfmRemoteMEPCCMLossEntry
     MAX-ACCESS not-accessible
     STATUS     current
     DESCRIPTION
            "The (conceptual) table listing the display 
             parameters for the Remote MEP CCM Loss table."  
     ::= { wwpLeosCfmRemoteMEPCCMLoss 1 }
                
 wwpLeosCfmRemoteMEPCCMLossEntry OBJECT-TYPE
     SYNTAX      WwpLeosCfmRemoteMEPCCMLossEntry
     MAX-ACCESS  not-accessible
     STATUS      current
     DESCRIPTION
           "An entry (conceptual row) in the wwpLeosCfmRemoteMEPCCMLossTable."
     INDEX {wwpLeosCfmServiceIndex, wwpLeosCfmRemoteMEPID, wwpLeosCfmRemoteMEPCCMLossNum}
     ::= { wwpLeosCfmRemoteMEPCCMLossTable 1 }
                
 WwpLeosCfmRemoteMEPCCMLossEntry ::=  SEQUENCE { 
     wwpLeosCfmRemoteMEPCCMLossNum			Unsigned32,
     wwpLeosCfmRemoteMEPCCMLossCount		Gauge32
 }

 wwpLeosCfmRemoteMEPCCMLossNum OBJECT-TYPE
 	SYNTAX		Unsigned32 (1..96)
 	MAX-ACCESS	not-accessible
 	STATUS		current
 	DESCRIPTION
 			"This object is used as an index into the table and is used to specify
 			the CCM Loss bucket to be returned."
 	::= { wwpLeosCfmRemoteMEPCCMLossEntry 1 }
 	
 wwpLeosCfmRemoteMEPCCMLossCount OBJECT-TYPE
 	SYNTAX		Gauge32
 	MAX-ACCESS	read-only
 	STATUS		current
 	DESCRIPTION
 			"Count of the number of CCM's lost during the
 			wwpLeosCfmServiceCCMLossBucketInterval sample period."
 	::= { wwpLeosCfmRemoteMEPCCMLossEntry 2 }
 
  
  --
  -- Loopback Msg table
  -- 
  wwpLeosCfmExtLoopbackMsgTable OBJECT-TYPE
     SYNTAX     SEQUENCE OF WwpLeosCfmExtLoopbackMsgEntry
     MAX-ACCESS not-accessible
     STATUS     current
     DESCRIPTION
            "The (conceptual) table listing the configuration parameters for the LoopbackMsg.
             The following attributes are required to create a LoopbackMsg:
             -- wwpLeosCfmServiceIndex
             -- wwpLeosCfmExtLoopbackMsgTargetMEPID or
             -- wwpLeosCfmExtLoopbackMsgTargetMacAddr
             -- wwpLeosCfmExtLoopbackMsgCount
             -- wwpLeosCfmExtLoopbackMsgData
             -- wwpLeosCfmExtLoopbackMsgPriority
             -- wwpLeosCfmExtLoopbackMsgAction
             -- wwpLeosCfmExtLoopbackMsgInterval
             -- wwpLeosCfmExtLoopbackMsgTimeout
             -- wwpLeosCfmExtLoopbackMsgLoss"  
              
     ::= { wwpLeosCfmExtLoopback 1 }
                
 wwpLeosCfmExtLoopbackMsgEntry OBJECT-TYPE
     SYNTAX      WwpLeosCfmExtLoopbackMsgEntry
     MAX-ACCESS  not-accessible
     STATUS      current
     DESCRIPTION
           "An entry (conceptual row) in the wwpLeosCfmExtLoopbackMsgTable."
     --wwpLeosCfmExtLoopbackMsgLocalMEPID is the new index in place of portId
     INDEX {wwpLeosCfmServiceIndex, wwpLeosCfmExtLoopbackMsgLocalMEPID}
     ::= { wwpLeosCfmExtLoopbackMsgTable 1 }
                
 WwpLeosCfmExtLoopbackMsgEntry ::=  SEQUENCE { 
     wwpLeosCfmExtLoopbackMsgLocalMEPID              Unsigned32,
     wwpLeosCfmExtLoopbackMsgTargetMEPID             Unsigned32,
     wwpLeosCfmExtLoopbackMsgTargetMacAddr           MacAddress,
     wwpLeosCfmExtLoopbackMsgCount                   INTEGER,
     wwpLeosCfmExtLoopbackMsgData                    DisplayString,
     wwpLeosCfmExtLoopbackMsgPriority                INTEGER,   
     wwpLeosCfmExtLoopbackMsgAction                  SendState,
     wwpLeosCfmExtLoopbackMsgInterval                INTEGER,
     wwpLeosCfmExtLoopbackMsgTimeout                 INTEGER, 
     wwpLeosCfmExtLoopbackMsgLoss                    INTEGER     
 }

 wwpLeosCfmExtLoopbackMsgLocalMEPID OBJECT-TYPE
     SYNTAX       Unsigned32 (1..8191)
     MAX-ACCESS   not-accessible
     STATUS       current
     DESCRIPTION
             "This object is used to specify the port."
     ::= { wwpLeosCfmExtLoopbackMsgEntry 1 }
 
 wwpLeosCfmExtLoopbackMsgTargetMEPID OBJECT-TYPE
     SYNTAX       Unsigned32 (1..8191)
     MAX-ACCESS   read-create
     STATUS       current
     DESCRIPTION
             "This object is used to specify the MEPID.
              This object should only be set if wwpLeosCfmExtLoopbackMsgTargetMacAddr 
              is not specified else error will be returned."
     ::= { wwpLeosCfmExtLoopbackMsgEntry 2 }
     
 wwpLeosCfmExtLoopbackMsgTargetMacAddr OBJECT-TYPE
     SYNTAX       MacAddress
     MAX-ACCESS   read-create
     STATUS       current
     DESCRIPTION
             "This object is used to specify the MacAddress to be used when sending 
              link LoopbackMsg. This object should only be set if 
              wwpLeosCfmExtLoopbackMsgTargetMEPID is not specified else error will 
              be returned."
     ::= { wwpLeosCfmExtLoopbackMsgEntry 3 }
     
 wwpLeosCfmExtLoopbackMsgCount OBJECT-TYPE
     SYNTAX       INTEGER (1..3000) 
     MAX-ACCESS   read-create
     STATUS       current
     DESCRIPTION
             "This object is used to specify the LoopbackMsg count to be used when 
              sending link LoopbackMsg. "
     ::= { wwpLeosCfmExtLoopbackMsgEntry 4 }
 
 wwpLeosCfmExtLoopbackMsgData OBJECT-TYPE
     SYNTAX       DisplayString  (SIZE(1..127))
     MAX-ACCESS   read-create
     STATUS       current
     DESCRIPTION                    
             "This object is used to specify the LoopbackMsg data to be used when 
              sending link LoopbackMsg. "
     ::= { wwpLeosCfmExtLoopbackMsgEntry 5 }

 wwpLeosCfmExtLoopbackMsgPriority OBJECT-TYPE
     SYNTAX       INTEGER (0..7)
     MAX-ACCESS   read-create
     STATUS       current
     DESCRIPTION
             "This object is used to specify the LoopbackMsg priority to be used when 
              sending link LoopbackMsg. "
     ::= { wwpLeosCfmExtLoopbackMsgEntry 6 }
     
 wwpLeosCfmExtLoopbackMsgAction OBJECT-TYPE
   SYNTAX       SendState
   MAX-ACCESS   read-create
   STATUS       current
   DESCRIPTION
             "This object represents the action for the message (send, clear or cancel).
             If set to send(1) and if wwpLeosCfmExtLoopbackMsgTargetMacAddr is specified 
             then loopbackMsg is sent to remote Mac.
             If set to send(1) and if wwpLeosCfmExtLoopbackMsgTargetMEPID is specified 
             then loopbackMsg is sent to remote mepid.
             If set to clear(2) will clear mep statistics for given service and mepid.
             If set to cancel(3) will return commit_failed_error."
     ::= { wwpLeosCfmExtLoopbackMsgEntry 7} 
     
 wwpLeosCfmExtLoopbackMsgInterval OBJECT-TYPE
     SYNTAX       INTEGER (10..60000) 
     MAX-ACCESS   read-create
     STATUS       current
     DESCRIPTION
             "This object is used to specify the LoopbackMsg interval to be used when 
              sending link LoopbackMsg. "
     ::= { wwpLeosCfmExtLoopbackMsgEntry 8 }      
 
 wwpLeosCfmExtLoopbackMsgTimeout OBJECT-TYPE
     SYNTAX       INTEGER (2000..10000) 
     MAX-ACCESS   read-create
     STATUS       current
     DESCRIPTION
             "This object is used to specify the LoopbackMsg timeout to be used when 
              sending link LoopbackMsg. "
     ::= { wwpLeosCfmExtLoopbackMsgEntry 9 }
  
 wwpLeosCfmExtLoopbackMsgLoss OBJECT-TYPE
     SYNTAX       INTEGER (1..3000)
     MAX-ACCESS   read-only
     STATUS       current
     DESCRIPTION
             "This object is used to display the LoopbackMsg loss count."
     ::= { wwpLeosCfmExtLoopbackMsgEntry 10 }

  --
  --  CFM MEP Table 
  --                                   
 wwpLeosCfmExtMEPTable OBJECT-TYPE
     SYNTAX     SEQUENCE OF WwpLeosCfmExtMEPEntry
     MAX-ACCESS not-accessible
     STATUS     current
     DESCRIPTION
            "The (conceptual) table listing the configuration 
            parameters for the CFM MEP table.
            To create entry in this table use SNMP multiple set operation.
             - wwpLeosCfmExtPortId must be specified.
             - wwpLeosCfmExtVlanId must be specified.
             - wwpLeosCfmExtMEPRowStatus must be set to 'CreateAndGo'"

     ::= { wwpLeosCfmExtMEP 1 }
                
 wwpLeosCfmExtMEPEntry OBJECT-TYPE
     SYNTAX      WwpLeosCfmExtMEPEntry
     MAX-ACCESS  not-accessible
     STATUS      current
     DESCRIPTION
           "An entry (conceptual row) in the wwpLeosCfmMEPTable."   
     --   wwpLeosCfmExtMEPId is the new index in place of mepport
     INDEX {wwpLeosCfmServiceIndex, wwpLeosCfmExtMEPId}
     ::= { wwpLeosCfmExtMEPTable 1 }
                
 WwpLeosCfmExtMEPEntry ::=  SEQUENCE { 
 	 wwpLeosCfmExtMEPId											    Unsigned32, 
 	 wwpLeosCfmExtPortId											INTEGER,
 	 wwpLeosCfmExtVlanId											INTEGER,
     wwpLeosCfmExtMEPAdminState                                     INTEGER,        
     wwpLeosCfmExtMEPOperState                                      INTEGER,        
     wwpLeosCfmExtMEPDirection                                      INTEGER,
     wwpLeosCfmExtMEPCCMState            							INTEGER,
     wwpLeosCfmExtMEPCCMPriority         							INTEGER,
     wwpLeosCfmExtMEPLTMPriority         							INTEGER,  
     wwpLeosCfmExtMEPMacAddr                                        MacAddress,
     wwpLeosCfmExtMEPNextLbmSeqNumber                               Counter32,
     wwpLeosCfmExtMEPNextLTMSeqNumber                               Counter32,
     wwpLeosCfmExtMEPRowStatus                                      RowStatus,
     wwpLeosCfmExtMEPDMMDelay										Counter32,
     wwpLeosCfmExtMEPDMMJitter										Counter32,
     wwpLeosCfmExtMEPLMMFrameLossNear								Counter32,
     wwpLeosCfmExtMEPLMMFrameLossFar								Counter32,
     wwpLeosCfmExtMEPServiceName									DisplayString,
     wwpLeosCfmExtMEPInterfaceName									DisplayString,
     wwpLeosCfmExtMEPServiceInstanceName							DisplayString,
     wwpLeosCfmExtMEPLogicalPortName								DisplayString,
     wwpLeosCfmExtMEPTagMode										INTEGER,
     wwpLeosCfmExtMEPTagVID											INTEGER,
     wwpLeosCfmExtMEPTagPriority									INTEGER,
     wwpLeosCfmExtMEPLMMBadSequence									Counter32,
     wwpLeosCfmExtMEPCCMComment										DisplayString,
     wwpLeosCfmExtMEPLMMMissingSequence								Counter32,
     wwpLeosCfmExtMEPBlockOppositeFaultCurrent						Counter32,
     wwpLeosCfmExtMEPBlockOppositeFaultThreshold					Unsigned32,
     wwpLeosCfmExtMEPBlockOppositeFaultTime							INTEGER,
     wwpLeosCfmExtMEPDMMMinDelay									Counter32,
     wwpLeosCfmExtMEPDMMMaxDelay									Counter32,
     wwpLeosCfmExtMEPDMMMinJitter									Counter32,
     wwpLeosCfmExtMEPDMMMaxJitter									Counter32,
     wwpLeosCfmExtMEPAccelerated									TruthValue
	}
   
 wwpLeosCfmExtMEPId OBJECT-TYPE
     SYNTAX      Unsigned32 (1..8191)
     MAX-ACCESS  accessible-for-notify
     STATUS      current
     DESCRIPTION
             "This is used as the index in the table. This object specifies the MEP id for the given service."
     ::= { wwpLeosCfmExtMEPEntry 1 } 
     
 wwpLeosCfmExtPortId OBJECT-TYPE
     SYNTAX  INTEGER (1..65535)
     MAX-ACCESS read-create
     STATUS current
     DESCRIPTION 
     	""
     ::= { wwpLeosCfmExtMEPEntry 2 }
    
 wwpLeosCfmExtVlanId OBJECT-TYPE
    SYNTAX INTEGER  (0..4094)
    MAX-ACCESS read-create
    STATUS current
    DESCRIPTION
    	""
    ::= { wwpLeosCfmExtMEPEntry 3 }

 wwpLeosCfmExtMEPAdminState OBJECT-TYPE
     SYNTAX      INTEGER   {
                                disabled(1),
                                enabled(2)  
                          }
     MAX-ACCESS  read-write
     STATUS      current
     DESCRIPTION
             "This object is used to specify the admin state of CFM MEP."
     ::= { wwpLeosCfmExtMEPEntry 4 }
 
 wwpLeosCfmExtMEPOperState OBJECT-TYPE
     SYNTAX      INTEGER   {
                                disabled(1),
                                enabled(2)  
                          }
     MAX-ACCESS  read-only
     STATUS      current
     DESCRIPTION
             "This object is used to specify the oper state of CFM MEP."
     ::= { wwpLeosCfmExtMEPEntry 5 }
     
 wwpLeosCfmExtMEPDirection OBJECT-TYPE
     SYNTAX      INTEGER {
                                up(1),
                                down(2)
                         }
     MAX-ACCESS  read-create
     STATUS      current
     DESCRIPTION
             "This object is used to specify the MEP direction of the service.
              This object can only be set if wwpLeosCfmServiceIndex is of type VLAN."
     ::= { wwpLeosCfmExtMEPEntry 6 } 
 
 wwpLeosCfmExtMEPCCMState OBJECT-TYPE
     SYNTAX       INTEGER {
                                on(1),
                                off(2)
                                }
     MAX-ACCESS   read-write
     STATUS       current
     DESCRIPTION
             "This object specifies the CCM transmission for the service specified by wwpLeosCfmServiceType."
     ::= { wwpLeosCfmExtMEPEntry 7 }
     
 wwpLeosCfmExtMEPCCMPriority OBJECT-TYPE
     SYNTAX       INTEGER (0..7)
     MAX-ACCESS   read-write
     STATUS       current
     DESCRIPTION
             "This object specified the priority of CCM messages transmitted."
     ::= { wwpLeosCfmExtMEPEntry 8 }
     
 wwpLeosCfmExtMEPLTMPriority OBJECT-TYPE
     SYNTAX      INTEGER (0..7)
     MAX-ACCESS  read-write
     STATUS      current
     DESCRIPTION
             "The priority received on the given service and MEP."  
     DEFVAL {7}
     ::= { wwpLeosCfmExtMEPEntry 9 } 
     
   
 wwpLeosCfmExtMEPMacAddr OBJECT-TYPE
     SYNTAX      MacAddress
     MAX-ACCESS  read-only
     STATUS      current
     DESCRIPTION
             "The mac address received on the given service and MEP."
     ::= { wwpLeosCfmExtMEPEntry 10 }
     
 wwpLeosCfmExtMEPNextLbmSeqNumber OBJECT-TYPE
     SYNTAX      Counter32 
     MAX-ACCESS  read-only
     STATUS      current
     DESCRIPTION
             "The next lbm sequence number received on the given service and MEP."
     ::= { wwpLeosCfmExtMEPEntry 11 }
     
      
 wwpLeosCfmExtMEPNextLTMSeqNumber OBJECT-TYPE
     SYNTAX      Counter32 
     MAX-ACCESS  read-only
     STATUS      current
     DESCRIPTION
             "The next LTM sequence number received on the given service and MEP."
     ::= { wwpLeosCfmExtMEPEntry 12 }
     
      
 wwpLeosCfmExtMEPRowStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this to 'destroy'."
     ::= { wwpLeosCfmExtMEPEntry 13 }  
        
 wwpLeosCfmExtMEPDMMDelay OBJECT-TYPE
     SYNTAX      Counter32
     MAX-ACCESS  read-only
     STATUS      current
     DESCRIPTION
             "The average delay in microseconds	measured during 
             the last DMM performance test on the given service and MEP."
     ::= { wwpLeosCfmExtMEPEntry 14 } 
     
 wwpLeosCfmExtMEPDMMJitter OBJECT-TYPE
     SYNTAX      Counter32
     MAX-ACCESS  read-only
     STATUS      current
     DESCRIPTION
             "The average jitter in microseconds measured during
             the last DMM performance test on the given service and MEP."
     ::= { wwpLeosCfmExtMEPEntry 15 } 
     
 wwpLeosCfmExtMEPLMMFrameLossNear OBJECT-TYPE
     SYNTAX      Counter32
     MAX-ACCESS  read-only
     STATUS      current
     DESCRIPTION
             "The number of lost frames on the near side measured during 
             the last LMM performance test on the given service and MEP."
     ::= { wwpLeosCfmExtMEPEntry 16 } 
     
 wwpLeosCfmExtMEPLMMFrameLossFar OBJECT-TYPE
     SYNTAX      Counter32
     MAX-ACCESS  read-only
     STATUS      current
     DESCRIPTION
             "The number of lost frames on the far side	 measured during 
             the last LMM performance test on the given service and MEP."
     ::= { wwpLeosCfmExtMEPEntry 17 }   
 
 wwpLeosCfmExtMEPServiceName OBJECT-TYPE
     SYNTAX      DisplayString (SIZE(1..31))
     MAX-ACCESS  read-only
     STATUS      current
     DESCRIPTION
             "The service name assigned to this MEP."
     ::= { wwpLeosCfmExtMEPEntry 50 } 
 
 wwpLeosCfmExtMEPInterfaceName	OBJECT-TYPE
     SYNTAX		DisplayString	(SIZE(1..31))
     MAX-ACCESS	 read-only
     STATUS		  current
     DESCRIPTION
     	     "The interface name associated with this MEP."
     ::= { wwpLeosCfmExtMEPEntry	51 }
 
 wwpLeosCfmExtMEPServiceInstanceName	OBJECT-TYPE
     SYNTAX		DisplayString	(SIZE(1..31))
     MAX-ACCESS	 read-only
     STATUS		  current
     DESCRIPTION
     	     "The service instance name associated 
     	     with this MEP."
     ::= { wwpLeosCfmExtMEPEntry	52 }
 
 wwpLeosCfmExtMEPLogicalPortName		OBJECT-TYPE
 	 SYNTAX		DisplayString	(SIZE(1..31))
 	 MAX-ACCESS		read-only
 	 STATUS			current
 	 DESCRIPTION
 	 		"Logical port name associated with this MEP."
 	 ::= { wwpLeosCfmExtMEPEntry	53 }  
  
  wwpLeosCfmExtMEPTagMode  OBJECT-TYPE
 	 SYNTAX		INTEGER {
 	 				on(1),
 	 				off(2)
 	 			}
 	 MAX-ACCESS		read-write
 	 STATUS			current
 	 DESCRIPTION
 	 		"Tag-mode for the given mep and service. When on(1) the MEP originates all frames 
 	 		with an additional inner-most tag. On a down MEP this is the CVLAN tag."
 	 DEFVAL {off}
 	 ::= { wwpLeosCfmExtMEPEntry	54 }  

  wwpLeosCfmExtMEPTagVID OBJECT-TYPE
 	 SYNTAX		INTEGER ( 0..4095)
 	 MAX-ACCESS		read-write
 	 STATUS			current
 	 DESCRIPTION
 	 		"VLAN ID for the additional tag given mep and service."
 	 DEFVAL {0}
 	 ::= { wwpLeosCfmExtMEPEntry	55 }
 	 
   wwpLeosCfmExtMEPTagPriority OBJECT-TYPE
 	 SYNTAX		INTEGER (0..7)
 	 MAX-ACCESS		read-write
 	 STATUS			current
 	 DESCRIPTION
 	 		"The priority encoded in the additional tag."
 	 DEFVAL {7}
 	 ::= { wwpLeosCfmExtMEPEntry	56 }
	
   wwpLeosCfmExtMEPLMMBadSequence OBJECT-TYPE
     SYNTAX      Counter32
     MAX-ACCESS  read-only
     STATUS      current
     DESCRIPTION
             "This object specifes the number of frames with bad sequence numbers
             measured during the last LMM performance test on the given service and MEP."
     ::= { wwpLeosCfmExtMEPEntry 57 }

 wwpLeosCfmExtMEPCCMComment OBJECT-TYPE
     SYNTAX       DisplayString (SIZE(1..32))
     MAX-ACCESS   read-create
     STATUS       current
     DESCRIPTION
             "This mib object allows to set the MEP CCM Comment."
     ::= { wwpLeosCfmExtMEPEntry 58 }
 
 wwpLeosCfmExtMEPLMMMissingSequence   OBJECT-TYPE
 	 SYNTAX      Counter32
     MAX-ACCESS  read-only
     STATUS      current
     DESCRIPTION
             "This object specifes the number of frames with missing sequence numbers
             measured during the last LMM performance test on the given service and MEP."
     ::= { wwpLeosCfmExtMEPEntry 59 }
 
 wwpLeosCfmExtMEPBlockOppositeFaultCurrent OBJECT-TYPE
     SYNTAX       Counter32
     MAX-ACCESS   read-only
     STATUS       current
     DESCRIPTION  "The number of frames seen in the current sample window."
     ::= { wwpLeosCfmExtMEPEntry 60 }
 
 wwpLeosCfmExtMEPBlockOppositeFaultThreshold OBJECT-TYPE
     SYNTAX       Unsigned32
     MAX-ACCESS   read-write
     STATUS       current
     DESCRIPTION  "The number of frames to block before generating a fault."
     ::= { wwpLeosCfmExtMEPEntry 61 }
 
 wwpLeosCfmExtMEPBlockOppositeFaultTime OBJECT-TYPE
     SYNTAX       INTEGER (1..3600)
     MAX-ACCESS   read-write
     STATUS       current
     DESCRIPTION  "The frame sample window size in minutes."
     ::= { wwpLeosCfmExtMEPEntry 62 }
        
 wwpLeosCfmExtMEPDMMMinDelay OBJECT-TYPE
     SYNTAX      Counter32
     MAX-ACCESS  read-only
     STATUS      current
     DESCRIPTION
             "The minimum delay in microseconds	measured during 
             the last DMM performance test on the given service and MEP."
     ::= { wwpLeosCfmExtMEPEntry 63 } 
        
 wwpLeosCfmExtMEPDMMMaxDelay OBJECT-TYPE
     SYNTAX      Counter32
     MAX-ACCESS  read-only
     STATUS      current
     DESCRIPTION
             "The maximum delay in microseconds	measured during 
             the last DMM performance test on the given service and MEP."
     ::= { wwpLeosCfmExtMEPEntry 64 } 
     
 wwpLeosCfmExtMEPDMMMinJitter OBJECT-TYPE
     SYNTAX      Counter32
     MAX-ACCESS  read-only
     STATUS      current
     DESCRIPTION
             "The minimum jitter in microseconds measured during
             the last DMM performance test on the given service and MEP."
     ::= { wwpLeosCfmExtMEPEntry 65 }
     
 wwpLeosCfmExtMEPDMMMaxJitter OBJECT-TYPE
     SYNTAX      Counter32
     MAX-ACCESS  read-only
     STATUS      current
     DESCRIPTION
             "The maximum jitter in microseconds measured during
             the last DMM performance test on the given service and MEP."
     ::= { wwpLeosCfmExtMEPEntry 66 }

 wwpLeosCfmExtMEPAccelerated OBJECT-TYPE
     SYNTAX      TruthValue
     MAX-ACCESS  read-only
     STATUS      current
     DESCRIPTION
             "Specifies if the mep is monitored in hardware."
     ::= { wwpLeosCfmExtMEPEntry 67 }

--
-- CFM MEP Statistics
--
   
 wwpLeosCfmExtMEPStatsTable OBJECT-TYPE
     SYNTAX     SEQUENCE OF WwpLeosCfmExtMEPStatsEntry
     MAX-ACCESS not-accessible
     STATUS     current
     DESCRIPTION
            "The (conceptual) table listing the configuration 
            parameters for the CFM MEP table."  
     ::= { wwpLeosCfmExtMEP 2 }
                
 wwpLeosCfmExtMEPStatsEntry OBJECT-TYPE
     SYNTAX      WwpLeosCfmExtMEPStatsEntry
     MAX-ACCESS  not-accessible
     STATUS      current
     DESCRIPTION
           "An entry (conceptual row) in the wwpLeosCfmMEPTable."   
     --   wwpLeosCfmExtMEPId is the new index in place of mepport
     INDEX {wwpLeosCfmServiceIndex, wwpLeosCfmExtMEPId}
     ::= { wwpLeosCfmExtMEPStatsTable 1 }   
 
  WwpLeosCfmExtMEPStatsEntry ::=  SEQUENCE { 
 	 wwpLeosCfmExtMEPStatsTotalValidFramesReceived								 Counter64, 
 	 wwpLeosCfmExtMEPStatsTotalInvalidFramesReceived							 Counter64,
 	 wwpLeosCfmExtMEPStatsTotalInvalidMessageOverflowReceived					 Counter64,
     wwpLeosCfmExtMEPStatsInvalidPortStatusTLVReceived                           Counter64,        
     wwpLeosCfmExtMEPStatsInvalidInterfaceStatusTLVReceived                      Counter64,        
     wwpLeosCfmExtMEPStatsInvalidSenderIDTLVReceived                             Counter64,
     wwpLeosCfmExtMEPStatsCCMTxmt            									 Counter64,
     wwpLeosCfmExtMEPStatsValidCCMReceived         								 Counter64,
     wwpLeosCfmExtMEPStatsCCMInSequenceReceived         						 Counter64,  
     wwpLeosCfmExtMEPStatsCCMSequenceErrorsReceived                              Counter64,
     wwpLeosCfmExtMEPStatsMDLevelXconCCMReceived                                 Counter64,
     wwpLeosCfmExtMEPStatsMAIDXconCCMReceived                                    Counter64,
     wwpLeosCfmExtMEPStatsIntervalErrorCCMReceived                               Counter64,
     wwpLeosCfmExtMEPStatsRxInvalidCCM											Counter64,
     wwpLeosCfmExtMEPStatsLBMTxmt												Counter64,
     wwpLeosCfmExtMEPStatsLBRTxmt												Counter64,
     wwpLeosCfmExtMEPStatsInOrderLBRReceived									Counter64, 
     wwpLeosCfmExtMEPStatsOutOfOrderLBRReceived									Counter64,
     wwpLeosCfmExtMEPStatsContentMismatchLBRReceived							Counter64,
     wwpLeosCfmExtMEPStatsUnexpectedLBRReceived									Counter64,
     wwpLeosCfmExtMEPStatsInvalidLBRReceived									Counter64,
     wwpLeosCfmExtMEPStatsLTMTxmt												Counter64,
     wwpLeosCfmExtMEPStatsValidLTMReceived										Counter64,
     wwpLeosCfmExtMEPStatsTotalInvalidLTMReceived								Counter64,
     wwpLeosCfmExtMEPStatsInvalidLTRAction										Counter64,
     wwpLeosCfmExtMEPStatsLTRTxmt												Counter64,
     wwpLeosCfmExtMEPStatsLTRReceived											Counter64,
     wwpLeosCfmExtMEPStatsDMMTxmt												Counter64,
     wwpLeosCfmExtMEPStatsDMMReceived											Counter64,
     wwpLeosCfmExtMEPStatsDMRTxmt												Counter64,
     wwpLeosCfmExtMEPStatsDMRReceived											Counter64,
     wwpLeosCfmExtMEPStatsDMReplyTimeout										Counter64,
     wwpLeosCfmExtMEPStatsLMMTxmt												Counter64,
     wwpLeosCfmExtMEPStatsLMMReceived											Counter64,
     wwpLeosCfmExtMEPStatsLMRTxmt												Counter64,
     wwpLeosCfmExtMEPStatsLMRReceived											Counter64,
     wwpLeosCfmExtMEPStatsLMRTimeout											Counter64,
     wwpLeosCfmExtMEPStatsMepIdErrorCCMReceived									Counter64,
     wwpLeosCfmExtMEPStatsClear													INTEGER,
     wwpLeosCfmExtMEPStatsValidLBMReceived 										Counter64,
     wwpLeosCfmExtMEPStatsInvalidLBMReceived                                    Counter64,
     wwpLeosCfmExtMEPStatsUnexpectedLTRReceived									Counter64,
     wwpLeosCfmExtMEPStatsInvalidDMMReceived									Counter64,
     wwpLeosCfmExtMEPStatsInvalidDMRReceived									Counter64,
     wwpLeosCfmExtMEPStatsUnexpectedDMRReceived									Counter64,
     wwpLeosCfmExtMEPStatsInvalidLMMReceived                                   	Counter64,
 	 wwpLeosCfmExtMEPStatsInvalidLMRReceived                                 	Counter64,
 	 wwpLeosCfmExtMEPStatsInvalidBlockedOppositeMep								Counter64
  }
 wwpLeosCfmExtMEPStatsTotalValidFramesReceived	OBJECT-TYPE
 	SYNTAX Counter64
 	MAX-ACCESS  read-only
     STATUS      current
     DESCRIPTION
             "This object specifies total valid frames received."
     ::= { wwpLeosCfmExtMEPStatsEntry 1 }  
     
 wwpLeosCfmExtMEPStatsTotalInvalidFramesReceived  OBJECT-TYPE
 	SYNTAX Counter64
 	MAX-ACCESS  read-only
     STATUS      current
     DESCRIPTION
             "This object specifies total invalid frames received."
     ::= { wwpLeosCfmExtMEPStatsEntry 2 }           
     
 wwpLeosCfmExtMEPStatsTotalInvalidMessageOverflowReceived  OBJECT-TYPE
 	SYNTAX Counter64
 	MAX-ACCESS  read-only
     STATUS      current
     DESCRIPTION
             "This object specifies total invalid message overflow frames received "
     ::= { wwpLeosCfmExtMEPStatsEntry 3 }
 
 wwpLeosCfmExtMEPStatsInvalidPortStatusTLVReceived  OBJECT-TYPE
 	SYNTAX Counter64
 	MAX-ACCESS  read-only
     STATUS      current
     DESCRIPTION
             "This object specifies total invalid port status TLVs received."
     ::= { wwpLeosCfmExtMEPStatsEntry 4 } 
 
 wwpLeosCfmExtMEPStatsInvalidInterfaceStatusTLVReceived  OBJECT-TYPE
 	SYNTAX Counter64
 	MAX-ACCESS  read-only
     STATUS      current
     DESCRIPTION
             "This object specifies total invalid interface status TLVs received."
     ::= { wwpLeosCfmExtMEPStatsEntry 5 }
  
  wwpLeosCfmExtMEPStatsInvalidSenderIDTLVReceived  OBJECT-TYPE
 	SYNTAX Counter64
 	MAX-ACCESS  read-only
     STATUS      current
     DESCRIPTION
             "This object specifies total invalid senderID frames received."
     ::= { wwpLeosCfmExtMEPStatsEntry 6 } 
    
   wwpLeosCfmExtMEPStatsCCMTxmt OBJECT-TYPE
 	SYNTAX Counter64
 	MAX-ACCESS  read-only
     STATUS      current
     DESCRIPTION
             "This object specifies total CCM sent."
     ::= { wwpLeosCfmExtMEPStatsEntry 7 } 
   
   wwpLeosCfmExtMEPStatsValidCCMReceived OBJECT-TYPE
 	SYNTAX Counter64
 	MAX-ACCESS  read-only
     STATUS      current
     DESCRIPTION
             "This object specifies total valid CCMs received."
     ::= { wwpLeosCfmExtMEPStatsEntry 8 }
   
   wwpLeosCfmExtMEPStatsCCMInSequenceReceived OBJECT-TYPE
   	 SYNTAX Counter64
 	 MAX-ACCESS  read-only
     STATUS      current
     DESCRIPTION
             "This object specifies total CCM received in sequence."
     ::= { wwpLeosCfmExtMEPStatsEntry 9 }
    
   wwpLeosCfmExtMEPStatsCCMSequenceErrorsReceived OBJECT-TYPE
   	 SYNTAX Counter64
 	 MAX-ACCESS  read-only
     STATUS      current
     DESCRIPTION
             "This object specifies total not in sequence received CCMs."
     ::= { wwpLeosCfmExtMEPStatsEntry 10 }
   
   wwpLeosCfmExtMEPStatsMDLevelXconCCMReceived  OBJECT-TYPE
   	  SYNTAX Counter64
 	 MAX-ACCESS  read-only
     STATUS      current
     DESCRIPTION
             "This object specifies Xcon CCMs received."
     ::= { wwpLeosCfmExtMEPStatsEntry 11 }  
   
   wwpLeosCfmExtMEPStatsMAIDXconCCMReceived  OBJECT-TYPE
   	  SYNTAX Counter64
 	 MAX-ACCESS  read-only
     STATUS      current
     DESCRIPTION
             "This object specifies MAID Xcon CCMs."
     ::= { wwpLeosCfmExtMEPStatsEntry 12 } 
  
  wwpLeosCfmExtMEPStatsIntervalErrorCCMReceived  OBJECT-TYPE
   	  SYNTAX Counter64
 	 MAX-ACCESS  read-only
     STATUS      current
     DESCRIPTION
             "This object specifies Interval Error CCM received."
     ::= { wwpLeosCfmExtMEPStatsEntry 13 } 
  
  wwpLeosCfmExtMEPStatsRxInvalidCCM  OBJECT-TYPE
   	  SYNTAX Counter64
 	 MAX-ACCESS  read-only
     STATUS      current
     DESCRIPTION
             "This object specified invalid CCMs received "
     ::= { wwpLeosCfmExtMEPStatsEntry 14 } 
  
  wwpLeosCfmExtMEPStatsLBMTxmt  OBJECT-TYPE
   	  SYNTAX Counter64
 	 MAX-ACCESS  read-only
     STATUS      current
     DESCRIPTION
             "This object specifies number of LBM sent"
     ::= { wwpLeosCfmExtMEPStatsEntry 15 }
  
  wwpLeosCfmExtMEPStatsLBRTxmt OBJECT-TYPE
  	 SYNTAX Counter64
 	 MAX-ACCESS  read-only
     STATUS      current
     DESCRIPTION
             "This object specifies number of LBR sent."
     ::= { wwpLeosCfmExtMEPStatsEntry 16 } 
  
  wwpLeosCfmExtMEPStatsInOrderLBRReceived OBJECT-TYPE
  	 SYNTAX Counter64
 	 MAX-ACCESS  read-only
     STATUS      current
     DESCRIPTION
             "This object specifies number of in order LBR received "
     ::= { wwpLeosCfmExtMEPStatsEntry 17 } 
   
   wwpLeosCfmExtMEPStatsOutOfOrderLBRReceived OBJECT-TYPE
  	 SYNTAX Counter64
 	 MAX-ACCESS  read-only
     STATUS      current
     DESCRIPTION
             "This object specifies Out of order LBR received"
     ::= { wwpLeosCfmExtMEPStatsEntry 18 }
   
   wwpLeosCfmExtMEPStatsContentMismatchLBRReceived  OBJECT-TYPE
  	 SYNTAX Counter64
 	 MAX-ACCESS  read-only
     STATUS      current
     DESCRIPTION
             "This object specifies number of content mismatch LBR received "
     ::= { wwpLeosCfmExtMEPStatsEntry 19 }
   
   wwpLeosCfmExtMEPStatsUnexpectedLBRReceived  OBJECT-TYPE
  	 SYNTAX Counter64
 	 MAX-ACCESS  read-only
     STATUS      current
     DESCRIPTION
             "This object specifies unexpected LBR received "
     ::= { wwpLeosCfmExtMEPStatsEntry 20 }
     
   wwpLeosCfmExtMEPStatsInvalidLBRReceived OBJECT-TYPE
  	 SYNTAX Counter64
 	 MAX-ACCESS  read-only
     STATUS      current
     DESCRIPTION
             "This object specifies invalid LBR Received."
     ::= { wwpLeosCfmExtMEPStatsEntry 21 } 
   
   wwpLeosCfmExtMEPStatsLTMTxmt   OBJECT-TYPE
   	  SYNTAX Counter64
 	 MAX-ACCESS  read-only
     STATUS      current
     DESCRIPTION
             "This object specifies number of LTM sent. "
     ::= { wwpLeosCfmExtMEPStatsEntry 22 }
   
   wwpLeosCfmExtMEPStatsValidLTMReceived  OBJECT-TYPE
   	  SYNTAX Counter64
 	 MAX-ACCESS  read-only
     STATUS      current
     DESCRIPTION
             "This object specifies total valid LTM received "
     ::= { wwpLeosCfmExtMEPStatsEntry 23 } 
   
   wwpLeosCfmExtMEPStatsTotalInvalidLTMReceived OBJECT-TYPE
   	  SYNTAX Counter64
 	  MAX-ACCESS  read-only
      STATUS      current
      DESCRIPTION
             "This object specifies total invalid LTM received. "
     ::= { wwpLeosCfmExtMEPStatsEntry 24 }
   
   wwpLeosCfmExtMEPStatsInvalidLTRAction  OBJECT-TYPE
   	  SYNTAX Counter64
 	  MAX-ACCESS  read-only
      STATUS      current
      DESCRIPTION
             "This object specifies total invalid LTR action. "
     ::= { wwpLeosCfmExtMEPStatsEntry 25 }
   
   wwpLeosCfmExtMEPStatsLTRTxmt OBJECT-TYPE
   	  SYNTAX Counter64
 	  MAX-ACCESS  read-only
      STATUS      current
      DESCRIPTION
             "This object specifies total LTR sent. "
     ::= { wwpLeosCfmExtMEPStatsEntry 26 }  
   
  wwpLeosCfmExtMEPStatsLTRReceived  OBJECT-TYPE
   	  SYNTAX Counter64
 	  MAX-ACCESS  read-only
      STATUS      current
      DESCRIPTION
             "This object specifies unexpected LTR sent. "
     ::= { wwpLeosCfmExtMEPStatsEntry 27 } 
   
  wwpLeosCfmExtMEPStatsDMMTxmt  OBJECT-TYPE
   	  SYNTAX Counter64
 	  MAX-ACCESS  read-only
      STATUS      current
      DESCRIPTION
             "This object specifies total DMM sent. "
     ::= { wwpLeosCfmExtMEPStatsEntry 28 }
   
  wwpLeosCfmExtMEPStatsDMMReceived  OBJECT-TYPE
   	  SYNTAX Counter64
 	  MAX-ACCESS  read-only
      STATUS      current
      DESCRIPTION
             "This object specifies total DMM received. "
     ::= { wwpLeosCfmExtMEPStatsEntry 29 }
  
  wwpLeosCfmExtMEPStatsDMRTxmt   OBJECT-TYPE
  	  SYNTAX Counter64
 	  MAX-ACCESS  read-only
      STATUS      current
      DESCRIPTION
             "This object specifies total DMR sent."
     ::= { wwpLeosCfmExtMEPStatsEntry 30 }
  
  wwpLeosCfmExtMEPStatsDMRReceived  OBJECT-TYPE
  	  SYNTAX Counter64
 	  MAX-ACCESS  read-only
      STATUS      current
      DESCRIPTION
             "This object specifies total DMR received"
     ::= { wwpLeosCfmExtMEPStatsEntry 31 } 
  
  wwpLeosCfmExtMEPStatsDMReplyTimeout OBJECT-TYPE
  	  SYNTAX Counter64
 	  MAX-ACCESS  read-only
      STATUS      current
      DESCRIPTION
             "This object specifies DMR Timeout."
     ::= { wwpLeosCfmExtMEPStatsEntry 32 }
  
  wwpLeosCfmExtMEPStatsLMMTxmt OBJECT-TYPE
  	  SYNTAX Counter64
 	  MAX-ACCESS  read-only
      STATUS      current
      DESCRIPTION
             "This object specifies total LMM Sent. "
     ::= { wwpLeosCfmExtMEPStatsEntry 33 }
  
  wwpLeosCfmExtMEPStatsLMMReceived  OBJECT-TYPE
  	  SYNTAX Counter64
 	  MAX-ACCESS  read-only
      STATUS      current
      DESCRIPTION
             "This object specifies total LMM received "
     ::= { wwpLeosCfmExtMEPStatsEntry 34 }
  
  wwpLeosCfmExtMEPStatsLMRTxmt OBJECT-TYPE
  	  SYNTAX Counter64
 	  MAX-ACCESS  read-only
      STATUS      current
      DESCRIPTION
             "This object specifies total LMR sent."
     ::= { wwpLeosCfmExtMEPStatsEntry 35 }
 
 wwpLeosCfmExtMEPStatsLMRReceived  OBJECT-TYPE
  	  SYNTAX Counter64
 	  MAX-ACCESS  read-only
      STATUS      current
      DESCRIPTION
             "This object specifies total LMR Received. "
     ::= { wwpLeosCfmExtMEPStatsEntry 36 } 
 
 wwpLeosCfmExtMEPStatsLMRTimeout OBJECT-TYPE
  	  SYNTAX Counter64
 	  MAX-ACCESS  read-only
      STATUS      current
      DESCRIPTION
             "This object specifies total LMR Timeout. "
     ::= { wwpLeosCfmExtMEPStatsEntry 37 }  
 
 wwpLeosCfmExtMEPStatsMepIdErrorCCMReceived  OBJECT-TYPE
  	  SYNTAX Counter64
 	  MAX-ACCESS  read-only
      STATUS      current
      DESCRIPTION
             "This object specifies total MEPID Error CCM Received. "
     ::= { wwpLeosCfmExtMEPStatsEntry 38 }                        
 
  
 wwpLeosCfmExtMEPStatsClear OBJECT-TYPE
 	SYNTAX INTEGER {
 			clear(1),
 			none(2)
 		}
 	MAX-ACCESS read-write
 	STATUS current
 	DESCRIPTION "Setting this object to clear will clear MEP stats for the given service and MepId.
 			     This object can't be set to none"
 	::= { wwpLeosCfmExtMEPStatsEntry 40 }    
 	
 wwpLeosCfmExtMEPStatsValidLBMReceived  OBJECT-TYPE
  	  SYNTAX Counter64
 	  MAX-ACCESS  read-only
      STATUS      current
      DESCRIPTION
             "This object specifies Valid LBM Received. "
     ::= { wwpLeosCfmExtMEPStatsEntry 41 }    
 
 wwpLeosCfmExtMEPStatsInvalidLBMReceived  OBJECT-TYPE
  	  SYNTAX Counter64
 	  MAX-ACCESS  read-only
      STATUS      current
      DESCRIPTION
             "This object specifies total invalid LBM Received. "
     ::= { wwpLeosCfmExtMEPStatsEntry 42 }
 
 wwpLeosCfmExtMEPStatsUnexpectedLTRReceived  OBJECT-TYPE
  	  SYNTAX Counter64
 	  MAX-ACCESS  read-only
      STATUS      current
      DESCRIPTION
             "This object specifies total unexpected LTR Received. "
     ::= { wwpLeosCfmExtMEPStatsEntry 43 }
 
 wwpLeosCfmExtMEPStatsInvalidDMMReceived OBJECT-TYPE
  	  SYNTAX Counter64
 	  MAX-ACCESS  read-only
      STATUS      current
      DESCRIPTION
             "This object specifies total invalid DMM Received. "
     ::= { wwpLeosCfmExtMEPStatsEntry 44 }
 
 wwpLeosCfmExtMEPStatsInvalidDMRReceived OBJECT-TYPE
  	  SYNTAX Counter64
 	  MAX-ACCESS  read-only
      STATUS      current
      DESCRIPTION
             "This object specifies total invalid DMR Received. "
     ::= { wwpLeosCfmExtMEPStatsEntry 45 }

 wwpLeosCfmExtMEPStatsUnexpectedDMRReceived OBJECT-TYPE
  	  SYNTAX Counter64
 	  MAX-ACCESS  read-only
      STATUS      current
      DESCRIPTION
             "This object specifies total unexpected DMR Received. "
     ::= { wwpLeosCfmExtMEPStatsEntry 46 }

 wwpLeosCfmExtMEPStatsInvalidLMMReceived OBJECT-TYPE
  	  SYNTAX Counter64
 	  MAX-ACCESS  read-only
      STATUS      current
      DESCRIPTION
             "This object specifies total invalid LMM Received. "
     ::= { wwpLeosCfmExtMEPStatsEntry 47 }

 wwpLeosCfmExtMEPStatsInvalidLMRReceived OBJECT-TYPE
  	  SYNTAX Counter64
 	  MAX-ACCESS  read-only
      STATUS      current
      DESCRIPTION
             "This object specifies total invalid LMR Received. "
     ::= { wwpLeosCfmExtMEPStatsEntry 48 }
 
 wwpLeosCfmExtMEPStatsInvalidBlockedOppositeMep OBJECT-TYPE
  	  SYNTAX Counter64
 	  MAX-ACCESS  read-only
      STATUS      current
      DESCRIPTION
             "This object specifies total invalid frames blocked by opposite MEP."
     ::= { wwpLeosCfmExtMEPStatsEntry 49 }

 --
 -- Last stats Table
 --
 
 wwpLeosCfmExtMEPLastStatsTable OBJECT-TYPE
     SYNTAX     SEQUENCE OF WwpLeosCfmExtMEPLastStatsEntry
     MAX-ACCESS not-accessible
     STATUS     current
     DESCRIPTION
            "The (conceptual) table listing the configuration 
            parameters for the CFM MEP table."  
     ::= { wwpLeosCfmExtMEP 3 }
                
 wwpLeosCfmExtMEPLastStatsEntry OBJECT-TYPE
     SYNTAX      WwpLeosCfmExtMEPLastStatsEntry
     MAX-ACCESS  not-accessible
     STATUS      current
     DESCRIPTION
           "An entry (conceptual row) in the wwpLeosCfmMEPTable."   
     --   wwpLeosCfmExtMEPId is the new index in place of mepport
     INDEX {wwpLeosCfmServiceIndex, wwpLeosCfmExtMEPId}
     ::= { wwpLeosCfmExtMEPLastStatsTable 1 }   

  
 WwpLeosCfmExtMEPLastStatsEntry ::= SEQUENCE {                    
 		wwpLeosCfmExtMEPLastStatsPriority				Counter64,			
 		wwpLeosCfmExtMEPLastStatsLBMCount				Counter64,
 		wwpLeosCfmExtMEPLastStatsLBMSent				Counter64,
 		wwpLeosCfmExtMEPLastStatsLBMToSend				Counter64,
 		wwpLeosCfmExtMEPLastStatsInOrderLBRReceived		Counter64,
 		wwpLeosCfmExtMEPLastStatsOutOfOrderLBRReceived  Counter64,
 		wwpLeosCfmExtMEPLastStatsDMMPriority			Counter64,
 		wwpLeosCfmExtMEPLastStatsDMMTxmt				Counter64,
 		wwpLeosCfmExtMEPLastStatsDMMReceived			Counter64,
 		wwpLeosCfmExtMEPLastStatsDMMDelay				Counter64,
 		wwpLeosCfmExtMEPLastStatsDMMJitter				Counter64,
 		wwpLeosCfmExtMEPLastStatsLMMPriority			Counter64,
 		wwpLeosCfmExtMEPLastStatsLMMTxtm				Counter64,
 		wwpLeosCfmExtMEPLastStatsLMMReceived			Counter64,
 		wwpLeosCfmExtMEPLastStatsFrameLossNear			Counter64,
 		wwpLeosCfmExtMEPLastStatsFrameLossFar			Counter64,
 		wwpLeosCfmExtMEPLastStatsLTMPriority			Counter64,
 		wwpLeosCfmExtMEPLastStatsLTMSequenceNo			Counter64,
 		wwpLeosCfmExtMEPLastStatsLTMInitialTTL			Counter64,
 		wwpLeosCfmExtMEPLastStatsFrameLossBadSequence	Counter64,
 		wwpLeosCfmExtMEPLastStatsDMMMinDelay			Counter64,
 		wwpLeosCfmExtMEPLastStatsDMMMaxDelay			Counter64,
 		wwpLeosCfmExtMEPLastStatsDMMMinJitter			Counter64,
 		wwpLeosCfmExtMEPLastStatsDMMMaxJitter			Counter64
 } 			
 wwpLeosCfmExtMEPLastStatsPriority	OBJECT-TYPE
 	SYNTAX Counter64
 	MAX-ACCESS read-only
 	STATUS current
 	DESCRIPTION
 		"This object specifies last LBM Priority"
 	::= {wwpLeosCfmExtMEPLastStatsEntry 1}
 
 wwpLeosCfmExtMEPLastStatsLBMCount OBJECT-TYPE
 	SYNTAX Counter64
 	MAX-ACCESS read-only
 	STATUS current
 	DESCRIPTION
 		"This object specifies last LBM Count"
 	::= {wwpLeosCfmExtMEPLastStatsEntry 2} 
 wwpLeosCfmExtMEPLastStatsLBMSent  OBJECT-TYPE
 	SYNTAX Counter64
 	MAX-ACCESS read-only
 	STATUS current
 	DESCRIPTION
 		"This object specifies last number LBM sent"
 	::= {wwpLeosCfmExtMEPLastStatsEntry 3} 
 
 wwpLeosCfmExtMEPLastStatsLBMToSend OBJECT-TYPE
 	SYNTAX Counter64
 	MAX-ACCESS read-only
 	STATUS current
 	DESCRIPTION
 		"This object specifies last LBM to send."
 	::= {wwpLeosCfmExtMEPLastStatsEntry 4}		
 
 wwpLeosCfmExtMEPLastStatsInOrderLBRReceived OBJECT-TYPE
 	SYNTAX Counter64
 	MAX-ACCESS read-only
 	STATUS current
 	DESCRIPTION
 		"This object specifies last In oder LBR received"
 	::= {wwpLeosCfmExtMEPLastStatsEntry 5}			
 
 wwpLeosCfmExtMEPLastStatsOutOfOrderLBRReceived	OBJECT-TYPE
 	SYNTAX Counter64
 	MAX-ACCESS read-only
 	STATUS current
 	DESCRIPTION
 		"This object specifies last out of order LBR received"
 	::= {wwpLeosCfmExtMEPLastStatsEntry 6}			
 			
 wwpLeosCfmExtMEPLastStatsDMMPriority OBJECT-TYPE
 	SYNTAX Counter64
 	MAX-ACCESS read-only
 	STATUS current
 	DESCRIPTION
 		"This object specifies Last DMM Priority"
 	::= {wwpLeosCfmExtMEPLastStatsEntry 7}
 
 wwpLeosCfmExtMEPLastStatsDMMTxmt  OBJECT-TYPE
 	SYNTAX Counter64
 	MAX-ACCESS read-only
 	STATUS current
 	DESCRIPTION
 		"This object specifies number of last DMM sent"
 	::= {wwpLeosCfmExtMEPLastStatsEntry 8} 
 
 wwpLeosCfmExtMEPLastStatsDMMReceived  OBJECT-TYPE
 	SYNTAX Counter64
 	MAX-ACCESS read-only
 	STATUS current
 	DESCRIPTION
 		"This object specifies last DMM Received"
 	::= {wwpLeosCfmExtMEPLastStatsEntry 9} 
 
 wwpLeosCfmExtMEPLastStatsDMMDelay  OBJECT-TYPE
 	SYNTAX Counter64
 	MAX-ACCESS read-only
 	STATUS current
 	DESCRIPTION
 		"This object specifies Last DMM Delay."
 	::= {wwpLeosCfmExtMEPLastStatsEntry 10} 
 
 wwpLeosCfmExtMEPLastStatsDMMJitter  OBJECT-TYPE
 	SYNTAX Counter64
 	MAX-ACCESS read-only
 	STATUS current
 	DESCRIPTION
 		"This object specifies last DMM Jitter."
 	::= {wwpLeosCfmExtMEPLastStatsEntry 11} 
 
 wwpLeosCfmExtMEPLastStatsLMMPriority  OBJECT-TYPE
 	SYNTAX Counter64
 	MAX-ACCESS read-only
 	STATUS current
 	DESCRIPTION
 		"This object specifies last LMM priority"
 	::= {wwpLeosCfmExtMEPLastStatsEntry 12}
 	
 wwpLeosCfmExtMEPLastStatsLMMTxtm OBJECT-TYPE
 	SYNTAX Counter64
 	MAX-ACCESS read-only
 	STATUS current
 	DESCRIPTION
 		"This object specifies last LMM sent."
 	::= {wwpLeosCfmExtMEPLastStatsEntry 13}

 wwpLeosCfmExtMEPLastStatsLMMReceived  OBJECT-TYPE
 	SYNTAX Counter64
 	MAX-ACCESS read-only
 	STATUS current
 	DESCRIPTION
 		"This object specifies number of last LMM received."
 	::= {wwpLeosCfmExtMEPLastStatsEntry 14}
 
 wwpLeosCfmExtMEPLastStatsFrameLossNear OBJECT-TYPE
 	SYNTAX Counter64
 	MAX-ACCESS read-only
 	STATUS current
 	DESCRIPTION
 		"This object specifies last near Frame Losses"
 	::= {wwpLeosCfmExtMEPLastStatsEntry 15}	
 
 wwpLeosCfmExtMEPLastStatsFrameLossFar 	OBJECT-TYPE
 	SYNTAX Counter64
 	MAX-ACCESS read-only
 	STATUS current
 	DESCRIPTION
 		"This object specifies last far Frames Loss"
 	::= {wwpLeosCfmExtMEPLastStatsEntry 16}	
 
 wwpLeosCfmExtMEPLastStatsLTMPriority OBJECT-TYPE
 	SYNTAX Counter64
 	MAX-ACCESS read-only
 	STATUS current
 	DESCRIPTION
 		"This object specifies last LTM Priority"
 	::= {wwpLeosCfmExtMEPLastStatsEntry 17}
 
 wwpLeosCfmExtMEPLastStatsLTMSequenceNo OBJECT-TYPE
 	SYNTAX Counter64
 	MAX-ACCESS read-only
 	STATUS current
 	DESCRIPTION
 		"This object specifies last LTM Sequence number."
 	::= {wwpLeosCfmExtMEPLastStatsEntry 18}   
 
 wwpLeosCfmExtMEPLastStatsLTMInitialTTL  OBJECT-TYPE
 	SYNTAX Counter64
 	MAX-ACCESS read-only
 	STATUS current
 	DESCRIPTION
 		"This object specifies last initial TTL LTM."
 	::= {wwpLeosCfmExtMEPLastStatsEntry 19}    

 wwpLeosCfmExtMEPLastStatsFrameLossBadSequence OBJECT-TYPE
 	SYNTAX Counter64
 	MAX-ACCESS read-only
 	STATUS current
 	DESCRIPTION
 		"This object specifes the number of frames with bad sequence numbers measured 
 		during the last LMM performance test on the given service and Mep."
 	::= {wwpLeosCfmExtMEPLastStatsEntry 20}
 
 wwpLeosCfmExtMEPLastStatsDMMMinDelay  OBJECT-TYPE
 	SYNTAX Counter64
 	MAX-ACCESS read-only
 	STATUS current
 	DESCRIPTION
 		"This object specifies Last DMM Minimum Delay."
 	::= {wwpLeosCfmExtMEPLastStatsEntry 21} 
 
 wwpLeosCfmExtMEPLastStatsDMMMaxDelay  OBJECT-TYPE
 	SYNTAX Counter64
 	MAX-ACCESS read-only
 	STATUS current
 	DESCRIPTION
 		"This object specifies Last DMM Maximum Delay."
 	::= {wwpLeosCfmExtMEPLastStatsEntry 22} 
 
 wwpLeosCfmExtMEPLastStatsDMMMinJitter  OBJECT-TYPE
 	SYNTAX Counter64
 	MAX-ACCESS read-only
 	STATUS current
 	DESCRIPTION
 		"This object specifies last DMM Minimum Jitter."
 	::= {wwpLeosCfmExtMEPLastStatsEntry 23} 
 
 wwpLeosCfmExtMEPLastStatsDMMMaxJitter  OBJECT-TYPE
 	SYNTAX Counter64
 	MAX-ACCESS read-only
 	STATUS current
 	DESCRIPTION
 		"This object specifies last DMM Maximum Jitter."
 	::= {wwpLeosCfmExtMEPLastStatsEntry 24} 
 	 
		
 wwpLeosCfmExtMEPClearStatistics OBJECT-TYPE
 	SYNTAX INTEGER {
 		clear(1),
 		none(2)
 		}
 	MAX-ACCESS read-write
 	STATUS current
 	DESCRIPTION "Setting this object to clear(1) will clear statistics for all Meps across all services"
 	DEFVAL {none}
 	::= {wwpLeosCfmExtMEP 4}


--
-- CFM MEP Delay History
--
   
 wwpLeosCfmExtMEPDelayHistoryTable OBJECT-TYPE
     SYNTAX     	SEQUENCE OF WwpLeosCfmExtMEPDelayHistoryEntry
     MAX-ACCESS 	not-accessible
     STATUS     	current
     DESCRIPTION 	"The (conceptual) table listing the Y.1731 Delay
     				History table for the CFM MEP."  
     ::= { wwpLeosCfmExtMEP 5 }
                
 wwpLeosCfmExtMEPDelayHistoryEntry OBJECT-TYPE
     SYNTAX      	WwpLeosCfmExtMEPDelayHistoryEntry
     MAX-ACCESS  	not-accessible
     STATUS      	current
     DESCRIPTION    "An entry (conceptual row) in the wwpLeosCfmMEPDelayHistoryTable."   
     INDEX {wwpLeosCfmServiceIndex, wwpLeosCfmExtMEPId, wwpLeosCfmExtMEPDelayHistoryIndex}
     ::= { wwpLeosCfmExtMEPDelayHistoryTable 1 }   
 
  WwpLeosCfmExtMEPDelayHistoryEntry ::=  SEQUENCE {
     wwpLeosCfmExtMEPDelayHistoryIndex					INTEGER,
  	 wwpLeosCfmExtMEPDelayHistoryStatus					INTEGER,
  	 wwpLeosCfmExtMEPDelayHistoryInterval				INTEGER,
  	 wwpLeosCfmExtMEPDelayHistoryPriority				INTEGER,
  	 wwpLeosCfmExtMEPDelayHistoryMEPId					Unsigned32,
  	 wwpLeosCfmExtMEPDelayHistoryNumDMMSent				Unsigned32,
  	 wwpLeosCfmExtMEPDelayHistoryNumDMRReceived			Unsigned32,
  	 wwpLeosCfmExtMEPDelayHistoryMinDelay				Unsigned32,
  	 wwpLeosCfmExtMEPDelayHistoryAveDelay				Unsigned32,
  	 wwpLeosCfmExtMEPDelayHistoryMaxDelay				Unsigned32, 
  	 wwpLeosCfmExtMEPDelayHistoryMinJitter				Unsigned32,
  	 wwpLeosCfmExtMEPDelayHistoryAveJitter				Unsigned32,
  	 wwpLeosCfmExtMEPDelayHistoryMaxJitter				Unsigned32, 
 	 wwpLeosCfmExtMEPDelayHistoryStartTime				Unsigned32,
 	 wwpLeosCfmExtMEPDelayHistoryStopTime				Unsigned32,
     wwpLeosCfmExtMEPDelayHistoryClear					INTEGER
  }

 wwpLeosCfmExtMEPDelayHistoryIndex OBJECT-TYPE
    SYNTAX      	INTEGER (0..255)
    MAX-ACCESS  	not-accessible
    STATUS      	current
    DESCRIPTION		"This is the history entry index into the table."
    ::= { wwpLeosCfmExtMEPDelayHistoryEntry 1 }
 	
 wwpLeosCfmExtMEPDelayHistoryStatus OBJECT-TYPE
    SYNTAX      	INTEGER {
     							running(1),
     							done(2),
     							canceled(3),
     							timeout(4)
     						}
    MAX-ACCESS  	read-only
    STATUS      	current
    DESCRIPTION     "The status of the test sent on the given service and MEP."  
    ::= { wwpLeosCfmExtMEPDelayHistoryEntry 2 } 
 
 wwpLeosCfmExtMEPDelayHistoryInterval OBJECT-TYPE
    SYNTAX      	INTEGER (0..7)
    MAX-ACCESS  	read-only
    STATUS      	current
    DESCRIPTION     "The transmit rate of the Y.1731 DMM Frames sent on the given service and MEP."  
    ::= { wwpLeosCfmExtMEPDelayHistoryEntry 3 } 
 
 wwpLeosCfmExtMEPDelayHistoryPriority OBJECT-TYPE
    SYNTAX      	INTEGER (0..7)
    MAX-ACCESS  	read-only
    STATUS      	current
    DESCRIPTION     "The priority of the Y.1731 DMM Frames sent on the given service and MEP."  
    ::= { wwpLeosCfmExtMEPDelayHistoryEntry 4 } 
 
 wwpLeosCfmExtMEPDelayHistoryMEPId OBJECT-TYPE
    SYNTAX      	Unsigned32 (1..8191)
    MAX-ACCESS  	read-only
    STATUS      	current
    DESCRIPTION     "The remote MEP id the test was ran against."
    ::= { wwpLeosCfmExtMEPDelayHistoryEntry 5 }
     
 wwpLeosCfmExtMEPDelayHistoryNumDMMSent OBJECT-TYPE
 	SYNTAX			Unsigned32
 	MAX-ACCESS		read-only
 	STATUS			current 
    DESCRIPTION		"The number of DMM frames sent on the given service and MEP."
    ::= { wwpLeosCfmExtMEPDelayHistoryEntry 6 }
    
 wwpLeosCfmExtMEPDelayHistoryNumDMRReceived OBJECT-TYPE
 	SYNTAX			Unsigned32
 	MAX-ACCESS		read-only
 	STATUS			current 
    DESCRIPTION		"The number of DMR frames received on the given service and MEP."
    ::= { wwpLeosCfmExtMEPDelayHistoryEntry 7 }
    
 wwpLeosCfmExtMEPDelayHistoryMinDelay OBJECT-TYPE
 	SYNTAX			Unsigned32
 	MAX-ACCESS		read-only
 	STATUS			current 
    DESCRIPTION		"The minimum delay(us) seen on DMR frames received on the given service and MEP."
    ::= { wwpLeosCfmExtMEPDelayHistoryEntry 8 }
    
 wwpLeosCfmExtMEPDelayHistoryAveDelay OBJECT-TYPE
 	SYNTAX			Unsigned32
 	MAX-ACCESS		read-only
 	STATUS			current 
    DESCRIPTION		"The average delay(us) seen on DMR frames received on the given service and MEP."
    ::= { wwpLeosCfmExtMEPDelayHistoryEntry 9 }
    
 wwpLeosCfmExtMEPDelayHistoryMaxDelay OBJECT-TYPE
 	SYNTAX			Unsigned32
 	MAX-ACCESS		read-only
 	STATUS			current 
    DESCRIPTION		"The maximum delay(us) seen on DMR frames received on the given service and MEP."
    ::= { wwpLeosCfmExtMEPDelayHistoryEntry 10 }
    
 wwpLeosCfmExtMEPDelayHistoryMinJitter OBJECT-TYPE
 	SYNTAX			Unsigned32
 	MAX-ACCESS		read-only
 	STATUS			current 
    DESCRIPTION		"The minimum jitter(us) seen on DMR frames received on the given service and MEP."
    ::= { wwpLeosCfmExtMEPDelayHistoryEntry 11 }
    
 wwpLeosCfmExtMEPDelayHistoryAveJitter OBJECT-TYPE
 	SYNTAX			Unsigned32
 	MAX-ACCESS		read-only
 	STATUS			current 
    DESCRIPTION		"The average jitter(us) seen on DMR frames received on the given service and MEP."
    ::= { wwpLeosCfmExtMEPDelayHistoryEntry 12 }
    
 wwpLeosCfmExtMEPDelayHistoryMaxJitter OBJECT-TYPE
 	SYNTAX			Unsigned32
 	MAX-ACCESS		read-only
 	STATUS			current 
    DESCRIPTION		"The maximum jitter(us) seen on DMR frames received on the given service and MEP."
    ::= { wwpLeosCfmExtMEPDelayHistoryEntry 13 }
 
 wwpLeosCfmExtMEPDelayHistoryStartTime OBJECT-TYPE
 	SYNTAX			Unsigned32
 	MAX-ACCESS		read-only
 	STATUS			current
 	DESCRIPTION		"The time the test began on the given service and MEP.
 					The timestamp is the number of seconds since 12AM Jan 1st, 1970"
 	::= { wwpLeosCfmExtMEPDelayHistoryEntry 14 }
 
 wwpLeosCfmExtMEPDelayHistoryStopTime OBJECT-TYPE
 	SYNTAX			Unsigned32
 	MAX-ACCESS		read-only
 	STATUS			current
 	DESCRIPTION		"The time the test terminated on the given service and MEP.
 					The timestamp is the number of seconds since 12AM Jan 1st, 1970"
 	::= { wwpLeosCfmExtMEPDelayHistoryEntry 15 }
 	
 wwpLeosCfmExtMEPDelayHistoryClear OBJECT-TYPE
 	SYNTAX 			INTEGER {
 								clear(1),
 								none(2)
 							}
 	MAX-ACCESS 		read-write
 	STATUS 			current
 	DESCRIPTION 	"Setting this object to clear will clear MEP delay history for the
 					given service and MepId.  This object can't be set to none"
 	::= { wwpLeosCfmExtMEPDelayHistoryEntry 16 }    
  
			   
 --
 --  Link Trace Message table
 --  
 wwpLeosCfmExtLinkTraceMsgTable OBJECT-TYPE
     SYNTAX     SEQUENCE OF WwpLeosCfmExtLinkTraceMsgEntry
     MAX-ACCESS not-accessible
     STATUS     current
     DESCRIPTION
            "The (conceptual) table listing the configuration 
            parameters for the LinkTraceMsg."  
     ::= { wwpLeosCfmExtLinkTrace 1 }
                
 wwpLeosCfmExtLinkTraceMsgEntry OBJECT-TYPE
     SYNTAX      WwpLeosCfmExtLinkTraceMsgEntry
     MAX-ACCESS  not-accessible
     STATUS      current
     DESCRIPTION
           "An entry (conceptual row) in the wwpLeosCfmLinkTraceMsgTable."
     INDEX {wwpLeosCfmServiceIndex, wwpLeosCfmExtLinkTraceMsgLocalMepID}
     ::= { wwpLeosCfmExtLinkTraceMsgTable 1 }
                                                                     
 WwpLeosCfmExtLinkTraceMsgEntry ::=  SEQUENCE {                      
     wwpLeosCfmExtLinkTraceMsgLocalMepID		    INTEGER, 
--     wwpLeosCfmExtLinkTraceMsgPortId             	INTEGER,
     wwpLeosCfmExtLinkTraceMsgTargetMEPID        	INTEGER,
     wwpLeosCfmExtLinkTraceMsgTargetMacAddr      	MacAddress,
     wwpLeosCfmExtLinkTraceMsgTTL                	INTEGER,
     wwpLeosCfmExtLinkTraceMsgSequenceNumber       Integer32,
     wwpLeosCfmExtLinkTraceMsgPriority             INTEGER,
     wwpLeosCfmExtLinkTraceMsgAction 			   SendState   
 }
  
 wwpLeosCfmExtLinkTraceMsgLocalMepID OBJECT-TYPE
     SYNTAX INTEGER (1..8191)
     MAX-ACCESS not-accessible
     STATUS current
     DESCRIPTION
     		"This represent local mepid"
     ::= { wwpLeosCfmExtLinkTraceMsgEntry 1}
 
-- wwpLeosCfmExtLinkTraceMsgPortId OBJECT-TYPE
--     SYNTAX       INTEGER (1..65535)
--     MAX-ACCESS   read-only
--     STATUS       current
--     DESCRIPTION
--             "This object is used to specify the port."
--     ::= { wwpLeosCfmExtLinkTraceMsgEntry 1 }
 
 wwpLeosCfmExtLinkTraceMsgTargetMEPID OBJECT-TYPE
     SYNTAX       INTEGER (1..8191)
     MAX-ACCESS   read-create
     STATUS       current
     DESCRIPTION
             "This object is used to specify the target MEPID.
              This object should only be set if wwpLeosCfmLinkTraceMsgTargetMacAddr is not specified else 
              error will be returned."
     ::= { wwpLeosCfmExtLinkTraceMsgEntry 2 }
     
 wwpLeosCfmExtLinkTraceMsgTargetMacAddr OBJECT-TYPE
     SYNTAX       MacAddress
     MAX-ACCESS   read-create
     STATUS       current
     DESCRIPTION
             "This object is used to specify the target MacAddress to be used when sending link LinkMsg.
              This object should only be set if wwpLeosCfmLinkTraceMsgTargetMEPID is not specified else 
              error will be returned."
     ::= { wwpLeosCfmExtLinkTraceMsgEntry 3 }
     
 wwpLeosCfmExtLinkTraceMsgTTL OBJECT-TYPE
     SYNTAX       INTEGER (1..255)
     MAX-ACCESS   read-create
     STATUS       current
     DESCRIPTION
             "This object is used to specify the TTL to be used when sending link LinkTraceMsg."
     ::= { wwpLeosCfmExtLinkTraceMsgEntry 4 }
 
 wwpLeosCfmExtLinkTraceMsgSequenceNumber OBJECT-TYPE
     SYNTAX       Integer32
     MAX-ACCESS   read-only
     STATUS       current
     DESCRIPTION
             "This object is used to specify the sequence number in the linkTraceMsg."
     ::= { wwpLeosCfmExtLinkTraceMsgEntry 5 }

 wwpLeosCfmExtLinkTraceMsgPriority OBJECT-TYPE
 	SYNTAX		INTEGER (0..7)
 	MAX-ACCESS	read-create
 	STATUS		current
 	DESCRIPTION                          
             "This object is used to specify the priority to be used when sending LinkTraceMsg."
 	::= { wwpLeosCfmExtLinkTraceMsgEntry 6 }  
 	
 wwpLeosCfmExtLinkTraceMsgAction  OBJECT-TYPE
    SYNTAX   SendState
    MAX-ACCESS   read-create
    STATUS       current
    DESCRIPTION
             "This object represents the action for the message (send, clear or cancel)
             If set to send(1) and if wwpLeosCfmExtLinkTraceMsgTargetMacAddr is specified 
             then LinkTraceMsg is sent to remote Mac.
             If set to send(1) and if wwpLeosCfmExtLinkTraceMsgTargetMEPID is specified 
             then LinktraceMsg is sent to remote mepid.
             If set to clear(2) will clear mep statistics for given service and mepid.
             If set to cancel(3) will return commit_failed_error. "
   ::= {wwpLeosCfmExtLinkTraceMsgEntry 7}     
   
 --
 --  Link Trace Message Reply table
 --  
 wwpLeosCfmExtLinkTraceMsgReplyTable OBJECT-TYPE
     SYNTAX     SEQUENCE OF WwpLeosCfmExtLinkTraceMsgReplyEntry
     MAX-ACCESS not-accessible
     STATUS     current
     DESCRIPTION
            "The (conceptual) table listing the display 
            parameters for the LinkTrace Msg Reply."  
     ::= { wwpLeosCfmExtLinkTrace 2 }
                
  wwpLeosCfmExtLinkTraceMsgReplyEntry OBJECT-TYPE
     SYNTAX      WwpLeosCfmExtLinkTraceMsgReplyEntry
     MAX-ACCESS  not-accessible
     STATUS      current
     DESCRIPTION
           "An entry (conceptual row) in the wwpLeosCfmExtLinkTraceMsgReplyTable."
     INDEX {wwpLeosCfmServiceIndex, wwpLeosCfmExtLinkTraceMsgLocalMepID, wwpLeosCfmExtLinkTraceMsgReplyTTL, wwpLeosCfmExtLinkTraceMsgReplyTTLIndex}
     ::= { wwpLeosCfmExtLinkTraceMsgReplyTable 1 }
                
  WwpLeosCfmExtLinkTraceMsgReplyEntry ::=  SEQUENCE {           
         wwpLeosCfmExtLinkTraceMsgReplyTTL                      	Integer32,
         wwpLeosCfmExtLinkTraceMsgReplyTTLIndex                    	Unsigned32,
         wwpLeosCfmExtLinkTraceMsgReplySequenceNumber              	Integer32,
         wwpLeosCfmExtLinkTraceMsgReplyMPMacAddr                   	MacAddress,
         wwpLeosCfmExtLinkTraceMsgReplyMEPID                       	Integer32,
         wwpLeosCfmExtLinkTraceMsgReplyTargetMacAddr               	MacAddress,
         wwpLeosCfmExtLinkTraceMsgReplyRelayAction 					INTEGER,
         wwpLeosCfmExtLinkTraceMsgReplyIngressPort   				INTEGER,
         wwpLeosCfmExtLinkTraceMsgReplyIngressAction   				INTEGER,
         wwpLeosCfmExtLinkTraceMsgReplyEgressPort   				INTEGER,
         wwpLeosCfmExtLinkTraceMsgReplyEgressAction 				INTEGER,
         wwpLeosCfmExtLinkTraceMsgReplyIngressPortStr				DisplayString,
         wwpLeosCfmExtLinkTraceMsgReplyEgressPortStr				DisplayString                
  }   
  
  wwpLeosCfmExtLinkTraceMsgReplyTTL OBJECT-TYPE
     SYNTAX       Integer32 (0..255)
     MAX-ACCESS   read-only
     STATUS       current
     DESCRIPTION
             "This object is used to specify the TTL of the received LinkTrace msg reply."
     ::= { wwpLeosCfmExtLinkTraceMsgReplyEntry 1 }
     
  wwpLeosCfmExtLinkTraceMsgReplyTTLIndex OBJECT-TYPE
     SYNTAX       Unsigned32 (1..24576)
     MAX-ACCESS   read-only
     STATUS       current
     DESCRIPTION
             "This object provides an additional index when multiple LinkTrace messages are received with the same TTL."
     ::= { wwpLeosCfmExtLinkTraceMsgReplyEntry 2 }
  
  wwpLeosCfmExtLinkTraceMsgReplySequenceNumber OBJECT-TYPE
     SYNTAX       Integer32
     MAX-ACCESS   read-only
     STATUS       current
     DESCRIPTION
             "This object is used to specify the sequence number of the received LinkTrace msg reply."
     ::= { wwpLeosCfmExtLinkTraceMsgReplyEntry 3 }

  wwpLeosCfmExtLinkTraceMsgReplyMPMacAddr OBJECT-TYPE
     SYNTAX       MacAddress
     MAX-ACCESS   read-only
     STATUS       current
     DESCRIPTION
             "This object is used to specify the mac address of the MP of received LinkTrace msg reply."
     ::= { wwpLeosCfmExtLinkTraceMsgReplyEntry 4 }

  wwpLeosCfmExtLinkTraceMsgReplyMEPID OBJECT-TYPE
     SYNTAX       Integer32
     MAX-ACCESS   read-only
     STATUS       current
     DESCRIPTION
             "This object is used to specify the MEP ID of the received LinkTrace msg reply."
     ::= { wwpLeosCfmExtLinkTraceMsgReplyEntry 5 }

  wwpLeosCfmExtLinkTraceMsgReplyTargetMacAddr OBJECT-TYPE
     SYNTAX       MacAddress
     MAX-ACCESS   read-only
     STATUS       current
     DESCRIPTION
             "This object is used to specify the Target Mac address of the received LinkTrace msg reply."
     ::= { wwpLeosCfmExtLinkTraceMsgReplyEntry 6 }
     
  wwpLeosCfmExtLinkTraceMsgReplyRelayAction OBJECT-TYPE
     SYNTAX       INTEGER   {
     					invalid(1), 
     					unknown(2),
     					fdb(3),
     					mpdb(4),
     					noLearn(5),
     					hit(6)
     				}     
     MAX-ACCESS   read-only
     STATUS       current
     DESCRIPTION
             "This object is used to specify the message reply relay action."
     ::= { wwpLeosCfmExtLinkTraceMsgReplyEntry 7 }
  
  wwpLeosCfmExtLinkTraceMsgReplyIngressPort  OBJECT-TYPE
     SYNTAX       INTEGER  (1..65535)
     MAX-ACCESS   read-only
     STATUS       obsolete
     DESCRIPTION
             "This object is used to specify the message reply ingress port."
     ::= { wwpLeosCfmExtLinkTraceMsgReplyEntry 8 }
 
  wwpLeosCfmExtLinkTraceMsgReplyIngressAction  OBJECT-TYPE
     SYNTAX       INTEGER  {
     					ok(1),
     					blocked(2),
     					vid(3),
     					down(4),
     					none(5)
     				}
     MAX-ACCESS   read-only
     STATUS       current
     DESCRIPTION
             "This object is used to specify the message reply ingress action."
     ::= { wwpLeosCfmExtLinkTraceMsgReplyEntry 9 }
 
  wwpLeosCfmExtLinkTraceMsgReplyEgressPort  OBJECT-TYPE
     SYNTAX       INTEGER  (1..65535)
     MAX-ACCESS   read-only
     STATUS       obsolete
     DESCRIPTION
             "This object is used to specify the message reply egress port."
     ::= { wwpLeosCfmExtLinkTraceMsgReplyEntry 10 }
  
  wwpLeosCfmExtLinkTraceMsgReplyEgressAction  OBJECT-TYPE
     SYNTAX       INTEGER  {
     				none(1),
     				ttl(2),
     				down(3),
     				blocked(4),
     				vid(5),
     				ok(6)
     				}
     MAX-ACCESS   read-only
     STATUS       current
     DESCRIPTION
             "This object is used to specify the message reply egress action."
     ::= { wwpLeosCfmExtLinkTraceMsgReplyEntry 11 } 
     
 wwpLeosCfmExtLinkTraceMsgReplyIngressPortStr OBJECT-TYPE
     SYNTAX       DisplayString (SIZE(1..8))
     MAX-ACCESS   read-only
     STATUS       current
     DESCRIPTION
             "This MIB object is used to specify the message reply ingress port."
     ::= { wwpLeosCfmExtLinkTraceMsgReplyEntry 12 }        
 
 wwpLeosCfmExtLinkTraceMsgReplyEgressPortStr OBJECT-TYPE
     SYNTAX       DisplayString (SIZE(1..8))
     MAX-ACCESS   read-only
     STATUS       current
     DESCRIPTION
             "This MIB object is used to specify the message reply egress port."
     ::= { wwpLeosCfmExtLinkTraceMsgReplyEntry 13 } 
 --
  -- Delay Measurement Msg table
  -- 
  wwpLeosCfmExtDelayMsgTable OBJECT-TYPE
     SYNTAX     SEQUENCE OF WwpLeosCfmExtDelayMsgEntry
     MAX-ACCESS not-accessible
     STATUS     current
     DESCRIPTION
            "The (conceptual) table listing the configuration 
            parameters for the DelayMeasurementMsg."
            
     ::= { wwpLeosCfmExtDelay 1 }
                
 wwpLeosCfmExtDelayMsgEntry OBJECT-TYPE
     SYNTAX      WwpLeosCfmExtDelayMsgEntry
     MAX-ACCESS  not-accessible
     STATUS      current
     DESCRIPTION
           "An entry (conceptual row) in the wwpLeosCfmDelayMsgTable.
           To send, clear or cancel the message, the corresponding MsgAction 
           needs to be specified. Individual objects in this table
           cannot be set.                                     
           To send or cancel a message, the TargetMepID or the 
           TargtetMacAddr objects need to be specified.
           Clear msgAction clears the counters for the message"      
     --wwpLeosCfmExtDelayMsgLocalMEPId is a new index in place of delayMsgPortId
     INDEX {wwpLeosCfmServiceIndex, wwpLeosCfmExtDelayMsgLocalMEPId}
     ::= { wwpLeosCfmExtDelayMsgTable 1 }
                
 WwpLeosCfmExtDelayMsgEntry ::=  SEQUENCE { 
     wwpLeosCfmExtDelayMsgLocalMEPId                  	INTEGER,
     wwpLeosCfmExtDelayMsgTargetMEPID              Unsigned32,
     wwpLeosCfmExtDelayMsgTargetMacAddr            MacAddress,
     wwpLeosCfmExtDelayMsgCount                   	INTEGER,
     wwpLeosCfmExtDelayMsgPriority                	INTEGER,
  	 wwpLeosCfmExtDelayMsgRepeat					INTEGER,
     wwpLeosCfmExtDelayMsgRepeatCount				INTEGER,
     wwpLeosCfmExtDelayMsgDelayThreshold			INTEGER,
     wwpLeosCfmExtDelayMsgJitterThreshold			INTEGER,
     wwpLeosCfmExtDelayMsgAction				    SendState,
     wwpLeosCfmExtDelayMsgMaxDelayThreshold			INTEGER,
     wwpLeosCfmExtDelayMsgMaxJitterThreshold		INTEGER
    }

 wwpLeosCfmExtDelayMsgLocalMEPId OBJECT-TYPE
     SYNTAX       INTEGER (1..65535)
     MAX-ACCESS   not-accessible
     STATUS       current
     DESCRIPTION
             "This object is used to specify the local MEPId."
     ::= { wwpLeosCfmExtDelayMsgEntry 1 }
 
 wwpLeosCfmExtDelayMsgTargetMEPID OBJECT-TYPE
     SYNTAX       Unsigned32 (1..8191)
     MAX-ACCESS   read-create
     STATUS       current
     DESCRIPTION
             "This object is used to specify the MEPID.
              This object should only be set if wwpLeosCfmExtDelayMsgTargetMacAddr is not specified else 
              error will be returned."
     ::= { wwpLeosCfmExtDelayMsgEntry 2 }
     
 wwpLeosCfmExtDelayMsgTargetMacAddr OBJECT-TYPE
     SYNTAX       MacAddress
     MAX-ACCESS   read-create
     STATUS       current
     DESCRIPTION
             "This object is used to specify the MacAddress to be used when sending link LoopbackMsg.
              This object should only be set if wwpLeosCfmExtDelayMsgTargetMEPID is not specified else 
              error will be returned."
     ::= {wwpLeosCfmExtDelayMsgEntry 3 }
     
 wwpLeosCfmExtDelayMsgCount OBJECT-TYPE
     SYNTAX       INTEGER (0 | 2..600) 
     MAX-ACCESS   read-create
     STATUS       current
     DESCRIPTION
              "This object is used to specify the DelayMeasurementMsg count to be used
              when sending link DelayMeasurementMsg. Counts between 2 and 600 are valid. The system 
              default count will be used if a value of 0 is entered."
     ::= { wwpLeosCfmExtDelayMsgEntry 4 }
 
 wwpLeosCfmExtDelayMsgPriority OBJECT-TYPE
     SYNTAX       INTEGER (0..7)
     MAX-ACCESS   read-create
     STATUS       current
     DESCRIPTION
             "This object is used to specify the DelayMeasurementMsg priority to be
             used when sending link DelayMeasurementMsg."
     ::= { wwpLeosCfmExtDelayMsgEntry 5 }
 
 
  wwpLeosCfmExtDelayMsgRepeat OBJECT-TYPE
 	 SYNTAX			INTEGER {
 	 					enable(1),
 	 					disable(2)
 	 					}
 	 MAX-ACCESS		read-create
 	 STATUS			current
 	 DESCRIPTION
 	 		"Used to make the Delay Measurement test a repeating test."
 	 ::= { wwpLeosCfmExtDelayMsgEntry 8 } 
 	 
 wwpLeosCfmExtDelayMsgRepeatCount OBJECT-TYPE
 	SYNTAX			INTEGER (0..1440)
 	MAX-ACCESS		read-create
 	STATUS			current
 	DESCRIPTION
 			"The repeat time in minutes for the Delay Measurement test.
 			If zero is specified, the test runs continuously."
 	::= { wwpLeosCfmExtDelayMsgEntry 9 }  

   wwpLeosCfmExtDelayMsgDelayThreshold OBJECT-TYPE
     SYNTAX       INTEGER (-1..65535)
     MAX-ACCESS   read-create
     STATUS       current
     DESCRIPTION
              "Represents the fault Threshold for the average delay, specified
              in microseconds.  A value of -1 disables the generatation of faults,
              0 or greater will be compared to the average delay result of the
              test and a fault will be generated if the threshold is exceeded."
     ::= {wwpLeosCfmExtDelayMsgEntry 41 }
  
  wwpLeosCfmExtDelayMsgJitterThreshold OBJECT-TYPE
     SYNTAX       INTEGER  (-1..65535)
     MAX-ACCESS   read-create
     STATUS       current
     DESCRIPTION
              "Represents the fault threshold value for the average Jitter, specified
              in microseconds.  A value of -1 disables the generation of faults,
              0 or greater will be compared to the average jitter result of the
              test and a fault will be generated if the threshold is exceeded."
     ::= { wwpLeosCfmExtDelayMsgEntry 42 }  
   
  wwpLeosCfmExtDelayMsgAction OBJECT-TYPE
     SYNTAX       SendState
     MAX-ACCESS   read-create
     STATUS       current
     DESCRIPTION
             "This object represents the action for the message (send, clear or cancel)
             If set to send(1) and if wwpLeosCfmExtDelayMsgTargetMacAddr is specified 
             then loopbackMsg is sent to remote Mac.
             If set to send(1) and if wwpLeosCfmExtDelayMsgTargetMEPID is specified 
             then loopbackMsg is sent to remote mepid.
             If set to clear(2) will clear mep statistics for given service and mepid.
             If set to cancel(3) and if wwpLeosCfmExtDelayMsgTargetMacAddr is specified 
             then it will cancel sending Delay messages to remoteMac.
             If set to cancel(3) and if wwpLeosCfmExtDelayMsgTargetMEPID is specified 
             then it will cancel sending Delay messages to remoteMEPID."
     ::= { wwpLeosCfmExtDelayMsgEntry 43 }
  
  wwpLeosCfmExtDelayMsgMaxDelayThreshold OBJECT-TYPE
     SYNTAX       INTEGER (-1..65535)
     MAX-ACCESS   read-create
     STATUS       current
     DESCRIPTION
              "Represents the Threshold for the maximum Delay, specified
              in microseconds.  A value of -1 disables the generatation of faults,
              0 or greater will be compared to the maximum delay result of the
              test and a fault will be generated if the threshold is exceeded."
     ::= {wwpLeosCfmExtDelayMsgEntry 44 }
  
  wwpLeosCfmExtDelayMsgMaxJitterThreshold OBJECT-TYPE
     SYNTAX       INTEGER  (-1..65535)
     MAX-ACCESS   read-create
     STATUS       current
     DESCRIPTION
              "Represents the threshold value for the maximum Jitter, specified
              in microseconds.  A value of -1 disables the generatation of faults,
              0 or greater will be compared to the maximum jitter result of the
              test and a fault will be generated if the threshold is exceeded."
     ::= { wwpLeosCfmExtDelayMsgEntry 45 }  
          
 
  --
  -- Frame Loss Measurement Msg table
  -- 
  wwpLeosCfmExtFrameLossMsgTable OBJECT-TYPE
     SYNTAX     SEQUENCE OF WwpLeosCfmExtFrameLossMsgEntry
     MAX-ACCESS not-accessible
     STATUS     current
     DESCRIPTION
            "The (conceptual) table listing the configuration 
            parameters for the FrameLossMeasurementMsg."  
     ::= { wwpLeosCfmExtFrameLoss 1 }
                
 wwpLeosCfmExtFrameLossMsgEntry OBJECT-TYPE
     SYNTAX      WwpLeosCfmExtFrameLossMsgEntry
     MAX-ACCESS  not-accessible
     STATUS      current
     DESCRIPTION
           "An entry (conceptual row) in the wwpLeosCfmFrameLossMsgTable.
           To send, clear or cancel the message, the corresponding MsgAction 
           needs to be specified. Individual objects in this table
           cannot be set.                                     
           RowStatus is a read-only field.
           To send or cancel a message, the TargetMepID or the 
           TargtetMacAddr objects need to be specified.
           Clear msgAction clears the counters for the message"
     --wwpLeosCfmExtFrameLossMsgLocalMEPId is a new index in place of framelossmsgportId
     INDEX {wwpLeosCfmServiceIndex, wwpLeosCfmExtFrameLossMsgLocalMEPId}
     ::= { wwpLeosCfmExtFrameLossMsgTable 1 }
                
 WwpLeosCfmExtFrameLossMsgEntry ::=  SEQUENCE { 
     wwpLeosCfmExtFrameLossMsgLocalMEPId                  	INTEGER,
     wwpLeosCfmExtFrameLossMsgTargetMEPID              Unsigned32,
     wwpLeosCfmExtFrameLossMsgTargetMacAddr            MacAddress,
     wwpLeosCfmExtFrameLossMsgCount                   	INTEGER,
     wwpLeosCfmExtFrameLossMsgPriority                	INTEGER,
     wwpLeosCfmExtFrameLossMsgRepeat					INTEGER,
     wwpLeosCfmExtFrameLossMsgRepeatCount				INTEGER,
     wwpLeosCfmExtFrameLossMsgFlnThreshold				INTEGER,
     wwpLeosCfmExtFrameLossMsgFlfThreshold				INTEGER,
     wwpLeosCfmExtFrameLossMsgAction					SendState,
     wwpLeosCfmExtFrameLossMsgSeqThreshold				INTEGER     
 
 }
  wwpLeosCfmExtFrameLossMsgLocalMEPId OBJECT-TYPE
     SYNTAX       INTEGER (1..65535)
     MAX-ACCESS   not-accessible
     STATUS       current
     DESCRIPTION
             "This object is used to specify the Local MEPID at teh source."
     ::= { wwpLeosCfmExtFrameLossMsgEntry 1 }
 
 wwpLeosCfmExtFrameLossMsgTargetMEPID OBJECT-TYPE
     SYNTAX       Unsigned32 (1..8191)
     MAX-ACCESS   read-create
     STATUS       current
     DESCRIPTION
             "This object is used to specify the MEPID.
              This object should only be set if wwpLeosCfmExtFrameLossMsgTargetMacAddr is not specified else 
              error will be returned."
     ::= { wwpLeosCfmExtFrameLossMsgEntry 2 }
     
 wwpLeosCfmExtFrameLossMsgTargetMacAddr OBJECT-TYPE
     SYNTAX       MacAddress
     MAX-ACCESS   read-create
     STATUS       current
     DESCRIPTION
             "This object is used to specify the MacAddress to be used when sending link LoopbackMsg.
              This object should only be set if wwpLeosCfmExtFrameLossMsgTargetMEPID is not specified else 
              error will be returned."
     ::= { wwpLeosCfmExtFrameLossMsgEntry 3 }
     
 wwpLeosCfmExtFrameLossMsgCount OBJECT-TYPE
     SYNTAX       INTEGER (2..600) 
     MAX-ACCESS   read-create
     STATUS       current
     DESCRIPTION
             "This object is used to specify the FrameLossMeasurementMsg count to be used
              when sending link FrameLossMeasurementMsg."
     ::= { wwpLeosCfmExtFrameLossMsgEntry 4 }
 
 wwpLeosCfmExtFrameLossMsgPriority OBJECT-TYPE
     SYNTAX       INTEGER (0..7)
     MAX-ACCESS   read-create
     STATUS       current
     DESCRIPTION
             "This object is used to specify the FrameLossMeasurementMsg priority to be
             used when sending link FrameLossMeasurementMsg."
     ::= { wwpLeosCfmExtFrameLossMsgEntry 5 }
 

  wwpLeosCfmExtFrameLossMsgRepeat OBJECT-TYPE
 	 SYNTAX			INTEGER {
 	 					enable(1),
 	 					disable(2)
 	 					}
 	 MAX-ACCESS		read-create
 	 STATUS			current
 	 DESCRIPTION
 	 		"Used to make the Frame Loss Measurement test a repeating test."
 	 ::= { wwpLeosCfmExtFrameLossMsgEntry 8 } 
 	 
 wwpLeosCfmExtFrameLossMsgRepeatCount OBJECT-TYPE
 	SYNTAX			INTEGER (0..1440)
 	MAX-ACCESS		read-create
 	STATUS			current
 	DESCRIPTION
 			"The repeat time in minutes for the Frame Loss Measurement test.
 			If zero is specified, the test runs continuously."
 	::= { wwpLeosCfmExtFrameLossMsgEntry 9 } 
 	
  wwpLeosCfmExtFrameLossMsgFlnThreshold OBJECT-TYPE
 	SYNTAX			INTEGER (-1..600)
 	MAX-ACCESS		read-create
 	STATUS			current
 	DESCRIPTION
 			"The fault threshold for the Frame Loss Measurement test.
 			A value of -1 disables the generate of faults, 0 or greater
 			will be compared to the frame loss near result of the
 			test and a fault will be generated if the threshold is exceeded."
 	::= { wwpLeosCfmExtFrameLossMsgEntry 10 }
 
 wwpLeosCfmExtFrameLossMsgFlfThreshold OBJECT-TYPE
 	SYNTAX			INTEGER (-1..600)
 	MAX-ACCESS		read-create
 	STATUS			current
 	DESCRIPTION
 			"The fault threshold for the Frame Loss Measurement test.
 			A value of -1 disables the generate of faults, 0 or greater
 			will be compared to the frame loss far result of the
 			test and a fault will be generated if the threshold is exceeded."
 	::= { wwpLeosCfmExtFrameLossMsgEntry 11 }   
 
  
 wwpLeosCfmExtFrameLossMsgAction OBJECT-TYPE
     SYNTAX       SendState
     MAX-ACCESS   read-create
     STATUS       current
     DESCRIPTION
             "This object represents the action for the message (send, clear or cancel)
             This object represents the action for the message (send, clear or cancel)
             If set to send(1) and if wwpLeosCfmExtFrameLossMacAddr is specified 
             then FrameLoss is sent to remote Mac.
             If set to send(1) and if wwpLeosCfmExtFrameLossMsgTargetMEPID is specified 
             then FrameLossMsg is sent to remote mepid.
             If set to clear(2) will clear mep statistics for given service and mepid.
             If set to cancel(3) and if wwpLeosCfmExtFrameLossMsgTargetMacAddr is specified 
             then it will cancel sending FrameLoss Messages to remoteMac.
             If set to cancel(3) and if wwpLeosCfmExtFrameLossMsgTargetMEPID is specified 
             then it will cancel sending FrameLoss messages to remoteMEPID."
     ::= { wwpLeosCfmExtFrameLossMsgEntry 12 }  
  
 wwpLeosCfmExtFrameLossMsgSeqThreshold	OBJECT-TYPE
 	SYNTAX			INTEGER (-1..600)
 	MAX-ACCESS		read-create
 	STATUS			current
 	DESCRIPTION
 			"The sequence threshold for the Frame Loss Measurement test.
 			A value of -1 disables the generate of faults, 0 or greater
 			will be compared to the frame loss far result of the
 			test and a fault will be generated if the threshold is exceeded."
 	::= { wwpLeosCfmExtFrameLossMsgEntry 13 }   

 
 --
  --  CFM EXT Port Stack Table
  --                                   
 wwpLeosCfmExtInterfaceStackTable OBJECT-TYPE
     SYNTAX     SEQUENCE OF WwpLeosCfmExtInterfaceStackEntry
     MAX-ACCESS not-accessible
     STATUS     current
     DESCRIPTION
            "The (conceptual) table listing the display 
             parameters for the CFM port stack table."  
     ::= { wwpLeosCfmExtInterfaceStack 1 }
                
 wwpLeosCfmExtInterfaceStackEntry OBJECT-TYPE
     SYNTAX      WwpLeosCfmExtInterfaceStackEntry
     MAX-ACCESS  not-accessible
     STATUS      current
     DESCRIPTION
           "An entry (conceptual row) in the wwpLeosTceCfmPortStackTable."
     INDEX {wwpLeosCfmExtInterfaceStackServiceInstanceType,
            wwpLeosCfmExtInterfaceStackServiceInstanceIndex,
            wwpLeosCfmExtInterfaceStackInterfaceType,
            wwpLeosCfmExtInterfaceStackInterfaceIndex,                        
            wwpLeosCfmExtInterfaceStackStackType,
            wwpLeosCfmExtInterfaceStackLevel            
            }
     ::= { wwpLeosCfmExtInterfaceStackTable 1 }
                
 WwpLeosCfmExtInterfaceStackEntry ::=  SEQUENCE {
  wwpLeosCfmExtInterfaceStackServiceInstanceType           INTEGER,
  wwpLeosCfmExtInterfaceStackServiceInstanceIndex          Unsigned32,
  wwpLeosCfmExtInterfaceStackInterfaceType                 INTEGER,
  wwpLeosCfmExtInterfaceStackInterfaceIndex                Unsigned32,
  wwpLeosCfmExtInterfaceStackLevel                         Unsigned32,
  wwpLeosCfmExtInterfaceStackStackType                     INTEGER,
  wwpLeosCfmExtInterfaceStackInterfaceName                 DisplayString,
  wwpLeosCfmExtInterfaceStackServiceInstanceName           DisplayString,    
  wwpLeosCfmExtInterfaceStackPortName                      DisplayString,
  wwpLeosCfmExtInterfaceStackOperState                     INTEGER, 
  wwpLeosCfmExtInterfaceStackVid                           INTEGER,
  wwpLeosCfmExtInterfaceStackPgid                          Unsigned32,
  wwpLeosCfmExtInterfaceStackMEPId                         INTEGER,
  wwpLeosCfmExtInterfaceStackMacAddress                    MacAddress
  }                           

 wwpLeosCfmExtInterfaceStackServiceInstanceType OBJECT-TYPE
     SYNTAX      INTEGER  {
                           ethVs(1),
                           vlan(2),
                           pbtTunnel(3)                                 
     }
     MAX-ACCESS  not-accessible
     STATUS      current
     DESCRIPTION
             "This object is used to specify the CFM port service type."
     ::= { wwpLeosCfmExtInterfaceStackEntry 1 }
 
 wwpLeosCfmExtInterfaceStackServiceInstanceIndex OBJECT-TYPE
     SYNTAX      Unsigned32 (1..65535) 
     MAX-ACCESS  not-accessible
     STATUS      current
     DESCRIPTION
             "A unique identifier for CFM domain entry."
     ::= { wwpLeosCfmExtInterfaceStackEntry 2 }


 wwpLeosCfmExtInterfaceStackInterfaceType OBJECT-TYPE
     SYNTAX      INTEGER  {
                                logicalPort(1),
                                pbtEncap(2),
                                pbtDecap(3),
                                none(99)
     }
     MAX-ACCESS  not-accessible
     STATUS      current
     DESCRIPTION
             "This object is used to specify the CFM interface type."
     ::= { wwpLeosCfmExtInterfaceStackEntry 3 }

 wwpLeosCfmExtInterfaceStackInterfaceIndex  OBJECT-TYPE
     SYNTAX      Unsigned32
     MAX-ACCESS  not-accessible
     STATUS      current
     DESCRIPTION
             "This object is used to specify the CFM sub port index."
     ::= { wwpLeosCfmExtInterfaceStackEntry 4 }
 
 wwpLeosCfmExtInterfaceStackLevel   OBJECT-TYPE
     SYNTAX      Unsigned32     (0..7)
     MAX-ACCESS  not-accessible
     STATUS      current
     DESCRIPTION
             "This object is used to specify the CFM interface level."
     ::= { wwpLeosCfmExtInterfaceStackEntry 5 }
 
 wwpLeosCfmExtInterfaceStackStackType    OBJECT-TYPE
     SYNTAX      INTEGER        {
                                        mepUp(1),
                                        mepDown(2),
                                        mipUp(3),
                                        mipDown(4)
     }
     MAX-ACCESS  not-accessible
     STATUS      current
     DESCRIPTION
             "This object is used to specify the CFM interface type."
     ::= { wwpLeosCfmExtInterfaceStackEntry 6 }
 
 wwpLeosCfmExtInterfaceStackInterfaceName    OBJECT-TYPE
     SYNTAX      DisplayString (SIZE(0..31))
     MAX-ACCESS  read-only
     STATUS      current
     DESCRIPTION
             "This object is used to specify the CFM interface name."
     ::= { wwpLeosCfmExtInterfaceStackEntry 7 }

 wwpLeosCfmExtInterfaceStackServiceInstanceName    OBJECT-TYPE
     SYNTAX      DisplayString (SIZE(0..31))
     MAX-ACCESS  read-only
     STATUS      current
     DESCRIPTION
             "This object is used to specify the CFM interface name."
     ::= { wwpLeosCfmExtInterfaceStackEntry 8 }
 
 wwpLeosCfmExtInterfaceStackPortName    OBJECT-TYPE
     SYNTAX      DisplayString (SIZE(0..31))
     MAX-ACCESS  read-only
     STATUS      current
     DESCRIPTION
             "This object is used to specify the CFM interface port name."
     ::= { wwpLeosCfmExtInterfaceStackEntry 9 }
 
 wwpLeosCfmExtInterfaceStackOperState    OBJECT-TYPE
     SYNTAX      INTEGER        {
                                        up(1),
                                        down(2)
     }
     MAX-ACCESS  read-only
     STATUS      current
     DESCRIPTION
             "This object is used to specify the CFM interface oper state."
     ::= { wwpLeosCfmExtInterfaceStackEntry 10 }
 
 wwpLeosCfmExtInterfaceStackVid    OBJECT-TYPE
     SYNTAX      INTEGER (0..4094)
     MAX-ACCESS  read-only
     STATUS      current
     DESCRIPTION
             "This object is used to specify the CFM interface vid."
     ::= { wwpLeosCfmExtInterfaceStackEntry 11 }
 
 wwpLeosCfmExtInterfaceStackPgid     OBJECT-TYPE
     SYNTAX      Unsigned32
     MAX-ACCESS  read-only
     STATUS      current
     DESCRIPTION
             "This object is used to specify the CFM interface pgid."
     ::= { wwpLeosCfmExtInterfaceStackEntry 12 }

 wwpLeosCfmExtInterfaceStackMEPId      OBJECT-TYPE
     SYNTAX      INTEGER  (1..8191)
     MAX-ACCESS  read-only
     STATUS      current
     DESCRIPTION
             "This object is used to specify the CFM interface mepid."
     ::= { wwpLeosCfmExtInterfaceStackEntry 13 }
 
 wwpLeosCfmExtInterfaceStackMacAddress      OBJECT-TYPE
     SYNTAX      MacAddress
     MAX-ACCESS  read-only
     STATUS      current
     DESCRIPTION
             "This object is used to specify the CFM interface macaddress."
     ::= { wwpLeosCfmExtInterfaceStackEntry 14 }                           

 --
 -- CFM EXT MIP Table
 --                          
 wwpLeosCfmExtMipTable OBJECT-TYPE
     SYNTAX     SEQUENCE OF WwpLeosCfmExtMipEntry
     MAX-ACCESS not-accessible
     STATUS     current
     DESCRIPTION
            "The (conceptual) table listing the configuration 
            parameters for the CFM Ext MIP Table. 
            This table is not applicable if wwpLeosCfmServiceType is set to pbtTunnel. 
            Any Get/Set/Walk will return error."  
     ::= { wwpLeosCfmExtMIP 1 }
                
 wwpLeosCfmExtMipEntry OBJECT-TYPE
     SYNTAX      WwpLeosCfmExtMipEntry
     MAX-ACCESS  not-accessible
     STATUS      current
     DESCRIPTION
           "An entry (conceptual row) in the wwpLeosCfmExtMipTable."
     INDEX {wwpLeosCfmExtMipVid, wwpLeosCfmExtMipPort, wwpLeosCfmExtMipLevel}
     ::= { wwpLeosCfmExtMipTable 1 }
                
 WwpLeosCfmExtMipEntry ::=  SEQUENCE { 
     wwpLeosCfmExtMipVid                        INTEGER,
     wwpLeosCfmExtMipPort                       INTEGER,
     wwpLeosCfmExtMipLevel                      INTEGER,
     wwpLeosCfmExtMipStatus                     RowStatus
 }

 wwpLeosCfmExtMipVid OBJECT-TYPE
     SYNTAX      INTEGER (0..24576)
     MAX-ACCESS  not-accessible
     STATUS      current
     DESCRIPTION
             "This object is used as index in the table and is used to specify the 
              VLAN service type for which intermediate maintenance points can be created."
     ::= { wwpLeosCfmExtMipEntry 1 }
 
 wwpLeosCfmExtMipPort OBJECT-TYPE
     SYNTAX      INTEGER (1..65535)
     MAX-ACCESS  not-accessible
     STATUS      current
     DESCRIPTION
             "This object is used as index in the table and is used to specify the 
              port."
     ::= { wwpLeosCfmExtMipEntry 2 }
                    
 wwpLeosCfmExtMipLevel OBJECT-TYPE
     SYNTAX       INTEGER (0..7)
     MAX-ACCESS   not-accessible
     STATUS       current
     DESCRIPTION
             "The level attribute."
     ::= { wwpLeosCfmExtMipEntry 3 }

 wwpLeosCfmExtMipStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set it to 'destroy'."
     ::= { wwpLeosCfmExtMipEntry 4 }

 --
 -- CFM EXT Interface MIP Table
 --                          
 wwpLeosCfmExtInterfaceMipTable OBJECT-TYPE
     SYNTAX     SEQUENCE OF WwpLeosCfmExtInterfaceMipEntry
     MAX-ACCESS not-accessible
     STATUS     current
     DESCRIPTION
            "The (conceptual) table listing the configuration 
            parameters for the CFM Ext MIP SI Table."
     ::= { wwpLeosCfmExtInterfaceMIP 1 }
                
 wwpLeosCfmExtInterfaceMipEntry OBJECT-TYPE
     SYNTAX      WwpLeosCfmExtInterfaceMipEntry
     MAX-ACCESS  not-accessible
     STATUS      current
     DESCRIPTION
           "An entry (conceptual row) in the wwpLeosCfmExtInterfaceMipTable."
     INDEX {wwpLeosCfmExtInterfaceMipServiceInstanceType,
            wwpLeosCfmExtInterfaceMipServiceInstanceIndex,
            wwpLeosCfmExtInterfaceMipInterfaceType,
            wwpLeosCfmExtInterfaceMipInterfaceIndex,
            wwpLeosCfmExtInterfaceMipInterfaceSubIndex,
            wwpLeosCfmExtInterfaceMipLevel}
     ::= { wwpLeosCfmExtInterfaceMipTable 1 }
                
 WwpLeosCfmExtInterfaceMipEntry ::=  SEQUENCE { 
     wwpLeosCfmExtInterfaceMipServiceInstanceType   INTEGER,
     wwpLeosCfmExtInterfaceMipServiceInstanceIndex  Unsigned32,
     wwpLeosCfmExtInterfaceMipInterfaceType         INTEGER,
     wwpLeosCfmExtInterfaceMipInterfaceIndex        Unsigned32,
     wwpLeosCfmExtInterfaceMipInterfaceSubIndex     Unsigned32,
     wwpLeosCfmExtInterfaceMipLevel                 INTEGER,
     wwpLeosCfmExtInterfaceMipStatus                RowStatus
 }

 wwpLeosCfmExtInterfaceMipServiceInstanceType OBJECT-TYPE
     SYNTAX      INTEGER  {
                           ethVs(1),
                           vlan(2),
                           pbtTunnel(3)                                 
     }
     MAX-ACCESS  not-accessible
     STATUS      current
     DESCRIPTION
             "This object is used to specify the service instance type.
              Interpretation of wwpLeosCfmExtInterfaceMipServiceInstanceIndex depends on the value of this MIB object."
     ::= { wwpLeosCfmExtInterfaceMipEntry 1 }
 
 wwpLeosCfmExtInterfaceMipServiceInstanceIndex OBJECT-TYPE
     SYNTAX      Unsigned32 (1..65535) 
     MAX-ACCESS  not-accessible
     STATUS      current
     DESCRIPTION
             "This object is used to specify the service instance index.
              Interpretation of this object depends on the value of wwpLeosCfmExtInterfaceMipServiceInstanceType."
     ::= { wwpLeosCfmExtInterfaceMipEntry 2 }

 wwpLeosCfmExtInterfaceMipInterfaceType OBJECT-TYPE
     SYNTAX      INTEGER  {
                                none(0),
                                portVlan(1),
                                pbtEncap(2),
                                pbtDecap(3)
     }
     MAX-ACCESS  not-accessible
     STATUS      current
     DESCRIPTION
             "This object is used to specify the CFM interface type."
     ::= { wwpLeosCfmExtInterfaceMipEntry 3 }

 wwpLeosCfmExtInterfaceMipInterfaceIndex  OBJECT-TYPE
     SYNTAX      Unsigned32
     MAX-ACCESS  not-accessible
     STATUS      current
     DESCRIPTION
             "This object is used to specify an interface index.
              When the value of object wwpLeosCfmExtInterfaceMipInterfaceType
              is portVlan this obect refers to a port."
     ::= { wwpLeosCfmExtInterfaceMipEntry 4 }

 wwpLeosCfmExtInterfaceMipInterfaceSubIndex  OBJECT-TYPE
     SYNTAX      Unsigned32
     MAX-ACCESS  not-accessible
     STATUS      current
     DESCRIPTION
             "This object is used to specify a sub interface index.
              When the value of object wwpLeosCfmExtInterfaceMipInterfaceType
              is portVlan this obect refers to a vlan."
     ::= { wwpLeosCfmExtInterfaceMipEntry 5 }                    

 wwpLeosCfmExtInterfaceMipLevel OBJECT-TYPE
     SYNTAX       INTEGER (0..7)
     MAX-ACCESS   not-accessible
     STATUS       current
     DESCRIPTION
             "The level attribute."
     ::= { wwpLeosCfmExtInterfaceMipEntry 6 }

 wwpLeosCfmExtInterfaceMipStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set it to 'destroy'."
     ::= { wwpLeosCfmExtInterfaceMipEntry 7 }

  --
  --  CFM OAM Port Table
  --                                   
 wwpLeosCfmExtOamPortTable OBJECT-TYPE
     SYNTAX     SEQUENCE OF WwpLeosCfmExtOamPortEntry
     MAX-ACCESS not-accessible
     STATUS     current
     DESCRIPTION
            "The (conceptual) table listing  if a port is OAM capable. "    
     ::= { wwpLeosCfmExtOamPort 1 }
                
 wwpLeosCfmExtOamPortEntry OBJECT-TYPE
     SYNTAX      WwpLeosCfmExtOamPortEntry
     MAX-ACCESS  not-accessible
     STATUS      current
     DESCRIPTION
           "An entry (conceptual row) in the wwpLeosCfmExtOamPortTable."
     INDEX {wwpLeosCfmExtOamPortIndex }
     ::= { wwpLeosCfmExtOamPortTable 1 }
                
 WwpLeosCfmExtOamPortEntry ::=  SEQUENCE {
  wwpLeosCfmExtOamPortIndex           Integer32,
  wwpLeosCfmExtOamPortSupported       TruthValue
  }                           

 wwpLeosCfmExtOamPortIndex OBJECT-TYPE
     SYNTAX      Integer32  (1..3072)
     MAX-ACCESS  not-accessible
     STATUS      current
     DESCRIPTION
             "Specifies the port index."
     ::= { wwpLeosCfmExtOamPortEntry 1 }
 
 wwpLeosCfmExtOamPortSupported OBJECT-TYPE
     SYNTAX      TruthValue 
     MAX-ACCESS  read-only
     STATUS      current
     DESCRIPTION
             "Specifies if the port is OAM capable."
     ::= { wwpLeosCfmExtOamPortEntry 2 }

  
 --
 -- TCE CFM 
 --
 wwpLeosTceCfmMIBObj       OBJECT IDENTIFIER ::= { wwpLeosCfmMIBObjects 20 } 
 wwpLeosTceCfmMIP          OBJECT IDENTIFIER ::= { wwpLeosTceCfmMIBObj 1 }        
 wwpLeosTceCfmLoopback     OBJECT IDENTIFIER ::= { wwpLeosTceCfmMIBObj 3 }
 wwpLeosTceCfmStack        OBJECT IDENTIFIER ::= { wwpLeosTceCfmMIBObj 5 } 
 wwpLeosTceCfmMEP          OBJECT IDENTIFIER ::=  { wwpLeosTceCfmMIBObj 7}
 wwpLeosTceCfmDelay		   OBJECT IDENTIFIER ::=  { wwpLeosTceCfmMIBObj 12}
 wwpLeosTceCfmFrameLoss    OBJECT IDENTIFIER ::=  { wwpLeosTceCfmMIBObj 13}
 wwpLeosTceCfmMipCCMDb     OBJECT IDENTIFIER ::= { wwpLeosTceCfmMIBObj 14 } 
  
 --
 -- TCE CFM MIP Table
 --
 wwpLeosTceCfmMipTable OBJECT-TYPE
     SYNTAX     SEQUENCE OF WwpLeosTceCfmMipEntry
     MAX-ACCESS not-accessible
     STATUS     current
     DESCRIPTION
            "The (conceptual) table listing the config 
            parameters for the CFM MIP Table. This table is not applicable 
            if wwpLeosTceCfmServiceType is set to pbtTunnel. 
            Any Get/Set/Walk will return error.
            Not applicable to 6.x"  
     ::= { wwpLeosTceCfmMIP 1 }
                
 wwpLeosTceCfmMipEntry OBJECT-TYPE
     SYNTAX      WwpLeosTceCfmMipEntry
     MAX-ACCESS  not-accessible
     STATUS      current
     DESCRIPTION
           "An entry (conceptual row) in the wwpLeosTceCfmMipTable."
    INDEX {wwpLeosTceCfmMipLiType, wwpLeosTceCfmMipLiIndex}
     ::= { wwpLeosTceCfmMipTable 1 }
                
 WwpLeosTceCfmMipEntry ::=  SEQUENCE { 
     wwpLeosTceCfmMipLiType              INTEGER,
     wwpLeosTceCfmMipLiIndex             INTEGER,
     wwpLeosTceCfmMipPgid                Unsigned32,
     wwpLeosTceCfmMipBayIndex            Unsigned32,
     wwpLeosTceCfmMipShelfIndex          Unsigned32,
     wwpLeosTceCfmMipModuleIndex         Unsigned32,
     wwpLeosTceCfmMipMacAddr             MacAddress,
     wwpLeosTceCfmMipLevel               INTEGER,
     wwpLeosTceCfmMipStatus              RowStatus,
     wwpLeosTceCfmMipLiName				 DisplayString
 }

 wwpLeosTceCfmMipLiType OBJECT-TYPE
     SYNTAX          INTEGER {
                      subPort(1),
 	 				  pbtService(2), 
	 				  mplsStaticPeMeshVC(3),
					  mplsDynamicPeMeshVC(4),
					  mplsStaticPeSpokeVC(5), 
					  mplsDynamicPeSpokeVC(6),
					  mplsStaticMtuSpokeVC(7),
					  mplsDynamicMtuSpokeVC(8),
					  none(99)
                     }
      MAX-ACCESS    not-accessible
      STATUS        current
      DESCRIPTION
	      "This object specifies an unique index into the table."
      ::= { wwpLeosTceCfmMipEntry 1 }

 wwpLeosTceCfmMipLiIndex OBJECT-TYPE
      SYNTAX        INTEGER (1..65535)
      MAX-ACCESS    not-accessible
      STATUS        current
      DESCRIPTION
	      "This object specifies an unique index into the table."
      ::= { wwpLeosTceCfmMipEntry 2 }
                                                            
 wwpLeosTceCfmMipPgid OBJECT-TYPE
     SYNTAX      Unsigned32
     MAX-ACCESS  read-only
     STATUS      current
     DESCRIPTION
             "This object is used to specify the port group id."
     ::= { wwpLeosTceCfmMipEntry 3 }
  
 wwpLeosTceCfmMipBayIndex          OBJECT-TYPE
     SYNTAX          Unsigned32 (1..1)
     MAX-ACCESS      read-only
     STATUS          current
     DESCRIPTION
           "This object is used to specify the chassis bay."               
     ::= { wwpLeosTceCfmMipEntry 4 }
     
 wwpLeosTceCfmMipShelfIndex          OBJECT-TYPE
     SYNTAX          Unsigned32 (1..1)
     MAX-ACCESS      read-only
     STATUS          current
     DESCRIPTION
           "This object is used to specify the chassis shelf."               
     ::= { wwpLeosTceCfmMipEntry 5 }                  

 wwpLeosTceCfmMipModuleIndex OBJECT-TYPE
     SYNTAX      Unsigned32 (1..7 | 255)
     MAX-ACCESS  read-only
     STATUS      current
     DESCRIPTION
             "This object is used to specify the chassis module."
     ::= { wwpLeosTceCfmMipEntry 6 }
                    
 wwpLeosTceCfmMipMacAddr OBJECT-TYPE
     SYNTAX      MacAddress
     MAX-ACCESS  read-only
     STATUS      current
     DESCRIPTION
             "This object is used to specify the Mac Address."
     ::= { wwpLeosTceCfmMipEntry 7 }
                    
 wwpLeosTceCfmMipLevel OBJECT-TYPE
     SYNTAX       INTEGER (0..7)
     MAX-ACCESS   read-create
     STATUS       current
     DESCRIPTION
             "This object is used to specify the level attribute."
     ::= { wwpLeosTceCfmMipEntry 8 }

 wwpLeosTceCfmMipStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set it to 'destroy'."
     ::= { wwpLeosTceCfmMipEntry 9 } 
 
 wwpLeosTceCfmMipLiName   OBJECT-TYPE
     SYNTAX       DisplayString
     MAX-ACCESS   read-only
     STATUS       current
     DESCRIPTION
             "Logical interface name associated with the Mip."
     ::= { wwpLeosTceCfmMipEntry 10 } 
  
  --
  --  CFM Mip CCM Db Table
  --                                   
 wwpLeosTceCfmMipCCMDbTable OBJECT-TYPE
     SYNTAX     SEQUENCE OF WwpLeosTceCfmMipCCMDbEntry
     MAX-ACCESS not-accessible
     STATUS     current
     DESCRIPTION
            "The (conceptual) table listing the display 
             parameters for the MIP CCM Db table.
             Not applicable to 6.x"  
     ::= { wwpLeosTceCfmMipCCMDb 1 }
                
 wwpLeosTceCfmMipCCMDbEntry OBJECT-TYPE
     SYNTAX      WwpLeosTceCfmMipCCMDbEntry
     MAX-ACCESS  not-accessible
     STATUS      current
     DESCRIPTION
           "An entry (conceptual row) in the wwpLeosCfmMipCCMDbTable."
     INDEX { wwpLeosTceCfmMipCCMDbIndex }
     ::= { wwpLeosTceCfmMipCCMDbTable 1 }
                
 WwpLeosTceCfmMipCCMDbEntry ::=  SEQUENCE { 
    wwpLeosTceCfmMipCCMDbIndex							 Unsigned32,                     
	wwpLeosTceCfmMipCCMDbMacAddr                         MacAddress,
	wwpLeosTceCfmMipCCMDbServiceName					 DisplayString,
	wwpLeosTceCfmMipCCMDbSubPortName                     DisplayString,
	wwpLeosTceCfmMipCCMdbNumCCMRx                        Counter32,
	wwpLeosTceCfmMipCCMDbCCMRxTime                       Unsigned32,
	wwpLeosTceCfmMipCCMDbLevel							 INTEGER,
	wwpLeosTceCfmMipCCMDbMEPID							 INTEGER,
	wwpLeosTceCfmMipRDI									 INTEGER,
	wwpLeosTceCfmMipLastPortStatus						 INTEGER  	
  }
  
  wwpLeosTceCfmMipCCMDbIndex   OBJECT-TYPE
  	SYNTAX Unsigned32 
  	MAX-ACCESS not-accessible
  	STATUS current
  	DESCRIPTION "Mip CCM database index."
  	::= {   wwpLeosTceCfmMipCCMDbEntry 1 } 
  	
  wwpLeosTceCfmMipCCMDbMacAddr OBJECT-TYPE
  	SYNTAX MacAddress
  	MAX-ACCESS read-only
  	STATUS current
  	DESCRIPTION "MAC Address"
  	::= {   wwpLeosTceCfmMipCCMDbEntry 2 } 
  
  wwpLeosTceCfmMipCCMDbServiceName  OBJECT-TYPE
  	SYNTAX DisplayString
  	MAX-ACCESS read-only
  	STATUS current
  	DESCRIPTION "Service Name"
  	::= {   wwpLeosTceCfmMipCCMDbEntry 3 } 
  
   wwpLeosTceCfmMipCCMDbSubPortName OBJECT-TYPE
   	 SYNTAX DisplayString
   	 MAX-ACCESS read-only
   	 STATUS current
   	 DESCRIPTION "SubPort Name"
   	 ::= { wwpLeosTceCfmMipCCMDbEntry 4 }
   
   wwpLeosTceCfmMipCCMdbNumCCMRx OBJECT-TYPE
   	SYNTAX Counter32
   	MAX-ACCESS read-only
   	STATUS current 
   	DESCRIPTION "Total Received CCMs"
   	::= {  wwpLeosTceCfmMipCCMDbEntry 5 }
   
   wwpLeosTceCfmMipCCMDbCCMRxTime OBJECT-TYPE
   	 SYNTAX Unsigned32
   	 MAX-ACCESS read-only
   	 STATUS current
   	 DESCRIPTION "CCM Rx Time in ms"
   ::= {  wwpLeosTceCfmMipCCMDbEntry 6 }
  
   wwpLeosTceCfmMipCCMDbLevel OBJECT-TYPE
   	SYNTAX INTEGER  (0..7)
   	MAX-ACCESS read-only
   	STATUS current
   	DESCRIPTION "Level"                      
   	::= {  wwpLeosTceCfmMipCCMDbEntry 7}
   
   
   wwpLeosTceCfmMipCCMDbMEPID OBJECT-TYPE
   	SYNTAX INTEGER  (1..8191)
   	MAX-ACCESS read-only
   	STATUS current
   	DESCRIPTION "Mep Id"                      
   	::= {  wwpLeosTceCfmMipCCMDbEntry 8}
   
   wwpLeosTceCfmMipRDI OBJECT-TYPE
   	 SYNTAX INTEGER {
   	 			on(1),
   	 			off(2)
   	 		}
   	 MAX-ACCESS read-only
   	 STATUS current
   	 DESCRIPTION "RDI"
   ::= { wwpLeosTceCfmMipCCMDbEntry  9 }
  
  wwpLeosTceCfmMipLastPortStatus OBJECT-TYPE
  	SYNTAX  INTEGER {
  			  blocked(1),
  			  up(2),
  			  none(99)
  			 }
    MAX-ACCESS read-only
    STATUS current
    DESCRIPTION "Last Port Status"
  ::= {wwpLeosTceCfmMipCCMDbEntry 10 }
   
  
  --
  -- TCE Loopback Msg table
  -- 
  wwpLeosTceCfmLoopbackMsgTable OBJECT-TYPE
     SYNTAX     SEQUENCE OF WwpLeosTceCfmLoopbackMsgEntry
     MAX-ACCESS not-accessible
     STATUS     current
     DESCRIPTION
            "The (conceptual) table listing the config parameters for the LoopbackMsg.
             The following attributes are required to create a LoopbackMsg:
             -- wwpLeosCfmServiceIndex
             -- wwpLeosTceCfmLoopbackMsgSubPortIndex
             -- wwpLeosTceCfmLoopbackMsgTargetMEPID or
             -- wwpLeosTceCfmLoopbackMsgTargetMacAddr
             -- wwpLeosTceCfmLoopbackMsgCount
             -- wwpLeosTceCfmLoopbackMsgData
             -- wwpLeosTceCfmLoopbackMsgPriority
             -- wwpLeosTceCfmLoopbackMsgRowStatus
            Not applicable to 6.x"  
     ::= { wwpLeosTceCfmLoopback 1 }
                
 wwpLeosTceCfmLoopbackMsgEntry OBJECT-TYPE
     SYNTAX      WwpLeosTceCfmLoopbackMsgEntry
     MAX-ACCESS  not-accessible
     STATUS      current
     DESCRIPTION
           "An entry (conceptual row) in the wwpLeosTceCfmLoopbackMsgTable."
     INDEX {wwpLeosCfmServiceIndex, wwpLeosTceCfmLoopbackMsgLocalMEPID}
     ::= { wwpLeosTceCfmLoopbackMsgTable 1 }
                
 WwpLeosTceCfmLoopbackMsgEntry ::=  SEQUENCE { 
     wwpLeosTceCfmLoopbackMsgLocalMEPID              Unsigned32,
     wwpLeosTceCfmLoopbackMsgTargetMEPID             Unsigned32,
     wwpLeosTceCfmLoopbackMsgTargetMacAddr           MacAddress,
     wwpLeosTceCfmLoopbackMsgCount                   INTEGER,
     wwpLeosTceCfmLoopbackMsgData                    DisplayString,
     wwpLeosTceCfmLoopbackMsgPriority                INTEGER,
     wwpLeosTceCfmLoopbackMsgServiceName             DisplayString,
     wwpLeosTceCfmLoopbackMsgSubPortName             DisplayString,
     wwpLeosTceCfmLoopbackMsgNextLbmTransId          Unsigned32,
     wwpLeosTceCfmLoopbackMsgTotalTxLbm              Unsigned32,
     wwpLeosTceCfmLoopbackMsgTotalRxLbrIo            Unsigned32,
     wwpLeosTceCfmLoopbackMsgTotalRxLbrOoo           Unsigned32,
     wwpLeosTceCfmLoopbackMsgRowStatus               RowStatus,
     wwpLeosTceCfmLoopbackMsgTotalRxLbrContentMismatch Unsigned32,
     wwpLeosTceCfmLoopbackMsgTotalRxLbrUnexpected      Unsigned32
 }

 wwpLeosTceCfmLoopbackMsgLocalMEPID OBJECT-TYPE
     SYNTAX       Unsigned32 (1..8191)
     MAX-ACCESS   not-accessible
     STATUS       current
     DESCRIPTION
             "This object is used to specify the port."
     ::= { wwpLeosTceCfmLoopbackMsgEntry 1 }
 
 wwpLeosTceCfmLoopbackMsgTargetMEPID OBJECT-TYPE
     SYNTAX       Unsigned32 (1..8191)
     MAX-ACCESS   read-create
     STATUS       current
     DESCRIPTION
             "This object is used to specify the MEPID.
              This object should only be set if wwpLeosTceCfmLoopbackMsgTargetMacAddr 
              is not specified else error will be returned."
     ::= { wwpLeosTceCfmLoopbackMsgEntry 2 }
     
 wwpLeosTceCfmLoopbackMsgTargetMacAddr OBJECT-TYPE
     SYNTAX       MacAddress
     MAX-ACCESS   read-create
     STATUS       current
     DESCRIPTION
             "This object is used to specify the MacAddress to be used when sending 
              link LoopbackMsg. This object should only be set if 
              wwpLeosTceCfmLoopbackMsgTargetMEPID is not specified else error will 
              be returned."
     ::= { wwpLeosTceCfmLoopbackMsgEntry 3 }
     
 wwpLeosTceCfmLoopbackMsgCount OBJECT-TYPE
     SYNTAX       INTEGER (1..20) 
     MAX-ACCESS   read-create
     STATUS       current
     DESCRIPTION
             "This object is used to specify the LoopbackMsg count to be used when 
              sending link LoopbackMsg. "
     ::= { wwpLeosTceCfmLoopbackMsgEntry 4 }
 
 wwpLeosTceCfmLoopbackMsgData OBJECT-TYPE
     SYNTAX       DisplayString  (SIZE(1..127))
     MAX-ACCESS   read-create
     STATUS       current
     DESCRIPTION                    
             "This object is used to specify the LoopbackMsg data to be used when 
              sending link LoopbackMsg. "
     ::= { wwpLeosTceCfmLoopbackMsgEntry 5 }

 wwpLeosTceCfmLoopbackMsgPriority OBJECT-TYPE
     SYNTAX       INTEGER (0..7)
     MAX-ACCESS   read-create
     STATUS       current
     DESCRIPTION
             "This object is used to specify the LoopbackMsg priority to be used when 
              sending link LoopbackMsg. "
     ::= { wwpLeosTceCfmLoopbackMsgEntry 6 }

 wwpLeosTceCfmLoopbackMsgServiceName OBJECT-TYPE
     SYNTAX       DisplayString (SIZE(1..31))
     MAX-ACCESS   read-only
     STATUS       current
     DESCRIPTION
             "This object is used to specify the Service used when 
              sending link LoopbackMsg."
     ::= { wwpLeosTceCfmLoopbackMsgEntry 7 }        

 wwpLeosTceCfmLoopbackMsgSubPortName OBJECT-TYPE
     SYNTAX       DisplayString (SIZE(1..31))
     MAX-ACCESS   read-only
     STATUS       current
     DESCRIPTION
             "This object is used to specify the sub-port used when 
              sending link LoopbackMsg."
     ::= { wwpLeosTceCfmLoopbackMsgEntry 8 }        

 wwpLeosTceCfmLoopbackMsgNextLbmTransId OBJECT-TYPE
     SYNTAX       Unsigned32
     MAX-ACCESS   read-only
     STATUS       current
     DESCRIPTION
             "This object is used to specify next LoopbackMsg transaction id."
     ::= { wwpLeosTceCfmLoopbackMsgEntry 9 }
     
 wwpLeosTceCfmLoopbackMsgTotalTxLbm OBJECT-TYPE
     SYNTAX       Unsigned32
     MAX-ACCESS   read-only
     STATUS       current
     DESCRIPTION
             "This object is used to specify total LoopbackMsg sent."
     ::= { wwpLeosTceCfmLoopbackMsgEntry 10 }
     
 wwpLeosTceCfmLoopbackMsgTotalRxLbrIo OBJECT-TYPE
     SYNTAX       Unsigned32
     MAX-ACCESS   read-only
     STATUS       current
     DESCRIPTION
             "This object is used to specify total in-order LoopbackMsg received."
     ::= { wwpLeosTceCfmLoopbackMsgEntry 11 }
     
 wwpLeosTceCfmLoopbackMsgTotalRxLbrOoo OBJECT-TYPE
     SYNTAX       Unsigned32
     MAX-ACCESS   read-only
     STATUS       current
     DESCRIPTION
             "This object is used to specify total out of order LoopbackMsg received."
     ::= { wwpLeosTceCfmLoopbackMsgEntry 12 }
 
 wwpLeosTceCfmLoopbackMsgRowStatus OBJECT-TYPE
     SYNTAX       RowStatus
     MAX-ACCESS   read-create
     STATUS       current
     DESCRIPTION
             "Used to manage the creation and deletion of the 
             conceptual rows in this table.

             To send a LoopbackMsg, a manager must
             set this object to 'createAndGo'. There is no concept of 
             delete a LoopbackMsg in this table."
     ::= { wwpLeosTceCfmLoopbackMsgEntry 13 }

 wwpLeosTceCfmLoopbackMsgTotalRxLbrContentMismatch OBJECT-TYPE
     SYNTAX       Unsigned32
     MAX-ACCESS   read-only
     STATUS       current
     DESCRIPTION
             "This object is used to specify total content mismatch LoopbackMsg received."
     ::= { wwpLeosTceCfmLoopbackMsgEntry 14 }

 wwpLeosTceCfmLoopbackMsgTotalRxLbrUnexpected OBJECT-TYPE
     SYNTAX       Unsigned32
     MAX-ACCESS   read-only
     STATUS       current
     DESCRIPTION
             "This object is used to specify total unexpected LoopbackMsg received."
     ::= { wwpLeosTceCfmLoopbackMsgEntry 15 }

  --
  --  TCE CFM Port Stack Table
  --                                   
 wwpLeosTceCfmPortStackTable OBJECT-TYPE
     SYNTAX     SEQUENCE OF WwpLeosTceCfmPortStackEntry
     MAX-ACCESS not-accessible
     STATUS     current
     DESCRIPTION
            "The (conceptual) table listing the display 
             parameters for the CFM port stack table.
             Not applicable to 6.x"  
     ::= { wwpLeosTceCfmStack 1 }
                
 wwpLeosTceCfmPortStackEntry OBJECT-TYPE
     SYNTAX      WwpLeosTceCfmPortStackEntry
     MAX-ACCESS  not-accessible
     STATUS      current
     DESCRIPTION
           "An entry (conceptual row) in the wwpLeosTceCfmPortStackTable."
     INDEX {wwpLeosTceCfmPortStackServiceType, wwpLeosTceCfmPortStackServiceIndex,
            wwpLeosTceCfmPortStackSubPortType, wwpLeosTceCfmPortStackSubPortIndex}
     ::= { wwpLeosTceCfmPortStackTable 1 }
                
 WwpLeosTceCfmPortStackEntry ::=  SEQUENCE {
     wwpLeosTceCfmPortStackServiceType              INTEGER,
     wwpLeosTceCfmPortStackServiceIndex             Unsigned32,
     wwpLeosTceCfmPortStackSubPortType              INTEGER,
     wwpLeosTceCfmPortStackSubPortIndex             Unsigned32,
     wwpLeosTceCfmPortStackSubPortName              DisplayString,
     wwpLeosTceCfmPortStackOperState                INTEGER,
     wwpLeosTceCfmPortStackPgid                     Unsigned32,
     wwpLeosTceCfmPortStackBayIndex                 Unsigned32,
     wwpLeosTceCfmPortStackShelfIndex               Unsigned32,
     wwpLeosTceCfmPortStackModuleIndex              Unsigned32,
     wwpLeosTceCfmPortStackVsPbtName                DisplayString,
     wwpLeosTceCfmPortStackEgressXformTagValue1     Unsigned32,
     wwpLeosTceCfmPortStackEgressXformTagPriority1  Unsigned32,
     wwpLeosTceCfmPortStackEgressXformTagEtype1     Unsigned32,
     wwpLeosTceCfmPortStackEgressXformTagValue2     Unsigned32,
     wwpLeosTceCfmPortStackEgressXformTagPriority2  Unsigned32,
     wwpLeosTceCfmPortStackEgressXformTagEtype2     Unsigned32,
     wwpLeosTceCfmPortStackMepCount                 Unsigned32,
     wwpLeosTceCfmPortStackMipLevel                 Unsigned32
 }

 wwpLeosTceCfmPortStackServiceType OBJECT-TYPE
     SYNTAX      INTEGER {
                    vs(1),
                    pbt(2)
                 }
     MAX-ACCESS  not-accessible
     STATUS      current
     DESCRIPTION
             "This object is used to specify the CFM sub-port service type."
     ::= { wwpLeosTceCfmPortStackEntry 1 }
 
 wwpLeosTceCfmPortStackServiceIndex OBJECT-TYPE
     SYNTAX      Unsigned32 (1..65535) 
     MAX-ACCESS  not-accessible
     STATUS      current
     DESCRIPTION
             "A unique identifier for CFM domain entry."
     ::= { wwpLeosTceCfmPortStackEntry 2 }


 wwpLeosTceCfmPortStackSubPortType OBJECT-TYPE
     SYNTAX      INTEGER {
                    vs(1),
                    encapPbt(2), -- future release
                    decapPbt(3)  -- future release
                 }
     MAX-ACCESS  not-accessible
     STATUS      current
     DESCRIPTION
             "This object is used to specify the CFM sub-port type."
     ::= { wwpLeosTceCfmPortStackEntry 3 }

 wwpLeosTceCfmPortStackSubPortIndex OBJECT-TYPE
     SYNTAX      Unsigned32
     MAX-ACCESS  not-accessible
     STATUS      current
     DESCRIPTION
             "This object is used to specify the CFM sub-port index."
     ::= { wwpLeosTceCfmPortStackEntry 4 }

 wwpLeosTceCfmPortStackSubPortName OBJECT-TYPE
     SYNTAX      DisplayString (SIZE(1..31))
     MAX-ACCESS  read-only
     STATUS      current
     DESCRIPTION
             "This object is used to specify the CFM sub-port name."
     ::= { wwpLeosTceCfmPortStackEntry 5 }

 wwpLeosTceCfmPortStackOperState OBJECT-TYPE
     SYNTAX      INTEGER {
                    unknown(1),
                    invalid(2),
                    enabled(3),
                    disabled(4),
                    notAuthenticated(5),
                    loopbackTx(6),    
                    loopbackRx(7),
                    unequipped(8)
                 }
     MAX-ACCESS  read-only
     STATUS      current
     DESCRIPTION
             "This object is used to specify the CFM sub-port operational state."
     ::= { wwpLeosTceCfmPortStackEntry 6 }

 wwpLeosTceCfmPortStackPgid OBJECT-TYPE
     SYNTAX      Unsigned32
     MAX-ACCESS  read-only
     STATUS      current
     DESCRIPTION
             "This object is used to specify the CFM sub-port group id."
     ::= { wwpLeosTceCfmPortStackEntry 7 }

 wwpLeosTceCfmPortStackBayIndex  OBJECT-TYPE
     SYNTAX          Unsigned32 (1..1)
     MAX-ACCESS      read-only
     STATUS          current
     DESCRIPTION
           "This object is used to specify the CFM sub-port agent bay."               
     ::= { wwpLeosTceCfmPortStackEntry 8 }
     
 wwpLeosTceCfmPortStackShelfIndex  OBJECT-TYPE
     SYNTAX          Unsigned32 (1..1)
     MAX-ACCESS      read-only
     STATUS          current
     DESCRIPTION
           "This object is used to specify the CFM sub-port agent shelf."               
     ::= { wwpLeosTceCfmPortStackEntry 9 }

 wwpLeosTceCfmPortStackModuleIndex OBJECT-TYPE
     SYNTAX      Unsigned32 (1..7 | 255)
     MAX-ACCESS  read-only
     STATUS      current
     DESCRIPTION
             "This object is used to specify the CFM sub-port agent slot.
              Index value of 255 is reserved for Lag ports."
     ::= { wwpLeosTceCfmPortStackEntry 10 }

 wwpLeosTceCfmPortStackVsPbtName OBJECT-TYPE
     SYNTAX      DisplayString (SIZE(1..32))
     MAX-ACCESS  read-only
     STATUS      current
     DESCRIPTION
             "This object is used to specify the CFM PBT name."
     ::= { wwpLeosTceCfmPortStackEntry 11 }

 wwpLeosTceCfmPortStackEgressXformTagValue1 OBJECT-TYPE
     SYNTAX      Unsigned32
     MAX-ACCESS  read-only
     STATUS      current
     DESCRIPTION
             "This object is used to specify the egress tag value."
     ::= { wwpLeosTceCfmPortStackEntry 13 }

 wwpLeosTceCfmPortStackEgressXformTagPriority1 OBJECT-TYPE
     SYNTAX      Unsigned32
     MAX-ACCESS  read-only
     STATUS      current
     DESCRIPTION
             "This object is used to specify the egress tag priority."
     ::= { wwpLeosTceCfmPortStackEntry 14 }

 wwpLeosTceCfmPortStackEgressXformTagEtype1 OBJECT-TYPE
     SYNTAX      Unsigned32
     MAX-ACCESS  read-only
     STATUS      current
     DESCRIPTION
             "This object is used to specify the egress tag etype."
     ::= { wwpLeosTceCfmPortStackEntry 15 }

 wwpLeosTceCfmPortStackEgressXformTagValue2 OBJECT-TYPE
     SYNTAX      Unsigned32
     MAX-ACCESS  read-only
     STATUS      current
     DESCRIPTION
             "This object is used to specify the egress tag value."
     ::= { wwpLeosTceCfmPortStackEntry 16 }

 wwpLeosTceCfmPortStackEgressXformTagPriority2 OBJECT-TYPE
     SYNTAX      Unsigned32
     MAX-ACCESS  read-only
     STATUS      current
     DESCRIPTION
             "This object is used to specify the egress tag priority."
     ::= { wwpLeosTceCfmPortStackEntry 17 }

 wwpLeosTceCfmPortStackEgressXformTagEtype2 OBJECT-TYPE
     SYNTAX      Unsigned32
     MAX-ACCESS  read-only
     STATUS      current
     DESCRIPTION
             "This object is used to specify the egress tag etype."
     ::= { wwpLeosTceCfmPortStackEntry 18 }

 wwpLeosTceCfmPortStackMepCount OBJECT-TYPE
     SYNTAX      Unsigned32
     MAX-ACCESS  read-only
     STATUS      current
     DESCRIPTION
             "This object is used to specify the MEP counts in both directions."
     ::= { wwpLeosTceCfmPortStackEntry 19 }

 wwpLeosTceCfmPortStackMipLevel OBJECT-TYPE
     SYNTAX      Unsigned32
     MAX-ACCESS  read-only
     STATUS      current
     DESCRIPTION
             "This object is used to specify the port stack MIP level."
     ::= { wwpLeosTceCfmPortStackEntry 20 }
     
  --
  --  CFM MEP Table 
  --                                   
 wwpLeosTceCfmMEPTable OBJECT-TYPE
     SYNTAX     SEQUENCE OF WwpLeosTceCfmMEPEntry
     MAX-ACCESS not-accessible
     STATUS     current
     DESCRIPTION
            "The (conceptual) table listing the config 
            parameters for the CFM MEP table.
            Not applicable to 6.x"  
     ::= { wwpLeosTceCfmMEP 1 }
                
 wwpLeosTceCfmMEPEntry OBJECT-TYPE
     SYNTAX      WwpLeosTceCfmMEPEntry
     MAX-ACCESS  not-accessible
     STATUS      current
     DESCRIPTION
           "An entry (conceptual row) in the wwpLeosCfmMEPTable."  
     INDEX {wwpLeosCfmServiceIndex, wwpLeosTceCfmMEPId}
     ::= { wwpLeosTceCfmMEPTable 1 }
                
 WwpLeosTceCfmMEPEntry ::=  SEQUENCE { 
 	 wwpLeosTceCfmMEPId											    Unsigned32,
     wwpLeosTceCfmMEPAdminState                                     INTEGER,        
     wwpLeosTceCfmMEPOperState                                      INTEGER,        
     wwpLeosTceCfmMEPDirection                                      INTEGER,
     wwpLeosTceCfmMEPCCMState            							INTEGER,
     wwpLeosTceCfmMEPCCMPriority         							INTEGER,
     wwpLeosTceCfmMEPLTMPriority         							INTEGER,  
     wwpLeosTceCfmMEPMacAddr                                        MacAddress,
     wwpLeosTceCfmMEPNextLbmSeqNumber                               Counter32,
     wwpLeosTceCfmMEPRxValidInOrderLoopbackReply       			    Counter32,
     wwpLeosTceCfmMEPRxValidOutOrderLoopbackReply          		    Counter32,
     wwpLeosTceCfmMEPNextLTMSeqNumber                               Counter32,
     wwpLeosTceCfmMEPNumLoopbackRepliesTxmt                		    Counter32,
     wwpLeosTceCfmMEPNumLTMRecevied                                 Counter32,
     wwpLeosTceCfmMEPNumLTMTxmt                                     Counter32,
     wwpLeosTceCfmMEPNumCCMTxmt                                     Counter32,     
     wwpLeosTceCfmMEPRowStatus                                      RowStatus,
     wwpLeosTceCfmMEPNumDMMSent									    Counter32,
     wwpLeosTceCfmMEPDMMDelay										Counter32,
     wwpLeosTceCfmMEPDMMJitter										Counter32,
     wwpLeosTceCfmMEPNumLMMSent									    Counter32,
     wwpLeosTceCfmMEPLMMFrameLossNear								Counter32,
     wwpLeosTceCfmMEPLMMFrameLossFar								Counter32,
     wwpLeosTceCfmMEPLiType											INTEGER,
     wwpLeosTceCfmMEPLiIndex										Unsigned32,
     wwpLeosTceCfmMEPServiceName                                    DisplayString,
     wwpLeosTceCfmMEPSubPortName                                    DisplayString,
     wwpLeosTceCfmMEPVsPbtName                                      DisplayString,
     wwpLeosTceCfmMEPLogicalPortName                                DisplayString,
     wwpLeosTceCfmMEPSubPortIndex                                   Unsigned32,
     wwpLeosTceCfmMEPEncapsulation                                  INTEGER,
     wwpLeosTceCfmMEPLeadPortBayIndex                               Unsigned32,
     wwpLeosTceCfmMEPLeadPortShelfIndex                             Unsigned32,
     wwpLeosTceCfmMEPLeadPortModuleIndex                            Unsigned32,
     wwpLeosTceCfmMEPPBTBvid                                        Unsigned32,
     wwpLeosTceCfmMEPPBTEtype                                       Unsigned32,
     wwpLeosTceCfmMEPNumLbmTxmt                                     Counter32,
     wwpLeosTceCfmMEPNumLbmReceived                                 Counter32,
     wwpLeosTceCfmMEPNumLoopbackRepliesReceived                     Counter32,
     wwpLeosTceCfmMEPNumLTRepliesTxmt                               Counter32,
     wwpLeosTceCfmMEPNumLTRepliesReceived                           Counter32,
     wwpLeosTceCfmMEPNumUnexpectedLTRepliesReceived                 Counter32,
     wwpLeosTceCfmMEPNumCCMReceived                                 Counter32,
     wwpLeosTceCfmMEPRxContentMismatchLoopbackReply                 Counter32,
     wwpLeosTceCfmMEPRxUnexpectedLoopbackReply                      Counter32
 }
   
 wwpLeosTceCfmMEPId OBJECT-TYPE
     SYNTAX      Unsigned32 (1..8191)
     MAX-ACCESS  not-accessible
     STATUS      current
     DESCRIPTION
             "This is used as the index in the table.This object specifies the mep id for the given service."
     ::= { wwpLeosTceCfmMEPEntry 1 }

 wwpLeosTceCfmMEPAdminState OBJECT-TYPE
     SYNTAX      INTEGER   {
                                disabled(1),
                                enabled(2)  
                          }
     MAX-ACCESS  read-write
     STATUS      current
     DESCRIPTION
             "This object is used to specify the admin state of CFM MEP."
     ::= { wwpLeosTceCfmMEPEntry 2 }
 
 wwpLeosTceCfmMEPOperState OBJECT-TYPE
     SYNTAX      INTEGER   {
                                disabled(1),
                                enabled(2)  
                          }
     MAX-ACCESS  read-only
     STATUS      current
     DESCRIPTION
             "This object is used to specify the oper state of CFM MEP."
     ::= { wwpLeosTceCfmMEPEntry 3 }
     
 wwpLeosTceCfmMEPDirection OBJECT-TYPE
     SYNTAX      INTEGER {
                                up(1),
                                down(2)
                         }
     MAX-ACCESS  read-create
     STATUS      current
     DESCRIPTION
             "This object is used to specify the MEP direction of the service.
              This object can only be set if wwpLeosCfmServiceIndex is of type vlan."
     ::= { wwpLeosTceCfmMEPEntry 4 } 
 
 wwpLeosTceCfmMEPCCMState OBJECT-TYPE
     SYNTAX       INTEGER {
                                on(1),
                                off(2)
                                }
     MAX-ACCESS   read-write
     STATUS       current
     DESCRIPTION
             "This object specifies the CCM transmission for the service specified by wwpLeosCfmServiceType."
     ::= { wwpLeosTceCfmMEPEntry 5 }
     
 wwpLeosTceCfmMEPCCMPriority OBJECT-TYPE
     SYNTAX       INTEGER (0..7)
     MAX-ACCESS   read-write
     STATUS       current
     DESCRIPTION
             "This object specified the priority of CCM messages transmitted."
     ::= { wwpLeosTceCfmMEPEntry 6 }
     
 wwpLeosTceCfmMEPLTMPriority OBJECT-TYPE
     SYNTAX      INTEGER (0..7)
     MAX-ACCESS  read-write
     STATUS      current
     DESCRIPTION
             "This object specifies the priority received on the given service and port."
     ::= { wwpLeosTceCfmMEPEntry 7 } 
     
   
 wwpLeosTceCfmMEPMacAddr OBJECT-TYPE
     SYNTAX      MacAddress
     MAX-ACCESS  read-only
     STATUS      current
     DESCRIPTION
             "This object specifies the mac address received on the given service and port.."
     ::= { wwpLeosTceCfmMEPEntry 8 }
     
 wwpLeosTceCfmMEPNextLbmSeqNumber OBJECT-TYPE
     SYNTAX      Counter32 
     MAX-ACCESS  read-only
     STATUS      current
     DESCRIPTION
             "This object specifies the next lbm sequence number received on the given service and port."
     ::= { wwpLeosTceCfmMEPEntry 9 }
     
 wwpLeosTceCfmMEPRxValidInOrderLoopbackReply OBJECT-TYPE
     SYNTAX      Counter32
     MAX-ACCESS  read-only
     STATUS      current
     DESCRIPTION
             "This object specifies the total valid in order loopback replies received on the given service and port."
     ::= { wwpLeosTceCfmMEPEntry 10 }
     
 wwpLeosTceCfmMEPRxValidOutOrderLoopbackReply OBJECT-TYPE
     SYNTAX      Counter32
     MAX-ACCESS  read-only
     STATUS      current
     DESCRIPTION
             "This object specifies the total valid out of order loopback replies received on the given service and port."
     ::= { wwpLeosTceCfmMEPEntry 11 }
     
 wwpLeosTceCfmMEPNextLTMSeqNumber OBJECT-TYPE
     SYNTAX      Counter32 
     MAX-ACCESS  read-only
     STATUS      current
     DESCRIPTION
             "This object specifies the next LTM sequence number received on the given service and port."
     ::= { wwpLeosTceCfmMEPEntry 12 }
     
 wwpLeosTceCfmMEPNumLoopbackRepliesTxmt OBJECT-TYPE
     SYNTAX      Counter32
     MAX-ACCESS  read-only
     STATUS      current
     DESCRIPTION
             "This object specifies the flags total loopback replies transmitted on the given service and port."
     ::= { wwpLeosTceCfmMEPEntry 13 }
     
 wwpLeosTceCfmMEPNumLTMRecevied OBJECT-TYPE
     SYNTAX      Counter32
     MAX-ACCESS  read-only
     STATUS      current
     DESCRIPTION
             "This object specifies the total LTM messages received on the given service and port."
     ::= { wwpLeosTceCfmMEPEntry 14 }
     
 wwpLeosTceCfmMEPNumLTMTxmt OBJECT-TYPE
     SYNTAX      Counter32
     MAX-ACCESS  read-only
     STATUS      current
     DESCRIPTION
             "This object specifies the total ltm transmitted on the given service and port."
     ::= { wwpLeosTceCfmMEPEntry 15 }
     
 wwpLeosTceCfmMEPNumCCMTxmt OBJECT-TYPE
     SYNTAX      Counter32
     MAX-ACCESS  read-only
     STATUS      current
     DESCRIPTION
             "This object specifies the total CCM messages transmitted on the given service and port."
     ::= { wwpLeosTceCfmMEPEntry 16 }     
     
 wwpLeosTceCfmMEPRowStatus OBJECT-TYPE
     SYNTAX       RowStatus
     MAX-ACCESS   read-create
     STATUS       current
     DESCRIPTION
             "Used to manage the creation and deletion of the 
             conceptual rows in this table.

             To create a row in this table, a manager must
             set this object to 'createAndGo'. To delete a row in this
             table, set this to 'destroy'."
     ::= { wwpLeosTceCfmMEPEntry 17 }  
     
  wwpLeosTceCfmMEPNumDMMSent OBJECT-TYPE
     SYNTAX      Counter32
     MAX-ACCESS  read-only
     STATUS      current
     DESCRIPTION
             "This object specifies the total delay measurement messages
             transmitted on the given service and port."
     ::= { wwpLeosTceCfmMEPEntry 18 } 
     
 wwpLeosTceCfmMEPDMMDelay OBJECT-TYPE
     SYNTAX      Counter32
     MAX-ACCESS  read-only
     STATUS      current
     DESCRIPTION
             "This object specifies the average delay in microseconds
             measured during the last DMM performance test on the given service and port."
     ::= { wwpLeosTceCfmMEPEntry 19 } 
     
 wwpLeosTceCfmMEPDMMJitter OBJECT-TYPE
     SYNTAX      Counter32
     MAX-ACCESS  read-only
     STATUS      current
     DESCRIPTION
             "This object specifies the average jitter in microseconds
             measured during the last DMM performance test on the given service and port."
     ::= { wwpLeosTceCfmMEPEntry 20 }
 
 wwpLeosTceCfmMEPNumLMMSent OBJECT-TYPE
     SYNTAX      Counter32
     MAX-ACCESS  read-only
     STATUS      current
     DESCRIPTION
             "This object specifies the total frame loss measurement messages
             transmitted on the given service and port."
     ::= { wwpLeosTceCfmMEPEntry 21 } 
     
 wwpLeosTceCfmMEPLMMFrameLossNear OBJECT-TYPE
     SYNTAX      Counter32
     MAX-ACCESS  read-only
     STATUS      current
     DESCRIPTION
             "This object specifies the number of lost frames on the near side
             measured during the last LMM performance test on the given service and port."
     ::= { wwpLeosTceCfmMEPEntry 22 } 
     
 wwpLeosTceCfmMEPLMMFrameLossFar OBJECT-TYPE
     SYNTAX      Counter32
     MAX-ACCESS  read-only
     STATUS      current
     DESCRIPTION
             "This object specifies the number of lost frames on the far side
             measured during the last LMM performance test on the given service and port."
     ::= { wwpLeosTceCfmMEPEntry 23 }  
  
 wwpLeosTceCfmMEPLiType   OBJECT-TYPE
 	 SYNTAX      INTEGER {
 	 				   vs(1),
 	 				   pbtService(2), 
	 				   mplsStaticPeMeshVC(3),
					   mplsDynamicPeMeshVC(4),
					   mplsStaticPeSpokeVC(5), 
					   mplsDynamicPeSpokeVC(6),
					   mplsStaticMtuSpokeVC(7),
					   mplsDynamicMtuSpokeVC(8),
 	 				   none(99)
 	 		     }
     MAX-ACCESS  read-create
     STATUS      current
     DESCRIPTION
             "This object specifies Li Type on which the Mep is created."
     ::= { wwpLeosTceCfmMEPEntry 24 }  
 
 wwpLeosTceCfmMEPLiIndex OBJECT-TYPE
 	SYNTAX    Unsigned32
 	MAX-ACCESS read-create
 	STATUS current
 	DESCRIPTION
 		"This object specifies LiIndex for creating MEP" 
 	::= { wwpLeosTceCfmMEPEntry 25 } 
  
 wwpLeosTceCfmMEPServiceName OBJECT-TYPE
     SYNTAX      DisplayString (SIZE(0..31))
     MAX-ACCESS  read-only
     STATUS      current
     DESCRIPTION
             "This object is used to specify the service name assigned to this port."
     ::= { wwpLeosTceCfmMEPEntry 50 }
  
 wwpLeosTceCfmMEPSubPortName OBJECT-TYPE
     SYNTAX      DisplayString (SIZE(0..31))
     MAX-ACCESS  read-only
     STATUS      current
     DESCRIPTION
             "This object represents the sub-port, PbtService or Mpls Vc name assigned to the given service and port." 
     ::= { wwpLeosTceCfmMEPEntry 51 }

 wwpLeosTceCfmMEPVsPbtName OBJECT-TYPE
     SYNTAX      DisplayString (SIZE(0..31))
     MAX-ACCESS  read-only
     STATUS      current
     DESCRIPTION
             "This object represents the virtual switch or Pbt tunnel assigned to the given service and port." 
     ::= { wwpLeosTceCfmMEPEntry 52 }

 wwpLeosTceCfmMEPLogicalPortName OBJECT-TYPE
     SYNTAX      DisplayString (SIZE(0..31))
     MAX-ACCESS  read-only
     STATUS      current
     DESCRIPTION
             "This object represents the logical port name assigned to the given service and port." 
     ::= { wwpLeosTceCfmMEPEntry 53 }

 wwpLeosTceCfmMEPSubPortIndex OBJECT-TYPE
     SYNTAX      Unsigned32
     MAX-ACCESS  read-write
     STATUS      current
     DESCRIPTION
             "This object is used to specify the CFM sub-port index."
     ::= { wwpLeosTceCfmMEPEntry 54 }

 wwpLeosTceCfmMEPEncapsulation OBJECT-TYPE
     SYNTAX      INTEGER {
                                ieee802dot1d(1),
                                pbtCfmEncap(2)
                         }
     MAX-ACCESS  read-only
     STATUS      current
     DESCRIPTION
             "This object is used to specify the encapsulation applied to the service and port."
     ::= { wwpLeosTceCfmMEPEntry 55 } 
 
 wwpLeosTceCfmMEPLeadPortBayIndex OBJECT-TYPE
     SYNTAX          Unsigned32 (1..1)
     MAX-ACCESS      read-only
     STATUS          current
     DESCRIPTION
           "This object is used as to specify the agent bay that MEP is in."               
     ::= { wwpLeosTceCfmMEPEntry 56 }

 wwpLeosTceCfmMEPLeadPortShelfIndex OBJECT-TYPE
     SYNTAX          Unsigned32 (1..1)
     MAX-ACCESS      read-only
     STATUS          current
     DESCRIPTION
           "This object is used as to specify the agent shelf that MEP is in."               
     ::= { wwpLeosTceCfmMEPEntry 57 }

 wwpLeosTceCfmMEPLeadPortModuleIndex OBJECT-TYPE
     SYNTAX          Unsigned32 (1..7 | 255)
     MAX-ACCESS      read-only
     STATUS          current
     DESCRIPTION
           "This object is used as to specify the agent module that MEP is in.
            Index = 255 is reserved for Lag ports and this this object cannot be set to 255
            in this table."               
     ::= { wwpLeosTceCfmMEPEntry 58 }
     
 wwpLeosTceCfmMEPPBTBvid OBJECT-TYPE
     SYNTAX          Unsigned32 (1..8191)
     MAX-ACCESS      read-only
     STATUS          current
     DESCRIPTION
             "This object specifies the BVID assigned to the given service and port."
     ::= { wwpLeosTceCfmMEPEntry 59 }

 wwpLeosTceCfmMEPPBTEtype OBJECT-TYPE
     SYNTAX          Unsigned32 (1..8191)
     MAX-ACCESS      read-only
     STATUS          current
     DESCRIPTION
             "This object specifies the E-type assigned to the given service and port."
     ::= { wwpLeosTceCfmMEPEntry 60 }

 wwpLeosTceCfmMEPNumLbmTxmt OBJECT-TYPE
     SYNTAX      Counter32
     MAX-ACCESS  read-only
     STATUS      current
     DESCRIPTION
             "This object specifies the total loopback messages transmitted on the 
              given service and port."
     ::= { wwpLeosTceCfmMEPEntry 61 }
     
 wwpLeosTceCfmMEPNumLbmReceived OBJECT-TYPE
     SYNTAX      Counter32
     MAX-ACCESS  read-only
     STATUS      current
     DESCRIPTION
             "This object specifies the total loopback messages received on the 
              given service and port."
     ::= { wwpLeosTceCfmMEPEntry 62 }

 wwpLeosTceCfmMEPNumLoopbackRepliesReceived OBJECT-TYPE
     SYNTAX      Counter32
     MAX-ACCESS  read-only
     STATUS      current
     DESCRIPTION
             "This object specifies the total loopback replies received on the 
              given service and port."
     ::= { wwpLeosTceCfmMEPEntry 63 }

 wwpLeosTceCfmMEPNumLTRepliesTxmt OBJECT-TYPE
     SYNTAX      Counter32
     MAX-ACCESS  read-only
     STATUS      current
     DESCRIPTION
             "This object specifies the total link trace replies transmitted on the 
              given service and port."
     ::= { wwpLeosTceCfmMEPEntry 64 }

 wwpLeosTceCfmMEPNumLTRepliesReceived OBJECT-TYPE
     SYNTAX      Counter32
     MAX-ACCESS  read-only
     STATUS      current
     DESCRIPTION
             "This object specifies the total link trace replies received on the 
              given service and port."
     ::= { wwpLeosTceCfmMEPEntry 65 }

 wwpLeosTceCfmMEPNumUnexpectedLTRepliesReceived OBJECT-TYPE
     SYNTAX      Counter32
     MAX-ACCESS  read-only
     STATUS      current
     DESCRIPTION
             "This object specifies the total unexpected link trace replies received on the 
              given service and port."
     ::= { wwpLeosTceCfmMEPEntry 66 }

 wwpLeosTceCfmMEPNumCCMReceived OBJECT-TYPE
     SYNTAX      Counter32
     MAX-ACCESS  read-only
     STATUS      current
     DESCRIPTION
             "This object specifies the total CCM messages received on the given service and port."
     ::= { wwpLeosTceCfmMEPEntry 67 }

 wwpLeosTceCfmMEPRxContentMismatchLoopbackReply OBJECT-TYPE
     SYNTAX      Counter32
     MAX-ACCESS  read-only
     STATUS      current
     DESCRIPTION
             "This object specifies the total content mismatch loopback replies received on the given service and port."
     ::= { wwpLeosTceCfmMEPEntry 68 }

 wwpLeosTceCfmMEPRxUnexpectedLoopbackReply OBJECT-TYPE
     SYNTAX      Counter32
     MAX-ACCESS  read-only
     STATUS      current
     DESCRIPTION
             "This object specifies the total unexpected loopback replies received on the given service and port."
     ::= { wwpLeosTceCfmMEPEntry 69 }

 --
  -- Delay Measurement Msg table
  -- 
  wwpLeosTceCfmDelayMsgTable OBJECT-TYPE
     SYNTAX     SEQUENCE OF WwpLeosTceCfmDelayMsgEntry
     MAX-ACCESS not-accessible
     STATUS     current
     DESCRIPTION
            "The (conceptual) table listing the config 
            parameters for the DelayMeasurementMsg.
            Not applicable to 6.x"
            
     ::= { wwpLeosTceCfmDelay 1 }
                
 wwpLeosTceCfmDelayMsgEntry OBJECT-TYPE
     SYNTAX      WwpLeosTceCfmDelayMsgEntry
     MAX-ACCESS  not-accessible
     STATUS      current
     DESCRIPTION
           "An entry (conceptual row) in the wwpLeosCfmDelayMsgTable.
           To send, clear or cancel the message, the corresponding MsgAction 
           needs to be specified. Individual objects in this table
           cannot be set.                                     
           RowStatus is a read-only field.
           To send or cancel a message, the TargetMepID or the 
           TargtetMacAddr objects need to be specified.
           Clear msgAction clears the counters for the message"
     INDEX {wwpLeosCfmServiceIndex, wwpLeosTceCfmDelayMsgLocalMEPId}
     ::= { wwpLeosTceCfmDelayMsgTable 1 }
                
 WwpLeosTceCfmDelayMsgEntry ::=  SEQUENCE { 
     wwpLeosTceCfmDelayMsgLocalMEPId                  	INTEGER,
     wwpLeosTceCfmDelayMsgTargetMEPID              Unsigned32,
     wwpLeosTceCfmDelayMsgTargetMacAddr            MacAddress,
     wwpLeosTceCfmDelayMsgCount                   	INTEGER,
     wwpLeosTceCfmDelayMsgPriority                	INTEGER,
     wwpLeosTceCfmDelayMsgRowStatus               	RowStatus,
     wwpLeosTceCfmDelayMsgRepeatInterval			Unsigned32,
     wwpLeosTceCfmDelayMsgDelayThreshold			INTEGER,
     wwpLeosTceCfmDelayMsgJitterThreshold			INTEGER,
     wwpLeosTceCfmDelayMsgServiceName				DisplayString,
     wwpLeosTceCfmDelayMsgSubPortName				DisplayString,
     wwpLeosTceCfmDelayMsgDelay					    Unsigned32,
     wwpLeosTceCfmDelayMsgJitter					Unsigned32,
     wwpLeosTceCfmDelayMsgTotalTxDmm				Unsigned32,
     wwpLeosTceCfmDelayMsgTotalRxDmm				Unsigned32,
     wwpLeosTceCfmDelayMsgTotalTxDmr				Unsigned32,
     wwpLeosTceCfmDelayMsgTotalRxDmr				Unsigned32,  
     wwpLeosTceCfmDelayMsgAction					SendState,
     wwpLeosTceCfmDelayMsgMaxDelay			        Unsigned32,
     wwpLeosTceCfmDelayMsgMaxJitter					Unsigned32, 
     wwpLeosTceCfmDelayMsgMaxDelayThreshold         INTEGER,
     wwpLeosTceCfmDelayMsgMaxJitterThreshold        INTEGER,
     wwpLeosTceCfmDelayMsgMinDelay			        Unsigned32,
     wwpLeosTceCfmDelayMsgMinJitter					Unsigned32
     
 }

 wwpLeosTceCfmDelayMsgLocalMEPId OBJECT-TYPE
     SYNTAX       INTEGER (1..65535)
     MAX-ACCESS   read-only
     STATUS       current
     DESCRIPTION
             "This object is used to specify the local MEPId."
     ::= { wwpLeosTceCfmDelayMsgEntry 1 }
 
 wwpLeosTceCfmDelayMsgTargetMEPID OBJECT-TYPE
     SYNTAX       Unsigned32 (1..8191)
     MAX-ACCESS   read-create
     STATUS       current
     DESCRIPTION
             "This object is used to specify the MEPID.
              This object should only be set if wwpLeosTceCfmDelayMsgTargetMacAddr is not specified else 
              error will be returned."
     ::= { wwpLeosTceCfmDelayMsgEntry 2 }
     
 wwpLeosTceCfmDelayMsgTargetMacAddr OBJECT-TYPE
     SYNTAX       MacAddress
     MAX-ACCESS   read-create
     STATUS       current
     DESCRIPTION
             "This object is used to specify the MacAddress to be used when sending link LoopbackMsg.
              This object should only be set if wwpLeosTceCfmDelayMsgTargetMEPID is not specified else 
              error will be returned."
     ::= {wwpLeosTceCfmDelayMsgEntry 3 }
     
 wwpLeosTceCfmDelayMsgCount OBJECT-TYPE
     SYNTAX       INTEGER (2..9000) 
     MAX-ACCESS   read-create
     STATUS       current
     DESCRIPTION
             "This object is used to specify the DelayMeasurementMsg count to be used
              when sending link DelayMeasurementMsg."
     ::= { wwpLeosTceCfmDelayMsgEntry 4 }
 
 wwpLeosTceCfmDelayMsgPriority OBJECT-TYPE
     SYNTAX       INTEGER (0..7)
     MAX-ACCESS   read-create
     STATUS       current
     DESCRIPTION
             "This object is used to specify the DelayMeasurementMsg priority to be
             used when sending link DelayMeasurementMsg."
     ::= { wwpLeosTceCfmDelayMsgEntry 5 }
 
 wwpLeosTceCfmDelayMsgRowStatus OBJECT-TYPE
     SYNTAX       RowStatus
     MAX-ACCESS   read-only
     STATUS       current
     DESCRIPTION
             "Is a display read-only field only. A row in this table
             is created by the system when a service and mep is created"
     ::= { wwpLeosTceCfmDelayMsgEntry 6 }
 
  wwpLeosTceCfmDelayMsgRepeatInterval OBJECT-TYPE
     SYNTAX       Unsigned32 (0..1440)
     UNITS		  "minutes"
     MAX-ACCESS   read-create
     STATUS       current
     DESCRIPTION
             "Represents the Transmission Period for the Cfm Delay."
     ::= { wwpLeosTceCfmDelayMsgEntry 40 }

   wwpLeosTceCfmDelayMsgDelayThreshold OBJECT-TYPE
     SYNTAX       INTEGER (1..65535)
     MAX-ACCESS   read-create
     STATUS       current
     DESCRIPTION
             "Represents the Threshold for the average delay"
     ::= {wwpLeosTceCfmDelayMsgEntry 41 }
  
  wwpLeosTceCfmDelayMsgJitterThreshold OBJECT-TYPE
     SYNTAX       INTEGER  (1..65535)
     MAX-ACCESS   read-create
     STATUS       current
     DESCRIPTION
             "Represents the threshold value for the Jitter"
     ::= { wwpLeosTceCfmDelayMsgEntry 42 }   
    
  wwpLeosTceCfmDelayMsgServiceName OBJECT-TYPE
     SYNTAX       DisplayString (SIZE(1..31))
     MAX-ACCESS   read-only
     STATUS       current
     DESCRIPTION
             "This object is used to specify the service to be used when
 	sending DelayMsg."
     ::= { wwpLeosTceCfmDelayMsgEntry 43 }
 
  wwpLeosTceCfmDelayMsgSubPortName OBJECT-TYPE
     SYNTAX       DisplayString (SIZE(1..31))
     MAX-ACCESS   read-only
     STATUS       current
     DESCRIPTION
             "This object represents the sub-port name where the DelayMsg
 	was sent."
     ::= { wwpLeosTceCfmDelayMsgEntry 44 }
   
  wwpLeosTceCfmDelayMsgDelay OBJECT-TYPE
     SYNTAX       Unsigned32
     UNITS		  "microseconds"
     MAX-ACCESS   read-only
     STATUS       current
     DESCRIPTION
             "This object represents the Average Delay"
     ::= { wwpLeosTceCfmDelayMsgEntry 50 }
  
  wwpLeosTceCfmDelayMsgJitter OBJECT-TYPE
     SYNTAX       Unsigned32
     UNITS		  "microseconds"
     MAX-ACCESS   read-only
     STATUS       current
     DESCRIPTION
             "This object represents the average jitter"
     ::= { wwpLeosTceCfmDelayMsgEntry 51 }   
        
   wwpLeosTceCfmDelayMsgTotalTxDmm OBJECT-TYPE
     SYNTAX       Unsigned32
     MAX-ACCESS   read-only
     STATUS       current
     DESCRIPTION
             "This object represents the total Delaymessages transmitted"
     ::= { wwpLeosTceCfmDelayMsgEntry 52 }
  
  wwpLeosTceCfmDelayMsgTotalRxDmm OBJECT-TYPE
     SYNTAX       Unsigned32
     MAX-ACCESS   read-only
     STATUS       current
     DESCRIPTION
             "This object represents the total Delaymessages received"
     ::= { wwpLeosTceCfmDelayMsgEntry 53 }
 
 wwpLeosTceCfmDelayMsgTotalTxDmr OBJECT-TYPE
     SYNTAX       Unsigned32
     MAX-ACCESS   read-only
     STATUS       current
     DESCRIPTION
             "This object represents the total DMRs transmitted"
     ::= { wwpLeosTceCfmDelayMsgEntry 54 }
     
  wwpLeosTceCfmDelayMsgTotalRxDmr OBJECT-TYPE
     SYNTAX       Unsigned32
     MAX-ACCESS   read-only
     STATUS       current
     DESCRIPTION
             "This object represents the total DMRs received"
     ::= { wwpLeosTceCfmDelayMsgEntry 55 }    
  
  wwpLeosTceCfmDelayMsgAction OBJECT-TYPE
     SYNTAX       SendState
     MAX-ACCESS   read-create
     STATUS       current
     DESCRIPTION
             "This object represents the action for the message (send, clear or cancel)"
     ::= { wwpLeosTceCfmDelayMsgEntry 56 } 
     
   wwpLeosTceCfmDelayMsgMaxDelay OBJECT-TYPE
     SYNTAX       Unsigned32
     UNITS		  "microseconds"
     MAX-ACCESS   read-only
     STATUS       current
     DESCRIPTION
             "This object represents the Maximum Delay"
     ::= { wwpLeosTceCfmDelayMsgEntry 57 }
  
  wwpLeosTceCfmDelayMsgMaxJitter OBJECT-TYPE
     SYNTAX       Unsigned32
     UNITS		  "microseconds"
     MAX-ACCESS   read-only
     STATUS       current
     DESCRIPTION
             "This object represents the Maximum jitter"
     ::= { wwpLeosTceCfmDelayMsgEntry 58 }  

  wwpLeosTceCfmDelayMsgMaxDelayThreshold OBJECT-TYPE
     SYNTAX       INTEGER (1..65535)
     MAX-ACCESS   read-create
     STATUS       current
     DESCRIPTION
             "Represents the threshold for maximum delay"
     ::= {wwpLeosTceCfmDelayMsgEntry 59 }
  
  wwpLeosTceCfmDelayMsgMaxJitterThreshold OBJECT-TYPE
     SYNTAX       INTEGER  (1..65535)
     MAX-ACCESS   read-create
     STATUS       current
     DESCRIPTION
             "Represents the threshold value for maximum Jitter"
     ::= { wwpLeosTceCfmDelayMsgEntry 60 }
     
  wwpLeosTceCfmDelayMsgMinDelay OBJECT-TYPE
     SYNTAX       Unsigned32
     UNITS		  "microseconds"
     MAX-ACCESS   read-only
     STATUS       current
     DESCRIPTION
             "This object represents the Maximum Delay"
     ::= { wwpLeosTceCfmDelayMsgEntry 61 }
  
  wwpLeosTceCfmDelayMsgMinJitter OBJECT-TYPE
     SYNTAX       Unsigned32
     UNITS		  "microseconds"
     MAX-ACCESS   read-only
     STATUS       current
     DESCRIPTION
             "This object represents the Maximum jitter"
     ::= { wwpLeosTceCfmDelayMsgEntry 62 }      
     
  
  --
  -- Frame Loss Measurement Msg table
  -- 
  wwpLeosTceCfmFrameLossMsgTable OBJECT-TYPE
     SYNTAX     SEQUENCE OF WwpLeosTceCfmFrameLossMsgEntry
     MAX-ACCESS not-accessible
     STATUS     current
     DESCRIPTION
            "The (conceptual) table listing the config 
            parameters for the FrameLossMeasurementMsg.
            Not applicable to 6.x"  
     ::= { wwpLeosTceCfmFrameLoss 1 }
                
 wwpLeosTceCfmFrameLossMsgEntry OBJECT-TYPE
     SYNTAX      WwpLeosTceCfmFrameLossMsgEntry
     MAX-ACCESS  not-accessible
     STATUS      current
     DESCRIPTION
           "An entry (conceptual row) in the wwpLeosCfmFrameLossMsgTable.
           To send, clear or cancel the message, the corresponding MsgAction 
           needs to be specified. Individual objects in this table
           cannot be set.                                     
           RowStatus is a read-only field.
           To send or cancel a message, the TargetMepID or the 
           TargtetMacAddr objects need to be specified.
           Clear msgAction clears the counters for the message"

     INDEX {wwpLeosCfmServiceIndex, wwpLeosTceCfmFrameLossMsgLocalMEPId}
     ::= { wwpLeosTceCfmFrameLossMsgTable 1 }
                
 WwpLeosTceCfmFrameLossMsgEntry ::=  SEQUENCE { 
     wwpLeosTceCfmFrameLossMsgLocalMEPId                  	INTEGER,
     wwpLeosTceCfmFrameLossMsgTargetMEPID              Unsigned32,
     wwpLeosTceCfmFrameLossMsgTargetMacAddr            MacAddress,
     wwpLeosTceCfmFrameLossMsgCount                   	INTEGER,
     wwpLeosTceCfmFrameLossMsgPriority                	INTEGER,
     wwpLeosTceCfmFrameLossMsgRowStatus               	RowStatus,
     wwpLeosTceCfmFrameLossMsgRepeatInterval			Unsigned32,
     wwpLeosTceCfmFrameLossMsgNearLossThreshold     	INTEGER,
     wwpLeosTceCfmFrameLossMsgFarLossThreshold			INTEGER,
     wwpLeosTceCfmFrameLossMsgServiceName				DisplayString,
     wwpLeosTceCfmFrameLossMsgSubPortName				DisplayString,
     wwpLeosTceCfmFrameLossMsgFrameLossNear			Unsigned32,
     wwpLeosTceCfmFrameLossMsgFrameLossFar				Unsigned32,
     wwpLeosTceCfmFrameLossMsgTotalTxLmm				Unsigned32,
     wwpLeosTceCfmFrameLossMsgTotalRxLmm				Unsigned32,
     wwpLeosTceCfmFrameLossMsgTotalTxLmr				Unsigned32,
     wwpLeosTceCfmFrameLossMsgTotalRxLmr				Unsigned32,
     wwpLeosTceCfmFrameLossMsgAction					SendState     
 }
  wwpLeosTceCfmFrameLossMsgLocalMEPId OBJECT-TYPE
     SYNTAX       INTEGER (1..65535)
     MAX-ACCESS   accessible-for-notify
     STATUS       current
     DESCRIPTION
             "This object is used to specify the Local MEPID at the source."
     ::= { wwpLeosTceCfmFrameLossMsgEntry 1 }
 
 wwpLeosTceCfmFrameLossMsgTargetMEPID OBJECT-TYPE
     SYNTAX       Unsigned32 (1..8191)
     MAX-ACCESS   read-create
     STATUS       current
     DESCRIPTION
             "This object is used to specify the MEPID.
              This object should only be set if wwpLeosTceCfmFrameLossMsgTargetMacAddr is not specified else 
              error will be returned."
     ::= { wwpLeosTceCfmFrameLossMsgEntry 2 }
     
 wwpLeosTceCfmFrameLossMsgTargetMacAddr OBJECT-TYPE
     SYNTAX       MacAddress
     MAX-ACCESS   read-create
     STATUS       current
     DESCRIPTION
             "This object is used to specify the MacAddress to be used when sending link LoopbackMsg.
              This object should only be set if wwpLeosTceCfmFrameLossMsgTargetMEPID is not specified else 
              error will be returned."
     ::= { wwpLeosTceCfmFrameLossMsgEntry 3 }
     
 wwpLeosTceCfmFrameLossMsgCount OBJECT-TYPE
     SYNTAX       INTEGER (2..600) 
     MAX-ACCESS   read-create
     STATUS       current
     DESCRIPTION
             "This object is used to specify the FrameLossMeasurementMsg count to be used
              when sending link FrameLossMeasurementMsg."
     ::= { wwpLeosTceCfmFrameLossMsgEntry 4 }
 
 wwpLeosTceCfmFrameLossMsgPriority OBJECT-TYPE
     SYNTAX       INTEGER (0..7)
     MAX-ACCESS   read-create
     STATUS       current
     DESCRIPTION
             "This object is used to specify the FrameLossMeasurementMsg priority to be
             used when sending link FrameLossMeasurementMsg."
     ::= { wwpLeosTceCfmFrameLossMsgEntry 5 }
 
 wwpLeosTceCfmFrameLossMsgRowStatus OBJECT-TYPE
     SYNTAX       RowStatus
     MAX-ACCESS   read-only
     STATUS       current
     DESCRIPTION
             "Is a read-only field. A row in this table is system-generated 
             on creation of cfm service and cfm mep objects"
     ::= { wwpLeosTceCfmFrameLossMsgEntry 6 }

  wwpLeosTceCfmFrameLossMsgRepeatInterval OBJECT-TYPE
     SYNTAX       Unsigned32 (0..1440)
     UNITS		  "minutes"
     MAX-ACCESS   read-create
     STATUS       current
     DESCRIPTION
             "Represents the Transmission Interval for the Frame loss messages"
     ::= { wwpLeosTceCfmFrameLossMsgEntry 50 }
 
 wwpLeosTceCfmFrameLossMsgNearLossThreshold OBJECT-TYPE
     SYNTAX       INTEGER (0..600)
     MAX-ACCESS   read-create
     STATUS       current
     DESCRIPTION
             "Represents the threshold value for the near-end frame loss"
     ::= { wwpLeosTceCfmFrameLossMsgEntry 51 }
 
 wwpLeosTceCfmFrameLossMsgFarLossThreshold OBJECT-TYPE
     SYNTAX       INTEGER (0..600)
     MAX-ACCESS   read-create
     STATUS       current
     DESCRIPTION
             "Represents the threshold value for the far-end frame loss"
     ::= { wwpLeosTceCfmFrameLossMsgEntry 52 }

  wwpLeosTceCfmFrameLossMsgServiceName OBJECT-TYPE
     SYNTAX       DisplayString (SIZE(1..31))
     MAX-ACCESS   read-only
     STATUS       current
     DESCRIPTION
             "This object is used to specify the service to be used when
 	sending FrameLossMsg (LMM)."
     ::= { wwpLeosTceCfmFrameLossMsgEntry 53 }
 
 wwpLeosTceCfmFrameLossMsgSubPortName OBJECT-TYPE
     SYNTAX       DisplayString (SIZE(1..31))
     MAX-ACCESS   read-only
     STATUS       current
     DESCRIPTION
             "This object is used to specify the sub-port name to be used when
 	sending FrameLossMsg (LMM)."
     ::= { wwpLeosTceCfmFrameLossMsgEntry 54 }
 
 wwpLeosTceCfmFrameLossMsgFrameLossNear OBJECT-TYPE
     SYNTAX       Unsigned32
     MAX-ACCESS   read-only
     STATUS       current
     DESCRIPTION
             "This object represents the near-end Frame Loss. For a MEP,
             near-end Frame loss refers to frame loss associated with the 
             ingress data frames."
     ::= { wwpLeosTceCfmFrameLossMsgEntry 55 }

wwpLeosTceCfmFrameLossMsgFrameLossFar OBJECT-TYPE
     SYNTAX       Unsigned32
     MAX-ACCESS   read-only
     STATUS       current
     DESCRIPTION
             "This object represents the far-end Frame Loss. For a MEP,
             far-end Frame loss refers to frame loss associated with the 
             egress data frames."
     ::= { wwpLeosTceCfmFrameLossMsgEntry 56 }

wwpLeosTceCfmFrameLossMsgTotalTxLmm OBJECT-TYPE
     SYNTAX       Unsigned32
     MAX-ACCESS   read-only
     STATUS       current
     DESCRIPTION
             "This object represents the total LMMs transmitted"
     ::= { wwpLeosTceCfmFrameLossMsgEntry 57 }

wwpLeosTceCfmFrameLossMsgTotalRxLmm OBJECT-TYPE
     SYNTAX       Unsigned32
     MAX-ACCESS   read-only
     STATUS       current
     DESCRIPTION
             "This object represents the total LMMs received"
     ::= { wwpLeosTceCfmFrameLossMsgEntry 58 } 
     
 wwpLeosTceCfmFrameLossMsgTotalTxLmr OBJECT-TYPE
     SYNTAX       Unsigned32
     MAX-ACCESS   read-only
     STATUS       current
     DESCRIPTION
             "This object represents the total LMRs transmitted"
     ::= { wwpLeosTceCfmFrameLossMsgEntry 59 }
 
 wwpLeosTceCfmFrameLossMsgTotalRxLmr OBJECT-TYPE
     SYNTAX       Unsigned32
     MAX-ACCESS   read-only
     STATUS       current
     DESCRIPTION
             "This object represents the total LMRs received"
     ::= { wwpLeosTceCfmFrameLossMsgEntry 60 }      
     
  wwpLeosTceCfmFrameLossMsgAction OBJECT-TYPE
     SYNTAX       SendState
     MAX-ACCESS   read-create
     STATUS       current
     DESCRIPTION
             "This object represents the action for the message (send, clear or cancel)."
     ::= { wwpLeosTceCfmFrameLossMsgEntry 61 }

 --
 -- CFM Fault trap control
 --    
 wwpLeosCfmFaultTrapState OBJECT-TYPE
     SYNTAX       INTEGER {
     				disabled(1),
     				enabled(2)
     				}
     MAX-ACCESS   read-write
     STATUS       current
     DESCRIPTION
             "Setting this object to 'disabled' will cause
              CFM fault traps to be suppressed." 
     DEFVAL { enabled }
     ::= { wwpLeosCfmFaultNotif 1 }     
      
 --
 -- Notifications
 --  
 wwpLeosCfmFaultTrap  NOTIFICATION-TYPE
    OBJECTS {
                        wwpLeosCfmServiceName,
                        wwpLeosCfmServiceVlan,
                        wwpLeosCfmServiceMdLevel,
                        wwpLeosCfmServiceFaultTime, 
                        wwpLeosCfmServiceFaultType,
                        wwpLeosCfmServiceFaultDesc,
                        wwpLeosCfmServiceFaultMep                        
                        }
        STATUS  current
        DESCRIPTION
                "A notification is sent whenever the fault is detected."
        ::= { wwpLeosCfmNotifMIBNotification 1 }

 wwpLeosCfmPbtFaultTrap  NOTIFICATION-TYPE
        OBJECTS {
                        wwpLeosCfmServiceName,
                        wwpLeosCfmServiceType,
                        wwpLeosCfmServiceValue,
                        wwpLeosCfmServiceAdminState,
                        wwpLeosCfmServiceOperState,
                        wwpLeosCfmServiceFaultTime, 
                        wwpLeosCfmServiceFaultType,
                        wwpLeosCfmServiceFaultDesc                                                
                        }
        STATUS     deprecated
        DESCRIPTION
                "A notification is sent whenever the fault is detected for a PBT tunnel.
                 wwpLeosCfmServiceType will always be set to pbtTunnel."
        ::= { wwpLeosCfmNotifMIBNotification 2 }        
        
 wwpLeosCfmDelayFaultTrap  NOTIFICATION-TYPE
        OBJECTS {
                        wwpLeosCfmServiceName,
                        wwpLeosCfmServiceVlan,
                        wwpLeosCfmRemoteMEPDelay,
                        wwpLeosCfmDelayMsgDelayThreshold
                }
        STATUS	   current
        DESCRIPTION
        "A notification is sent whenever the fault is detected during
         a Delay Measurement test with a fault threshold."
        ::= { wwpLeosCfmNotifMIBNotification 3 }   
 
 wwpLeosCfmJitterFaultTrap  NOTIFICATION-TYPE
 	OBJECTS {
        		wwpLeosCfmServiceName,
        		wwpLeosCfmServiceVlan,
        		wwpLeosCfmRemoteMEPJitter,
        		wwpLeosCfmDelayMsgJitterThreshold        				        				
		   	}
	STATUS	   current
	DESCRIPTION
		"A notification is sent whenever the fault is detected during
		a Delay Measurement test with a fault threshold."
	::= { wwpLeosCfmNotifMIBNotification 4 }   

 wwpLeosCfmFrameLossNearFaultTrap  NOTIFICATION-TYPE
 	OBJECTS {
        		wwpLeosCfmServiceName,
        		wwpLeosCfmServiceVlan,
        		wwpLeosCfmRemoteMEPFrameLossNear,
        		wwpLeosCfmFrameLossMsgFlnThreshold        				        				
		   	}
	STATUS	   current
	DESCRIPTION
		"A notification is sent whenever the fault is detected during
		a Frame Loss Measurement test with a fault threshold."
	::= { wwpLeosCfmNotifMIBNotification 5 }   
 
 wwpLeosCfmFrameLossFarFaultTrap  NOTIFICATION-TYPE
 	OBJECTS {
        		wwpLeosCfmServiceName,
        		wwpLeosCfmServiceVlan,
        		wwpLeosCfmRemoteMEPFrameLossFar,
        		wwpLeosCfmFrameLossMsgFlfThreshold        				        				
		   	}
	STATUS	   current
	DESCRIPTION
		"A notification is sent whenever the fault is detected during
		a Frame Loss Measurement test with a fault threshold."
	::= { wwpLeosCfmNotifMIBNotification 6 } 
	
wwpLeosCfmExtDelayFaultTrap  NOTIFICATION-TYPE
 	OBJECTS {
        		wwpLeosCfmServiceName,
        		wwpLeosCfmServiceVlan,
        		wwpLeosCfmRemoteMEPDelay,
        		wwpLeosCfmExtDelayMsgDelayThreshold        				        				
		   	}
	STATUS	   current
	DESCRIPTION
		"A notification is sent whenever the fault is detected during
		a Delay Measurement test with a fault threshold."
	::= { wwpLeosCfmNotifMIBNotification 7 }   
 
 wwpLeosCfmExtJitterFaultTrap  NOTIFICATION-TYPE
 	OBJECTS {
        		wwpLeosCfmServiceName,
        		wwpLeosCfmServiceVlan,
        		wwpLeosCfmRemoteMEPJitter,
        		wwpLeosCfmExtDelayMsgJitterThreshold        				        				
		   	}
	STATUS	   current
	DESCRIPTION
		"A notification is sent whenever the fault is detected during
		a Delay Measurement test with a fault threshold."
	::= { wwpLeosCfmNotifMIBNotification 8 }   

 wwpLeosCfmExtFrameLossNearFaultTrap  NOTIFICATION-TYPE
 	OBJECTS {
        		wwpLeosCfmServiceName,
        		wwpLeosCfmServiceVlan,
        		wwpLeosCfmRemoteMEPFrameLossNear,
        		wwpLeosCfmExtFrameLossMsgFlnThreshold        				        				
		   	}
	STATUS	   current
	DESCRIPTION
		"A notification is sent whenever the fault is detected during
		a Frame Loss Measurement test with a fault threshold."
	::= { wwpLeosCfmNotifMIBNotification 9 }   
 
 wwpLeosCfmExtFrameLossFarFaultTrap  NOTIFICATION-TYPE
 	OBJECTS {
        		wwpLeosCfmServiceName,
        		wwpLeosCfmServiceVlan,
        		wwpLeosCfmRemoteMEPFrameLossFar,
        		wwpLeosCfmExtFrameLossMsgFlfThreshold        				        				
		   	}
	STATUS	   current
	DESCRIPTION
		"A notification is sent whenever the fault is detected during
		a Frame Loss Measurement test with a fault threshold."
	::= { wwpLeosCfmNotifMIBNotification 20 }   
 
 wwpLeosCfmExtFaultTrapSet  NOTIFICATION-TYPE
        OBJECTS      {
          		wwpLeosCfmServiceName,                                      
          		wwpLeosCfmServiceType,
          		wwpLeosCfmServiceValue,
          		wwpLeosCfmServiceAdminState,                 
          		wwpLeosCfmServiceOperState,
          		wwpLeosCfmServiceMdLevel,                 
          		wwpLeosCfmServiceFaultTime, 
          		wwpLeosCfmServiceFaultType,
          		wwpLeosCfmServiceFaultDesc,
          		wwpLeosCfmServiceFaultMep
       }
   STATUS      current
   DESCRIPTION
      "A notification is sent whenever the fault is detected."
   ::= { wwpLeosCfmNotifMIBNotification 21 }

 wwpLeosCfmExtFaultTrapClear  NOTIFICATION-TYPE
        OBJECTS      {
          		wwpLeosCfmServiceName,
          		wwpLeosCfmServiceType,        				        				
        		wwpLeosCfmServiceValue,
        		wwpLeosCfmServiceAdminState,                 
                wwpLeosCfmServiceOperState,
  		        wwpLeosCfmServiceMdLevel,     				
	            wwpLeosCfmServiceFaultTime, 
                wwpLeosCfmServiceFaultType,
                wwpLeosCfmServiceFaultDesc,
                wwpLeosCfmServiceFaultMep          }
   STATUS      current
   DESCRIPTION
      "A notification is sent whenever the fault is resolved and cleared."
   ::= { wwpLeosCfmNotifMIBNotification 22 }   
 
 wwpLeosCfmBadSequenceFaultTrap   NOTIFICATION-TYPE
 		OBJECTS { 
 				wwpLeosCfmServiceName,
        		wwpLeosCfmServiceVlan,  
        		wwpLeosCfmExtMEPLMMBadSequence,
        	 	wwpLeosCfmExtFrameLossMsgSeqThreshold     
        	 	}
 		STATUS      current
   		DESCRIPTION
      		"A notification is sent whenever wwpLeosCfmExtMEPLMMBadSequence exceeds wwpLeosCfmExtFrameLossMsgSeqThreshold 
      		in a Frame Loss Measurement test."
   ::= { wwpLeosCfmNotifMIBNotification 23 }
   
 wwpLeosCfmBlockOppositeMEPSetTrap	NOTIFICATION-TYPE
 	OBJECTS {
 				sysName,
 				wwpLeosCfmServiceMdLevel,
 				wwpLeosCfmServiceCfmMAID,
 				wwpLeosCfmExtMEPId,
 				wwpLeosCfmExtVlanId,
 				wwpLeosCfmExtMEPTagVID,
 				wwpLeosCfmExtMEPBlockOppositeFaultCurrent
 			}
 	STATUS	current
 	DESCRIPTION "A notification sent whenever the number of frames blocked by the presence
 				of a MEP of the opposite type exceeds the threshold during the sample window."
 	::= { wwpLeosCfmNotifMIBNotification 24 }
 
  wwpLeosCfmBlockOppositeMEPClearTrap	NOTIFICATION-TYPE
 	OBJECTS {
 				sysName,
 				wwpLeosCfmServiceMdLevel,
 				wwpLeosCfmServiceCfmMAID,
 				wwpLeosCfmExtMEPId,
 				wwpLeosCfmExtVlanId,
 				wwpLeosCfmExtMEPTagVID
 			}
 	STATUS	current
 	DESCRIPTION "A notification sent whenever the number of frames blocked by the presence
 				of a MEP of the opposite type drops below the threshold during the sample window."
 	::= { wwpLeosCfmNotifMIBNotification 25 }
	   
  --
 -- TCE Notifications
 --  
 wwpLeosCfmFaultTrapSet  NOTIFICATION-TYPE
        OBJECTS      {
          wwpLeosCfmServiceName,                                      
          wwpLeosCfmServiceType,
          wwpLeosCfmServiceValue,
          wwpLeosCfmServiceAdminState,                 
          wwpLeosCfmServiceOperState,
          wwpLeosCfmServiceMdLevel,                 
          wwpLeosCfmServiceFaultTime, 
          wwpLeosCfmServiceFaultType,
          wwpLeosCfmServiceFaultDesc,
          wwpLeosCfmServiceFaultMep,
          wwpLeosCfmServiceVsPbtName
       }
   STATUS      current
   DESCRIPTION
      "A notification is sent whenever the fault is detected."
   ::= { wwpLeosCfmNotifMIBNotification 10 }

 wwpLeosCfmFaultTrapClear  NOTIFICATION-TYPE
        OBJECTS      {
          wwpLeosCfmServiceName,                                      
          wwpLeosCfmServiceType,
          wwpLeosCfmServiceValue,
          wwpLeosCfmServiceAdminState,                 
          wwpLeosCfmServiceOperState,
          wwpLeosCfmServiceMdLevel,
          wwpLeosCfmServiceVsPbtName
       }
   STATUS      current
   DESCRIPTION
      "A notification is sent whenever the fault is resolved and cleared."
   ::= { wwpLeosCfmNotifMIBNotification 11 }
  
  wwpLeosCfmDmmTrap  NOTIFICATION-TYPE
        OBJECTS      {
          wwpLeosTceCfmDelayMsgServiceName,                                      
          wwpLeosTceCfmDelayMsgLocalMEPId,
          --wwpLeosTceCfmDelayMsgTargetMacAddr,                 
          wwpLeosTceCfmDelayMsgDelayThreshold,
          wwpLeosTceCfmDelayMsgDelay,
          wwpLeosTceCfmDelayMsgJitterThreshold,
          wwpLeosTceCfmDelayMsgJitter,
          wwpLeosTceCfmDelayMsgMaxJitterThreshold,
          wwpLeosTceCfmDelayMsgMaxJitter,
          wwpLeosTceCfmDelayMsgMaxDelayThreshold,
          wwpLeosTceCfmDelayMsgMaxDelay
          
                 }
   STATUS      current
   DESCRIPTION
      "A notification is sent whenever delay average goes above delay-threshold during a delay measurement test, 
      also generated when delay average goes below threshold after going up as a clearing event. 
      Same notification is generated whenever the average jitter goes above Jitter threshold during a delay measurement test
      and when the maximum delay and jitter go above the maximum delay and jitter thresholds respectively.
      Also generated when jitter average goes below jitter threshold after going up as a clearing event.
      When jitter event is generated, wwpLeosTceCfmDelayMsgDelayThreshold and wwpLeosTceCfmDelayMsgDelay
      varbind values are set to 0. Similarly when max delay event is generated wwpLeosTceCfmDelayMsgMaxJitter and
      wwpLeosTceCfmDelayMsgMaxJitterThreshold are set to 0 and vice versa"
   ::= { wwpLeosCfmNotifMIBNotification 12 }
  
  wwpLeosCfmLmmTrap  NOTIFICATION-TYPE
        OBJECTS      {
          wwpLeosTceCfmFrameLossMsgServiceName,                                      
          wwpLeosTceCfmFrameLossMsgLocalMEPId,
          --wwpLeosTceCfmFrameLossMsgTargetMacAddr,                 
          wwpLeosTceCfmFrameLossMsgNearLossThreshold,
          wwpLeosTceCfmFrameLossMsgFrameLossNear,
          wwpLeosTceCfmFrameLossMsgFarLossThreshold,
          wwpLeosTceCfmFrameLossMsgFrameLossFar
          
                 }
   STATUS      current
   DESCRIPTION
      "A notification is sent whenever FrameLoss Near average goes above FrameLoss Near threshold during a 
      Frame Loss measurement test. Also generated when FrameLoss Near average goes below FrameLoss Near threshold 
      after going up as a clearing event. 
      Same notification is generated whenever FrameLoss Far Average goes above Frameloss Far threshold value during a 
      Frame Loss measurement test. Also generated when Frameloss Far average goes below Frameloss Far threshold after going up
      as a clearing event. 
      When FrameLoss Near event is generated wwpLeosTceCfmFrameLossMsgFrameLossFar and  
      wwpLeosTceCfmFrameLossMsgFarLossThreshold varbind values are 0"
   ::= { wwpLeosCfmNotifMIBNotification 13 }

 --
 -- Add groups into the table
 --
 --

 END
