-- ArubaOS 7.2.0.0_36526
WLSX-STACK-MIB DEFINITIONS ::= BEGIN
IMPORTS
    TEXTUAL-CONVENTION, MODULE-IDENTITY, OBJECT-TYPE, Integer32,
    Counter64
                            FROM SNMPv2-SMI
    MacAddress
                            FROM SNMPv2-TC
    SnmpAdminString
                            FROM SNMP-FRAMEWORK-MIB
    OBJECT-GROUP
                            FROM SNMPv2-CONF
    wlsxEnterpriseMibModules
                            FROM ARUBA-MIB
	ArubaStackState FROM ARUBA-TC	
	;

    wlsxStackMIB MODULE-IDENTITY
    LAST-UPDATED "201108110000Z"
    ORGANIZATION "Aruba Wireless Networks"
    CONTACT-INFO
        "Postal:    1322 Crossman Avenue
                    Sunnyvale, CA 94089
        E-mail:     dl-support@arubanetworks.com
        Phone:      +1 408 227 4500"
    DESCRIPTION
        "This module describes an authoritative enterprise-specific Simple
        Network Management Protocol (SNMP) Management Information Base 
        (MIB):
        Stacking.
        Stacking feature allows for a set of devices connected through stacking
        ports to behave as a single chassis. Other network elements view it as a
        single node. The advantage with this feature is the simplified
        management and in L2 domain, multiple redundant links connected to stack
        do not form a loop.

        Copyright (C) 2002-2011 by Aruba Networks, Inc.
        All Rights Reserved."
    REVISION        "201108110000Z"
    DESCRIPTION
        "The initial revision of Stacking MIB." 
    ::= { wlsxEnterpriseMibModules 19 }

-- -----------------------------------------------------------------------------
    wlsxStackMIBObjects OBJECT-IDENTITY
    STATUS current
    DESCRIPTION
        "Branch For Stacking Subsystem Managed Objects."
    ::= { wlsxStackMIB 1 }
    
    wlsxStackMIBConformance OBJECT-IDENTITY
    STATUS current
    DESCRIPTION
        "Branch For Stacking Subsystem Conformance Information."
    ::= { wlsxStackMIB 2 }
     
    wlsxStackMIBGroups OBJECT-IDENTITY
    STATUS current
    DESCRIPTION
        "Branch For Stacking Subsystem Units of Conformance."
    ::= { wlsxStackMIBConformance 1 }
    
    wlsxStackMIBCompliances OBJECT-IDENTITY
    STATUS current
    DESCRIPTION
        "Branch For Stacking Subsystem Compliance Statements."
    ::= { wlsxStackMIBConformance 2 }

-- ----------------------------------------------------------------------------
    wlsxStackMember OBJECT IDENTIFIER ::= { wlsxStackMIBObjects 1 }

    wlsxStackMemberTable OBJECT-TYPE
    SYNTAX      SEQUENCE OF WlsxStackMemberEntry
    MAX-ACCESS  not-accessible
    STATUS      current
    DESCRIPTION
        "Stacking Member Table."
    ::= { wlsxStackMember 1 }

    wlsxStackMemberEntry OBJECT-TYPE
    SYNTAX      WlsxStackMemberEntry
    MAX-ACCESS  not-accessible
    STATUS      current
    DESCRIPTION
        "Am Entry in Stacking Member Table."
    INDEX { wlsxStackMemberId }
    ::= { wlsxStackMemberTable 1 }
    
    WlsxStackMemberEntry ::= SEQUENCE {
            wlsxStackMemberId                   Integer32,
            wlsxStackMemberState                ArubaStackState,
            wlsxStackMemberMacAddr              MacAddress,
            wlsxStackMemberPriority             Integer32,
            wlsxStackMemberHostName             SnmpAdminString,
            wlsxStackMemberSysLocation          SnmpAdminString,
            wlsxStackMemberChangeDetectSeqNum   Integer32,
            wlsxStackMemberSysUpTime            Integer32,
            wlsxStackMemberModelName            SnmpAdminString,
            wlsxStackMemberSWVersion            SnmpAdminString
    }
    
    wlsxStackMemberId OBJECT-TYPE
    SYNTAX      Integer32
    MAX-ACCESS  read-only
    STATUS      current
    DESCRIPTION
        "This object specifies the slot number of this element in stack."
    ::= { wlsxStackMemberEntry 1 }

    wlsxStackMemberState OBJECT-TYPE
    SYNTAX      ArubaStackState
    MAX-ACCESS  read-only
    STATUS      current
    DESCRIPTION
        "This object specifies state of this element in stack."
    ::= { wlsxStackMemberEntry 2 }

    wlsxStackMemberMacAddr OBJECT-TYPE
    SYNTAX      MacAddress
    MAX-ACCESS  read-only
    STATUS      current
    DESCRIPTION
        "This object specifies mac-address of this stack element."
    ::= { wlsxStackMemberEntry 3 }

    wlsxStackMemberPriority OBJECT-TYPE
    SYNTAX      Integer32
    MAX-ACCESS  read-only
    STATUS      current
    DESCRIPTION
        "This object specifies configured priority of this stack element."
    ::= { wlsxStackMemberEntry 4 }

    wlsxStackMemberHostName OBJECT-TYPE
    SYNTAX      SnmpAdminString
    MAX-ACCESS  read-only
    STATUS      current
    DESCRIPTION
        "This object specifies local host name of this stack element."
    ::= { wlsxStackMemberEntry 5 }

    wlsxStackMemberSysLocation OBJECT-TYPE
    SYNTAX      SnmpAdminString
    MAX-ACCESS  read-only
    STATUS      current
    DESCRIPTION
        "This object specifies local sys location of this stack element." 
    ::= { wlsxStackMemberEntry 6 }

    wlsxStackMemberChangeDetectSeqNum OBJECT-TYPE
    SYNTAX      Integer32
    MAX-ACCESS  read-only
    STATUS      current
    DESCRIPTION
        "This object specifies sequence number for any change that has been
        detected by the Aruba Stacking Protocol."
    ::= { wlsxStackMemberEntry 7 }

    wlsxStackMemberSysUpTime OBJECT-TYPE
    SYNTAX      Integer32
    UNITS       "seconds"
    MAX-ACCESS  read-only
    STATUS      current
    DESCRIPTION
        "This object specifies system up time of this stacking member since
        boot."
    ::= { wlsxStackMemberEntry 8 }

    wlsxStackMemberModelName OBJECT-TYPE
    SYNTAX      SnmpAdminString
    MAX-ACCESS  read-only
    STATUS      current
    DESCRIPTION
        "This object specifies Model Name of this element in the stack."
    ::= { wlsxStackMemberEntry 9 }

    wlsxStackMemberSWVersion OBJECT-TYPE
    SYNTAX      SnmpAdminString
    MAX-ACCESS  read-only
    STATUS      current
    DESCRIPTION
        "This object specifies software version running on this element in the
        stack."
    ::= { wlsxStackMemberEntry 10 }
-- ----------------------------------------------------------------------------
    wlsxStackProtoIf OBJECT IDENTIFIER ::= { wlsxStackMIBObjects 2 }

    wlsxStackProtoIfTable OBJECT-TYPE
    SYNTAX      SEQUENCE OF WlsxStackIfEntry
    MAX-ACCESS  not-accessible
    STATUS      current
    DESCRIPTION
        "Stacking Interface Table."
    ::= { wlsxStackProtoIf 1 }

    wlsxStackProtoIfEntry OBJECT-TYPE
    SYNTAX     WlsxStackIfEntry
    MAX-ACCESS  not-accessible
    STATUS      current
    DESCRIPTION
        "An Entry in Stack Manager Interface Table."
    INDEX { wlsxStackMemberId, wlsxStackProtoIfName }
    ::= { wlsxStackProtoIfTable 1 }

    WlsxStackIfEntry ::= SEQUENCE {
            wlsxStackProtoIfName                    SnmpAdminString,
            wlsxStackProtoIfNeighborState           INTEGER,
            wlsxStackProtoIfStatTxPkt               Counter64,
            wlsxStackProtoIfStatRxPkt               Counter64,
            wlsxStackProtoIfStatTxErr               Counter64,
            wlsxStackProtoIfStatNeighborTransDown   Counter64,
            wlsxStackProtoIfStatNeighborTransUp     Counter64,
            wlsxStackProtoIfStatKeepAliveTx         Counter64,
            wlsxStackProtoIfStatKeepAliveRx         Counter64,
            wlsxStackProtoIfStatRouteUpdateTx       Counter64,
            wlsxStackProtoIfStatRouteUpdateRx       Counter64
    }

    wlsxStackProtoIfName OBJECT-TYPE
    SYNTAX      SnmpAdminString
    MAX-ACCESS  not-accessible
    STATUS      current
    DESCRIPTION
        "This object specifies the interface name which is part of stacking
        link connected to other stacking element."
    ::= { wlsxStackProtoIfEntry 1 }

    wlsxStackProtoIfNeighborState OBJECT-TYPE
    SYNTAX      INTEGER {
                          up(1),
                          down(2)
                        }
    MAX-ACCESS  read-only
    STATUS      current
    DESCRIPTION
        "This object specifies adjacency state of this interface."
    ::= { wlsxStackProtoIfEntry 2 }

    wlsxStackProtoIfStatTxPkt OBJECT-TYPE
    SYNTAX      Counter64
    MAX-ACCESS  read-only
    STATUS      current
    DESCRIPTION
        "This object specifies count of stacking protocol packets transmitted 
        from this interface."
    ::= { wlsxStackProtoIfEntry 3 }

    wlsxStackProtoIfStatRxPkt OBJECT-TYPE
    SYNTAX      Counter64
    MAX-ACCESS  read-only
    STATUS      current
    DESCRIPTION
        "This object specifies count of stacking protocol packets received
        by this interface."
    ::= { wlsxStackProtoIfEntry 4 }

    wlsxStackProtoIfStatTxErr OBJECT-TYPE
    SYNTAX      Counter64
    MAX-ACCESS  read-only
    STATUS      current
    DESCRIPTION
        "This object specifies count of stacking protocol error packets
        transmitted from this interface."
    ::= { wlsxStackProtoIfEntry 5 }

    wlsxStackProtoIfStatNeighborTransDown OBJECT-TYPE
    SYNTAX      Counter64
    MAX-ACCESS  read-only
    STATUS      current
    DESCRIPTION
        "This object specifies count of transitions that a neighbor's state
        changed from up to down."
    ::= { wlsxStackProtoIfEntry 6 }

    wlsxStackProtoIfStatNeighborTransUp OBJECT-TYPE
    SYNTAX      Counter64
    MAX-ACCESS  read-only
    STATUS      current
    DESCRIPTION
        "This object specifies count of transitions that a neighbor's state
        changed from down to up."
    ::= { wlsxStackProtoIfEntry 7 }

    wlsxStackProtoIfStatKeepAliveTx OBJECT-TYPE
    SYNTAX      Counter64
    MAX-ACCESS  read-only
    STATUS      current
    DESCRIPTION
        "This object specifies count of transmitted keep-alive packets to its
        neighbor."
    ::= { wlsxStackProtoIfEntry 8 }

    wlsxStackProtoIfStatKeepAliveRx OBJECT-TYPE
    SYNTAX      Counter64
    MAX-ACCESS  read-only
    STATUS      current
    DESCRIPTION
        "This object specifies count of received keep-alive packets by this
        interface."
    ::= { wlsxStackProtoIfEntry 9 }

    wlsxStackProtoIfStatRouteUpdateTx OBJECT-TYPE
    SYNTAX      Counter64
    MAX-ACCESS  read-only
    STATUS      current
    DESCRIPTION
        "This object specifies count of transmitted route update notifications
        to its neighbor."
    ::= { wlsxStackProtoIfEntry 10 }

    wlsxStackProtoIfStatRouteUpdateRx OBJECT-TYPE
    SYNTAX      Counter64
    MAX-ACCESS  read-only
    STATUS      current
    DESCRIPTION
        "This object specifies count of received route update notifications by this interface."
    ::= { wlsxStackProtoIfEntry 11 }

-- ----------------------------------------------------------------------------

    wlsxStackTopo OBJECT IDENTIFIER ::= { wlsxStackMIBObjects 3 }

    wlsxStackTopoTable OBJECT-TYPE
    SYNTAX      SEQUENCE OF WlsxStackTopoEntry
    MAX-ACCESS  not-accessible
    STATUS      current
    DESCRIPTION
        "Stacking Topology Table."
    ::= { wlsxStackTopo 1 }

    wlsxStackTopoEntry OBJECT-TYPE
    SYNTAX     WlsxStackTopoEntry 
    MAX-ACCESS  not-accessible
    STATUS      current
    DESCRIPTION
        "An Entry in Stacking Topology Table."
    INDEX { wlsxStackMemberId, 
            wlsxStackProtoIfName }
    ::= { wlsxStackTopoTable 1 }

    WlsxStackTopoEntry ::= SEQUENCE {
            wlsxStackTopoNeighborSlot         Integer32,
            wlsxStackTopoNeighborIfName       SnmpAdminString,
            wlsxStackNeighborState            INTEGER
    }

    wlsxStackTopoNeighborSlot OBJECT-TYPE
    SYNTAX      Integer32
    MAX-ACCESS  read-only
    STATUS      current
    DESCRIPTION
        "This object specifies the Slot number of the neighbor stack element to
        which this one is connected."
    ::= { wlsxStackTopoEntry 1 }

    wlsxStackTopoNeighborIfName OBJECT-TYPE
    SYNTAX      SnmpAdminString
    MAX-ACCESS  read-only
    STATUS      current
    DESCRIPTION
        "This object specifies the interface name of the neighbor slot to which this
        element is connected."
    ::= { wlsxStackTopoEntry 2 }

    wlsxStackNeighborState OBJECT-TYPE
    SYNTAX      INTEGER {
                          unknown(1),
                          initializing(2),
                          up(3),
                          failed(4),
                          down(5)
                        }
    MAX-ACCESS  read-only
    STATUS      current
    DESCRIPTION
        "This object specifies the state of the neighbor slot.
            unknown(1)      - The state of the neighbor slot can not be retrieved.
            initializing(2) - The neighbor is in initializing state.
            up(3)           - The neighbor element is up and running.
            failed(4)       - The neighbor element has failed to operate.
            down(5)         - The neighbor element is in down state."
    ::= { wlsxStackTopoEntry 3 }

-- ----------------------------------------------------------------------------
-- COMPLIANCE
-- ----------------------------------------------------------------------------
    wlsxStackMIBCompliance MODULE-COMPLIANCE
    STATUS    current
    DESCRIPTION
        "Compliance statement for Stacking."
    MODULE
    MANDATORY-GROUPS {
                       wlsxStackChasGroup,
                       wlsxStackTopologyGroup,
                       wlsxStackProtoIfGroup
                    }
    ::= { wlsxStackMIBCompliances 1 }

-- ----------------------------------------------------------------------------
-- UNITS OF CONFORMANCE
-- ----------------------------------------------------------------------------
    wlsxStackChasGroup OBJECT-GROUP
    OBJECTS {
              wlsxStackMemberState,
              wlsxStackMemberMacAddr,
              wlsxStackMemberPriority,
              wlsxStackMemberHostName,
              wlsxStackMemberSysLocation,
              wlsxStackMemberChangeDetectSeqNum,
              wlsxStackMemberSysUpTime,
              wlsxStackMemberModelName,
              wlsxStackMemberSWVersion
           }
    STATUS current
    DESCRIPTION
        "Collection of objects for Stacking Member Entry."
    ::= { wlsxStackMIBGroups 1 }

    wlsxStackTopologyGroup OBJECT-GROUP
    OBJECTS {
                wlsxStackTopoNeighborSlot,
                wlsxStackTopoNeighborIfName
            }
    STATUS current
    DESCRIPTION
        "Collection of objects for Stacking Topology formation."
    ::= { wlsxStackMIBGroups 2 }

    wlsxStackProtoIfGroup OBJECT-GROUP
    OBJECTS {
               wlsxStackProtoIfName,
               wlsxStackProtoIfNeighborState,
               wlsxStackProtoIfStatTxPkt,
               wlsxStackProtoIfStatRxPkt,
               wlsxStackProtoIfStatTxErr,
               wlsxStackProtoIfStatNeighborTransDown,
               wlsxStackProtoIfStatNeighborTransUp,
               wlsxStackProtoIfStatKeepAliveTx,
               wlsxStackProtoIfStatKeepAliveRx,
               wlsxStackProtoIfStatRouteUpdateTx,
               wlsxStackProtoIfStatRouteUpdateRx
            }
    STATUS current
    DESCRIPTION
        "Collection of objects for Interface list information."
    ::= { wlsxStackMIBGroups 3 }

-- ----------------------------------------------------------------------------
END
