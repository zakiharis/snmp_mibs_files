--
-- WS-INFRA-SMTP-NOTIFY.my
-- MIB generated by MG-SOFT Visual MIB Builder Version 6.0  Build 88
-- Tuesday, June 17, 2008 at 14:29:37
--

	WS-INFRA-SMTP-NOTIFY DEFINITIONS ::= BEGIN
 
		IMPORTS
			OBJECT-GROUP, MODULE-COMPLIANCE			
				FROM SNMPv2-CONF			
			OBJECT-TYPE, MODULE-IDENTITY			
				FROM SNMPv2-SMI			
			DisplayString, TruthValue			
				FROM SNMPv2-TC			
			wsInfraSmtpNotify			
				FROM WS-INFRA-SMI-MIB			
			AbbrevRowStatus			
				FROM WS-TYPE-MIB;
	
	
		-- 1.3.6.1.4.1.388.14.1.12.1
		wsInfraSmtpNotifyMibModule MODULE-IDENTITY 
			LAST-UPDATED "200806171427Z"		-- June 17, 2008 at 14:27 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"SMTP Notification Configuration and Status."
			REVISION "200806171427Z"		-- June 17, 2008 at 14:27 GMT
			DESCRIPTION 
				"01a03
				Removed wsInfraSmtpNotifyServerAddr.
				
				Redefined wsInfraSmtpNotifyServerName 
				to be either the FQDN or 
				the IP address of the SMTP server."
			REVISION "200806031150Z"		-- June 03, 2008 at 11:50 GMT
			DESCRIPTION 
				"01a02
				
				Added the following objects:
				- wsInfraSmtpNotifySubjectPrefix
				- wsInfraSmtpNotifyServerAuthEnable
				- wsInfraSmtpNotifyServerAuthUserName
				- wsInfraSmtpNotifyServerAuthPassword"
			REVISION "200805011427Z"		-- May 01, 2008 at 14:27 GMT
			DESCRIPTION 
				"01a01
				Initial revision."
			::= { wsInfraSmtpNotify 1 }

		
	
	
	
--
-- Node definitions
--
	
		-- 1.3.6.1.4.1.388.14.1.12.1.1
		wsInfraSmtpNotifyMIB OBJECT IDENTIFIER ::= { wsInfraSmtpNotifyMibModule 1 }

		
		-- 1.3.6.1.4.1.388.14.1.12.1.1.1
		wsInfraSmtpNotifyServerName OBJECT-TYPE
			SYNTAX DisplayString
			MAX-ACCESS read-write
			STATUS current
			DESCRIPTION
				"The fully-qualified domain name or the IP address of the SMTP server.
				If the name is unknown, the value is a zero-length string."
			::= { wsInfraSmtpNotifyMIB 1 }

		
		-- 1.3.6.1.4.1.388.14.1.12.1.1.3
		wsInfraSmtpNotifyServerPort OBJECT-TYPE
			SYNTAX INTEGER (1..65535)
			MAX-ACCESS read-write
			STATUS current
			DESCRIPTION
				"The TCP port number of the SMTP server.
				The default TCP port is 25."
			::= { wsInfraSmtpNotifyMIB 3 }

		
		-- 1.3.6.1.4.1.388.14.1.12.1.1.4
		wsInfraSmtpNotifyFromAddr OBJECT-TYPE
			SYNTAX DisplayString (SIZE (1..128))
			MAX-ACCESS read-write
			STATUS current
			DESCRIPTION
				"Sender e-mail address in the e-mail notification."
			::= { wsInfraSmtpNotifyMIB 4 }

		
		-- 1.3.6.1.4.1.388.14.1.12.1.1.5
		wsInfraSmtpNotifyToAddrTable OBJECT-TYPE
			SYNTAX SEQUENCE OF WsInfraSmtpNotifyToAddrEntry
			MAX-ACCESS not-accessible
			STATUS current
			DESCRIPTION
				"Recipient e-mail addresses in the e-mail notification."
			::= { wsInfraSmtpNotifyMIB 5 }

		
		-- 1.3.6.1.4.1.388.14.1.12.1.1.5.1
		wsInfraSmtpNotifyToAddrEntry OBJECT-TYPE
			SYNTAX WsInfraSmtpNotifyToAddrEntry
			MAX-ACCESS not-accessible
			STATUS current
			DESCRIPTION
				" "
			INDEX { wsInfraSmtpNotifyToAddrIdx }
			::= { wsInfraSmtpNotifyToAddrTable 1 }

		
		WsInfraSmtpNotifyToAddrEntry ::=
			SEQUENCE { 
				wsInfraSmtpNotifyToAddrIdx
					INTEGER,
				wsInfraSmtpNotifyToAddrVal
					DisplayString,
				wsInfraSmtpNotifyToAddrRowStatus
					AbbrevRowStatus
			 }

		-- 1.3.6.1.4.1.388.14.1.12.1.1.5.1.1
		wsInfraSmtpNotifyToAddrIdx OBJECT-TYPE
			SYNTAX INTEGER (1..4)
			MAX-ACCESS read-only
			STATUS current
			DESCRIPTION
				"Simple index."
			::= { wsInfraSmtpNotifyToAddrEntry 1 }

		
		-- 1.3.6.1.4.1.388.14.1.12.1.1.5.1.2
		wsInfraSmtpNotifyToAddrVal OBJECT-TYPE
			SYNTAX DisplayString (SIZE (1..128))
			MAX-ACCESS read-create
			STATUS current
			DESCRIPTION
				"Recipient e-mail address."
			::= { wsInfraSmtpNotifyToAddrEntry 2 }

		
		-- 1.3.6.1.4.1.388.14.1.12.1.1.5.1.3
		wsInfraSmtpNotifyToAddrRowStatus OBJECT-TYPE
			SYNTAX AbbrevRowStatus
			MAX-ACCESS read-create
			STATUS current
			DESCRIPTION
				"The Row status. All columns must be supplied to create a row."
			::= { wsInfraSmtpNotifyToAddrEntry 3 }

		
		-- 1.3.6.1.4.1.388.14.1.12.1.1.6
		wsInfraSmtpNotifyEnable OBJECT-TYPE
			SYNTAX TruthValue
			MAX-ACCESS read-write
			STATUS current
			DESCRIPTION
				"Enable e-mail notification."
			::= { wsInfraSmtpNotifyMIB 6 }

		
		-- 1.3.6.1.4.1.388.14.1.12.1.1.7
		wsInfraSmtpNotifyLastFailedReason OBJECT-TYPE
			SYNTAX DisplayString
			MAX-ACCESS read-only
			STATUS current
			DESCRIPTION
				"Last e-mail notification failed reason."
			::= { wsInfraSmtpNotifyMIB 7 }

		
		-- 1.3.6.1.4.1.388.14.1.12.1.1.8
		wsInfraSmtpNotifySubjectPrefix OBJECT-TYPE
			SYNTAX DisplayString (SIZE (0..16))
			MAX-ACCESS read-write
			STATUS current
			DESCRIPTION
				"Prefix for E-mail Notification subject line."
			::= { wsInfraSmtpNotifyMIB 8 }

		
		-- 1.3.6.1.4.1.388.14.1.12.1.1.9
		wsInfraSmtpNotifyServerAuth OBJECT IDENTIFIER ::= { wsInfraSmtpNotifyMIB 9 }

		
		-- 1.3.6.1.4.1.388.14.1.12.1.1.9.1
		wsInfraSmtpNotifyServerAuthEnable OBJECT-TYPE
			SYNTAX TruthValue
			MAX-ACCESS read-write
			STATUS current
			DESCRIPTION
				"Enable or disable SMTP Server Authentication."
			::= { wsInfraSmtpNotifyServerAuth 1 }

		
		-- 1.3.6.1.4.1.388.14.1.12.1.1.9.2
		wsInfraSmtpNotifyServerAuthUserName OBJECT-TYPE
			SYNTAX DisplayString (SIZE (0..64))
			MAX-ACCESS read-write
			STATUS current
			DESCRIPTION
				"Username to be used during SMTP Server Authentication."
			::= { wsInfraSmtpNotifyServerAuth 2 }

		
		-- 1.3.6.1.4.1.388.14.1.12.1.1.9.3
		wsInfraSmtpNotifyServerAuthPassword OBJECT-TYPE
			SYNTAX DisplayString (SIZE (0..64))
			MAX-ACCESS read-write
			STATUS current
			DESCRIPTION
				"Password to be used during SMTP Server Authentication.
				
				This object returns NULL string when read."
			::= { wsInfraSmtpNotifyServerAuth 3 }

		
		-- 1.3.6.1.4.1.388.14.1.12.1.1.100
		wsInfraSmtpNotifyConf OBJECT IDENTIFIER ::= { wsInfraSmtpNotifyMIB 100 }

		
		-- 1.3.6.1.4.1.388.14.1.12.1.1.100.1
		wsInfraSmtpNotifyGroups OBJECT IDENTIFIER ::= { wsInfraSmtpNotifyConf 1 }

		
		-- 1.3.6.1.4.1.388.14.1.12.1.1.100.1.1
		wsInfraSmtpNotifyObjectGroup OBJECT-GROUP
			OBJECTS { wsInfraSmtpNotifyServerName, wsInfraSmtpNotifyServerPort, wsInfraSmtpNotifyFromAddr, wsInfraSmtpNotifyToAddrIdx, wsInfraSmtpNotifyToAddrVal, 
				wsInfraSmtpNotifyToAddrRowStatus, wsInfraSmtpNotifyEnable, wsInfraSmtpNotifyLastFailedReason, wsInfraSmtpNotifySubjectPrefix, wsInfraSmtpNotifyServerAuthEnable, 
				wsInfraSmtpNotifyServerAuthUserName, wsInfraSmtpNotifyServerAuthPassword }
			STATUS current
			DESCRIPTION 
				" "
			::= { wsInfraSmtpNotifyGroups 1 }

		
		-- 1.3.6.1.4.1.388.14.1.12.1.1.100.2
		wsInfraSmtpNotifyCompliances OBJECT IDENTIFIER ::= { wsInfraSmtpNotifyConf 2 }

		
		-- 1.3.6.1.4.1.388.14.1.12.1.1.100.2.1
		wsInfraSmtpNotifyCompliance MODULE-COMPLIANCE
			STATUS current
			DESCRIPTION 
				" "
			MODULE -- this module
				MANDATORY-GROUPS { wsInfraSmtpNotifyObjectGroup }
			::= { wsInfraSmtpNotifyCompliances 1 }

		
	
	END

--
-- WS-INFRA-SMTP-NOTIFY.my
--
