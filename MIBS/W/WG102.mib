-- ********************************************************************
-- * Wireless LAN Access Point Management Base
-- ********************************************************************

	WG102 DEFINITIONS ::= BEGIN
 
		IMPORTS
		    TimeTicks
                FROM RFC1155-SMI		
			OBJECT-GROUP			
				FROM SNMPv2-CONF
			MODULE-IDENTITY, OBJECT-TYPE, Unsigned32, enterprises, IpAddress			
				FROM SNMPv2-SMI			
			DisplayString, TruthValue			
				FROM SNMPv2-TC;
	
	
		wg102 MODULE-IDENTITY 
			LAST-UPDATED "200611151600Z"		-- Nov 15, 2006 at 16:00 GMT
			ORGANIZATION 
				"NETGEAR Inc."
			CONTACT-INFO 
				"4500 Great America Parkway
				Santa Clara, California 95054
				Phone: (408) 907-8000
				Fax: (408) 907-8097
				Web Site: http://www.netgear.com"
			DESCRIPTION 
				"The MIB module for 802.11b/g ProSafe Wireless Access Point entities.
				iso(1).org(3).dod(6).internet(1).private(4).
				enterprises(1).netgear(4526).wireless(4).wg102(3)"
			::= { wireless 3 }

		
	
	
--
-- Node definitions
--
	
		netgear OBJECT IDENTIFIER ::= { enterprises 4526 }

		
		wireless OBJECT IDENTIFIER ::= { netgear 4 }

		
		sysSettings OBJECT IDENTIFIER ::= { wg102 1 }

		
		sysMacAddress OBJECT-TYPE
			SYNTAX DisplayString (SIZE(6..17))
			MAX-ACCESS read-only
			STATUS current
			DESCRIPTION
				"This field indicates the system MAC Address."
			::= { sysSettings 1 }

		
		sysVersion OBJECT-TYPE
			SYNTAX DisplayString
			MAX-ACCESS read-only
			STATUS current
			DESCRIPTION
				"This field indicates the system firmware version."
			::= { sysSettings 2 }

		
		sysAPName OBJECT-TYPE
			SYNTAX DisplayString (SIZE (1..32))
			MAX-ACCESS read-write
			STATUS current
			DESCRIPTION
				"This field indicates the name of AP. The name is also the
				NETBIOS name of the AP."
			::= { sysSettings 3 }

		
		sysAdminName OBJECT-TYPE
			SYNTAX DisplayString (SIZE (0..32))
			MAX-ACCESS read-only
			STATUS current
			DESCRIPTION
				"This field indicates the administrator name, which is used
				to sign in web GUI, SSH, CLI, and FTP server of the AP."
			::= { sysSettings 4 }

		
		sysAdminPasswd OBJECT-TYPE
			SYNTAX DisplayString (SIZE (0..32))
			MAX-ACCESS read-only
			STATUS current
			DESCRIPTION
				"This field indicates the administrator password, which is
				used to sign in web GUI, SSH, CLI, and FTP server of the
				AP."
			::= { sysSettings 5 }

		
		sysCountryRegion OBJECT-TYPE
			SYNTAX INTEGER
				{
				asia(410),
        		australia(36),
        		canada(124),
        		denmark(208),
        		europe(40),
        		finland(246),
        		france(250),
        		germany(276),
        		ireland(372),
        		italy(380),
        		japan(392),
        		mexico(484),
        		netherlands(528),
        		newZealand(554),
        		norway(578),
        		puertoRico(630),
        		southAmerica(340),
        		spain(724),
        		sweden(752),
        		switzerland(756),
        		unitedKingdom(826),
        		unitedStates(840)
				}
			MAX-ACCESS read-write
			STATUS current
			DESCRIPTION
				"This field indicates the country/region of the AP."
			::= { sysSettings 7 }

		
		timeSettings OBJECT IDENTIFIER ::= { sysSettings 8 }

		
		timeCurrentTime OBJECT-TYPE
			SYNTAX DisplayString (SIZE (1..20))
			MAX-ACCESS read-only
			STATUS current
			DESCRIPTION
				"This field indicates the current system time in a format:
				YYYY/MM/DD hh:mm:ss."
			::= { timeSettings 1 }

		
		timeTimeZone OBJECT-TYPE
			SYNTAX INTEGER
				{
				gmt00UkGreenWichCasablancaMonrovia(0),		                      
				gmtwest12EniwetokKwajalein(1),                                  
				gmtwest11MidwayIslandSamoa(2),                                    
				gmtwest10Hawaii(3),                                              
				gmtwest9dot5MarqesasIs(4),                                        
				gmtwest09Alaska(5),                                              
				gmtwest8dot5PitciarnIs(6),                                        
				gmtwest08PacificTimeUsCanada(7),                        
				gmtwest07MountainTimeUsArizona(8),                           
				gmtwest06CentralTimeUsMexicoCityTequciqalpa(9),            
				gmtwest05EasternTimeUsBogotaLimaQuitoIndianaEast(10),     
				gmtwest04CaracasLaPaz(11),                                      
				gmtwest3dot5Newfoundland(12),                                        
				gmtwest03BrasiliaBeunosAiresGeorgetown(13),                    
				gmtwest02MidAtlantic(14),                                        
				gmtwest01AzoresCapeVerdeIs(15),                               
				gmteast01Europe(16),                                              
				gmteast02EgyptFinlandRomaniaTurkeyGreeceIsraelJordan(17),    
				gmteast03IraqSyriaRussia(18),                                  
				gmteast3dot5Iran(19),                                                
				gmteast04ArmeniaAzerbaijan(20),                                 
				gmteast4dot5Afghanistan(21),                                         
				gmteast05RussiaPakistan(22),                                     
				gmteast5dot5India(23),                                               
				gmteast06BangladeshRussia(24),                                   
				gmteast6dot5Burma(25),                                               
				gmteast07RussiaThailandCombodiaLaos(26),                     
				gmteast08RussiaChinaMongoliaIndonesiaPhilippinesTaiwanWA(27),
				gmteast09RussiaJapanKorea(28),                                  
				gmteast9dot5AdelaideDarwin(29),                                     
				gmteast10EasternStandardAustRussiaGaumPapuaNewGuinea(30)
				}
			MAX-ACCESS read-write
			STATUS current
			DESCRIPTION
				"This field indicates the timezone of the system.
				0     UK,GreenWich,Casablanca,Monrovia (GMT),
    			-12   Eniwetok,Kwajalein (GMT-12:00),
    			-11   Midway I., Samoa (GMT-11:00),
    			-10   Hawaii (GMT-10:00),
    			-9.5  Marqesas Is. (GMT-09:30),
    			-9    Alaska (GMT-09:00),
    			-8.5  Pitciarn Is. (GMT-08:30),
    			-8    Pacific Time ..US and Canada (GMT-08:00),
    			-7    MountainTime(USA),Arizona (GMT-07:00),
    			-6    CentralTime(USA),Mexico City,Tequciqalpa (GMT-06:00),
    			-5    EasternTime(USA),Bogota,Lima,Quito,Indiana East (GMT-05:00),
    			-4    Caracas,La Paz (GMT-04:00),
    			-3.5  Newfoundland (GMT-03:30),
    			-3    Brasilia,Beunos Aires,Georgetown (GMT-03:00),
    			-2    Mid-Atlantic (GMT-02:00),
    			-1    Azores,Cape Verde Is. (GMT-01:00),
    			1     Europe (GMT+01:00),
    			2     Egypt,Finland,Romania,Turkey,Greece,Israel,Jordan(GMT+02:00),
    			3     Iraq, Syria,Russia (GMT+03:00),
    			3.5   Iran (GMT+03:30),
    			4     Armenia, Azerbaijan (GMT+04:00),
    			4.5   Afghanistan (GMT+04:30),
    			5     Russia,Pakistan (GMT+05:00),
    			5.5   India (GMT+05:30),
    			6     Bangladesh,Russia (GMT+06:00),
    			6.5   Burma (GMT+06:30),
    			7     Russia,Thailand, Combodia, Laos (GMT+07:00),
    			8     Russia,China,Mongolia,Indonesia,Philippines,Taiwan,WA (GMT+08:00),
    			9     Russia,Japan,Korea (GMT+09:00),
    			9.5   Adelaide,Darwin (GMT+09:30),
    			10    Eastern Standard(Aust),Russia,Gaum,Papua New Guinea (GMT+10:00)"
			::= { timeSettings 2 }

		
		timeDaylightSaving OBJECT-TYPE
			SYNTAX TruthValue
			MAX-ACCESS read-write
			STATUS current
			DESCRIPTION
				"This field indicates whether the Daylight Saving time is
				used."
			::= { timeSettings 3 }
			
		 timeNtpServer OBJECT-TYPE
            SYNTAX DisplayString (SIZE (1..32))
			MAX-ACCESS read-write
			STATUS current
			DESCRIPTION
				"This field indicates the hostname or IP address for the NTP server.
				If you want to use a custom NTP server, you can specify it for the Access Point. 
				Otherwise, you can just leave it blank."
			::= { timeSettings 4 }

		
		ipSettings OBJECT IDENTIFIER ::= { sysSettings 9 }

		
		ipDhcpClientEnable OBJECT-TYPE
			SYNTAX TruthValue
			MAX-ACCESS read-write
			STATUS current
			DESCRIPTION
				"This field indicates whether DHCP client is enabled."
			::= { ipSettings 1 }

		
		ipIPAddress OBJECT-TYPE
			SYNTAX IpAddress
			MAX-ACCESS read-write
			STATUS current
			DESCRIPTION
				"This field indicates the IP address of the AP. "
			::= { ipSettings 2 }

		
		ipNetmask OBJECT-TYPE
			SYNTAX IpAddress
			MAX-ACCESS read-write
			STATUS current
			DESCRIPTION
				"This field indicates the netmask addressof the AP."
			::= { ipSettings 3 }

		
		ipGateway OBJECT-TYPE
			SYNTAX IpAddress
			MAX-ACCESS read-write
			STATUS current
			DESCRIPTION
				"This field indicates the default gateway address of the AP."
			::= { ipSettings 4 }

		
		ipDnsServer OBJECT-TYPE
			SYNTAX IpAddress
			MAX-ACCESS read-write
			STATUS current
			DESCRIPTION
				"This field indicates the IP address of the DNS
				server. *** Note: The value can only be set to an IP
				address in dot format."
			::= { ipSettings 5 }
			
		
		wlanSettings OBJECT IDENTIFIER ::= { wg102 2 }

		
-- **********************************************************************
-- *  Wireless Settings Table
-- **********************************************************************
		wlanSettingTable OBJECT-TYPE
			SYNTAX SEQUENCE OF WlanSettingEntry
			MAX-ACCESS not-accessible
			STATUS current
			DESCRIPTION
				"wlanSettingsallow for multiple instances on an agent."
			::= { wlanSettings 1 }

		
		wlanSettingEntry OBJECT-TYPE
			SYNTAX WlanSettingEntry
			MAX-ACCESS not-accessible
			STATUS current
			DESCRIPTION
				"An entry in the wlanSettingTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex }
			::= { wlanSettingTable 1 }

		
		WlanSettingEntry ::=
			SEQUENCE { 
				radioIndex
					INTEGER,
				radioEnable
					TruthValue,
				wirelessMode
					INTEGER,
				channel
					INTEGER,
				txRate
					INTEGER,
				txPower
					INTEGER,
				beaconInterval
					INTEGER,
				dtimInterval
					INTEGER,
				rtsThreshold
					INTEGER,
				fragmentationThreshold
					INTEGER,
				dot11bPreamble
					INTEGER,
				superMode
					TruthValue,
				wmm	
					TruthValue,
				wmmNoAck
					TruthValue,		
				acEnabled
					TruthValue,
				acEnhancedRFSecurity
					INTEGER,	
				acRogueDevDetection
					TruthValue,
				accessControlMode
					INTEGER
			 }
			 
			 
		radioIndex OBJECT-TYPE
			SYNTAX INTEGER
				{
				dot11a(0),
				dot11bg(1)
				}
			MAX-ACCESS read-only
			STATUS current
			DESCRIPTION
				"This attribute shall indicate the radio's band."
			::= { wlanSettingEntry 1 }
			
			
		radioEnable OBJECT-TYPE
			SYNTAX TruthValue
			MAX-ACCESS read-write
			STATUS current
			DESCRIPTION
				"This attribute shall indicate whether the radio is enabled."
			::= { wlanSettingEntry 2 }
		
		wirelessMode OBJECT-TYPE
			SYNTAX INTEGER
				{
				auto(0),
				dot11a(1),
				dot11b(2),
				dot11g(3)
				}
			MAX-ACCESS read-write
			STATUS current
			DESCRIPTION
				"This attribute shall indicate the desired wireless
				operating mode.
				
				Options are:
				  auto - Both 802.11g and 802.11b wireless stations can be
				         used.
				dot11a - Only 802.11a wireless stations can be used.
				dot11b - All 802.11b wireless stations can be used.
					 802.11g wireless stations can still be used
					 if they can operate in 802.11b mode.
				dot11g - Only 802.11g wireless stations can be used."
			::= { wlanSettingEntry 5 }

		
		channel OBJECT-TYPE
			SYNTAX INTEGER (0..165)
			MAX-ACCESS read-write
			STATUS current
			DESCRIPTION
				"This attribute shall indicate the channel number to be
				used. And the zero indicates that auto channel selection is enabled."
			::= { wlanSettingEntry 6 }

		
		txRate OBJECT-TYPE
			SYNTAX INTEGER
				{
				best(0),
				rate1Mbps(1),
				rate2Mbps(2),
				rate5dot5Mbps(3),
				rate6Mbps(4),
				rate9Mbps(5),
				rate11Mbps(6),
				rate12Mbps(7),
				rate18Mbps(8),
				rate24Mbps(9),
				rate36Mbps(10),
				rate48Mbps(11),
				rate54Mbps(12)
				}
			MAX-ACCESS read-write
			STATUS current
			DESCRIPTION
				"This attribute shall indicate the transmite rate. When
				the operatemode is:
				
				   auto(0) - can set to 0:best, 1:1Mb/s, 2:2Mb/s,
				             5.5:5.5Mb/s, 11:11 Mb/s, 6:6Mb/s, 9:9Mb/s,
				             12:12Mb/s, 18:18Mb/s, 24:24Mb/s, 36:36Mb/s,
				             48:48Mb/s, and 54:54Mb/s.
				
				 dot11a(1) - can set to 0:best, 6:6Mb/s, 9:9Mb/s,
				             12:12Mb/s, 18:18Mb/s, 24:24Mb/s,
				             36:36Mb/s, 48:48Mb/s, 54:54Mb/s.
				
				 dot11b(2) - can set to 0:best, 1:1Mb/s, 2:2Mb/s,
				             5.5:5.5Mb/s, and 11:11 Mb/s.
				
				 dot11g(3) - can set to 0:best, 6:6Mb/s, 9:9Mb/s,
				             12:12Mb/s, 18:18Mb/s, 24:24Mb/s,
				             36:36Mb/s, 48:48Mb/s, 54:54Mb/s."
			::= { wlanSettingEntry 7 }

		
		txPower OBJECT-TYPE
			SYNTAX INTEGER
				{
				full(0),
				half(1),
				quarter(2),
				eighth(3),
				min(4)
				}
			MAX-ACCESS read-write
			STATUS current
			DESCRIPTION
				"This attribute shall indicate the transmitting power."
			::= { wlanSettingEntry 8 }

		
		beaconInterval OBJECT-TYPE
			SYNTAX INTEGER (20..1000)
			UNITS "1024 microsecond"
			MAX-ACCESS read-write
			STATUS current
			DESCRIPTION
				"This attribute shall indicate the beacon interval."
			::= { wlanSettingEntry 9 }

		
		dtimInterval OBJECT-TYPE
			SYNTAX INTEGER (1..255)
			MAX-ACCESS read-write
			STATUS current
			DESCRIPTION
				"This attribute shall indicate the DTIM period."
			::= { wlanSettingEntry 10 }

		
		rtsThreshold OBJECT-TYPE
			SYNTAX INTEGER (0..2346)
			MAX-ACCESS read-write
			STATUS current
			DESCRIPTION
				"This attribute shall indicate the RTS threshold."
			::= { wlanSettingEntry 11 }

		
		fragmentationThreshold OBJECT-TYPE
			SYNTAX INTEGER (256..2346)
			MAX-ACCESS read-write
			STATUS current
			DESCRIPTION
				"This attribute shall indicate the fragmentation threshold."
			::= { wlanSettingEntry 12 }

		
		dot11bPreamble OBJECT-TYPE
			SYNTAX INTEGER
				{
				long(0),
				auto(1)
				}
			MAX-ACCESS read-write
			STATUS current
			DESCRIPTION
				"This attribute shall indicate the preamble setting.
				This setting is only applicable to 802.11b mode."
			::= { wlanSettingEntry 13 }

		
		superMode OBJECT-TYPE
			SYNTAX TruthValue
			MAX-ACCESS read-write
			STATUS current
			DESCRIPTION
				"This attribute shall indicate whether super mode (super-A
				for 11a radio, Super-G for 11g radio) is enabled."
			::= { wlanSettingEntry 14 }
		
		
		wmm OBJECT-TYPE
			SYNTAX TruthValue
			MAX-ACCESS read-write
			STATUS current
			DESCRIPTION
				"This attribute shall indicate whether wmm is enabled."
			::= { wlanSettingEntry 15 }
		
		
		wmmNoAck OBJECT-TYPE
			SYNTAX TruthValue
			MAX-ACCESS read-write
			STATUS current
			DESCRIPTION
				"This attribute shall indicate whether wmm with no ack is enabled."
			::= { wlanSettingEntry 16 }
		
		acEnabled OBJECT-TYPE
			SYNTAX TruthValue
			MAX-ACCESS read-write
			STATUS current
			DESCRIPTION
				"This field indicates whether enable AutoCell."
			::= { wlanSettingEntry 17 }

		
		acEnhancedRFSecurity OBJECT-TYPE
			SYNTAX INTEGER
				{
				disable(0),
				enable(3)
				}
			MAX-ACCESS read-write
			STATUS current
			DESCRIPTION
				"This field indicates whether enable Enhanced RF Security."
			::= { wlanSettingEntry 18 }
		
		acRogueDevDetection OBJECT-TYPE
			SYNTAX TruthValue
			MAX-ACCESS read-write
			STATUS current
			DESCRIPTION
				"This field indicates whether enable Rogue Device Detection."
			::= { wlanSettingEntry 19 }
					
		accessControlMode OBJECT-TYPE
			SYNTAX INTEGER
				{
				disabled(0),
				local(2),
				server(3)
				}
			MAX-ACCESS read-write
			STATUS current
			DESCRIPTION
				"The field indicates whether the access control list is
				enabled and the source of the database of the access
				control list."
			::= { wlanSettingEntry 20 }

		
		wlanSecurityTable OBJECT-TYPE
			SYNTAX SEQUENCE OF WlanSecurityEntry
			MAX-ACCESS not-accessible
			STATUS current
			DESCRIPTION
				"Security attributes in tablular form to allow for multiple
				instances on an agent."
			::= { wlanSettings 2 }

		
		wlanSecurityEntry OBJECT-TYPE
			SYNTAX WlanSecurityEntry
			MAX-ACCESS not-accessible
			STATUS current
			DESCRIPTION
				"An entry in the securityTable. It is possible for there to
				be multiple AP interfaces on one agent, each with its
				unique MAC address. The relationship between an AP
				interface and an interface in the context of the Internet-
				standard MIB is one-to-one. As such, the value of an
				radioIndex object instance can be directly used to identify
				corresponding instances of the objects defined herein. "
			INDEX { radioIndex, securityProfileNo}
			::= { wlanSecurityTable 1 }

		
		WlanSecurityEntry ::=
			SEQUENCE {
				securityProfileNo
					INTEGER,
				securityProfileEnabled
					TruthValue,
				securityProfileName
					DisplayString,
				ssid
					DisplayString,
				ssidBroadcastEnable
					TruthValue,	
				authentication
					INTEGER,
				encryption
					INTEGER,
				wepKey1
					DisplayString,
				wepKey2
					DisplayString,
				wepKey3
					DisplayString,
				wepKey4
					DisplayString,			
				wepKeyDefault
					INTEGER,
				wpaPSK
					DisplayString,
				wlanSeparatorEnable
					TruthValue,
				wlanMaxUser
				    INTEGER	
			 }
		
		securityProfileNo OBJECT-TYPE
			SYNTAX INTEGER(1..4)
			MAX-ACCESS read-only
			STATUS current
			DESCRIPTION
				"The field indicates the security profile NO."
			::= { wlanSecurityEntry 1 }
				
		securityProfileEnabled OBJECT-TYPE
			SYNTAX TruthValue
			MAX-ACCESS read-write
			STATUS current
			DESCRIPTION
				"This attribute shall indicate whether the security profile is enabled."
			::= { wlanSecurityEntry 2 }
				
		securityProfileName OBJECT-TYPE
			SYNTAX DisplayString (SIZE (1..32))
			MAX-ACCESS read-write
			STATUS current
			DESCRIPTION
				"This attribute shall indicate SSID."
			::= { wlanSecurityEntry 3 }	 
			
		ssid OBJECT-TYPE
			SYNTAX DisplayString (SIZE (1..32))
			MAX-ACCESS read-write
			STATUS current
			DESCRIPTION
				"This attribute shall indicate SSID."
			::= { wlanSecurityEntry 4 }

		
		ssidBroadcastEnable OBJECT-TYPE
			SYNTAX TruthValue
			MAX-ACCESS read-write
			STATUS current
			DESCRIPTION
				"This attribute shall indicate whether wireless network
				Name (SSID) will be broadcasted."
			::= { wlanSecurityEntry 5 }
				 
		authentication OBJECT-TYPE
			SYNTAX INTEGER
				{
				openSystem(0),
				sharedKey(1),
				legacy8021x(2),
				wpaPSK(3),
				wpaRadius(4),
				wpa2-psk(5),
				wpawpa2-psk(6),
				wpa2-802dot1x(7),
				wpawpa2-802dot1x(8)
				}
			MAX-ACCESS read-write
			STATUS current
			DESCRIPTION
				"The field indicates how to authenticate the station."
			::= { wlanSecurityEntry 6 }
			
			
		encryption OBJECT-TYPE
			SYNTAX INTEGER
				{
				none(0),
				wep64(1),
				wep128(2),
				wep152(3),
				tkip(4),
				aes-tkip(5),
				aes(6)
				}
			MAX-ACCESS read-write
			STATUS current
			DESCRIPTION
				"The field indicates how to encryption the data and the type of WEP key."
			::= { wlanSecurityEntry 7 }

		
		wepKey1 OBJECT-TYPE
			SYNTAX DisplayString (SIZE (0..32))
			MAX-ACCESS read-write
			STATUS current
			DESCRIPTION
				"The field shall indicate the WEP key.
				
				wep key type  length  valid chars
				============  ======  ===========
				none          0
				wep64         10      0-9,a-f,A-F
				wep128        26      0-9,a-f,A-F
				wep152        32      0-9,a-f,A-F"
			::= { wlanSecurityEntry 8 }
		
		wepKey2 OBJECT-TYPE
			SYNTAX DisplayString (SIZE (0..32))
			MAX-ACCESS read-write
			STATUS current
			DESCRIPTION
				"The field shall indicate the WEP key.
				
				wep key type  length  valid chars
				============  ======  ===========
				none          0
				wep64         10      0-9,a-f,A-F
				wep128        26      0-9,a-f,A-F
				wep152        32      0-9,a-f,A-F"
			::= { wlanSecurityEntry 9 }
		
		wepKey3 OBJECT-TYPE
			SYNTAX DisplayString (SIZE (0..32))
			MAX-ACCESS read-write
			STATUS current
			DESCRIPTION
				"The field shall indicate the WEP key.
				
				wep key type  length  valid chars
				============  ======  ===========
				none          0
				wep64         10      0-9,a-f,A-F
				wep128        26      0-9,a-f,A-F
				wep152        32      0-9,a-f,A-F"
			::= { wlanSecurityEntry 10 }
		
		wepKey4 OBJECT-TYPE
			SYNTAX DisplayString (SIZE (0..32))
			MAX-ACCESS read-write
			STATUS current
			DESCRIPTION
				"The field shall indicate the WEP key.
				
				wep key type  length  valid chars
				============  ======  ===========
				none          0
				wep64         10      0-9,a-f,A-F
				wep128        26      0-9,a-f,A-F
				wep152        32      0-9,a-f,A-F"
			::= { wlanSecurityEntry 11 }
					
		wepKeyDefault OBJECT-TYPE
			SYNTAX INTEGER (1..4)
			MAX-ACCESS read-write
			STATUS current
			DESCRIPTION
				"The field shall indicate the WEP key number to encrypt TX
				data."
			::= { wlanSecurityEntry 12 }

		
		wpaPSK OBJECT-TYPE
			SYNTAX DisplayString (SIZE (8..63))
			MAX-ACCESS read-write
			STATUS current
			DESCRIPTION
				"This attribute shall indicate WPA Pre-Shared Key."
			::= { wlanSecurityEntry 13 }

		wlanSeparatorEnable OBJECT-TYPE
			SYNTAX TruthValue
			MAX-ACCESS read-write
			STATUS current
			DESCRIPTION
				"This attribute shall indicate whether block the
				communications between two wireless clients."
			::= { wlanSecurityEntry 14 }
		
		
		wlanMaxUser OBJECT-TYPE
		    SYNTAX INTEGER(0..64)
			MAX-ACCESS read-write
			STATUS current
			DESCRIPTION
				"This attribute shall indicates the max wireless clients that allowed to 
				associated.When the value is set 0,and the wireless clients are not limited"
			::= { wlanSecurityEntry 15 }
			
		wlanAccessControlLocalTable OBJECT-TYPE
			SYNTAX SEQUENCE OF WlanAccessControlLocalEntry
			MAX-ACCESS not-accessible
			STATUS current
			DESCRIPTION
				"ACL attributes in tablular form to allow for multiple
				instances on an agent."
			::= { wlanSettings 3 }

		
		wlanAccessControlLocalEntry OBJECT-TYPE
			SYNTAX WlanAccessControlLocalEntry
			MAX-ACCESS not-accessible
			STATUS current
			DESCRIPTION
				"An entry in the wlanAccessControlListTable. It is possible
				for there to be multiple AP interfaces on one agent, each
				with its unique MAC address. The relationship between an
				AP interface and an interface in the context of the
				Internet-standard MIB is one-to-one. As such, the value of
				an radioIndex object instance can be directly used to identify
				corresponding instances of the objects defined herein. "
			INDEX { radioIndex, aclIndex }
			::= { wlanAccessControlLocalTable 1 }

		
		WlanAccessControlLocalEntry ::=
			SEQUENCE { 
				aclIndex
					INTEGER,
				aclMAC
					DisplayString
			 }

		aclIndex OBJECT-TYPE
			SYNTAX INTEGER (1..256 | 9999)
			MAX-ACCESS not-accessible
			STATUS current
			DESCRIPTION
				"This field should indicate an index to the access control
				local database entry. When write this field aclIndex=9999,
				shall append new MAC address into the local database "
			::= { wlanAccessControlLocalEntry 1 }

		
		aclMAC OBJECT-TYPE
			SYNTAX DisplayString (SIZE(6..17))
			MAX-ACCESS read-write
			STATUS current
			DESCRIPTION
				"This field should indicate an MAC address entry in the
				access control local database. When write this field
				aclMAC=000000000000, shall remove current MAC address from
				local database. Otherwise, shall update the MAC address."
			::= { wlanAccessControlLocalEntry 2 }

		
		wlanWdsTable OBJECT-TYPE
			SYNTAX SEQUENCE OF WlanWdsEntry
			MAX-ACCESS not-accessible
			STATUS current
			DESCRIPTION
				"WDS attributes in tablular form to allow for multiple
				instances on an agent."
			::= { wlanSettings 4 }

		
		wlanWdsEntry OBJECT-TYPE
			SYNTAX WlanWdsEntry
			MAX-ACCESS not-accessible
			STATUS current
			DESCRIPTION
				"An entry in the wlanWdsTable. It is possible for there to
				be multiple AP interfaces on one agent, each with its
				unique MAC address. The relationship between an AP
				interface and an interface in the context of the Internet-
				standard MIB is one-to-one. As such, the value of an
				radioIndex object instance can be directly used to identify
				corresponding instances of the objects defined herein. "
			INDEX { radioIndex }
			::= { wlanWdsTable 1 }

		
		WlanWdsEntry ::=
			SEQUENCE { 
				operationMode
					INTEGER,
				localMacAddress
					DisplayString,
				ptpRemoteMacAddress
					DisplayString,
				pxpRemoteMacAddress1
					DisplayString,
				pxpRemoteMacAddress2
					DisplayString,
				pxpRemoteMacAddress3
					DisplayString,
				pxpRemoteMacAddress4
					DisplayString,
				repeaterParentMacAddress
					DisplayString,
				repeaterChildMacAddress
					DisplayString
			 }

		operationMode OBJECT-TYPE
			SYNTAX INTEGER
				{
				ap(0),
				ptp(2),
				ptpAP(3),
				pxp(4),
				pxpAP(5),
				repeater(6)
				}
			MAX-ACCESS read-write
			STATUS current
			DESCRIPTION
				"This attribute shall indicate the operation mode."
			::= { wlanWdsEntry 1 }

		
		localMacAddress OBJECT-TYPE
			SYNTAX DisplayString (SIZE(6..17))
			MAX-ACCESS read-only
			STATUS current
			DESCRIPTION
				"This attribute shall indicate the local MAC Address."
			::= { wlanWdsEntry 2 }

		
		ptpRemoteMacAddress OBJECT-TYPE
			SYNTAX DisplayString (SIZE(6..17))
			MAX-ACCESS read-write
			STATUS current
			DESCRIPTION
				"This attribute shall indicate the stationID."
			::= { wlanWdsEntry 3 }

		
		pxpRemoteMacAddress1 OBJECT-TYPE
			SYNTAX DisplayString (SIZE(6..17))
			MAX-ACCESS read-write
			STATUS current
			DESCRIPTION
				"This attribute shall indicate the stationID."
			::= { wlanWdsEntry 4 }

		
		pxpRemoteMacAddress2 OBJECT-TYPE
			SYNTAX DisplayString (SIZE(6..17))
			MAX-ACCESS read-write
			STATUS current
			DESCRIPTION
				"This attribute shall indicate the stationID."
			::= { wlanWdsEntry 5 }

		
		pxpRemoteMacAddress3 OBJECT-TYPE
			SYNTAX DisplayString (SIZE(6..17))
			MAX-ACCESS read-write
			STATUS current
			DESCRIPTION
				"This attribute shall indicate the stationID."
			::= { wlanWdsEntry 6 }

		
		pxpRemoteMacAddress4 OBJECT-TYPE
			SYNTAX DisplayString (SIZE(6..17))
			MAX-ACCESS read-write
			STATUS current
			DESCRIPTION
				"This attribute shall indicate the stationID."
			::= { wlanWdsEntry 7 }

		
		repeaterParentMacAddress OBJECT-TYPE
			SYNTAX DisplayString (SIZE(6..17))
			MAX-ACCESS read-write
			STATUS current
			DESCRIPTION
				"This attribute shall indicate the stationID."
			::= { wlanWdsEntry 8 }

		
		repeaterChildMacAddress OBJECT-TYPE
			SYNTAX DisplayString (SIZE(6..17))
			MAX-ACCESS read-write
			STATUS current
			DESCRIPTION
				"This attribute shall indicate the stationID."
			::= { wlanWdsEntry 9 }

		
-- **********************************************************************
-- *  Station List Table
-- **********************************************************************
		wlanClientsTable OBJECT-TYPE
			SYNTAX SEQUENCE OF WlanClientsEntry
			MAX-ACCESS not-accessible
			STATUS current
			DESCRIPTION
				"wireless clients attributes in tablular form to allow for
				multiple instances on an agent."
			::= { wlanSettings 5 }

		
		wlanClientsEntry OBJECT-TYPE
			SYNTAX WlanClientsEntry
			MAX-ACCESS not-accessible
			STATUS current
			DESCRIPTION
				"An entry in the wlanClientsTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex, clientIndex }
			::= { wlanClientsTable 1 }

		
		WlanClientsEntry ::=
			SEQUENCE { 
				clientIndex
					INTEGER,
				clientMacAddress
					DisplayString,
				clientIP
					IpAddress,
				clientSSID
					DisplayString,
				clientStatus
					INTEGER
			 }

		clientIndex OBJECT-TYPE
			SYNTAX INTEGER (1..255)
			MAX-ACCESS read-only
			STATUS current
			DESCRIPTION
				"This attribute shall indicate sequence number (ID) of the
				associated station."
			::= { wlanClientsEntry 1 }

		
		clientMacAddress OBJECT-TYPE
			SYNTAX DisplayString (SIZE(6..17))
			MAX-ACCESS read-only
			STATUS current
			DESCRIPTION
				"This attribute shall indicate MAC address of the
				associated stationID."
			::= { wlanClientsEntry 2 }

		
		clientIP OBJECT-TYPE
			SYNTAX IpAddress
			MAX-ACCESS read-only
			STATUS current
			DESCRIPTION
				"This attribute shall indicate the IP address of the
				associated stationID."
			::= { wlanClientsEntry 3 }

		
		clientSSID OBJECT-TYPE
			SYNTAX DisplayString (SIZE (1..32))
			MAX-ACCESS read-only
			STATUS current
			DESCRIPTION
				"This attribute shall indicate the SSID that the
				wireless client associates to."
			::= { wlanClientsEntry 4 }

		
		clientStatus OBJECT-TYPE
			SYNTAX INTEGER
				{
				blocked(0),
				authenticating(1),
				authenticated(2),
				associating(3),
				associated(4)
				}
			MAX-ACCESS read-only
			STATUS current
			DESCRIPTION
				"This attribute shall indicate the status of the associated
				stationID."
			::= { wlanClientsEntry 5 }
		
		
-- **********************************************************************
-- *  Unknown AP List Table
-- **********************************************************************
		wlanUnknownApTable OBJECT-TYPE
			SYNTAX SEQUENCE OF WlanUnknownApEntry
			MAX-ACCESS not-accessible
			STATUS current
			DESCRIPTION
				"wireless Unknown AP attributes in tablular form to allow for
				multiple instances on an agent."
			::= { wlanSettings 6 }

		
		wlanUnknownApEntry OBJECT-TYPE
			SYNTAX WlanUnknownApEntry
			MAX-ACCESS not-accessible
			STATUS current
			DESCRIPTION
				"An entry in the wlanUnknownApTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex, unknowApIndex }
			::= { wlanUnknownApTable 1 }

		
		WlanUnknownApEntry ::=
			SEQUENCE { 
				unknowApIndex
					INTEGER,
				unknowApAuthorize
					TruthValue,
				unknowApSSID
					DisplayString,
				unknowApMacAddress	
					DisplayString,
				unknowApChannel
					DisplayString,
				unknowApAutoCellEnabled
					DisplayString
			 }

		unknowApIndex OBJECT-TYPE
			SYNTAX INTEGER (1..255)
			MAX-ACCESS read-only
			STATUS current
			DESCRIPTION
				"This attribute shall indicate sequence number (ID) of the
				detected unknow AP."
			::= { wlanUnknownApEntry 1 }

		unknowApAuthorize OBJECT-TYPE
			SYNTAX TruthValue
			MAX-ACCESS read-write
			STATUS current
			DESCRIPTION
				"This attribute is used to authorize the AP to the authorized AP List."
			::= { wlanUnknownApEntry 2 }
		
		unknowApSSID OBJECT-TYPE
			SYNTAX DisplayString (SIZE (1..32))
			MAX-ACCESS read-only
			STATUS current
			DESCRIPTION
				"This attribute shall indicate the SSID of the AP."
			::= { wlanUnknownApEntry 3 }
		
		
		unknowApMacAddress OBJECT-TYPE
			SYNTAX DisplayString (SIZE(6..17))
			MAX-ACCESS read-only
			STATUS current
			DESCRIPTION
				"This attribute shall indicate MAC address of the AP."
			::= { wlanUnknownApEntry 4 }

		unknowApChannel OBJECT-TYPE
			SYNTAX DisplayString (SIZE(1..5))
			MAX-ACCESS read-only
			STATUS current
			DESCRIPTION
				"This attribute shall indicate the channel number of the AP."
			::= { wlanUnknownApEntry 5 }
		
		unknowApAutoCellEnabled OBJECT-TYPE
			SYNTAX DisplayString (SIZE(1..5))
			MAX-ACCESS read-only
			STATUS current
			DESCRIPTION
				"This attribute shall indicate whether the AutoCell is enabled on the AP or not."
			::= { wlanUnknownApEntry 6 }
			
-- **********************************************************************
-- *  Authorized AP List Table
-- **********************************************************************
		wlanAuthorizedApTable OBJECT-TYPE
			SYNTAX SEQUENCE OF WlanAuthorizedApEntry
			MAX-ACCESS not-accessible
			STATUS current
			DESCRIPTION
				"wireless Authorized AP attributes in tablular form to allow for
				multiple instances on an agent."
			::= { wlanSettings 7 }

		
		wlanAuthorizedApEntry OBJECT-TYPE
			SYNTAX WlanAuthorizedApEntry
			MAX-ACCESS not-accessible
			STATUS current
			DESCRIPTION
				"An entry in the wlanAuthorizedApTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex, unknowApIndex }
			::= { wlanAuthorizedApTable 1 }

		
		WlanAuthorizedApEntry ::=
			SEQUENCE { 
				authorizedApIndex
					INTEGER,
				authorizedApDelete
					TruthValue,
				authorizedApSSID
					DisplayString,
				authorizedApMacAddress	
					DisplayString,
				authorizedApChannel
					DisplayString,
				authorizedApAutoCellEnabled
					DisplayString
			 }

		authorizedApIndex OBJECT-TYPE
			SYNTAX INTEGER (1..255)
			MAX-ACCESS read-only
			STATUS current
			DESCRIPTION
				"This attribute shall indicate sequence number (ID) of the
				detected authorized AP."
			::= { wlanAuthorizedApEntry 1 }

		authorizedApDelete OBJECT-TYPE
			SYNTAX TruthValue
			MAX-ACCESS read-write
			STATUS current
			DESCRIPTION
				"This attribute is used to delete the AP from authorized AP List."
			::= { wlanAuthorizedApEntry 2 }
		
		authorizedApSSID OBJECT-TYPE
			SYNTAX DisplayString (SIZE (1..32))
			MAX-ACCESS read-only
			STATUS current
			DESCRIPTION
				"This attribute shall indicate the SSID of the AP."
			::= { wlanAuthorizedApEntry 3 }
		
		
		authorizedApMacAddress OBJECT-TYPE
			SYNTAX DisplayString (SIZE(6..17))
			MAX-ACCESS read-only
			STATUS current
			DESCRIPTION
				"This attribute shall indicate MAC address of the AP."
			::= { wlanAuthorizedApEntry 4 }

		authorizedApChannel OBJECT-TYPE
			SYNTAX DisplayString (SIZE(1..5))
			MAX-ACCESS read-only
			STATUS current
			DESCRIPTION
				"This attribute shall indicate the channel number of the AP."
			::= { wlanAuthorizedApEntry 5 }
		
		authorizedApAutoCellEnabled OBJECT-TYPE
			SYNTAX DisplayString (SIZE(1..5))
			MAX-ACCESS read-only
			STATUS current
			DESCRIPTION
				"This attribute shall indicate whether the AutoCell is enabled on the AP or not."
			::= { wlanAuthorizedApEntry 6 }
			
					
		
-- **********************************************************************
-- *  Unknown Station List Table
-- **********************************************************************
		wlanUnknownStationTable OBJECT-TYPE
			SYNTAX SEQUENCE OF WlanUnknownStationEntry
			MAX-ACCESS not-accessible
			STATUS current
			DESCRIPTION
				"wireless Unknown Station attributes in tablular form to allow for
				multiple instances on an agent."
			::= { wlanSettings 8 }

		
		wlanUnknownStationEntry OBJECT-TYPE
			SYNTAX WlanUnknownStationEntry
			MAX-ACCESS not-accessible
			STATUS current
			DESCRIPTION
				"An entry in the wlanUnknownStationTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex, unknowStationIndex }
			::= { wlanUnknownStationTable 1 }

		
		WlanUnknownStationEntry ::=
			SEQUENCE { 
				unknowStationIndex
					INTEGER,
				unknowStationAuthorize
					TruthValue,
				unknowStationMacAddress	
					DisplayString,
				unknowStationChannel
					DisplayString,
				unknowStationAutoCellEnabled
					DisplayString
			 }

		unknowStationIndex OBJECT-TYPE
			SYNTAX INTEGER (1..255)
			MAX-ACCESS read-only
			STATUS current
			DESCRIPTION
				"This attribute shall indicate sequence number (ID) of the
				detected unknow Station."
			::= { wlanUnknownStationEntry 1 }

		unknowStationAuthorize OBJECT-TYPE
			SYNTAX TruthValue
			MAX-ACCESS read-write
			STATUS current
			DESCRIPTION
				"This attribute is used to authorize the Station to the authorized Station List."
			::= { wlanUnknownStationEntry 2 }
		
		unknowStationMacAddress OBJECT-TYPE
			SYNTAX DisplayString (SIZE(6..17))
			MAX-ACCESS read-only
			STATUS current
			DESCRIPTION
				"This attribute shall indicate MAC address of the Station."
			::= { wlanUnknownStationEntry 3 }

		unknowStationChannel OBJECT-TYPE
			SYNTAX DisplayString (SIZE(1..5))
			MAX-ACCESS read-only
			STATUS current
			DESCRIPTION
				"This attribute shall indicate the channel number of the Station."
			::= { wlanUnknownStationEntry 4 }
		
		unknowStationAutoCellEnabled OBJECT-TYPE
			SYNTAX DisplayString (SIZE(1..5))
			MAX-ACCESS read-only
			STATUS current
			DESCRIPTION
				"This attribute shall indicate whether the AutoCell is enabled on the Station or not."
			::= { wlanUnknownStationEntry 5 }
			
-- **********************************************************************
-- *  Authorized Station List Table
-- **********************************************************************
		wlanAuthorizedStationTable OBJECT-TYPE
			SYNTAX SEQUENCE OF WlanAuthorizedStationEntry
			MAX-ACCESS not-accessible
			STATUS current
			DESCRIPTION
				"wireless Authorized Station attributes in tablular form to allow for
				multiple instances on an agent."
			::= { wlanSettings 9 }

		
		wlanAuthorizedStationEntry OBJECT-TYPE
			SYNTAX WlanAuthorizedStationEntry
			MAX-ACCESS not-accessible
			STATUS current
			DESCRIPTION
				"An entry in the wlanAuthorizedStationTable. It is possible for there
				to be multiple AP interfaces on one agent, each with its
				unique MAC address. The relationship between an AP
				interface and an interface in the context of the Internet-
				standard MIB is one-to-one. As such, the value of an
				radioIndex object instance can be directly used to identify
				corresponding instances of the objects defined herein. "
			INDEX { radioIndex, unknowStationIndex }
			::= { wlanAuthorizedStationTable 1 }

		
		WlanAuthorizedStationEntry ::=
			SEQUENCE { 
				authorizedStationIndex
					INTEGER,
				authorizedStationDelete
					TruthValue,
				authorizedStationMacAddress	
					DisplayString,
				authorizedStationChannel
					DisplayString,
				authorizedStationAutoCellEnabled
					DisplayString
			 }

		authorizedStationIndex OBJECT-TYPE
			SYNTAX INTEGER (1..255)
			MAX-ACCESS read-only
			STATUS current
			DESCRIPTION
				"This attribute shall indicate sequence number (ID) of the
				detected authorized Station."
			::= { wlanAuthorizedStationEntry 1 }

		authorizedStationDelete OBJECT-TYPE
			SYNTAX TruthValue
			MAX-ACCESS read-write
			STATUS current
			DESCRIPTION
				"This attribute is used to delete the Station from authorized Station List."
			::= { wlanAuthorizedStationEntry 2 }
		
		authorizedStationMacAddress OBJECT-TYPE
			SYNTAX DisplayString (SIZE(6..17))
			MAX-ACCESS read-only
			STATUS current
			DESCRIPTION
				"This attribute shall indicate MAC address of the Station."
			::= { wlanAuthorizedStationEntry 3 }

		authorizedStationChannel OBJECT-TYPE
			SYNTAX DisplayString (SIZE(1..5))
			MAX-ACCESS read-only
			STATUS current
			DESCRIPTION
				"This attribute shall indicate the channel number of the Station."
			::= { wlanAuthorizedStationEntry 4 }
		
		authorizedStationAutoCellEnabled OBJECT-TYPE
			SYNTAX DisplayString (SIZE(1..5))
			MAX-ACCESS read-only
			STATUS current
			DESCRIPTION
				"This attribute shall indicate whether the AutoCell is enabled on the Station or not."
			::= { wlanAuthorizedStationEntry 5 }
								
					
		vlanSettings OBJECT IDENTIFIER ::= { wg102 3 }
		
		vlanEnable OBJECT-TYPE
			SYNTAX TruthValue
			MAX-ACCESS read-write
			STATUS current
			DESCRIPTION
				"This attribute shall indicate whether vlan(802.1Q) is
				enabled."
			::= { vlanSettings 1 }
		
		managementVlanId OBJECT-TYPE
			SYNTAX INTEGER (1..4095)
			MAX-ACCESS read-write
			STATUS current
			DESCRIPTION
				"This attribute shall indicate the management VLAN ID."
			::= { vlanSettings 2 }
		
		securityProfileVlanTable OBJECT-TYPE
			SYNTAX SEQUENCE OF SecurityProfileVlanEntry
			MAX-ACCESS not-accessible
			STATUS current
			DESCRIPTION
				"Description."
			::= { vlanSettings 3 }

		
		securityProfileVlanEntry OBJECT-TYPE
			SYNTAX SecurityProfileVlanEntry
			MAX-ACCESS not-accessible
			STATUS current
			DESCRIPTION
				"Description."
			INDEX { wlanSecurityProfileNo }
			::= { securityProfileVlanTable 1 }

		
		SecurityProfileVlanEntry ::=
			SEQUENCE { 
				profileNo
					INTEGER,
				profileVlan
					INTEGER
			 }
		profileNo OBJECT-TYPE
			SYNTAX INTEGER(1..4)
			MAX-ACCESS read-only
			STATUS current
			DESCRIPTION
				"the field indicates the security profile NO."
			::= { securityProfileVlanEntry 1 }	 
		
		profileVlan OBJECT-TYPE
			SYNTAX INTEGER(1..4095)
			MAX-ACCESS read-write
			STATUS current
			DESCRIPTION
				"the field indicates the security profile's VLAN."
			::= { securityProfileVlanEntry 2 }	
		
		
		sysStatistics OBJECT IDENTIFIER ::= { wg102 4 }

		
		ethernetStat OBJECT IDENTIFIER ::= { sysStatistics 1 }

		
		ethInPackets OBJECT-TYPE
			SYNTAX Unsigned32
			MAX-ACCESS read-only
			STATUS current
			DESCRIPTION
				"the field indicates the sum of received packets."
			::= { ethernetStat 1 }

		
		ethOutPackets OBJECT-TYPE
			SYNTAX Unsigned32
			MAX-ACCESS read-only
			STATUS current
			DESCRIPTION
				"the field indicates the sum of transmitted packets."
			::= { ethernetStat 2 }

		
		ethInBytes OBJECT-TYPE
			SYNTAX Unsigned32
			MAX-ACCESS read-only
			STATUS current
			DESCRIPTION
				"the field indicates the sum of received bytes."
			::= { ethernetStat 3 }

		
		ethOutBytes OBJECT-TYPE
			SYNTAX Unsigned32
			MAX-ACCESS read-only
			STATUS current
			DESCRIPTION
				"the field indicates the sum of transmitted bytes."
			::= { ethernetStat 4 }

		
		wirelessStatTable OBJECT-TYPE
			SYNTAX SEQUENCE OF WirelessStatEntry
			MAX-ACCESS not-accessible
			STATUS current
			DESCRIPTION
				"Description."
			::= { sysStatistics 2 }

		
		wirelessStatEntry OBJECT-TYPE
			SYNTAX WirelessStatEntry
			MAX-ACCESS not-accessible
			STATUS current
			DESCRIPTION
				"Description."
			INDEX { radioIndex }
			::= { wirelessStatTable 1 }

		
		WirelessStatEntry ::=
			SEQUENCE { 
				wlanSecurityProfileNo
					INTEGER,
				wlanInPacketsUnicast
					Unsigned32,
				wlanOutPacketsUnicast
					Unsigned32,
				wlanInPacketsBroadcast
					Unsigned32,
				wlanOutPacketsBroadcast
					Unsigned32,
				wlanInPacketsMulticast
					Unsigned32,
				wlanOutPacketsMulticast
					Unsigned32,
				wlanInPacketsTotal
					Unsigned32,
				wlanOutPacketsTotal
					Unsigned32,
				wlanInBytesTotal
					Unsigned32,
				wlanOutBytesTotal
					Unsigned32
			 }
		wlanSecurityProfileNo OBJECT-TYPE
			SYNTAX INTEGER(1..4)
			MAX-ACCESS read-only
			STATUS current
			DESCRIPTION
				"the field indicates the security profile NO."
			::= { wirelessStatEntry 1 }	 
		
		wlanInPacketsUnicast OBJECT-TYPE
			SYNTAX Unsigned32
			MAX-ACCESS read-only
			STATUS current
			DESCRIPTION
				"the field indicates the sum of received unicast packets."
			::= { wirelessStatEntry 2 }

		
		wlanOutPacketsUnicast OBJECT-TYPE
			SYNTAX Unsigned32
			MAX-ACCESS read-only
			STATUS current
			DESCRIPTION
				"the field indicates the sum of transmitted unicast packets."
			::= { wirelessStatEntry 3 }

		
		wlanInPacketsBroadcast OBJECT-TYPE
			SYNTAX Unsigned32
			MAX-ACCESS read-only
			STATUS current
			DESCRIPTION
				"the field indicates the sum of received broadcast packets."
			::= { wirelessStatEntry 4 }

		
		wlanOutPacketsBroadcast OBJECT-TYPE
			SYNTAX Unsigned32
			MAX-ACCESS read-only
			STATUS current
			DESCRIPTION
				"the field indicates the sum of transmitted broadcast packets."
			::= { wirelessStatEntry 5 }

		
		wlanInPacketsMulticast OBJECT-TYPE
			SYNTAX Unsigned32
			MAX-ACCESS read-only
			STATUS current
			DESCRIPTION
				"the field indicates the sum of received multicast packets."
			::= { wirelessStatEntry 6 }

		
		wlanOutPacketsMulticast OBJECT-TYPE
			SYNTAX Unsigned32
			MAX-ACCESS read-only
			STATUS current
			DESCRIPTION
				"the field indicates the sum of transmitted multicast packets."
			::= { wirelessStatEntry 7 }

		
		wlanInPacketsTotal OBJECT-TYPE
			SYNTAX Unsigned32
			MAX-ACCESS read-only
			STATUS current
			DESCRIPTION
				"the field indicates the sum of received packets."
			::= { wirelessStatEntry 8 }

		
		wlanOutPacketsTotal OBJECT-TYPE
			SYNTAX Unsigned32
			MAX-ACCESS read-only
			STATUS current
			DESCRIPTION
				"the field indicates the sum of transmitted packets."
			::= { wirelessStatEntry 9 }

		
		wlanInBytesTotal OBJECT-TYPE
			SYNTAX Unsigned32
			MAX-ACCESS read-only
			STATUS current
			DESCRIPTION
				"the field indicates the sum of received bytes."
			::= { wirelessStatEntry 10 }

		
		wlanOutBytesTotal OBJECT-TYPE
			SYNTAX Unsigned32
			MAX-ACCESS read-only
			STATUS current
			DESCRIPTION
				"the field indicates the sum of transmitted bytes."
			::= { wirelessStatEntry 11 }

        ethWrongPackets OBJECT-TYPE
        	SYNTAX Unsigned32
        	MAX-ACCESS read-only
        	STATUS current
        	DESCRIPTION
        		"the field indicates the sum of wrong Ethernet packets."
        	::= { sysStatistics 3 }
        
        wrongWLANSTAPackets OBJECT-TYPE
        	SYNTAX Unsigned32
        	MAX-ACCESS read-only
        	STATUS current
        	DESCRIPTION
        		"the field indicates the sum of wrong wireless station packets."
        	::= { sysStatistics 4 }
        
        wlanStationCount OBJECT-TYPE
        	SYNTAX Unsigned32
        	MAX-ACCESS read-only
        	STATUS current
        	DESCRIPTION
        		"the field indicates the number of stations."
        	::= { sysStatistics 5 }
        	
        wirelessLinkStatTable OBJECT-TYPE
			SYNTAX SEQUENCE OF WirelessLinkStatEntry
			MAX-ACCESS not-accessible
			STATUS current
			DESCRIPTION
			"The table is for wireless client's association request, successful associated, granted access and aggregative clients disconnection with date & time section and read flag information."
			::= { sysStatistics 6 }
			
		wirelessLinkStatEntry OBJECT-TYPE
			SYNTAX WirelessLinkStatEntry
			MAX-ACCESS not-accessible
			STATUS current
			DESCRIPTION
				"Providing entries for wirelessLinkStatTable"
			INDEX { wirelessLinkStatIndex }
			::= { wirelessLinkStatTable 1 }
			
			
			WirelessLinkStatEntry ::=
			SEQUENCE { 
				wirelessLinkStatIndex
					INTEGER,
				wirelessLinkStatDate
					DisplayString,
				wirelessLinkStatTime
					INTEGER,
				wirelessLinkStatRequest
					Unsigned32,
				wirelessLinkStatResponse
					Unsigned32,
				wirelessLinkStatGrant
					Unsigned32,
				wirelessLinkStatDisconnect
					Unsigned32,
				wirelessLinkStatDisconnectAll
					Unsigned32,
				wirelessLinkStatFlag
					TruthValue
			 }
			 
		wirelessLinkStatIndex OBJECT-TYPE
			SYNTAX INTEGER(1..48)
			MAX-ACCESS read-only
			STATUS current
			DESCRIPTION
				"This field indicates the index of this statistic records."
			::= { wirelessLinkStatEntry 1 }	 
			
		wirelessLinkStatDate OBJECT-TYPE
			SYNTAX DisplayString (SIZE (1..20))
			MAX-ACCESS read-only
			STATUS current
			DESCRIPTION
				"This field indicates the date of this statistic record in the format:
				YYYY/MM/DD."
			::= { wirelessLinkStatEntry 2 }
			
		wirelessLinkStatTime OBJECT-TYPE
			SYNTAX INTEGER(0..23)
			MAX-ACCESS read-only
			STATUS current
			DESCRIPTION
				"This field indicates the time slice of this statistic record.
					Total 24 time slice are defined in one day, such as time scale 0 is from 12am to 1am, time scale 1 is from 1am to 2 am, and so forth"
			::= { wirelessLinkStatEntry 3 }	 
		
		wirelessLinkStatRequest OBJECT-TYPE
			SYNTAX Unsigned32
			MAX-ACCESS read-only
			STATUS current
			DESCRIPTION
				"This field indicates the statistic of Association Request to the AP."
			::= { wirelessLinkStatEntry 4 }
			
		wirelessLinkStatResponse OBJECT-TYPE
			SYNTAX Unsigned32
			MAX-ACCESS read-only
			STATUS current
			DESCRIPTION
				"This field indicates the statistic of Association Response sent by the AP."
			::= { wirelessLinkStatEntry 5 }
			
		wirelessLinkStatGrant OBJECT-TYPE
			SYNTAX Unsigned32
			MAX-ACCESS read-only
			STATUS current
			DESCRIPTION
				"This field indicates the statistic of Successful Association with the AP."
			::= { wirelessLinkStatEntry 6 }		
        
        	wirelessLinkStatDisconnect OBJECT-TYPE
			SYNTAX Unsigned32
			MAX-ACCESS read-only
			STATUS current
			DESCRIPTION
				"This field indicates the statistic how many AP detects client's disconnection due to timeout."
			::= { wirelessLinkStatEntry 7 }
		
		wirelessLinkStatDisconnectAll OBJECT-TYPE
			SYNTAX Unsigned32
			MAX-ACCESS read-only
			STATUS current
			DESCRIPTION
					"This field indicates the statistic that the AP detects all wireless clients (>1) disconnecting within 1 second"
			::= { wirelessLinkStatEntry 8 }
		
		wirelessLinkStatFlag OBJECT-TYPE
			SYNTAX TruthValue
			MAX-ACCESS read-write
			STATUS current
			DESCRIPTION
				"This field indicates if the network management system has already read this record.
				When network management system read the record successfully, it should set it to 1.
					If this field is set to be 1, the record will be deleted if the time slice is over."
			::= { wirelessLinkStatEntry 9 }
			
        wlanAuthenticatedStationCount OBJECT-TYPE
        	SYNTAX Unsigned32
        	MAX-ACCESS read-only
        	STATUS current
        	DESCRIPTION
        		"The field indicates the number of stations that 802.1x authenticated."
        	::= { sysStatistics 8 }
        
        sysTotalMemory OBJECT-TYPE
        	SYNTAX Unsigned32
        	MAX-ACCESS read-only
        	STATUS current
        	DESCRIPTION
        		"The field indicates the total memory size of the system."
        	::= { sysStatistics 9 }	
        
        sysFreeMemory OBJECT-TYPE
        	SYNTAX Unsigned32
        	MAX-ACCESS read-only
        	STATUS current
        	DESCRIPTION
        		"The field indicates the current free memory size of the system."
        	::= { sysStatistics 10 }
	
        sysRuntime OBJECT-TYPE
        	SYNTAX TimeTicks
        	MAX-ACCESS read-only
        	STATUS current
        	DESCRIPTION
        		"The field indicates the time (in hundredths of a second) since the 
        		system was last re-initialized."
        	::= { sysStatistics 11 }	
        		
        		
		radiusSettings OBJECT IDENTIFIER ::= { wg102 5 }

--    The primary authentication RADIUS server setting.
		radiusAuthPrimaryServer OBJECT IDENTIFIER ::= { radiusSettings 1 }

		
		radiusAuthPrimaryServerIP OBJECT-TYPE
			SYNTAX IpAddress
			MAX-ACCESS read-write
			STATUS current
			DESCRIPTION
				"This field shall indicate the primary authentication
				RADIUS server IP address."
			::= { radiusAuthPrimaryServer 1 }

		
		radiusAuthPrimaryServerPort OBJECT-TYPE
			SYNTAX INTEGER (0..65535)
			MAX-ACCESS read-write
			STATUS current
			DESCRIPTION
				"This field shall indicate the primary authentication
				RADIUS server port number. Default: 1812."
			::= { radiusAuthPrimaryServer 2 }

		
		radiusAuthPrimaryServerSecret OBJECT-TYPE
			SYNTAX DisplayString (SIZE (0..127))
			MAX-ACCESS read-write
			STATUS current
			DESCRIPTION
				"This field shall indicate the primary authentication
				RADIUS server shared secret string."
			::= { radiusAuthPrimaryServer 3 }

		
--    The secondary authentication RADIUS server setting.
		radiusAuthSecondaryServer OBJECT IDENTIFIER ::= { radiusSettings 2 }

		
		radiusAuthSecondaryServerIP OBJECT-TYPE
			SYNTAX IpAddress
			MAX-ACCESS read-write
			STATUS current
			DESCRIPTION
				"This field shall indicate the secondary authentication
				RADIUS server IP address."
			::= { radiusAuthSecondaryServer 1 }

		
		radiusAuthSecondaryServerPort OBJECT-TYPE
			SYNTAX INTEGER (0..65535)
			MAX-ACCESS read-write
			STATUS current
			DESCRIPTION
				"This field shall indicate the secondary authentication
				RADIUS server port number. Default: 1812."
			::= { radiusAuthSecondaryServer 2 }

		
		radiusAuthSecondaryServerSecret OBJECT-TYPE
			SYNTAX DisplayString (SIZE (0..127))
			MAX-ACCESS read-write
			STATUS current
			DESCRIPTION
				"This field shall indicate the secondary authentication
				RADIUS server shared secret string."
			::= { radiusAuthSecondaryServer 3 }

--    Authentication Settings.
		authenticationSettings OBJECT IDENTIFIER ::= { radiusSettings 3 }
		
		
		reauthTime OBJECT-TYPE
			SYNTAX INTEGER (1800..36000)
			MAX-ACCESS read-write
			STATUS current
			DESCRIPTION
				"This attribute shall indicate 802.1x reauth time."
			::= { authenticationSettings 1 }

		
		wpaGroupKeyUpdateCondition OBJECT-TYPE
			SYNTAX INTEGER
				{
				never(0),
				seconds(1),
				disconnect(2),
				secondsAndDisconnect(3)
				}
			MAX-ACCESS read-write
			STATUS current
			DESCRIPTION
				"This attribute shall indicate WPA group key update
				condition."
			::= { authenticationSettings 2 }

		
		wpaGroupKeyUpdateIntervalSecond OBJECT-TYPE
			SYNTAX INTEGER (0..65535)
			MAX-ACCESS read-write
			STATUS current
			DESCRIPTION
				"This fields indicates the wpa keyupdate sec interval."
			::= { authenticationSettings 3 }

		
		
--    The primary account RADIUS server setting.
		radiusAccountPrimaryServer OBJECT IDENTIFIER ::= { radiusSettings 4 }

		
		radiusAccountPrimaryServerIP OBJECT-TYPE
			SYNTAX IpAddress
			MAX-ACCESS read-write
			STATUS current
			DESCRIPTION
				"This field shall indicate the primary account RADIUS
				server IP address."
			::= { radiusAccountPrimaryServer 1 }

		
		radiusAccountPrimaryServerPort OBJECT-TYPE
			SYNTAX INTEGER (0..65535)
			MAX-ACCESS read-write
			STATUS current
			DESCRIPTION
				"This field shall indicate the primary account RADIUS
				server port number. Default: 1813."
			::= { radiusAccountPrimaryServer 2 }

		
		radiusAccountPrimaryServerSecret OBJECT-TYPE
			SYNTAX DisplayString (SIZE (0..127))
			MAX-ACCESS read-write
			STATUS current
			DESCRIPTION
				"This field shall indicate the primary account RADIUS
				server shared secret string."
			::= { radiusAccountPrimaryServer 3 }

		
--    The secondary account RADIUS server setting.
		radiusAccountSecondaryServer OBJECT IDENTIFIER ::= { radiusSettings 5 }

		
		radiusAccountSecondaryServerIP OBJECT-TYPE
			SYNTAX IpAddress
			MAX-ACCESS read-write
			STATUS current
			DESCRIPTION
				"This field shall indicate the secondary account RADIUS
				server IP address."
			::= { radiusAccountSecondaryServer 1 }

		
		radiusAccountSecondaryServerPort OBJECT-TYPE
			SYNTAX INTEGER (0..65535)
			MAX-ACCESS read-write
			STATUS current
			DESCRIPTION
				"This field shall indicate the secondary account RADIUS
				server port number. Default: 1813."
			::= { radiusAccountSecondaryServer 2 }

		
		radiusAccountSecondaryServerSecret OBJECT-TYPE
			SYNTAX DisplayString (SIZE (0..127))
			MAX-ACCESS read-write
			STATUS current
			DESCRIPTION
				"This field shall indicate the secondary account RADIUS
				server shared secret string."
			::= { radiusAccountSecondaryServer 3 }

		
		hotspotSettings OBJECT IDENTIFIER ::= { wg102 6 }

		
		httpRedirectEnable OBJECT-TYPE
			SYNTAX TruthValue
			MAX-ACCESS read-write
			STATUS current
			DESCRIPTION
				"This attribute shall indicate whether the HTTP redirect is
				enabled."
			::= { hotspotSettings 1 }

		httpRedirectUrl OBJECT-TYPE
			SYNTAX DisplayString (SIZE (0..32))
			MAX-ACCESS read-write
			STATUS current
			DESCRIPTION
				"This attribute shall indicate http redirect URL."
			::= { hotspotSettings 2 }
		

		syslogSettings OBJECT IDENTIFIER ::= { wg102 7 }

		
		syslogEnable OBJECT-TYPE
			SYNTAX TruthValue
			MAX-ACCESS read-write
			STATUS current
			DESCRIPTION
				"This attribute shall indicate whether the syslog is enabled."
			::= { syslogSettings 1 }

		
		syslogServerIP OBJECT-TYPE
			SYNTAX IpAddress
			MAX-ACCESS read-write
			STATUS current
			DESCRIPTION
				"This attributes shall indicates the IP address of the
				syslog server. ***The value can only be set to an IP
				address in dot format."
			::= { syslogSettings 2 }

		
		syslogServerPort OBJECT-TYPE
			SYNTAX INTEGER (0..65535)
			MAX-ACCESS read-write
			STATUS current
			DESCRIPTION
				"This attributes shall indicates the Port of the Syslog
				server."
			::= { syslogSettings 3 }

		
		remoteMgmtSettings OBJECT IDENTIFIER ::= { wg102 8 }

		
		snmpEnable OBJECT-TYPE
			SYNTAX TruthValue
			MAX-ACCESS read-write
			STATUS current
			DESCRIPTION
				"This attribute shall indicate whether the SNMP agent is
				enabled."
			::= { remoteMgmtSettings 1 }
			
        snmpManageIP OBJECT-TYPE
			SYNTAX IpAddress
			MAX-ACCESS read-write
			STATUS current
			DESCRIPTION
				"The field indicates the SNMP manage IP address.
				***The value can only be set to an IP address in dot
				format."
			::= { remoteMgmtSettings 2 }
		
		snmpTrapServerIP OBJECT-TYPE
			SYNTAX IpAddress
			MAX-ACCESS read-write
			STATUS current
			DESCRIPTION
				"The field indicates the SNMP trap server IP address.
				***The value can only be set to an IP address in dot
				format."
			::= { remoteMgmtSettings 3 }

		
		snmpReadCommunity OBJECT-TYPE
			SYNTAX DisplayString (SIZE (1..31))
			MAX-ACCESS read-write
			STATUS current
			DESCRIPTION
				"The field indicates the SNMP read only community name.
				***The value can only be set to 1 to 32 readable string."
			::= { remoteMgmtSettings 4 }

		
		snmpWriteCommunity OBJECT-TYPE
			SYNTAX DisplayString (SIZE (1..31))
			MAX-ACCESS read-write
			STATUS current
			DESCRIPTION
				"The field indicates the SNMP read write community name.
				***The value can only be set to 1 to 32 readable string."
			::= { remoteMgmtSettings 5 }

        snmpTrapPort OBJECT-TYPE
			SYNTAX INTEGER (0..65535)
			MAX-ACCESS read-write
			STATUS current
			DESCRIPTION
				"This field shall indicate the port for trap. Default: 162."
			::= { remoteMgmtSettings 6 }
		
		
		mgmtWebAccessCtrl OBJECT-TYPE
			SYNTAX TruthValue
			MAX-ACCESS read-write
			STATUS current
			DESCRIPTION
				"This attribute shall allow you to turn the WEB access control on or off.
				"
			::= { remoteMgmtSettings 8 }
			
		mgmtWebIPSubnet1 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 9 }
			
		mgmtWebIPSubnet2 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 10 }	
        
        mgmtWebIPSubnet3 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 11 }
			
		
		mgmtWebIPSubnet4 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 12 }
	    
	    mgmtWebIPSubnet5 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 13 }
			
		mgmtWebIPSubnet6 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 14 }
			
		mgmtWebIPSubnet7 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 15 }
			
		mgmtWebIPSubnet8 OBJECT-TYPE
			SYNTAX DisplayString (SIZE(7..31))
			MAX-ACCESS read-write
			STATUS current
			DESCRIPTION
				"The field indicates the IP Subnet: a base IP address and a subnet mask.
				***Please follow this format: xxx.xxx.xxx.xxx/xxx.xxx.xxx.xxx
				"
			::= { remoteMgmtSettings 16 }
								
		auxCommand OBJECT IDENTIFIER ::= { wg102 9 }

		
		resetAP OBJECT-TYPE
			SYNTAX TruthValue
			MAX-ACCESS read-write
			STATUS current
			DESCRIPTION
				"This a command field for conntrol AP action. Write any
				value to reset the AP."
			::= { auxCommand 1 }
			
		
		resetToFactoryDefault OBJECT-TYPE
			SYNTAX TruthValue
			MAX-ACCESS read-write
			STATUS current
			DESCRIPTION
				"This a command field for conntrol AP action. Write any
				value to reset the Access Point to the original factory 
				default settings."
			::= { auxCommand 2 }	
			
	END
