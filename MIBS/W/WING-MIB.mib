--
-- WING-MIB.my
-- MIB generated by MG-SOFT Visual MIB Builder Version 6.0  Build 88
-- Tuesday, November 29, 2011 at 14:31:15
--

	WING-MIB DEFINITIONS ::= BEGIN
 
		IMPORTS
			OBJECT-GROUP, MODULE-COMPLIANCE, NOTIFICATION-GROUP			
				FROM SNMPv2-CONF			
			Integer32, Unsigned32, Counter32, Counter64, 
			OBJECT-TYPE, MODULE-IDENTITY, OBJECT-IDENTITY, NOTIFICATION-TYPE			
				FROM SNMPv2-SMI			
			DisplayString, MacAddress, TruthValue, RowStatus			
				FROM SNMPv2-TC			
			wirelessProducts
				FROM EXTREME-BASE-MIB;
	
	
		-- 1.3.6.1.4.1.1916.2.131.50
		wingMIB MODULE-IDENTITY 
			LAST-UPDATED "201109210447Z"            -- August 23, 2011 at 00:25 GMT
			ORGANIZATION 
				"Extreme Networks"
			CONTACT-INFO 
				"Extreme Networks"
			DESCRIPTION 
				"WiNG MIB"
			REVISION "201109211647Z"		-- September 21, 2011 at 16:47 GMT
			DESCRIPTION 
				"Added l2tpv3-tunnel-policy Table"
			REVISION "201108231224Z"		-- August 23, 2011 at 12:24 GMT
			DESCRIPTION 
				"Implemented wingCfgProfDynRoute and wingCfgDevDynRoute Groups."
			REVISION "201107291725Z"		-- July 29, 2011 at 17:25 GMT
			DESCRIPTION 
				"Fixed OID mapping in wingStatsDevWlApDetectTable."
			REVISION "201107291340Z"		-- July 29, 2011 at 13:40 GMT
			DESCRIPTION 
				"Added wingActionDisassociateClient group"
			REVISION "201107251654Z"		-- July 25, 2011 at 16:54 GMT
			DESCRIPTION 
				"Added wingStatsDevWlApDetectTable and cleaned tables below ."
			REVISION "201107251312Z"		-- July 25, 2011 at 13:12 GMT
			DESCRIPTION 
				"Changed the Description of Configuration Checksum as per reviewer comments."
			REVISION "201107251140Z"		-- July 25, 2011 at 11:40 GMT
			DESCRIPTION 
				"Added Configuration Checksum Action group with In and Out subgroups"
			REVISION "201107191736Z"		-- July 19, 2011 at 17:36 GMT
			DESCRIPTION 
				"Added Adopted AP IP Address fiels in wingStatsRfdWlApInfoTable"
			REVISION "201107191448Z"		-- July 19, 2011 at 14:48 GMT
			DESCRIPTION 
				"Added txRetriedBytes for ClientStatDetail and RadioStatDetail"
			REVISION "201103211357Z"		-- March 21, 2011 at 13:57 GMT
			DESCRIPTION 
				"01a05
				Corrected description of objects."
			REVISION "201102091502Z"		-- February 09, 2011 at 15:02 GMT
			DESCRIPTION 
				"01a04
				Added tables under wingStats for 5.1 release."
			REVISION "201009271513Z"		-- September 27, 2010 at 15:13 GMT
			DESCRIPTION 
				"01a03
				Added system object identifier for AP4700."
			REVISION "201008041549Z"		-- August 04, 2010 at 15:49 GMT
			DESCRIPTION 
				"01a02
				Added system object identifiers for AP4511 and AP4021."
			REVISION "201002031404Z"		-- February 03, 2010 at 14:04 GMT
			DESCRIPTION 
				"01a01
				Initial revision"
			::= { wirelessProducts 50 }

		
	
--
-- Type definitions
--
	
-- pattern "[0-9a-zA-Z]([0-9a-zA-Z\-_ ]*[0-9a-zA-Z])?"
		WingIdentifier ::= OCTET STRING (SIZE (1..96))

-- This datatype always means that the MIB variable is
-- a simple ENUM that when written to 'doActionRightNow', 
-- causes the described action to take place, (much like 
-- a button pressed in a UI).
-- 
-- Such a value does NOT remain in state 'doActionRightNow'
-- while the operation is in-process, but instead when read 
-- always returns 'idleState'.
		WingDoActionNow ::= INTEGER
			{
			doActionRightNow(1),
			idleState(2)
			}

	
	
--
-- Node definitions
--
	
		-- 1.3.6.1.4.1.1916.2.131.50.0
		wingNotifications OBJECT IDENTIFIER ::= { wingMIB 0 }

		
		-- 1.3.6.1.4.1.1916.2.131.50.0.1
		wingTrapGeneric NOTIFICATION-TYPE
			OBJECTS { wingEventMnemonic, wingEventModule, wingEventSeverity, wingEventMsg, wingEventSourceAddr, 
				wingEventSourceHostname }
			STATUS current
			DESCRIPTION 
				"Generic WiNG Trap"
			::= { wingNotifications 1 }


--AAA/Radius module
		--1.3.6.1.4.1.1916.2.131.50.0.2
		wingTrapsAaa OBJECT IDENTIFIER ::= { wingNotifications 2 }


		--1.3.6.1.4.1.1916.2.131.50.0.2.0
		wingTrapsAaaPrefix OBJECT IDENTIFIER ::= { wingTrapsAaa 0 }


		-- 1.3.6.1.4.1.1916.2.131.50.0.2.0.1
		wingTrapAaaRadiusDisconMsg NOTIFICATION-TYPE
			OBJECTS { wingEventMnemonic, wingEventModule, wingEventSeverity, wingEventMsg, wingEventSourceAddr,
				wingEventSourceHostname }
			STATUS current
			DESCRIPTION
				"Received radius disconnect request"
				::= { wingTrapsAaaPrefix 1}


		-- 1.3.6.1.4.1.1916.2.131.50.0.2.0.2
		wingTrapAaaRadiusVlanUpdate NOTIFICATION-TYPE
			OBJECTS { wingEventMnemonic, wingEventModule, wingEventSeverity, wingEventMsg, wingEventSourceAddr,
				wingEventSourceHostname }
			STATUS current
			DESCRIPTION
				"Client vlan updated by radius"
				::= { wingTrapsAaaPrefix 2}


		-- 1.3.6.1.4.1.1916.2.131.50.0.2.0.3
		wingTrapAaaRadiusSessionNotStarted NOTIFICATION-TYPE
			OBJECTS { wingEventMnemonic, wingEventModule, wingEventSeverity, wingEventMsg, wingEventSourceAddr,
				wingEventSourceHostname }
			STATUS current
			DESCRIPTION
				"Start-time from Radius not yet valid"
				::= { wingTrapsAaaPrefix 3}


		-- 1.3.6.1.4.1.1916.2.131.50.0.2.0.4
		wingTrapAaaRadiusSessionExpired NOTIFICATION-TYPE
			OBJECTS { wingEventMnemonic, wingEventModule, wingEventSeverity, wingEventMsg, wingEventSourceAddr,
				wingEventSourceHostname }
			STATUS current
			DESCRIPTION
				"Session-time from Radius already expired"
				::= { wingTrapsAaaPrefix 4}


--adv-wips module
		--1.3.6.1.4.1.1916.2.131.50.0.3
		wingTrapsAdvWips OBJECT IDENTIFIER ::= { wingNotifications 3 }


		--1.3.6.1.4.1.1916.2.131.50.0.3.0
		wingTrapsAdvWipsPrefix OBJECT IDENTIFIER ::= { wingTrapsAdvWips 0 }


		-- 1.3.6.1.4.1.1916.2.131.50.0.3.0.1
		wingTrapAdvWipsAdvWipsEvent1 NOTIFICATION-TYPE
			OBJECTS { wingEventMnemonic, wingEventModule, wingEventSeverity, wingEventMsg, wingEventSourceAddr,
				wingEventSourceHostname }
			STATUS current
			DESCRIPTION
				"DoS Deauthentication attack "
				::= { wingTrapsAdvWipsPrefix 1}


		-- 1.3.6.1.4.1.1916.2.131.50.0.3.0.2
		wingTrapAdvWipsAdvWipsEvent2 NOTIFICATION-TYPE
			OBJECTS { wingEventMnemonic, wingEventModule, wingEventSeverity, wingEventMsg, wingEventSourceAddr,
				wingEventSourceHostname }
			STATUS current
			DESCRIPTION
				"DoS Disassociation attack "
				::= { wingTrapsAdvWipsPrefix 2}


		-- 1.3.6.1.4.1.1916.2.131.50.0.3.0.3
		wingTrapAdvWipsAdvWipsEvent3 NOTIFICATION-TYPE
			OBJECTS { wingEventMnemonic, wingEventModule, wingEventSeverity, wingEventMsg, wingEventSourceAddr,
				wingEventSourceHostname }
			STATUS current
			DESCRIPTION
				"EAP failure spoof attack "
				::= { wingTrapsAdvWipsPrefix 3}


		-- 1.3.6.1.4.1.1916.2.131.50.0.3.0.4
		wingTrapAdvWipsAdvWipsEvent10 NOTIFICATION-TYPE
			OBJECTS { wingEventMnemonic, wingEventModule, wingEventSeverity, wingEventMsg, wingEventSourceAddr,
				wingEventSourceHostname }
			STATUS current
			DESCRIPTION
				"ID-Theft out of sequence attack "
				::= { wingTrapsAdvWipsPrefix 4}


		-- 1.3.6.1.4.1.1916.2.131.50.0.3.0.5
		wingTrapAdvWipsAdvWipsEvent11 NOTIFICATION-TYPE
			OBJECTS { wingEventMnemonic, wingEventModule, wingEventSeverity, wingEventMsg, wingEventSourceAddr,
				wingEventSourceHostname }
			STATUS current
			DESCRIPTION
				"Possible ID-Theft EAPoL Success spoof attack "
				::= { wingTrapsAdvWipsPrefix 5}


		-- 1.3.6.1.4.1.1916.2.131.50.0.3.0.6
		wingTrapAdvWipsAdvWipsEvent12 NOTIFICATION-TYPE
			OBJECTS { wingEventMnemonic, wingEventModule, wingEventSeverity, wingEventMsg, wingEventSourceAddr,
				wingEventSourceHostname }
			STATUS current
			DESCRIPTION
				"Possible WLAN-Jack attack "
				::= { wingTrapsAdvWipsPrefix 6}


		-- 1.3.6.1.4.1.1916.2.131.50.0.3.0.7
		wingTrapAdvWipsAdvWipsEvent13 NOTIFICATION-TYPE
			OBJECTS { wingEventMnemonic, wingEventModule, wingEventSeverity, wingEventMsg, wingEventSourceAddr,
				wingEventSourceHostname }
			STATUS current
			DESCRIPTION
				"Possible ESSID-Jack attack "
				::= { wingTrapsAdvWipsPrefix 7}


		-- 1.3.6.1.4.1.1916.2.131.50.0.3.0.8
		wingTrapAdvWipsAdvWipsEvent14 NOTIFICATION-TYPE
			OBJECTS { wingEventMnemonic, wingEventModule, wingEventSeverity, wingEventMsg, wingEventSourceAddr,
				wingEventSourceHostname }
			STATUS current
			DESCRIPTION
				"Possible Monkey-Jack attack "
				::= { wingTrapsAdvWipsPrefix 8}


		-- 1.3.6.1.4.1.1916.2.131.50.0.3.0.9
		wingTrapAdvWipsAdvWipsEvent16 NOTIFICATION-TYPE
			OBJECTS { wingEventMnemonic, wingEventModule, wingEventSeverity, wingEventMsg, wingEventSourceAddr,
				wingEventSourceHostname }
			STATUS current
			DESCRIPTION
				"Possible NULL Probe Response attack "
				::= { wingTrapsAdvWipsPrefix 9}


		-- 1.3.6.1.4.1.1916.2.131.50.0.3.0.10
		wingTrapAdvWipsAdvWipsEvent19 NOTIFICATION-TYPE
			OBJECTS { wingEventMnemonic, wingEventModule, wingEventSeverity, wingEventMsg, wingEventSourceAddr,
				wingEventSourceHostname }
			STATUS current
			DESCRIPTION
				"DoS EAPoL Logoff storm attack "
				::= { wingTrapsAdvWipsPrefix 10}


		-- 1.3.6.1.4.1.1916.2.131.50.0.3.0.11
		wingTrapAdvWipsAdvWipsEvent21 NOTIFICATION-TYPE
			OBJECTS { wingEventMnemonic, wingEventModule, wingEventSeverity, wingEventMsg, wingEventSourceAddr,
				wingEventSourceHostname }
			STATUS current
			DESCRIPTION
				"DoS CTS flood attack "
				::= { wingTrapsAdvWipsPrefix 11}


		-- 1.3.6.1.4.1.1916.2.131.50.0.3.0.12
		wingTrapAdvWipsAdvWipsEvent25 NOTIFICATION-TYPE
			OBJECTS { wingEventMnemonic, wingEventModule, wingEventSeverity, wingEventMsg, wingEventSourceAddr,
				wingEventSourceHostname }
			STATUS current
			DESCRIPTION
				"Possible FATA-Jack attack "
				::= { wingTrapsAdvWipsPrefix 12}


		-- 1.3.6.1.4.1.1916.2.131.50.0.3.0.13
		wingTrapAdvWipsAdvWipsEvent29 NOTIFICATION-TYPE
			OBJECTS { wingEventMnemonic, wingEventModule, wingEventSeverity, wingEventMsg, wingEventSourceAddr,
				wingEventSourceHostname }
			STATUS current
			DESCRIPTION
				"Possible Fake DHCP server "
				::= { wingTrapsAdvWipsPrefix 13}


		-- 1.3.6.1.4.1.1916.2.131.50.0.3.0.14
		wingTrapAdvWipsAdvWipsEvent47 NOTIFICATION-TYPE
			OBJECTS { wingEventMnemonic, wingEventModule, wingEventSeverity, wingEventMsg, wingEventSourceAddr,
				wingEventSourceHostname }
			STATUS current
			DESCRIPTION
				"Crackable WEP IV used  "
				::= { wingTrapsAdvWipsPrefix 14}


		-- 1.3.6.1.4.1.1916.2.131.50.0.3.0.15
		wingTrapAdvWipsAdvWipsEvent87 NOTIFICATION-TYPE
			OBJECTS { wingEventMnemonic, wingEventModule, wingEventSeverity, wingEventMsg, wingEventSourceAddr,
				wingEventSourceHostname }
			STATUS current
			DESCRIPTION
				"Rogue-AP on wired network "
				::= { wingTrapsAdvWipsPrefix 15}


		-- 1.3.6.1.4.1.1916.2.131.50.0.3.0.16
		wingTrapAdvWipsAdvWipsEvent105 NOTIFICATION-TYPE
			OBJECTS { wingEventMnemonic, wingEventModule, wingEventSeverity, wingEventMsg, wingEventSourceAddr,
				wingEventSourceHostname }
			STATUS current
			DESCRIPTION
				"Sanctioned MU detected associated with unsanctioned/neighboring AP"
				::= { wingTrapsAdvWipsPrefix 16}


		-- 1.3.6.1.4.1.1916.2.131.50.0.3.0.17
		wingTrapAdvWipsAdvWipsEvent109 NOTIFICATION-TYPE
			OBJECTS { wingEventMnemonic, wingEventModule, wingEventSeverity, wingEventMsg, wingEventSourceAddr,
				wingEventSourceHostname }
			STATUS current
			DESCRIPTION
				"Multicast all systems traffic"
				::= { wingTrapsAdvWipsPrefix 17}


		-- 1.3.6.1.4.1.1916.2.131.50.0.3.0.18
		wingTrapAdvWipsAdvWipsEvent110 NOTIFICATION-TYPE
			OBJECTS { wingEventMnemonic, wingEventModule, wingEventSeverity, wingEventMsg, wingEventSourceAddr,
				wingEventSourceHostname }
			STATUS current
			DESCRIPTION
				"Multicast all routers traffic "
				::= { wingTrapsAdvWipsPrefix 18}


		-- 1.3.6.1.4.1.1916.2.131.50.0.3.0.19
		wingTrapAdvWipsAdvWipsEvent111 NOTIFICATION-TYPE
			OBJECTS { wingEventMnemonic, wingEventModule, wingEventSeverity, wingEventMsg, wingEventSourceAddr,
				wingEventSourceHostname }
			STATUS current
			DESCRIPTION
				"Multicast OSPF all traffic "
				::= { wingTrapsAdvWipsPrefix 19}


		-- 1.3.6.1.4.1.1916.2.131.50.0.3.0.20
		wingTrapAdvWipsAdvWipsEvent112 NOTIFICATION-TYPE
			OBJECTS { wingEventMnemonic, wingEventModule, wingEventSeverity, wingEventMsg, wingEventSourceAddr,
				wingEventSourceHostname }
			STATUS current
			DESCRIPTION
				"Multicast OSPF Deisgnated Routers traffic "
				::= { wingTrapsAdvWipsPrefix 20}


		-- 1.3.6.1.4.1.1916.2.131.50.0.3.0.21
		wingTrapAdvWipsAdvWipsEvent113 NOTIFICATION-TYPE
			OBJECTS { wingEventMnemonic, wingEventModule, wingEventSeverity, wingEventMsg, wingEventSourceAddr,
				wingEventSourceHostname }
			STATUS current
			DESCRIPTION
				"Multicast RIP-2 Routers traffic "
				::= { wingTrapsAdvWipsPrefix 21}


		-- 1.3.6.1.4.1.1916.2.131.50.0.3.0.22
		wingTrapAdvWipsAdvWipsEvent114 NOTIFICATION-TYPE
			OBJECTS { wingEventMnemonic, wingEventModule, wingEventSeverity, wingEventMsg, wingEventSourceAddr,
				wingEventSourceHostname }
			STATUS current
			DESCRIPTION
				"Multicast IGRP Routers traffic "
				::= { wingTrapsAdvWipsPrefix 22}


		-- 1.3.6.1.4.1.1916.2.131.50.0.3.0.23
		wingTrapAdvWipsAdvWipsEvent115 NOTIFICATION-TYPE
			OBJECTS { wingEventMnemonic, wingEventModule, wingEventSeverity, wingEventMsg, wingEventSourceAddr,
				wingEventSourceHostname }
			STATUS current
			DESCRIPTION
				"Multicast DHCP Server Relay Agent traffic "
				::= { wingTrapsAdvWipsPrefix 23}


		-- 1.3.6.1.4.1.1916.2.131.50.0.3.0.24
		wingTrapAdvWipsAdvWipsEvent116 NOTIFICATION-TYPE
			OBJECTS { wingEventMnemonic, wingEventModule, wingEventSeverity, wingEventMsg, wingEventSourceAddr,
				wingEventSourceHostname }
			STATUS current
			DESCRIPTION
				"Multicast VRRP Agent traffic "
				::= { wingTrapsAdvWipsPrefix 24}


		-- 1.3.6.1.4.1.1916.2.131.50.0.3.0.25
		wingTrapAdvWipsAdvWipsEvent117 NOTIFICATION-TYPE
			OBJECTS { wingEventMnemonic, wingEventModule, wingEventSeverity, wingEventMsg, wingEventSourceAddr,
				wingEventSourceHostname }
			STATUS current
			DESCRIPTION
				"Multicast HSRP Agent traffic "
				::= { wingTrapsAdvWipsPrefix 25}


		-- 1.3.6.1.4.1.1916.2.131.50.0.3.0.26
		wingTrapAdvWipsAdvWipsEvent118 NOTIFICATION-TYPE
			OBJECTS { wingEventMnemonic, wingEventModule, wingEventSeverity, wingEventMsg, wingEventSourceAddr,
				wingEventSourceHostname }
			STATUS current
			DESCRIPTION
				"Multicast IGMP traffic "
				::= { wingTrapsAdvWipsPrefix 26}


		-- 1.3.6.1.4.1.1916.2.131.50.0.3.0.27
		wingTrapAdvWipsAdvWipsEvent119 NOTIFICATION-TYPE
			OBJECTS { wingEventMnemonic, wingEventModule, wingEventSeverity, wingEventMsg, wingEventSourceAddr,
				wingEventSourceHostname }
			STATUS current
			DESCRIPTION
				"Detected NETBIOS traffic "
				::= { wingTrapsAdvWipsPrefix 27}


		-- 1.3.6.1.4.1.1916.2.131.50.0.3.0.28
		wingTrapAdvWipsAdvWipsEvent120 NOTIFICATION-TYPE
			OBJECTS { wingEventMnemonic, wingEventModule, wingEventSeverity, wingEventMsg, wingEventSourceAddr,
				wingEventSourceHostname }
			STATUS current
			DESCRIPTION
				"Detected STP traffic "
				::= { wingTrapsAdvWipsPrefix 28}


		-- 1.3.6.1.4.1.1916.2.131.50.0.3.0.29
		wingTrapAdvWipsAdvWipsEvent121 NOTIFICATION-TYPE
			OBJECTS { wingEventMnemonic, wingEventModule, wingEventSeverity, wingEventMsg, wingEventSourceAddr,
				wingEventSourceHostname }
			STATUS current
			DESCRIPTION
				"Detected IPX traffic "
				::= { wingTrapsAdvWipsPrefix 29}


		-- 1.3.6.1.4.1.1916.2.131.50.0.3.0.30
		wingTrapAdvWipsAdvWipsEvent142 NOTIFICATION-TYPE
			OBJECTS { wingEventMnemonic, wingEventModule, wingEventSeverity, wingEventMsg, wingEventSourceAddr,
				wingEventSourceHostname }
			STATUS current
			DESCRIPTION
				"Possible Probe Response attack "
				::= { wingTrapsAdvWipsPrefix 30}


		-- 1.3.6.1.4.1.1916.2.131.50.0.3.0.31
		wingTrapAdvWipsAdvWipsEvent221 NOTIFICATION-TYPE
			OBJECTS { wingEventMnemonic, wingEventModule, wingEventSeverity, wingEventMsg, wingEventSourceAddr,
				wingEventSourceHostname }
			STATUS current
			DESCRIPTION
				"Invalid Management Frames "
				::= { wingTrapsAdvWipsPrefix 31}


		-- 1.3.6.1.4.1.1916.2.131.50.0.3.0.32
		wingTrapAdvWipsAdvWipsEvent222 NOTIFICATION-TYPE
			OBJECTS { wingEventMnemonic, wingEventModule, wingEventSeverity, wingEventMsg, wingEventSourceAddr,
				wingEventSourceHostname }
			STATUS current
			DESCRIPTION
				"Invalid Channel Advertisement "
				::= { wingTrapsAdvWipsPrefix 32}


		-- 1.3.6.1.4.1.1916.2.131.50.0.3.0.33
		wingTrapAdvWipsAdvWipsEvent63 NOTIFICATION-TYPE
			OBJECTS { wingEventMnemonic, wingEventModule, wingEventSeverity, wingEventMsg, wingEventSourceAddr,
				wingEventSourceHostname }
			STATUS current
			DESCRIPTION
				"Windows ZERO Configuration Memory Leak "
				::= { wingTrapsAdvWipsPrefix 33}


		-- 1.3.6.1.4.1.1916.2.131.50.0.3.0.34
		wingTrapAdvWipsAdvWipsEvent26 NOTIFICATION-TYPE
			OBJECTS { wingEventMnemonic, wingEventModule, wingEventSeverity, wingEventMsg, wingEventSourceAddr,
				wingEventSourceHostname }
			STATUS current
			DESCRIPTION
				"DoS RTS flood attack "
				::= { wingTrapsAdvWipsPrefix 34}


		-- 1.3.6.1.4.1.1916.2.131.50.0.3.0.35
		wingTrapAdvWipsAdvWipsEvent220 NOTIFICATION-TYPE
			OBJECTS { wingEventMnemonic, wingEventModule, wingEventSeverity, wingEventMsg, wingEventSourceAddr,
				wingEventSourceHostname }
			STATUS current
			DESCRIPTION
				"Unauthorized Bridge "
				::= { wingTrapsAdvWipsPrefix 35}


--Access point module
		--1.3.6.1.4.1.1916.2.131.50.0.4
		wingTrapsAp OBJECT IDENTIFIER ::= { wingNotifications 4 }


		--1.3.6.1.4.1.1916.2.131.50.0.4.0
		wingTrapsApPrefix OBJECT IDENTIFIER ::= { wingTrapsAp 0 }


		-- 1.3.6.1.4.1.1916.2.131.50.0.4.0.1
		wingTrapApAdopted NOTIFICATION-TYPE
			OBJECTS { wingEventMnemonic, wingEventModule, wingEventSeverity, wingEventMsg, wingEventSourceAddr,
				wingEventSourceHostname }
			STATUS current
			DESCRIPTION
				"Access point adopted"
				::= { wingTrapsApPrefix 1}


		-- 1.3.6.1.4.1.1916.2.131.50.0.4.0.2
		wingTrapApUnadopted NOTIFICATION-TYPE
			OBJECTS { wingEventMnemonic, wingEventModule, wingEventSeverity, wingEventMsg, wingEventSourceAddr,
				wingEventSourceHostname }
			STATUS current
			DESCRIPTION
				"Access point unadopted"
				::= { wingTrapsApPrefix 2}


		-- 1.3.6.1.4.1.1916.2.131.50.0.4.0.3
		wingTrapApAdoptedToController NOTIFICATION-TYPE
			OBJECTS { wingEventMnemonic, wingEventModule, wingEventSeverity, wingEventMsg, wingEventSourceAddr,
				wingEventSourceHostname }
			STATUS current
			DESCRIPTION
				"Access point adopted to controller"
				::= { wingTrapsApPrefix 3}


		-- 1.3.6.1.4.1.1916.2.131.50.0.4.0.4
		wingTrapApReset NOTIFICATION-TYPE
			OBJECTS { wingEventMnemonic, wingEventModule, wingEventSeverity, wingEventMsg, wingEventSourceAddr,
				wingEventSourceHostname }
			STATUS current
			DESCRIPTION
				"Access point reset"
				::= { wingTrapsApPrefix 4}


		-- 1.3.6.1.4.1.1916.2.131.50.0.4.0.5
		wingTrapApSwConnLost NOTIFICATION-TYPE
			OBJECTS { wingEventMnemonic, wingEventModule, wingEventSeverity, wingEventMsg, wingEventSourceAddr,
				wingEventSourceHostname }
			STATUS current
			DESCRIPTION
				"controller connectivity lost"
				::= { wingTrapsApPrefix 5}


		-- 1.3.6.1.4.1.1916.2.131.50.0.4.0.6
		wingTrapApApAutoupTimeout NOTIFICATION-TYPE
			OBJECTS { wingEventMnemonic, wingEventModule, wingEventSeverity, wingEventMsg, wingEventSourceAddr,
				wingEventSourceHostname }
			STATUS current
			DESCRIPTION
				"Time out while trying to auto upgrade an AP"
				::= { wingTrapsApPrefix 6}


		-- 1.3.6.1.4.1.1916.2.131.50.0.4.0.7
		wingTrapApApAutoupReboot NOTIFICATION-TYPE
			OBJECTS { wingEventMnemonic, wingEventModule, wingEventSeverity, wingEventMsg, wingEventSourceAddr,
				wingEventSourceHostname }
			STATUS current
			DESCRIPTION
				"Rebooting AP after upgrade"
				::= { wingTrapsApPrefix 7}


		-- 1.3.6.1.4.1.1916.2.131.50.0.4.0.8
		wingTrapApApAutoupNoNeed NOTIFICATION-TYPE
			OBJECTS { wingEventMnemonic, wingEventModule, wingEventSeverity, wingEventMsg, wingEventSourceAddr,
				wingEventSourceHostname }
			STATUS current
			DESCRIPTION
				"Auto upgrade is not initiated"
				::= { wingTrapsApPrefix 8}


		-- 1.3.6.1.4.1.1916.2.131.50.0.4.0.9
		wingTrapApApAutoupNeeded NOTIFICATION-TYPE
			OBJECTS { wingEventMnemonic, wingEventModule, wingEventSeverity, wingEventMsg, wingEventSourceAddr,
				wingEventSourceHostname }
			STATUS current
			DESCRIPTION
				"Auto upgrade is initiated on the AP"
				::= { wingTrapsApPrefix 9}


		-- 1.3.6.1.4.1.1916.2.131.50.0.4.0.10
		wingTrapApApAutoupDone NOTIFICATION-TYPE
			OBJECTS { wingEventMnemonic, wingEventModule, wingEventSeverity, wingEventMsg, wingEventSourceAddr,
				wingEventSourceHostname }
			STATUS current
			DESCRIPTION
				"Autoupgrade successful"
				::= { wingTrapsApPrefix 10}


		-- 1.3.6.1.4.1.1916.2.131.50.0.4.0.11
		wingTrapApApAutoupFail NOTIFICATION-TYPE
			OBJECTS { wingEventMnemonic, wingEventModule, wingEventSeverity, wingEventMsg, wingEventSourceAddr,
				wingEventSourceHostname }
			STATUS current
			DESCRIPTION
				"Failed auto upgrade attempt "
				::= { wingTrapsApPrefix 11}


		-- 1.3.6.1.4.1.1916.2.131.50.0.4.0.12
		wingTrapApApAutoupVer NOTIFICATION-TYPE
			OBJECTS { wingEventMnemonic, wingEventModule, wingEventSeverity, wingEventMsg, wingEventSourceAddr,
				wingEventSourceHostname }
			STATUS current
			DESCRIPTION
				"Available AP firmware versions for auto upgrade"
				::= { wingTrapsApPrefix 12}


		-- 1.3.6.1.4.1.1916.2.131.50.0.4.0.13
		wingTrapApNoImageFile NOTIFICATION-TYPE
			OBJECTS { wingEventMnemonic, wingEventModule, wingEventSeverity, wingEventMsg, wingEventSourceAddr,
				wingEventSourceHostname }
			STATUS current
			DESCRIPTION
				"AP firmware not on controller"
				::= { wingTrapsApPrefix 13}


		-- 1.3.6.1.4.1.1916.2.131.50.0.4.0.14
		wingTrapApImageParseFailure NOTIFICATION-TYPE
			OBJECTS { wingEventMnemonic, wingEventModule, wingEventSeverity, wingEventMsg, wingEventSourceAddr,
				wingEventSourceHostname }
			STATUS current
			DESCRIPTION
				"Invalid AP firmware file"
				::= { wingTrapsApPrefix 14}


		-- 1.3.6.1.4.1.1916.2.131.50.0.4.0.15
		wingTrapApLegacyAutoUpdate NOTIFICATION-TYPE
			OBJECTS { wingEventMnemonic, wingEventModule, wingEventSeverity, wingEventMsg, wingEventSourceAddr,
				wingEventSourceHostname }
			STATUS current
			DESCRIPTION
				"Legacy AP updated"
				::= { wingTrapsApPrefix 15}


		-- 1.3.6.1.4.1.1916.2.131.50.0.4.0.16
		wingTrapApApAdopted NOTIFICATION-TYPE
			OBJECTS { wingEventMnemonic, wingEventModule, wingEventSeverity, wingEventMsg, wingEventSourceAddr,
				wingEventSourceHostname }
			STATUS current
			DESCRIPTION
				"Access port adopted"
				::= { wingTrapsApPrefix 16}


		-- 1.3.6.1.4.1.1916.2.131.50.0.4.0.17
		wingTrapApApUnadopted NOTIFICATION-TYPE
			OBJECTS { wingEventMnemonic, wingEventModule, wingEventSeverity, wingEventMsg, wingEventSourceAddr,
				wingEventSourceHostname }
			STATUS current
			DESCRIPTION
				"Access port unadopted"
				::= { wingTrapsApPrefix 17}


		-- 1.3.6.1.4.1.1916.2.131.50.0.4.0.18
		wingTrapApApResetDetected NOTIFICATION-TYPE
			OBJECTS { wingEventMnemonic, wingEventModule, wingEventSeverity, wingEventMsg, wingEventSourceAddr,
				wingEventSourceHostname }
			STATUS current
			DESCRIPTION
				"Access port reset detected"
				::= { wingTrapsApPrefix 18}


		-- 1.3.6.1.4.1.1916.2.131.50.0.4.0.19
		wingTrapApApResetRequest NOTIFICATION-TYPE
			OBJECTS { wingEventMnemonic, wingEventModule, wingEventSeverity, wingEventMsg, wingEventSourceAddr,
				wingEventSourceHostname }
			STATUS current
			DESCRIPTION
				"Access port user requested reset"
				::= { wingTrapsApPrefix 19}


		-- 1.3.6.1.4.1.1916.2.131.50.0.4.0.20
		wingTrapApApTimeout NOTIFICATION-TYPE
			OBJECTS { wingEventMnemonic, wingEventModule, wingEventSeverity, wingEventMsg, wingEventSourceAddr,
				wingEventSourceHostname }
			STATUS current
			DESCRIPTION
				"Access port timed out"
				::= { wingTrapsApPrefix 20}


--Captive Portal
		--1.3.6.1.4.1.1916.2.131.50.0.5
		wingTrapsCaptivePortal OBJECT IDENTIFIER ::= { wingNotifications 5 }


		--1.3.6.1.4.1.1916.2.131.50.0.5.0
		wingTrapsCaptivePortalPrefix OBJECT IDENTIFIER ::= { wingTrapsCaptivePortal 0 }


		-- 1.3.6.1.4.1.1916.2.131.50.0.5.0.1
		wingTrapCaptivePortalAuthSuccess NOTIFICATION-TYPE
			OBJECTS { wingEventMnemonic, wingEventModule, wingEventSeverity, wingEventMsg, wingEventSourceAddr,
				wingEventSourceHostname }
			STATUS current
			DESCRIPTION
				"Authentication sucess"
				::= { wingTrapsCaptivePortalPrefix 1}


		-- 1.3.6.1.4.1.1916.2.131.50.0.5.0.2
		wingTrapCaptivePortalAuthFailed NOTIFICATION-TYPE
			OBJECTS { wingEventMnemonic, wingEventModule, wingEventSeverity, wingEventMsg, wingEventSourceAddr,
				wingEventSourceHostname }
			STATUS current
			DESCRIPTION
				"Authentication failed"
				::= { wingTrapsCaptivePortalPrefix 2}


		-- 1.3.6.1.4.1.1916.2.131.50.0.5.0.3
		wingTrapCaptivePortalSessionTimeout NOTIFICATION-TYPE
			OBJECTS { wingEventMnemonic, wingEventModule, wingEventSeverity, wingEventMsg, wingEventSourceAddr,
				wingEventSourceHostname }
			STATUS current
			DESCRIPTION
				"Session timed out"
				::= { wingTrapsCaptivePortalPrefix 3}


		-- 1.3.6.1.4.1.1916.2.131.50.0.5.0.4
		wingTrapCaptivePortalClientDisconnect NOTIFICATION-TYPE
			OBJECTS { wingEventMnemonic, wingEventModule, wingEventSeverity, wingEventMsg, wingEventSourceAddr,
				wingEventSourceHostname }
			STATUS current
			DESCRIPTION
				"Client disconnected"
				::= { wingTrapsCaptivePortalPrefix 4}


		-- 1.3.6.1.4.1.1916.2.131.50.0.5.0.5
		wingTrapCaptivePortalPurgeClient NOTIFICATION-TYPE
			OBJECTS { wingEventMnemonic, wingEventModule, wingEventSeverity, wingEventMsg, wingEventSourceAddr,
				wingEventSourceHostname }
			STATUS current
			DESCRIPTION
				"Client purged"
				::= { wingTrapsCaptivePortalPrefix 5}


		-- 1.3.6.1.4.1.1916.2.131.50.0.5.0.6
		wingTrapCaptivePortalFlexLogAccess NOTIFICATION-TYPE
			OBJECTS { wingEventMnemonic, wingEventModule, wingEventSeverity, wingEventMsg, wingEventSourceAddr,
				wingEventSourceHostname }
			STATUS current
			DESCRIPTION
				"Flex-log access granted to client"
				::= { wingTrapsCaptivePortalPrefix 6}


		-- 1.3.6.1.4.1.1916.2.131.50.0.5.0.7
		wingTrapCaptivePortalInactivityTimeout NOTIFICATION-TYPE
			OBJECTS { wingEventMnemonic, wingEventModule, wingEventSeverity, wingEventMsg, wingEventSourceAddr,
				wingEventSourceHostname }
			STATUS current
			DESCRIPTION
				"Client timed out due to inactivity"
				::= { wingTrapsCaptivePortalPrefix 7}


		-- 1.3.6.1.4.1.1916.2.131.50.0.5.0.8
		wingTrapCaptivePortalAllowAccess NOTIFICATION-TYPE
			OBJECTS { wingEventMnemonic, wingEventModule, wingEventSeverity, wingEventMsg, wingEventSourceAddr,
				wingEventSourceHostname }
			STATUS current
			DESCRIPTION
				"Client allowed access"
				::= { wingTrapsCaptivePortalPrefix 8}


		-- 1.3.6.1.4.1.1916.2.131.50.0.5.0.9
		wingTrapCaptivePortalClientRemoved NOTIFICATION-TYPE
			OBJECTS { wingEventMnemonic, wingEventModule, wingEventSeverity, wingEventMsg, wingEventSourceAddr,
				wingEventSourceHostname }
			STATUS current
			DESCRIPTION
				"Client removed due to admin changes"
				::= { wingTrapsCaptivePortalPrefix 9}


		-- 1.3.6.1.4.1.1916.2.131.50.0.5.0.10
		wingTrapCaptivePortalPageCreFailed NOTIFICATION-TYPE
			OBJECTS { wingEventMnemonic, wingEventModule, wingEventSeverity, wingEventMsg, wingEventSourceAddr,
				wingEventSourceHostname }
			STATUS current
			DESCRIPTION
				"Page Creation failure"
				::= { wingTrapsCaptivePortalPrefix 10}


		-- 1.3.6.1.4.1.1916.2.131.50.0.5.0.11
		wingTrapCaptivePortalDataLimitExceed NOTIFICATION-TYPE
			OBJECTS { wingEventMnemonic, wingEventModule, wingEventSeverity, wingEventMsg, wingEventSourceAddr,
				wingEventSourceHostname }
			STATUS current
			DESCRIPTION
				"Client data limit exceed       "
				::= { wingTrapsCaptivePortalPrefix 11}


--Certificate Manager
		--1.3.6.1.4.1.1916.2.131.50.0.6
		wingTrapsCertmgr OBJECT IDENTIFIER ::= { wingNotifications 6 }


		--1.3.6.1.4.1.1916.2.131.50.0.6.0
		wingTrapsCertmgrPrefix OBJECT IDENTIFIER ::= { wingTrapsCertmgr 0 }


		-- 1.3.6.1.4.1.1916.2.131.50.0.6.0.1
		wingTrapCertmgrRsaKeyActionsSuccess NOTIFICATION-TYPE
			OBJECTS { wingEventMnemonic, wingEventModule, wingEventSeverity, wingEventMsg, wingEventSourceAddr,
				wingEventSourceHostname }
			STATUS current
			DESCRIPTION
				"Successful completion of RSA key related actions (import, export, etc)"
				::= { wingTrapsCertmgrPrefix 1}


		-- 1.3.6.1.4.1.1916.2.131.50.0.6.0.2
		wingTrapCertmgrRsaKeyActionsFailure NOTIFICATION-TYPE
			OBJECTS { wingEventMnemonic, wingEventModule, wingEventSeverity, wingEventMsg, wingEventSourceAddr,
				wingEventSourceHostname }
			STATUS current
			DESCRIPTION
				"Failure of RSA key related actions (import, export, etc)"
				::= { wingTrapsCertmgrPrefix 2}


		-- 1.3.6.1.4.1.1916.2.131.50.0.6.0.3
		wingTrapCertmgrCaCertActionsSuccess NOTIFICATION-TYPE
			OBJECTS { wingEventMnemonic, wingEventModule, wingEventSeverity, wingEventMsg, wingEventSourceAddr,
				wingEventSourceHostname }
			STATUS current
			DESCRIPTION
				"Successful completion of CA certificate related actions (import, export, etc)"
				::= { wingTrapsCertmgrPrefix 3}


		-- 1.3.6.1.4.1.1916.2.131.50.0.6.0.4
		wingTrapCertmgrCaCertActionsFailure NOTIFICATION-TYPE
			OBJECTS { wingEventMnemonic, wingEventModule, wingEventSeverity, wingEventMsg, wingEventSourceAddr,
				wingEventSourceHostname }
			STATUS current
			DESCRIPTION
				"Failure of CA certificate actions (import, export, etc)"
				::= { wingTrapsCertmgrPrefix 4}


		-- 1.3.6.1.4.1.1916.2.131.50.0.6.0.5
		wingTrapCertmgrSrvCertActionsSuccess NOTIFICATION-TYPE
			OBJECTS { wingEventMnemonic, wingEventModule, wingEventSeverity, wingEventMsg, wingEventSourceAddr,
				wingEventSourceHostname }
			STATUS current
			DESCRIPTION
				"Successful completion of Server certificate actions (import, export, etc)"
				::= { wingTrapsCertmgrPrefix 5}


		-- 1.3.6.1.4.1.1916.2.131.50.0.6.0.6
		wingTrapCertmgrSvrCertActionsFailure NOTIFICATION-TYPE
			OBJECTS { wingEventMnemonic, wingEventModule, wingEventSeverity, wingEventMsg, wingEventSourceAddr,
				wingEventSourceHostname }
			STATUS current
			DESCRIPTION
				"Failure of Server certificate actions (import, export, etc)"
				::= { wingTrapsCertmgrPrefix 6}


		-- 1.3.6.1.4.1.1916.2.131.50.0.6.0.7
		wingTrapCertmgrCsrExportSuccess NOTIFICATION-TYPE
			OBJECTS { wingEventMnemonic, wingEventModule, wingEventSeverity, wingEventMsg, wingEventSourceAddr,
				wingEventSourceHostname }
			STATUS current
			DESCRIPTION
				"Successful export of Certificate Signing Request"
				::= { wingTrapsCertmgrPrefix 7}


		-- 1.3.6.1.4.1.1916.2.131.50.0.6.0.8
		wingTrapCertmgrCsrExportFailure NOTIFICATION-TYPE
			OBJECTS { wingEventMnemonic, wingEventModule, wingEventSeverity, wingEventMsg, wingEventSourceAddr,
				wingEventSourceHostname }
			STATUS current
			DESCRIPTION
				"Failed to export Certificate Signing Request"
				::= { wingTrapsCertmgrPrefix 8}


		-- 1.3.6.1.4.1.1916.2.131.50.0.6.0.9
		wingTrapCertmgrCrlActionsSuccess NOTIFICATION-TYPE
			OBJECTS { wingEventMnemonic, wingEventModule, wingEventSeverity, wingEventMsg, wingEventSourceAddr,
				wingEventSourceHostname }
			STATUS current
			DESCRIPTION
				"Successful completion of Certificate Revocation List actions"
				::= { wingTrapsCertmgrPrefix 9}


		-- 1.3.6.1.4.1.1916.2.131.50.0.6.0.10
		wingTrapCertmgrCrlActionsFailure NOTIFICATION-TYPE
			OBJECTS { wingEventMnemonic, wingEventModule, wingEventSeverity, wingEventMsg, wingEventSourceAddr,
				wingEventSourceHostname }
			STATUS current
			DESCRIPTION
				"Failure of Certificate Revocation List actions"
				::= { wingTrapsCertmgrPrefix 10}


		-- 1.3.6.1.4.1.1916.2.131.50.0.6.0.11
		wingTrapCertmgrDeleteTrustpointAction NOTIFICATION-TYPE
			OBJECTS { wingEventMnemonic, wingEventModule, wingEventSeverity, wingEventMsg, wingEventSourceAddr,
				wingEventSourceHostname }
			STATUS current
			DESCRIPTION
				"Deletion of Trustpoint"
				::= { wingTrapsCertmgrPrefix 11}


		-- 1.3.6.1.4.1.1916.2.131.50.0.6.0.12
		wingTrapCertmgrImportTrustpoint NOTIFICATION-TYPE
			OBJECTS { wingEventMnemonic, wingEventModule, wingEventSeverity, wingEventMsg, wingEventSourceAddr,
				wingEventSourceHostname }
			STATUS current
			DESCRIPTION
				"Import of Trustpoint"
				::= { wingTrapsCertmgrPrefix 12}


		-- 1.3.6.1.4.1.1916.2.131.50.0.6.0.13
		wingTrapCertmgrExportTrustpoint NOTIFICATION-TYPE
			OBJECTS { wingEventMnemonic, wingEventModule, wingEventSeverity, wingEventMsg, wingEventSourceAddr,
				wingEventSourceHostname }
			STATUS current
			DESCRIPTION
				"Export of Trustpoint"
				::= { wingTrapsCertmgrPrefix 13}


		-- 1.3.6.1.4.1.1916.2.131.50.0.6.0.14
		wingTrapCertmgrCertExpiry NOTIFICATION-TYPE
			OBJECTS { wingEventMnemonic, wingEventModule, wingEventSeverity, wingEventMsg, wingEventSourceAddr,
				wingEventSourceHostname }
			STATUS current
			DESCRIPTION
				"Certificate expiry"
				::= { wingTrapsCertmgrPrefix 14}


		-- 1.3.6.1.4.1.1916.2.131.50.0.6.0.15
		wingTrapCertmgrCaKeyActionsSuccess NOTIFICATION-TYPE
			OBJECTS { wingEventMnemonic, wingEventModule, wingEventSeverity, wingEventMsg, wingEventSourceAddr,
				wingEventSourceHostname }
			STATUS current
			DESCRIPTION
				"Successful completion of CA private key actions"
				::= { wingTrapsCertmgrPrefix 15}


		-- 1.3.6.1.4.1.1916.2.131.50.0.6.0.16
		wingTrapCertmgrCaKeyActionsFailure NOTIFICATION-TYPE
			OBJECTS { wingEventMnemonic, wingEventModule, wingEventSeverity, wingEventMsg, wingEventSourceAddr,
				wingEventSourceHostname }
			STATUS current
			DESCRIPTION
				"Failure of CA private key actions"
				::= { wingTrapsCertmgrPrefix 16}


--cfgd module
		--1.3.6.1.4.1.1916.2.131.50.0.7
		wingTrapsCfgd OBJECT IDENTIFIER ::= { wingNotifications 7 }


		--1.3.6.1.4.1.1916.2.131.50.0.7.0
		wingTrapsCfgdPrefix OBJECT IDENTIFIER ::= { wingTrapsCfgd 0 }


		-- 1.3.6.1.4.1.1916.2.131.50.0.7.0.1
		wingTrapCfgdAclRuleAltered NOTIFICATION-TYPE
			OBJECTS { wingEventMnemonic, wingEventModule, wingEventSeverity, wingEventMsg, wingEventSourceAddr,
				wingEventSourceHostname }
			STATUS current
			DESCRIPTION
				"ACL rule altered"
				::= { wingTrapsCfgdPrefix 1}


		-- 1.3.6.1.4.1.1916.2.131.50.0.7.0.2
		wingTrapCfgdAclAttachedAltered NOTIFICATION-TYPE
			OBJECTS { wingEventMnemonic, wingEventModule, wingEventSeverity, wingEventMsg, wingEventSourceAddr,
				wingEventSourceHostname }
			STATUS current
			DESCRIPTION
				"ACL altered"
				::= { wingTrapsCfgdPrefix 2}


--cluster module
		--1.3.6.1.4.1.1916.2.131.50.0.8
		wingTrapsCluster OBJECT IDENTIFIER ::= { wingNotifications 8 }


		--1.3.6.1.4.1.1916.2.131.50.0.8.0
		wingTrapsClusterPrefix OBJECT IDENTIFIER ::= { wingTrapsCluster 0 }


		-- 1.3.6.1.4.1.1916.2.131.50.0.8.0.1
		wingTrapClusterCmasterCfgUpdateFail NOTIFICATION-TYPE
			OBJECTS { wingEventMnemonic, wingEventModule, wingEventSeverity, wingEventMsg, wingEventSourceAddr,
				wingEventSourceHostname }
			STATUS current
			DESCRIPTION
				"Cluster master config update failed"
				::= { wingTrapsClusterPrefix 1}


		-- 1.3.6.1.4.1.1916.2.131.50.0.8.0.2
		wingTrapClusterMaxExceeded NOTIFICATION-TYPE
			OBJECTS { wingEventMnemonic, wingEventModule, wingEventSeverity, wingEventMsg, wingEventSourceAddr,
				wingEventSourceHostname }
			STATUS current
			DESCRIPTION
				"Max cluster count exceeded"
				::= { wingTrapsClusterPrefix 2}


--DHCP Configuration Daemon
		--1.3.6.1.4.1.1916.2.131.50.0.9
		wingTrapsDhcpsvr OBJECT IDENTIFIER ::= { wingNotifications 9 }


		--1.3.6.1.4.1.1916.2.131.50.0.9.0
		wingTrapsDhcpsvrPrefix OBJECT IDENTIFIER ::= { wingTrapsDhcpsvr 0 }


		-- 1.3.6.1.4.1.1916.2.131.50.0.9.0.1
		wingTrapDhcpsvrRelayNoIface NOTIFICATION-TYPE
			OBJECTS { wingEventMnemonic, wingEventModule, wingEventSeverity, wingEventMsg, wingEventSourceAddr,
				wingEventSourceHostname }
			STATUS current
			DESCRIPTION
				"No interface for DHCP relay"
				::= { wingTrapsDhcpsvrPrefix 1}


		-- 1.3.6.1.4.1.1916.2.131.50.0.9.0.2
		wingTrapDhcpsvrRelayIfaceNoIp NOTIFICATION-TYPE
			OBJECTS { wingEventMnemonic, wingEventModule, wingEventSeverity, wingEventMsg, wingEventSourceAddr,
				wingEventSourceHostname }
			STATUS current
			DESCRIPTION
				"No IP address on DHCP relay interface"
				::= { wingTrapsDhcpsvrPrefix 2}


		-- 1.3.6.1.4.1.1916.2.131.50.0.9.0.3
		wingTrapDhcpsvrRelayStart NOTIFICATION-TYPE
			OBJECTS { wingEventMnemonic, wingEventModule, wingEventSeverity, wingEventMsg, wingEventSourceAddr,
				wingEventSourceHostname }
			STATUS current
			DESCRIPTION
				"DHCP relay agent started"
				::= { wingTrapsDhcpsvrPrefix 3}


		-- 1.3.6.1.4.1.1916.2.131.50.0.9.0.4
		wingTrapDhcpsvrRelayStop NOTIFICATION-TYPE
			OBJECTS { wingEventMnemonic, wingEventModule, wingEventSeverity, wingEventMsg, wingEventSourceAddr,
				wingEventSourceHostname }
			STATUS current
			DESCRIPTION
				"DHCP relay agent stopped"
				::= { wingTrapsDhcpsvrPrefix 4}


		-- 1.3.6.1.4.1.1916.2.131.50.0.9.0.5
		wingTrapDhcpsvrDhcpsvrStart NOTIFICATION-TYPE
			OBJECTS { wingEventMnemonic, wingEventModule, wingEventSeverity, wingEventMsg, wingEventSourceAddr,
				wingEventSourceHostname }
			STATUS current
			DESCRIPTION
				"DHCP server started"
				::= { wingTrapsDhcpsvrPrefix 5}


		-- 1.3.6.1.4.1.1916.2.131.50.0.9.0.6
		wingTrapDhcpsvrDhcpsvrStop NOTIFICATION-TYPE
			OBJECTS { wingEventMnemonic, wingEventModule, wingEventSeverity, wingEventMsg, wingEventSourceAddr,
				wingEventSourceHostname }
			STATUS current
			DESCRIPTION
				"DHCP server stopped"
				::= { wingTrapsDhcpsvrPrefix 6}


		-- 1.3.6.1.4.1.1916.2.131.50.0.9.0.7
		wingTrapDhcpsvrDhcpsvrStop NOTIFICATION-TYPE
			OBJECTS { wingEventMnemonic, wingEventModule, wingEventSeverity, wingEventMsg, wingEventSourceAddr,
				wingEventSourceHostname }
			STATUS current
			DESCRIPTION
				"DHCP server stopped"
				::= { wingTrapsDhcpsvrPrefix 7}


--diag module
		--1.3.6.1.4.1.1916.2.131.50.0.10
		wingTrapsDiag OBJECT IDENTIFIER ::= { wingNotifications 10 }


		--1.3.6.1.4.1.1916.2.131.50.0.10.0
		wingTrapsDiagPrefix OBJECT IDENTIFIER ::= { wingTrapsDiag 0 }


		-- 1.3.6.1.4.1.1916.2.131.50.0.10.0.1
		wingTrapDiagFanUnderspeed NOTIFICATION-TYPE
			OBJECTS { wingEventMnemonic, wingEventModule, wingEventSeverity, wingEventMsg, wingEventSourceAddr,
				wingEventSourceHostname }
			STATUS current
			DESCRIPTION
				"Event fan-underspeed"
				::= { wingTrapsDiagPrefix 1}


		-- 1.3.6.1.4.1.1916.2.131.50.0.10.0.2
		wingTrapDiagUnderVoltage NOTIFICATION-TYPE
			OBJECTS { wingEventMnemonic, wingEventModule, wingEventSeverity, wingEventMsg, wingEventSourceAddr,
				wingEventSourceHostname }
			STATUS current
			DESCRIPTION
				"Event under-voltage"
				::= { wingTrapsDiagPrefix 2}


		-- 1.3.6.1.4.1.1916.2.131.50.0.10.0.3
		wingTrapDiagOverVoltage NOTIFICATION-TYPE
			OBJECTS { wingEventMnemonic, wingEventModule, wingEventSeverity, wingEventMsg, wingEventSourceAddr,
				wingEventSourceHostname }
			STATUS current
			DESCRIPTION
				"Event over-voltage"
				::= { wingTrapsDiagPrefix 3}


		-- 1.3.6.1.4.1.1916.2.131.50.0.10.0.4
		wingTrapDiagLowTemp NOTIFICATION-TYPE
			OBJECTS { wingEventMnemonic, wingEventModule, wingEventSeverity, wingEventMsg, wingEventSourceAddr,
				wingEventSourceHostname }
			STATUS current
			DESCRIPTION
				"Event low-temp"
				::= { wingTrapsDiagPrefix 4}


		-- 1.3.6.1.4.1.1916.2.131.50.0.10.0.5
		wingTrapDiagHighTemp NOTIFICATION-TYPE
			OBJECTS { wingEventMnemonic, wingEventModule, wingEventSeverity, wingEventMsg, wingEventSourceAddr,
				wingEventSourceHostname }
			STATUS current
			DESCRIPTION
				"Event high-temp"
				::= { wingTrapsDiagPrefix 5}


		-- 1.3.6.1.4.1.1916.2.131.50.0.10.0.6
		wingTrapDiagOverTemp NOTIFICATION-TYPE
			OBJECTS { wingEventMnemonic, wingEventModule, wingEventSeverity, wingEventMsg, wingEventSourceAddr,
				wingEventSourceHostname }
			STATUS current
			DESCRIPTION
				"Event over-temp"
				::= { wingTrapsDiagPrefix 6}


		-- 1.3.6.1.4.1.1916.2.131.50.0.10.0.7
		wingTrapDiagWdStateChange NOTIFICATION-TYPE
			OBJECTS { wingEventMnemonic, wingEventModule, wingEventSeverity, wingEventMsg, wingEventSourceAddr,
				wingEventSourceHostname }
			STATUS current
			DESCRIPTION
				"Event wd-state-change"
				::= { wingTrapsDiagPrefix 7}


		-- 1.3.6.1.4.1.1916.2.131.50.0.10.0.8
		wingTrapDiagElapsedTime NOTIFICATION-TYPE
			OBJECTS { wingEventMnemonic, wingEventModule, wingEventSeverity, wingEventMsg, wingEventSourceAddr,
				wingEventSourceHostname }
			STATUS current
			DESCRIPTION
				"Event elapsed-time"
				::= { wingTrapsDiagPrefix 8}


		-- 1.3.6.1.4.1.1916.2.131.50.0.10.0.9
		wingTrapDiagAutogenTechSprt NOTIFICATION-TYPE
			OBJECTS { wingEventMnemonic, wingEventModule, wingEventSeverity, wingEventMsg, wingEventSourceAddr,
				wingEventSourceHostname }
			STATUS current
			DESCRIPTION
				"Event autogen-tech-sprt"
				::= { wingTrapsDiagPrefix 9}


		-- 1.3.6.1.4.1.1916.2.131.50.0.10.0.10
		wingTrapDiagPoeInitFail NOTIFICATION-TYPE
			OBJECTS { wingEventMnemonic, wingEventModule, wingEventSeverity, wingEventMsg, wingEventSourceAddr,
				wingEventSourceHostname }
			STATUS current
			DESCRIPTION
				"Event poe-init-fail"
				::= { wingTrapsDiagPrefix 10}


		-- 1.3.6.1.4.1.1916.2.131.50.0.10.0.11
		wingTrapDiagPoePowerLevel NOTIFICATION-TYPE
			OBJECTS { wingEventMnemonic, wingEventModule, wingEventSeverity, wingEventMsg, wingEventSourceAddr,
				wingEventSourceHostname }
			STATUS current
			DESCRIPTION
				"Event poe-power-level"
				::= { wingTrapsDiagPrefix 11}


		-- 1.3.6.1.4.1.1916.2.131.50.0.10.0.12
		wingTrapDiagPoeReadFail NOTIFICATION-TYPE
			OBJECTS { wingEventMnemonic, wingEventModule, wingEventSeverity, wingEventMsg, wingEventSourceAddr,
				wingEventSourceHostname }
			STATUS current
			DESCRIPTION
				"Event poe-read-fail"
				::= { wingTrapsDiagPrefix 12}


		-- 1.3.6.1.4.1.1916.2.131.50.0.10.0.13
		wingTrapDiagPoeStateChange NOTIFICATION-TYPE
			OBJECTS { wingEventMnemonic, wingEventModule, wingEventSeverity, wingEventMsg, wingEventSourceAddr,
				wingEventSourceHostname }
			STATUS current
			DESCRIPTION
				"Event poe-state-change"
				::= { wingTrapsDiagPrefix 13}


		-- 1.3.6.1.4.1.1916.2.131.50.0.10.0.14
		wingTrapDiagRaidDegraded NOTIFICATION-TYPE
			OBJECTS { wingEventMnemonic, wingEventModule, wingEventSeverity, wingEventMsg, wingEventSourceAddr,
				wingEventSourceHostname }
			STATUS current
			DESCRIPTION
				"Event raid-degraded"
				::= { wingTrapsDiagPrefix 14}


		-- 1.3.6.1.4.1.1916.2.131.50.0.10.0.15
		wingTrapDiagRaidError NOTIFICATION-TYPE
			OBJECTS { wingEventMnemonic, wingEventModule, wingEventSeverity, wingEventMsg, wingEventSourceAddr,
				wingEventSourceHostname }
			STATUS current
			DESCRIPTION
				"Event raid-error"
				::= { wingTrapsDiagPrefix 15}


		-- 1.3.6.1.4.1.1916.2.131.50.0.10.0.16
		wingTrapDiagPwrsplyFail NOTIFICATION-TYPE
			OBJECTS { wingEventMnemonic, wingEventModule, wingEventSeverity, wingEventMsg, wingEventSourceAddr,
				wingEventSourceHostname }
			STATUS current
			DESCRIPTION
				"Event pwrsply-fail"
				::= { wingTrapsDiagPrefix 16}


		-- 1.3.6.1.4.1.1916.2.131.50.0.10.0.17
		wingTrapDiagWdResetSys NOTIFICATION-TYPE
			OBJECTS { wingEventMnemonic, wingEventModule, wingEventSeverity, wingEventMsg, wingEventSourceAddr,
				wingEventSourceHostname }
			STATUS current
			DESCRIPTION
				"Event wd-reset-sys"
				::= { wingTrapsDiagPrefix 17}


		-- 1.3.6.1.4.1.1916.2.131.50.0.10.0.18
		wingTrapDiagCpuLoad NOTIFICATION-TYPE
			OBJECTS { wingEventMnemonic, wingEventModule, wingEventSeverity, wingEventMsg, wingEventSourceAddr,
				wingEventSourceHostname }
			STATUS current
			DESCRIPTION
				"Event cpu-load"
				::= { wingTrapsDiagPrefix 18}


		-- 1.3.6.1.4.1.1916.2.131.50.0.10.0.19
		wingTrapDiagRamUsage NOTIFICATION-TYPE
			OBJECTS { wingEventMnemonic, wingEventModule, wingEventSeverity, wingEventMsg, wingEventSourceAddr,
				wingEventSourceHostname }
			STATUS current
			DESCRIPTION
				"Event ram-usage"
				::= { wingTrapsDiagPrefix 19}


		-- 1.3.6.1.4.1.1916.2.131.50.0.10.0.20
		wingTrapDiagBufUsage NOTIFICATION-TYPE
			OBJECTS { wingEventMnemonic, wingEventModule, wingEventSeverity, wingEventMsg, wingEventSourceAddr,
				wingEventSourceHostname }
			STATUS current
			DESCRIPTION
				"Event buf-usage"
				::= { wingTrapsDiagPrefix 20}


		-- 1.3.6.1.4.1.1916.2.131.50.0.10.0.21
		wingTrapDiagHeadCacheUsage NOTIFICATION-TYPE
			OBJECTS { wingEventMnemonic, wingEventModule, wingEventSeverity, wingEventMsg, wingEventSourceAddr,
				wingEventSourceHostname }
			STATUS current
			DESCRIPTION
				"Event head-cache-usage"
				::= { wingTrapsDiagPrefix 21}


		-- 1.3.6.1.4.1.1916.2.131.50.0.10.0.22
		wingTrapDiagIpDestUsage NOTIFICATION-TYPE
			OBJECTS { wingEventMnemonic, wingEventModule, wingEventSeverity, wingEventMsg, wingEventSourceAddr,
				wingEventSourceHostname }
			STATUS current
			DESCRIPTION
				"Event ip-dest-usage"
				::= { wingTrapsDiagPrefix 22}


		-- 1.3.6.1.4.1.1916.2.131.50.0.10.0.23
		wingTrapDiagFreeRam NOTIFICATION-TYPE
			OBJECTS { wingEventMnemonic, wingEventModule, wingEventSeverity, wingEventMsg, wingEventSourceAddr,
				wingEventSourceHostname }
			STATUS current
			DESCRIPTION
				"Event free-ram"
				::= { wingTrapsDiagPrefix 23}


		-- 1.3.6.1.4.1.1916.2.131.50.0.10.0.24
		wingTrapDiagFreeFlashDisk NOTIFICATION-TYPE
			OBJECTS { wingEventMnemonic, wingEventModule, wingEventSeverity, wingEventMsg, wingEventSourceAddr,
				wingEventSourceHostname }
			STATUS current
			DESCRIPTION
				"Event free-flash-disk"
				::= { wingTrapsDiagPrefix 24}


		-- 1.3.6.1.4.1.1916.2.131.50.0.10.0.25
		wingTrapDiagFreeFlashInodes NOTIFICATION-TYPE
			OBJECTS { wingEventMnemonic, wingEventModule, wingEventSeverity, wingEventMsg, wingEventSourceAddr,
				wingEventSourceHostname }
			STATUS current
			DESCRIPTION
				"Event free-flash-inodes"
				::= { wingTrapsDiagPrefix 25}


		-- 1.3.6.1.4.1.1916.2.131.50.0.10.0.26
		wingTrapDiagFreeNvramDisk NOTIFICATION-TYPE
			OBJECTS { wingEventMnemonic, wingEventModule, wingEventSeverity, wingEventMsg, wingEventSourceAddr,
				wingEventSourceHostname }
			STATUS current
			DESCRIPTION
				"Event free-nvram-disk"
				::= { wingTrapsDiagPrefix 26}


		-- 1.3.6.1.4.1.1916.2.131.50.0.10.0.27
		wingTrapDiagFreeNvramInodes NOTIFICATION-TYPE
			OBJECTS { wingEventMnemonic, wingEventModule, wingEventSeverity, wingEventMsg, wingEventSourceAddr,
				wingEventSourceHostname }
			STATUS current
			DESCRIPTION
				"Event free-nvram-inodes"
				::= { wingTrapsDiagPrefix 27}


		-- 1.3.6.1.4.1.1916.2.131.50.0.10.0.28
		wingTrapDiagFreeRamDisk NOTIFICATION-TYPE
			OBJECTS { wingEventMnemonic, wingEventModule, wingEventSeverity, wingEventMsg, wingEventSourceAddr,
				wingEventSourceHostname }
			STATUS current
			DESCRIPTION
				"Event free-ram-disk"
				::= { wingTrapsDiagPrefix 28}


		-- 1.3.6.1.4.1.1916.2.131.50.0.10.0.29
		wingTrapDiagFreeRamInodes NOTIFICATION-TYPE
			OBJECTS { wingEventMnemonic, wingEventModule, wingEventSeverity, wingEventMsg, wingEventSourceAddr,
				wingEventSourceHostname }
			STATUS current
			DESCRIPTION
				"Event free-ram-inodes"
				::= { wingTrapsDiagPrefix 29}


		-- 1.3.6.1.4.1.1916.2.131.50.0.10.0.30
		wingTrapDiagFdCount NOTIFICATION-TYPE
			OBJECTS { wingEventMnemonic, wingEventModule, wingEventSeverity, wingEventMsg, wingEventSourceAddr,
				wingEventSourceHostname }
			STATUS current
			DESCRIPTION
				"Event fd-count"
				::= { wingTrapsDiagPrefix 30}


		-- 1.3.6.1.4.1.1916.2.131.50.0.10.0.31
		wingTrapDiagDiskUsage NOTIFICATION-TYPE
			OBJECTS { wingEventMnemonic, wingEventModule, wingEventSeverity, wingEventMsg, wingEventSourceAddr,
				wingEventSourceHostname }
			STATUS current
			DESCRIPTION
				"Event disk-usage"
				::= { wingTrapsDiagPrefix 31}


		-- 1.3.6.1.4.1.1916.2.131.50.0.10.0.32
		wingTrapDiagNewLedState NOTIFICATION-TYPE
			OBJECTS { wingEventMnemonic, wingEventModule, wingEventSeverity, wingEventMsg, wingEventSourceAddr,
				wingEventSourceHostname }
			STATUS current
			DESCRIPTION
				"Event new-led-state"
				::= { wingTrapsDiagPrefix 32}


		-- 1.3.6.1.4.1.1916.2.131.50.0.10.0.33
		wingTrapDiagLedIdentify NOTIFICATION-TYPE
			OBJECTS { wingEventMnemonic, wingEventModule, wingEventSeverity, wingEventMsg, wingEventSourceAddr,
				wingEventSourceHostname }
			STATUS current
			DESCRIPTION
				"Event led-identify"
				::= { wingTrapsDiagPrefix 33}


--802.11 management module
		--1.3.6.1.4.1.1916.2.131.50.0.11
		wingTrapsDot11 OBJECT IDENTIFIER ::= { wingNotifications 11 }


		--1.3.6.1.4.1.1916.2.131.50.0.11.0
		wingTrapsDot11Prefix OBJECT IDENTIFIER ::= { wingTrapsDot11 0 }


		-- 1.3.6.1.4.1.1916.2.131.50.0.11.0.1
		wingTrapDot11CountryCode NOTIFICATION-TYPE
			OBJECTS { wingEventMnemonic, wingEventModule, wingEventSeverity, wingEventMsg, wingEventSourceAddr,
				wingEventSourceHostname }
			STATUS current
			DESCRIPTION
				"Country of operation configured"
				::= { wingTrapsDot11Prefix 1}


		-- 1.3.6.1.4.1.1916.2.131.50.0.11.0.2
		wingTrapDot11CountryCodeError NOTIFICATION-TYPE
			OBJECTS { wingEventMnemonic, wingEventModule, wingEventSeverity, wingEventMsg, wingEventSourceAddr,
				wingEventSourceHostname }
			STATUS current
			DESCRIPTION
				"Error setting country of operation"
				::= { wingTrapsDot11Prefix 2}


		-- 1.3.6.1.4.1.1916.2.131.50.0.11.0.3
		wingTrapDot11ClientAssociated NOTIFICATION-TYPE
			OBJECTS { wingEventMnemonic, wingEventModule, wingEventSeverity, wingEventMsg, wingEventSourceAddr,
				wingEventSourceHostname }
			STATUS current
			DESCRIPTION
				"Client associated event"
				::= { wingTrapsDot11Prefix 3}


		-- 1.3.6.1.4.1.1916.2.131.50.0.11.0.4
		wingTrapDot11ClientDisassociated NOTIFICATION-TYPE
			OBJECTS { wingEventMnemonic, wingEventModule, wingEventSeverity, wingEventMsg, wingEventSourceAddr,
				wingEventSourceHostname }
			STATUS current
			DESCRIPTION
				"Client disassociated"
				::= { wingTrapsDot11Prefix 4}


		-- 1.3.6.1.4.1.1916.2.131.50.0.11.0.5
		wingTrapDot11ClientDeniedAssoc NOTIFICATION-TYPE
			OBJECTS { wingEventMnemonic, wingEventModule, wingEventSeverity, wingEventMsg, wingEventSourceAddr,
				wingEventSourceHostname }
			STATUS current
			DESCRIPTION
				"Client denied association"
				::= { wingTrapsDot11Prefix 5}


		-- 1.3.6.1.4.1.1916.2.131.50.0.11.0.6
		wingTrapDot11WpaWpa2Success NOTIFICATION-TYPE
			OBJECTS { wingEventMnemonic, wingEventModule, wingEventSeverity, wingEventMsg, wingEventSourceAddr,
				wingEventSourceHostname }
			STATUS current
			DESCRIPTION
				"Client completed WPA/WPA2 handshake"
				::= { wingTrapsDot11Prefix 6}


		-- 1.3.6.1.4.1.1916.2.131.50.0.11.0.7
		wingTrapDot11WpaWpa2Failed NOTIFICATION-TYPE
			OBJECTS { wingEventMnemonic, wingEventModule, wingEventSeverity, wingEventMsg, wingEventSourceAddr,
				wingEventSourceHostname }
			STATUS current
			DESCRIPTION
				"Client failed WPA/WPA2 handshake"
				::= { wingTrapsDot11Prefix 7}


		-- 1.3.6.1.4.1.1916.2.131.50.0.11.0.8
		wingTrapDot11WpaWpa2KeyRotn NOTIFICATION-TYPE
			OBJECTS { wingEventMnemonic, wingEventModule, wingEventSeverity, wingEventMsg, wingEventSourceAddr,
				wingEventSourceHostname }
			STATUS current
			DESCRIPTION
				"Rotating WPA/WPA2 group keys on wlan"
				::= { wingTrapsDot11Prefix 8}


		-- 1.3.6.1.4.1.1916.2.131.50.0.11.0.9
		wingTrapDot11TkipMicFailReport NOTIFICATION-TYPE
			OBJECTS { wingEventMnemonic, wingEventModule, wingEventSeverity, wingEventMsg, wingEventSourceAddr,
				wingEventSourceHostname }
			STATUS current
			DESCRIPTION
				"TKIP MIC failure report"
				::= { wingTrapsDot11Prefix 9}


		-- 1.3.6.1.4.1.1916.2.131.50.0.11.0.10
		wingTrapDot11TkipMicFailure NOTIFICATION-TYPE
			OBJECTS { wingEventMnemonic, wingEventModule, wingEventSeverity, wingEventMsg, wingEventSourceAddr,
				wingEventSourceHostname }
			STATUS current
			DESCRIPTION
				"TKIP MIC check failed"
				::= { wingTrapsDot11Prefix 10}


		-- 1.3.6.1.4.1.1916.2.131.50.0.11.0.11
		wingTrapDot11TkipCntrmeasStart NOTIFICATION-TYPE
			OBJECTS { wingEventMnemonic, wingEventModule, wingEventSeverity, wingEventMsg, wingEventSourceAddr,
				wingEventSourceHostname }
			STATUS current
			DESCRIPTION
				"TKIP countermeasures initiated"
				::= { wingTrapsDot11Prefix 11}


		-- 1.3.6.1.4.1.1916.2.131.50.0.11.0.12
		wingTrapDot11TkipCntrmeasEnd NOTIFICATION-TYPE
			OBJECTS { wingEventMnemonic, wingEventModule, wingEventSeverity, wingEventMsg, wingEventSourceAddr,
				wingEventSourceHostname }
			STATUS current
			DESCRIPTION
				"TKIP countermeasures ended"
				::= { wingTrapsDot11Prefix 12}


		-- 1.3.6.1.4.1.1916.2.131.50.0.11.0.13
		wingTrapDot11EapSuccess NOTIFICATION-TYPE
			OBJECTS { wingEventMnemonic, wingEventModule, wingEventSeverity, wingEventMsg, wingEventSourceAddr,
				wingEventSourceHostname }
			STATUS current
			DESCRIPTION
				"EAP authentication success"
				::= { wingTrapsDot11Prefix 13}


		-- 1.3.6.1.4.1.1916.2.131.50.0.11.0.14
		wingTrapDot11EapFailed NOTIFICATION-TYPE
			OBJECTS { wingEventMnemonic, wingEventModule, wingEventSeverity, wingEventMsg, wingEventSourceAddr,
				wingEventSourceHostname }
			STATUS current
			DESCRIPTION
				"EAP authentication failure"
				::= { wingTrapsDot11Prefix 14}


		-- 1.3.6.1.4.1.1916.2.131.50.0.11.0.15
		wingTrapDot11EapClientTimeout NOTIFICATION-TYPE
			OBJECTS { wingEventMnemonic, wingEventModule, wingEventSeverity, wingEventMsg, wingEventSourceAddr,
				wingEventSourceHostname }
			STATUS current
			DESCRIPTION
				"EAP authentication timed out"
				::= { wingTrapsDot11Prefix 15}


		-- 1.3.6.1.4.1.1916.2.131.50.0.11.0.16
		wingTrapDot11EapServerTimeout NOTIFICATION-TYPE
			OBJECTS { wingEventMnemonic, wingEventModule, wingEventSeverity, wingEventMsg, wingEventSourceAddr,
				wingEventSourceHostname }
			STATUS current
			DESCRIPTION
				"Radius server timed out"
				::= { wingTrapsDot11Prefix 16}


		-- 1.3.6.1.4.1.1916.2.131.50.0.11.0.17
		wingTrapDot11EapCachedKeys NOTIFICATION-TYPE
			OBJECTS { wingEventMnemonic, wingEventModule, wingEventSeverity, wingEventMsg, wingEventSourceAddr,
				wingEventSourceHostname }
			STATUS current
			DESCRIPTION
				"Key cache used for authentication"
				::= { wingTrapsDot11Prefix 17}


		-- 1.3.6.1.4.1.1916.2.131.50.0.11.0.18
		wingTrapDot11EapOppCachedKeys NOTIFICATION-TYPE
			OBJECTS { wingEventMnemonic, wingEventModule, wingEventSeverity, wingEventMsg, wingEventSourceAddr,
				wingEventSourceHostname }
			STATUS current
			DESCRIPTION
				"Opportunistic key cached used for authentication"
				::= { wingTrapsDot11Prefix 18}


		-- 1.3.6.1.4.1.1916.2.131.50.0.11.0.19
		wingTrapDot11EapPreauthSuccess NOTIFICATION-TYPE
			OBJECTS { wingEventMnemonic, wingEventModule, wingEventSeverity, wingEventMsg, wingEventSourceAddr,
				wingEventSourceHostname }
			STATUS current
			DESCRIPTION
				"EAP pre-authentication success"
				::= { wingTrapsDot11Prefix 19}


		-- 1.3.6.1.4.1.1916.2.131.50.0.11.0.20
		wingTrapDot11EapPreauthFailed NOTIFICATION-TYPE
			OBJECTS { wingEventMnemonic, wingEventModule, wingEventSeverity, wingEventMsg, wingEventSourceAddr,
				wingEventSourceHostname }
			STATUS current
			DESCRIPTION
				"EAP pre-authentication failed"
				::= { wingTrapsDot11Prefix 20}


		-- 1.3.6.1.4.1.1916.2.131.50.0.11.0.21
		wingTrapDot11EapPreauthClientTimeout NOTIFICATION-TYPE
			OBJECTS { wingEventMnemonic, wingEventModule, wingEventSeverity, wingEventMsg, wingEventSourceAddr,
				wingEventSourceHostname }
			STATUS current
			DESCRIPTION
				"EAP pre-authentication client timeout"
				::= { wingTrapsDot11Prefix 21}


		-- 1.3.6.1.4.1.1916.2.131.50.0.11.0.22
		wingTrapDot11EapPreauthServerTimeout NOTIFICATION-TYPE
			OBJECTS { wingEventMnemonic, wingEventModule, wingEventSeverity, wingEventMsg, wingEventSourceAddr,
				wingEventSourceHostname }
			STATUS current
			DESCRIPTION
				"EAP pre-authentication server timeout"
				::= { wingTrapsDot11Prefix 22}


		-- 1.3.6.1.4.1.1916.2.131.50.0.11.0.23
		wingTrapDot11KerberosWlanSuccess NOTIFICATION-TYPE
			OBJECTS { wingEventMnemonic, wingEventModule, wingEventSeverity, wingEventMsg, wingEventSourceAddr,
				wingEventSourceHostname }
			STATUS current
			DESCRIPTION
				"Kerberos authentication success"
				::= { wingTrapsDot11Prefix 23}


		-- 1.3.6.1.4.1.1916.2.131.50.0.11.0.24
		wingTrapDot11KerberosWlanTimeout NOTIFICATION-TYPE
			OBJECTS { wingEventMnemonic, wingEventModule, wingEventSeverity, wingEventMsg, wingEventSourceAddr,
				wingEventSourceHostname }
			STATUS current
			DESCRIPTION
				"Kerberos authentication timed out"
				::= { wingTrapsDot11Prefix 24}


		-- 1.3.6.1.4.1.1916.2.131.50.0.11.0.25
		wingTrapDot11KerberosWlanFailed NOTIFICATION-TYPE
			OBJECTS { wingEventMnemonic, wingEventModule, wingEventSeverity, wingEventMsg, wingEventSourceAddr,
				wingEventSourceHostname }
			STATUS current
			DESCRIPTION
				"Wlan kerberos authentication failed"
				::= { wingTrapsDot11Prefix 25}


		-- 1.3.6.1.4.1.1916.2.131.50.0.11.0.26
		wingTrapDot11KerberosClientSuccess NOTIFICATION-TYPE
			OBJECTS { wingEventMnemonic, wingEventModule, wingEventSeverity, wingEventMsg, wingEventSourceAddr,
				wingEventSourceHostname }
			STATUS current
			DESCRIPTION
				"Client kerberos authentication success"
				::= { wingTrapsDot11Prefix 26}


		-- 1.3.6.1.4.1.1916.2.131.50.0.11.0.27
		wingTrapDot11KerberosClientFailed NOTIFICATION-TYPE
			OBJECTS { wingEventMnemonic, wingEventModule, wingEventSeverity, wingEventMsg, wingEventSourceAddr,
				wingEventSourceHostname }
			STATUS current
			DESCRIPTION
				"Client kerberos authentication failed"
				::= { wingTrapsDot11Prefix 27}


		-- 1.3.6.1.4.1.1916.2.131.50.0.11.0.28
		wingTrapDot11VoiceCallFailed NOTIFICATION-TYPE
			OBJECTS { wingEventMnemonic, wingEventModule, wingEventSeverity, wingEventMsg, wingEventSourceAddr,
				wingEventSourceHostname }
			STATUS current
			DESCRIPTION
				"Voice call failed"
				::= { wingTrapsDot11Prefix 28}


		-- 1.3.6.1.4.1.1916.2.131.50.0.11.0.29
		wingTrapDot11VoiceCallEstablished NOTIFICATION-TYPE
			OBJECTS { wingEventMnemonic, wingEventModule, wingEventSeverity, wingEventMsg, wingEventSourceAddr,
				wingEventSourceHostname }
			STATUS current
			DESCRIPTION
				"Voice call established"
				::= { wingTrapsDot11Prefix 29}


		-- 1.3.6.1.4.1.1916.2.131.50.0.11.0.30
		wingTrapDot11VoiceCallCompleted NOTIFICATION-TYPE
			OBJECTS { wingEventMnemonic, wingEventModule, wingEventSeverity, wingEventMsg, wingEventSourceAddr,
				wingEventSourceHostname }
			STATUS current
			DESCRIPTION
				"Voice call completed"
				::= { wingTrapsDot11Prefix 30}


		-- 1.3.6.1.4.1.1916.2.131.50.0.11.0.31
		wingTrapDot11UnsanctionedApActive NOTIFICATION-TYPE
			OBJECTS { wingEventMnemonic, wingEventModule, wingEventSeverity, wingEventMsg, wingEventSourceAddr,
				wingEventSourceHostname }
			STATUS current
			DESCRIPTION
				"Unsanctioned AP active"
				::= { wingTrapsDot11Prefix 31}


		-- 1.3.6.1.4.1.1916.2.131.50.0.11.0.32
		wingTrapDot11UnsanctionedApInactive NOTIFICATION-TYPE
			OBJECTS { wingEventMnemonic, wingEventModule, wingEventSeverity, wingEventMsg, wingEventSourceAddr,
				wingEventSourceHostname }
			STATUS current
			DESCRIPTION
				"Unsanctioned AP inactive"
				::= { wingTrapsDot11Prefix 32}


		-- 1.3.6.1.4.1.1916.2.131.50.0.11.0.33
		wingTrapDot11UnsanctionedApStatusChange NOTIFICATION-TYPE
			OBJECTS { wingEventMnemonic, wingEventModule, wingEventSeverity, wingEventMsg, wingEventSourceAddr,
				wingEventSourceHostname }
			STATUS current
			DESCRIPTION
				"Unsanctioned AP changed state"
				::= { wingTrapsDot11Prefix 33}


		-- 1.3.6.1.4.1.1916.2.131.50.0.11.0.34
		wingTrapDot11NeighborDeniedAssoc NOTIFICATION-TYPE
			OBJECTS { wingEventMnemonic, wingEventModule, wingEventSeverity, wingEventMsg, wingEventSourceAddr,
				wingEventSourceHostname }
			STATUS current
			DESCRIPTION
				"Neighbor denied association"
				::= { wingTrapsDot11Prefix 34}


		-- 1.3.6.1.4.1.1916.2.131.50.0.11.0.35
		wingTrapDot11WlanTimeAccessDisable NOTIFICATION-TYPE
			OBJECTS { wingEventMnemonic, wingEventModule, wingEventSeverity, wingEventMsg, wingEventSourceAddr,
				wingEventSourceHostname }
			STATUS current
			DESCRIPTION
				"Wlan disabled by time-based-access"
				::= { wingTrapsDot11Prefix 35}


		-- 1.3.6.1.4.1.1916.2.131.50.0.11.0.36
		wingTrapDot11WlanTimeAccessEnable NOTIFICATION-TYPE
			OBJECTS { wingEventMnemonic, wingEventModule, wingEventSeverity, wingEventMsg, wingEventSourceAddr,
				wingEventSourceHostname }
			STATUS current
			DESCRIPTION
				"Wlan re-enabled by time-based-access"
				::= { wingTrapsDot11Prefix 36}


		-- 1.3.6.1.4.1.1916.2.131.50.0.11.0.37
		wingTrapDot11MoveOperationSuccess NOTIFICATION-TYPE
			OBJECTS { wingEventMnemonic, wingEventModule, wingEventSeverity, wingEventMsg, wingEventSourceAddr,
				wingEventSourceHostname }
			STATUS current
			DESCRIPTION
				"Move operation success"
				::= { wingTrapsDot11Prefix 37}


		-- 1.3.6.1.4.1.1916.2.131.50.0.11.0.38
		wingTrapDot11FtRoamSuccess NOTIFICATION-TYPE
			OBJECTS { wingEventMnemonic, wingEventModule, wingEventSeverity, wingEventMsg, wingEventSourceAddr,
				wingEventSourceHostname }
			STATUS current
			DESCRIPTION
				"Client fast bss transition"
				::= { wingTrapsDot11Prefix 38}


--Firmware update module
		--1.3.6.1.4.1.1916.2.131.50.0.13
		wingTrapsFwu OBJECT IDENTIFIER ::= { wingNotifications 13 }


		--1.3.6.1.4.1.1916.2.131.50.0.13.0
		wingTrapsFwuPrefix OBJECT IDENTIFIER ::= { wingTrapsFwu 0 }


		-- 1.3.6.1.4.1.1916.2.131.50.0.13.0.1
		wingTrapFwuFwudone NOTIFICATION-TYPE
			OBJECTS { wingEventMnemonic, wingEventModule, wingEventSeverity, wingEventMsg, wingEventSourceAddr,
				wingEventSourceHostname }
			STATUS current
			DESCRIPTION
				"Update successfully completed"
				::= { wingTrapsFwuPrefix 1}


		-- 1.3.6.1.4.1.1916.2.131.50.0.13.0.2
		wingTrapFwuFwuaborted NOTIFICATION-TYPE
			OBJECTS { wingEventMnemonic, wingEventModule, wingEventSeverity, wingEventMsg, wingEventSourceAddr,
				wingEventSourceHostname }
			STATUS current
			DESCRIPTION
				"Update aborted"
				::= { wingTrapsFwuPrefix 2}


		-- 1.3.6.1.4.1.1916.2.131.50.0.13.0.3
		wingTrapFwuFwunoneed NOTIFICATION-TYPE
			OBJECTS { wingEventMnemonic, wingEventModule, wingEventSeverity, wingEventMsg, wingEventSourceAddr,
				wingEventSourceHostname }
			STATUS current
			DESCRIPTION
				"Update not required, running and update version are the same"
				::= { wingTrapsFwuPrefix 3}


		-- 1.3.6.1.4.1.1916.2.131.50.0.13.0.4
		wingTrapFwuFwusyserr NOTIFICATION-TYPE
			OBJECTS { wingEventMnemonic, wingEventModule, wingEventSeverity, wingEventMsg, wingEventSourceAddr,
				wingEventSourceHostname }
			STATUS current
			DESCRIPTION
				"Update unsuccessful, system cmd failed"
				::= { wingTrapsFwuPrefix 4}


		-- 1.3.6.1.4.1.1916.2.131.50.0.13.0.5
		wingTrapFwuFwubadconfig NOTIFICATION-TYPE
			OBJECTS { wingEventMnemonic, wingEventModule, wingEventSeverity, wingEventMsg, wingEventSourceAddr,
				wingEventSourceHostname }
			STATUS current
			DESCRIPTION
				"Update unsuccessful, unable to read config file"
				::= { wingTrapsFwuPrefix 5}


		-- 1.3.6.1.4.1.1916.2.131.50.0.13.0.6
		wingTrapFwuFwuserverundef NOTIFICATION-TYPE
			OBJECTS { wingEventMnemonic, wingEventModule, wingEventSeverity, wingEventMsg, wingEventSourceAddr,
				wingEventSourceHostname }
			STATUS current
			DESCRIPTION
				"Update unsuccessful, server undefined"
				::= { wingTrapsFwuPrefix 6}


		-- 1.3.6.1.4.1.1916.2.131.50.0.13.0.7
		wingTrapFwuFwufileundef NOTIFICATION-TYPE
			OBJECTS { wingEventMnemonic, wingEventModule, wingEventSeverity, wingEventMsg, wingEventSourceAddr,
				wingEventSourceHostname }
			STATUS current
			DESCRIPTION
				"Update unsuccessful, update file undefined"
				::= { wingTrapsFwuPrefix 7}


		-- 1.3.6.1.4.1.1916.2.131.50.0.13.0.8
		wingTrapFwuFwuserverunreachable NOTIFICATION-TYPE
			OBJECTS { wingEventMnemonic, wingEventModule, wingEventSeverity, wingEventMsg, wingEventSourceAddr,
				wingEventSourceHostname }
			STATUS current
			DESCRIPTION
				"Update unsuccessful, server unreachable"
				::= { wingTrapsFwuPrefix 8}


		-- 1.3.6.1.4.1.1916.2.131.50.0.13.0.9
		wingTrapFwuFwucouldntgetfile NOTIFICATION-TYPE
			OBJECTS { wingEventMnemonic, wingEventModule, wingEventSeverity, wingEventMsg, wingEventSourceAddr,
				wingEventSourceHostname }
			STATUS current
			DESCRIPTION
				"Update unsuccessful, could not get file"
				::= { wingTrapsFwuPrefix 9}


		-- 1.3.6.1.4.1.1916.2.131.50.0.13.0.10
		wingTrapFwuFwuvermismatch NOTIFICATION-TYPE
			OBJECTS { wingEventMnemonic, wingEventModule, wingEventSeverity, wingEventMsg, wingEventSourceAddr,
				wingEventSourceHostname }
			STATUS current
			DESCRIPTION
				"Update unsuccessful, version mismatch"
				::= { wingTrapsFwuPrefix 10}


		-- 1.3.6.1.4.1.1916.2.131.50.0.13.0.11
		wingTrapFwuFwuprodmismatch NOTIFICATION-TYPE
			OBJECTS { wingEventMnemonic, wingEventModule, wingEventSeverity, wingEventMsg, wingEventSourceAddr,
				wingEventSourceHostname }
			STATUS current
			DESCRIPTION
				"Update unsuccessful, product mismatch"
				::= { wingTrapsFwuPrefix 11}


		-- 1.3.6.1.4.1.1916.2.131.50.0.13.0.12
		wingTrapFwuFwucorruptedfile NOTIFICATION-TYPE
			OBJECTS { wingEventMnemonic, wingEventModule, wingEventSeverity, wingEventMsg, wingEventSourceAddr,
				wingEventSourceHostname }
			STATUS current
			DESCRIPTION
				"Update unsuccessful, corrupted file"
				::= { wingTrapsFwuPrefix 12}


		-- 1.3.6.1.4.1.1916.2.131.50.0.13.0.13
		wingTrapFwuFwusignmismatch NOTIFICATION-TYPE
			OBJECTS { wingEventMnemonic, wingEventModule, wingEventSeverity, wingEventMsg, wingEventSourceAddr,
				wingEventSourceHostname }
			STATUS current
			DESCRIPTION
				"Update unsuccessful, signature mismatch"
				::= { wingTrapsFwuPrefix 13}


		-- 1.3.6.1.4.1.1916.2.131.50.0.13.0.14
		wingTrapFwuFwuunsupportedhw NOTIFICATION-TYPE
			OBJECTS { wingEventMnemonic, wingEventModule, wingEventSeverity, wingEventMsg, wingEventSourceAddr,
				wingEventSourceHostname }
			STATUS current
			DESCRIPTION
				"Update unsuccessful, unsupported hardware"
				::= { wingTrapsFwuPrefix 14}


--License module
		--1.3.6.1.4.1.1916.2.131.50.0.14
		wingTrapsLicmgr OBJECT IDENTIFIER ::= { wingNotifications 14 }


		--1.3.6.1.4.1.1916.2.131.50.0.14.0
		wingTrapsLicmgrPrefix OBJECT IDENTIFIER ::= { wingTrapsLicmgr 0 }


		-- 1.3.6.1.4.1.1916.2.131.50.0.14.0.1
		wingTrapLicmgrLicInstalled NOTIFICATION-TYPE
			OBJECTS { wingEventMnemonic, wingEventModule, wingEventSeverity, wingEventMsg, wingEventSourceAddr,
				wingEventSourceHostname }
			STATUS current
			DESCRIPTION
				"License Installation "
				::= { wingTrapsLicmgrPrefix 1}


		-- 1.3.6.1.4.1.1916.2.131.50.0.14.0.2
		wingTrapLicmgrLicInstallDefault NOTIFICATION-TYPE
			OBJECTS { wingEventMnemonic, wingEventModule, wingEventSeverity, wingEventMsg, wingEventSourceAddr,
				wingEventSourceHostname }
			STATUS current
			DESCRIPTION
				"Default License Installation "
				::= { wingTrapsLicmgrPrefix 2}


		-- 1.3.6.1.4.1.1916.2.131.50.0.14.0.3
		wingTrapLicmgrLicInstallCount NOTIFICATION-TYPE
			OBJECTS { wingEventMnemonic, wingEventModule, wingEventSeverity, wingEventMsg, wingEventSourceAddr,
				wingEventSourceHostname }
			STATUS current
			DESCRIPTION
				"License Count"
				::= { wingTrapsLicmgrPrefix 3}


		-- 1.3.6.1.4.1.1916.2.131.50.0.14.0.4
		wingTrapLicmgrLicRemoved NOTIFICATION-TYPE
			OBJECTS { wingEventMnemonic, wingEventModule, wingEventSeverity, wingEventMsg, wingEventSourceAddr,
				wingEventSourceHostname }
			STATUS current
			DESCRIPTION
				"License Removed"
				::= { wingTrapsLicmgrPrefix 4}


		-- 1.3.6.1.4.1.1916.2.131.50.0.14.0.5
		wingTrapLicmgrLicInvalid NOTIFICATION-TYPE
			OBJECTS { wingEventMnemonic, wingEventModule, wingEventSeverity, wingEventMsg, wingEventSourceAddr,
				wingEventSourceHostname }
			STATUS current
			DESCRIPTION
				"License Installation Failed"
				::= { wingTrapsLicmgrPrefix 5}


--Mesh module
		--1.3.6.1.4.1.1916.2.131.50.0.15
		wingTrapsMesh OBJECT IDENTIFIER ::= { wingNotifications 15 }


		--1.3.6.1.4.1.1916.2.131.50.0.15.0
		wingTrapsMeshPrefix OBJECT IDENTIFIER ::= { wingTrapsMesh 0 }


		-- 1.3.6.1.4.1.1916.2.131.50.0.15.0.1
		wingTrapMeshMeshLinkUp NOTIFICATION-TYPE
			OBJECTS { wingEventMnemonic, wingEventModule, wingEventSeverity, wingEventMsg, wingEventSourceAddr,
				wingEventSourceHostname }
			STATUS current
			DESCRIPTION
				"Mesh link up"
				::= { wingTrapsMeshPrefix 1}


		-- 1.3.6.1.4.1.1916.2.131.50.0.15.0.2
		wingTrapMeshMeshLinkDown NOTIFICATION-TYPE
			OBJECTS { wingEventMnemonic, wingEventModule, wingEventSeverity, wingEventMsg, wingEventSourceAddr,
				wingEventSourceHostname }
			STATUS current
			DESCRIPTION
				"Mesh link down"
				::= { wingTrapsMeshPrefix 2}


		-- 1.3.6.1.4.1.1916.2.131.50.0.15.0.3
		wingTrapMeshMeshpointUp NOTIFICATION-TYPE
			OBJECTS { wingEventMnemonic, wingEventModule, wingEventSeverity, wingEventMsg, wingEventSourceAddr,
				wingEventSourceHostname }
			STATUS current
			DESCRIPTION
				"Event meshpoint-up"
				::= { wingTrapsMeshPrefix 3}


		-- 1.3.6.1.4.1.1916.2.131.50.0.15.0.4
		wingTrapMeshMeshpointDown NOTIFICATION-TYPE
			OBJECTS { wingEventMnemonic, wingEventModule, wingEventSeverity, wingEventMsg, wingEventSourceAddr,
				wingEventSourceHostname }
			STATUS current
			DESCRIPTION
				"Event meshpoint-down"
				::= { wingTrapsMeshPrefix 4}


		-- 1.3.6.1.4.1.1916.2.131.50.0.15.0.5
		wingTrapMeshMeshpointLoopPreventOn NOTIFICATION-TYPE
			OBJECTS { wingEventMnemonic, wingEventModule, wingEventSeverity, wingEventMsg, wingEventSourceAddr,
				wingEventSourceHostname }
			STATUS current
			DESCRIPTION
				"Event meshpoint-loop-prevent-on"
				::= { wingTrapsMeshPrefix 5}


		-- 1.3.6.1.4.1.1916.2.131.50.0.15.0.6
		wingTrapMeshMeshpointLoopPreventOff NOTIFICATION-TYPE
			OBJECTS { wingEventMnemonic, wingEventModule, wingEventSeverity, wingEventMsg, wingEventSourceAddr,
				wingEventSourceHostname }
			STATUS current
			DESCRIPTION
				"Event meshpoint-loop-prevent-off"
				::= { wingTrapsMeshPrefix 6}


		-- 1.3.6.1.4.1.1916.2.131.50.0.15.0.7
		wingTrapMeshMeshpointRootChange NOTIFICATION-TYPE
			OBJECTS { wingEventMnemonic, wingEventModule, wingEventSeverity, wingEventMsg, wingEventSourceAddr,
				wingEventSourceHostname }
			STATUS current
			DESCRIPTION
				"Event meshpoint-root-change"
				::= { wingTrapsMeshPrefix 7}


		-- 1.3.6.1.4.1.1916.2.131.50.0.15.0.8
		wingTrapMeshMeshpointPathChange NOTIFICATION-TYPE
			OBJECTS { wingEventMnemonic, wingEventModule, wingEventSeverity, wingEventMsg, wingEventSourceAddr,
				wingEventSourceHostname }
			STATUS current
			DESCRIPTION
				"Event meshpoint-path-change"
				::= { wingTrapsMeshPrefix 8}


--Network Services Module
		--1.3.6.1.4.1.1916.2.131.50.0.16
		wingTrapsNsm OBJECT IDENTIFIER ::= { wingNotifications 16 }


		--1.3.6.1.4.1.1916.2.131.50.0.16.0
		wingTrapsNsmPrefix OBJECT IDENTIFIER ::= { wingTrapsNsm 0 }


		-- 1.3.6.1.4.1.1916.2.131.50.0.16.0.1
		wingTrapNsmIfup NOTIFICATION-TYPE
			OBJECTS { wingEventMnemonic, wingEventModule, wingEventSeverity, wingEventMsg, wingEventSourceAddr,
				wingEventSourceHostname }
			STATUS current
			DESCRIPTION
				"Interface up"
				::= { wingTrapsNsmPrefix 1}


		-- 1.3.6.1.4.1.1916.2.131.50.0.16.0.2
		wingTrapNsmIfdown NOTIFICATION-TYPE
			OBJECTS { wingEventMnemonic, wingEventModule, wingEventSeverity, wingEventMsg, wingEventSourceAddr,
				wingEventSourceHostname }
			STATUS current
			DESCRIPTION
				"Interface down"
				::= { wingTrapsNsmPrefix 2}


		-- 1.3.6.1.4.1.1916.2.131.50.0.16.0.3
		wingTrapNsmDhcpip NOTIFICATION-TYPE
			OBJECTS { wingEventMnemonic, wingEventModule, wingEventSeverity, wingEventMsg, wingEventSourceAddr,
				wingEventSourceHostname }
			STATUS current
			DESCRIPTION
				"Interface assigned DHCP IP address"
				::= { wingTrapsNsmPrefix 3}


		-- 1.3.6.1.4.1.1916.2.131.50.0.16.0.4
		wingTrapNsmDhcpdefrt NOTIFICATION-TYPE
			OBJECTS { wingEventMnemonic, wingEventModule, wingEventSeverity, wingEventMsg, wingEventSourceAddr,
				wingEventSourceHostname }
			STATUS current
			DESCRIPTION
				"Default route learnt via DHCP"
				::= { wingTrapsNsmPrefix 4}


		-- 1.3.6.1.4.1.1916.2.131.50.0.16.0.5
		wingTrapNsmDhcpipchg NOTIFICATION-TYPE
			OBJECTS { wingEventMnemonic, wingEventModule, wingEventSeverity, wingEventMsg, wingEventSourceAddr,
				wingEventSourceHostname }
			STATUS current
			DESCRIPTION
				"DHCP Interface IP changed"
				::= { wingTrapsNsmPrefix 5}


		-- 1.3.6.1.4.1.1916.2.131.50.0.16.0.6
		wingTrapNsmDhcpnodefrt NOTIFICATION-TYPE
			OBJECTS { wingEventMnemonic, wingEventModule, wingEventSeverity, wingEventMsg, wingEventSourceAddr,
				wingEventSourceHostname }
			STATUS current
			DESCRIPTION
				"Interface no default route"
				::= { wingTrapsNsmPrefix 6}


		-- 1.3.6.1.4.1.1916.2.131.50.0.16.0.7
		wingTrapNsmIfipcfg NOTIFICATION-TYPE
			OBJECTS { wingEventMnemonic, wingEventModule, wingEventSeverity, wingEventMsg, wingEventSourceAddr,
				wingEventSourceHostname }
			STATUS current
			DESCRIPTION
				"Interface IP address "
				::= { wingTrapsNsmPrefix 7}


		-- 1.3.6.1.4.1.1916.2.131.50.0.16.0.8
		wingTrapNsmDhcpcErr NOTIFICATION-TYPE
			OBJECTS { wingEventMnemonic, wingEventModule, wingEventSeverity, wingEventMsg, wingEventSourceAddr,
				wingEventSourceHostname }
			STATUS current
			DESCRIPTION
				"DHCP server-client config conflict"
				::= { wingTrapsNsmPrefix 8}


		-- 1.3.6.1.4.1.1916.2.131.50.0.16.0.9
		wingTrapNsmDhcpipnoadd NOTIFICATION-TYPE
			OBJECTS { wingEventMnemonic, wingEventModule, wingEventSeverity, wingEventMsg, wingEventSourceAddr,
				wingEventSourceHostname }
			STATUS current
			DESCRIPTION
				"DHCP IP overlaps static IP address"
				::= { wingTrapsNsmPrefix 9}


		-- 1.3.6.1.4.1.1916.2.131.50.0.16.0.10
		wingTrapNsmDhcplsexp NOTIFICATION-TYPE
			OBJECTS { wingEventMnemonic, wingEventModule, wingEventSeverity, wingEventMsg, wingEventSourceAddr,
				wingEventSourceHostname }
			STATUS current
			DESCRIPTION
				"Interace DHCP lease expired"
				::= { wingTrapsNsmPrefix 10}


		-- 1.3.6.1.4.1.1916.2.131.50.0.16.0.11
		wingTrapNsmDhcpnak NOTIFICATION-TYPE
			OBJECTS { wingEventMnemonic, wingEventModule, wingEventSeverity, wingEventMsg, wingEventSourceAddr,
				wingEventSourceHostname }
			STATUS current
			DESCRIPTION
				"DHCP Server returned DHCP NAK response"
				::= { wingTrapsNsmPrefix 11}


		-- 1.3.6.1.4.1.1916.2.131.50.0.16.0.12
		wingTrapNsmNsmNtp NOTIFICATION-TYPE
			OBJECTS { wingEventMnemonic, wingEventModule, wingEventSeverity, wingEventMsg, wingEventSourceAddr,
				wingEventSourceHostname }
			STATUS current
			DESCRIPTION
				"Translate host name"
				::= { wingTrapsNsmPrefix 12}


		-- 1.3.6.1.4.1.1916.2.131.50.0.16.0.13
		wingTrapNsmIfFailover NOTIFICATION-TYPE
			OBJECTS { wingEventMnemonic, wingEventModule, wingEventSeverity, wingEventMsg, wingEventSourceAddr,
				wingEventSourceHostname }
			STATUS current
			DESCRIPTION
				"Interface failover"
				::= { wingTrapsNsmPrefix 13}


		-- 1.3.6.1.4.1.1916.2.131.50.0.16.0.14
		wingTrapNsmIfFailback NOTIFICATION-TYPE
			OBJECTS { wingEventMnemonic, wingEventModule, wingEventSeverity, wingEventMsg, wingEventSourceAddr,
				wingEventSourceHostname }
			STATUS current
			DESCRIPTION
				"Interface failback"
				::= { wingTrapsNsmPrefix 14}


--Process-monitor module
		--1.3.6.1.4.1.1916.2.131.50.0.17
		wingTrapsPm OBJECT IDENTIFIER ::= { wingNotifications 17 }


		--1.3.6.1.4.1.1916.2.131.50.0.17.0
		wingTrapsPmPrefix OBJECT IDENTIFIER ::= { wingTrapsPm 0 }


		-- 1.3.6.1.4.1.1916.2.131.50.0.17.0.1
		wingTrapPmProcstart NOTIFICATION-TYPE
			OBJECTS { wingEventMnemonic, wingEventModule, wingEventSeverity, wingEventMsg, wingEventSourceAddr,
				wingEventSourceHostname }
			STATUS current
			DESCRIPTION
				"Process started"
				::= { wingTrapsPmPrefix 1}


		-- 1.3.6.1.4.1.1916.2.131.50.0.17.0.2
		wingTrapPmProcrstrt NOTIFICATION-TYPE
			OBJECTS { wingEventMnemonic, wingEventModule, wingEventSeverity, wingEventMsg, wingEventSourceAddr,
				wingEventSourceHostname }
			STATUS current
			DESCRIPTION
				"Process restarted"
				::= { wingTrapsPmPrefix 2}


		-- 1.3.6.1.4.1.1916.2.131.50.0.17.0.3
		wingTrapPmProcmaxrstrt NOTIFICATION-TYPE
			OBJECTS { wingEventMnemonic, wingEventModule, wingEventSeverity, wingEventMsg, wingEventSourceAddr,
				wingEventSourceHostname }
			STATUS current
			DESCRIPTION
				"Process reached max number of restarts"
				::= { wingTrapsPmPrefix 3}


		-- 1.3.6.1.4.1.1916.2.131.50.0.17.0.4
		wingTrapPmProcsysrstrt NOTIFICATION-TYPE
			OBJECTS { wingEventMnemonic, wingEventModule, wingEventSeverity, wingEventMsg, wingEventSourceAddr,
				wingEventSourceHostname }
			STATUS current
			DESCRIPTION
				"Process reached max restarts. Rebooting system."
				::= { wingTrapsPmPrefix 4}


		-- 1.3.6.1.4.1.1916.2.131.50.0.17.0.5
		wingTrapPmProcstop NOTIFICATION-TYPE
			OBJECTS { wingEventMnemonic, wingEventModule, wingEventSeverity, wingEventMsg, wingEventSourceAddr,
				wingEventSourceHostname }
			STATUS current
			DESCRIPTION
				"Process has been stopped"
				::= { wingTrapsPmPrefix 5}


		-- 1.3.6.1.4.1.1916.2.131.50.0.17.0.6
		wingTrapPmProcid NOTIFICATION-TYPE
			OBJECTS { wingEventMnemonic, wingEventModule, wingEventSeverity, wingEventMsg, wingEventSourceAddr,
				wingEventSourceHostname }
			STATUS current
			DESCRIPTION
				"Process changed pid"
				::= { wingTrapsPmPrefix 6}


		-- 1.3.6.1.4.1.1916.2.131.50.0.17.0.7
		wingTrapPmStartupcomplete NOTIFICATION-TYPE
			OBJECTS { wingEventMnemonic, wingEventModule, wingEventSeverity, wingEventMsg, wingEventSourceAddr,
				wingEventSourceHostname }
			STATUS current
			DESCRIPTION
				"System startup completed"
				::= { wingTrapsPmPrefix 7}


		-- 1.3.6.1.4.1.1916.2.131.50.0.17.0.8
		wingTrapPmProcnoresp NOTIFICATION-TYPE
			OBJECTS { wingEventMnemonic, wingEventModule, wingEventSeverity, wingEventMsg, wingEventSourceAddr,
				wingEventSourceHostname }
			STATUS current
			DESCRIPTION
				"Process is not responding"
				::= { wingTrapsPmPrefix 8}


--Radius Configuration Daemon
		--1.3.6.1.4.1.1916.2.131.50.0.18
		wingTrapsRadconf OBJECT IDENTIFIER ::= { wingNotifications 18 }


		--1.3.6.1.4.1.1916.2.131.50.0.18.0
		wingTrapsRadconfPrefix OBJECT IDENTIFIER ::= { wingTrapsRadconf 0 }


		-- 1.3.6.1.4.1.1916.2.131.50.0.18.0.1
		wingTrapRadconfRadiusdstart NOTIFICATION-TYPE
			OBJECTS { wingEventMnemonic, wingEventModule, wingEventSeverity, wingEventMsg, wingEventSourceAddr,
				wingEventSourceHostname }
			STATUS current
			DESCRIPTION
				"RADIUS server started"
				::= { wingTrapsRadconfPrefix 1}


		-- 1.3.6.1.4.1.1916.2.131.50.0.18.0.2
		wingTrapRadconfRadiusdstop NOTIFICATION-TYPE
			OBJECTS { wingEventMnemonic, wingEventModule, wingEventSeverity, wingEventMsg, wingEventSourceAddr,
				wingEventSourceHostname }
			STATUS current
			DESCRIPTION
				"RADIUS server stopped"
				::= { wingTrapsRadconfPrefix 2}


		-- 1.3.6.1.4.1.1916.2.131.50.0.18.0.3
		wingTrapRadconfCouldNotStopRadiusd NOTIFICATION-TYPE
			OBJECTS { wingEventMnemonic, wingEventModule, wingEventSeverity, wingEventMsg, wingEventSourceAddr,
				wingEventSourceHostname }
			STATUS current
			DESCRIPTION
				"Event could-not-stop-radiusd"
				::= { wingTrapsRadconfPrefix 3}


--Radio module
		--1.3.6.1.4.1.1916.2.131.50.0.19
		wingTrapsRadio OBJECT IDENTIFIER ::= { wingNotifications 19 }


		--1.3.6.1.4.1.1916.2.131.50.0.19.0
		wingTrapsRadioPrefix OBJECT IDENTIFIER ::= { wingTrapsRadio 0 }


		-- 1.3.6.1.4.1.1916.2.131.50.0.19.0.1
		wingTrapRadioChannelCountryMismatch NOTIFICATION-TYPE
			OBJECTS { wingEventMnemonic, wingEventModule, wingEventSeverity, wingEventMsg, wingEventSourceAddr,
				wingEventSourceHostname }
			STATUS current
			DESCRIPTION
				"Channel and country of operation mismatch"
				::= { wingTrapsRadioPrefix 1}


		-- 1.3.6.1.4.1.1916.2.131.50.0.19.0.2
		wingTrapRadioRadioStateChange NOTIFICATION-TYPE
			OBJECTS { wingEventMnemonic, wingEventModule, wingEventSeverity, wingEventMsg, wingEventSourceAddr,
				wingEventSourceHostname }
			STATUS current
			DESCRIPTION
				"Radio state changed"
				::= { wingTrapsRadioPrefix 2}


		-- 1.3.6.1.4.1.1916.2.131.50.0.19.0.3
		wingTrapRadioRadarScanStarted NOTIFICATION-TYPE
			OBJECTS { wingEventMnemonic, wingEventModule, wingEventSeverity, wingEventMsg, wingEventSourceAddr,
				wingEventSourceHostname }
			STATUS current
			DESCRIPTION
				"Radar scan started"
				::= { wingTrapsRadioPrefix 3}


		-- 1.3.6.1.4.1.1916.2.131.50.0.19.0.4
		wingTrapRadioRadarScanCompleted NOTIFICATION-TYPE
			OBJECTS { wingEventMnemonic, wingEventModule, wingEventSeverity, wingEventMsg, wingEventSourceAddr,
				wingEventSourceHostname }
			STATUS current
			DESCRIPTION
				"Radar scan completed"
				::= { wingTrapsRadioPrefix 4}


		-- 1.3.6.1.4.1.1916.2.131.50.0.19.0.5
		wingTrapRadioRadarDetected NOTIFICATION-TYPE
			OBJECTS { wingEventMnemonic, wingEventModule, wingEventSeverity, wingEventMsg, wingEventSourceAddr,
				wingEventSourceHostname }
			STATUS current
			DESCRIPTION
				"Radar detected"
				::= { wingTrapsRadioPrefix 5}


		-- 1.3.6.1.4.1.1916.2.131.50.0.19.0.6
		wingTrapRadioRadarDetInfo NOTIFICATION-TYPE
			OBJECTS { wingEventMnemonic, wingEventModule, wingEventSeverity, wingEventMsg, wingEventSourceAddr,
				wingEventSourceHostname }
			STATUS current
			DESCRIPTION
				"Radar info"
				::= { wingTrapsRadioPrefix 6}


		-- 1.3.6.1.4.1.1916.2.131.50.0.19.0.7
		wingTrapRadioResumeHomeChannel NOTIFICATION-TYPE
			OBJECTS { wingEventMnemonic, wingEventModule, wingEventSeverity, wingEventMsg, wingEventSourceAddr,
				wingEventSourceHostname }
			STATUS current
			DESCRIPTION
				"Radio resuming on home channel"
				::= { wingTrapsRadioPrefix 7}


		-- 1.3.6.1.4.1.1916.2.131.50.0.19.0.8
		wingTrapRadioAcsScanStarted NOTIFICATION-TYPE
			OBJECTS { wingEventMnemonic, wingEventModule, wingEventSeverity, wingEventMsg, wingEventSourceAddr,
				wingEventSourceHostname }
			STATUS current
			DESCRIPTION
				"ACS Scan Started"
				::= { wingTrapsRadioPrefix 8}


		-- 1.3.6.1.4.1.1916.2.131.50.0.19.0.9
		wingTrapRadioAcsScanComplete NOTIFICATION-TYPE
			OBJECTS { wingEventMnemonic, wingEventModule, wingEventSeverity, wingEventMsg, wingEventSourceAddr,
				wingEventSourceHostname }
			STATUS current
			DESCRIPTION
				"ACS Scan Complete"
				::= { wingTrapsRadioPrefix 9}


		-- 1.3.6.1.4.1.1916.2.131.50.0.19.0.10
		wingTrapRadioRadioAntennaError NOTIFICATION-TYPE
			OBJECTS { wingEventMnemonic, wingEventModule, wingEventSeverity, wingEventMsg, wingEventSourceAddr,
				wingEventSourceHostname }
			STATUS current
			DESCRIPTION
				"Invalid antenna type on this radio"
				::= { wingTrapsRadioPrefix 10}


		-- 1.3.6.1.4.1.1916.2.131.50.0.19.0.11
		wingTrapRadioRadioAntennaSetting NOTIFICATION-TYPE
			OBJECTS { wingEventMnemonic, wingEventModule, wingEventSeverity, wingEventMsg, wingEventSourceAddr,
				wingEventSourceHostname }
			STATUS current
			DESCRIPTION
				"Antenna type setting on this radio"
				::= { wingTrapsRadioPrefix 11}


--Smart-rf module
		--1.3.6.1.4.1.1916.2.131.50.0.21
		wingTrapsSmrt OBJECT IDENTIFIER ::= { wingNotifications 21 }


		--1.3.6.1.4.1.1916.2.131.50.0.21.0
		wingTrapsSmrtPrefix OBJECT IDENTIFIER ::= { wingTrapsSmrt 0 }


		-- 1.3.6.1.4.1.1916.2.131.50.0.21.0.1
		wingTrapSmrtCalibrationStarted NOTIFICATION-TYPE
			OBJECTS { wingEventMnemonic, wingEventModule, wingEventSeverity, wingEventMsg, wingEventSourceAddr,
				wingEventSourceHostname }
			STATUS current
			DESCRIPTION
				"Calibration started"
				::= { wingTrapsSmrtPrefix 1}


		-- 1.3.6.1.4.1.1916.2.131.50.0.21.0.2
		wingTrapSmrtCalibrationDone NOTIFICATION-TYPE
			OBJECTS { wingEventMnemonic, wingEventModule, wingEventSeverity, wingEventMsg, wingEventSourceAddr,
				wingEventSourceHostname }
			STATUS current
			DESCRIPTION
				"Calibration done"
				::= { wingTrapsSmrtPrefix 2}


		-- 1.3.6.1.4.1.1916.2.131.50.0.21.0.3
		wingTrapSmrtNeighborRecovery NOTIFICATION-TYPE
			OBJECTS { wingEventMnemonic, wingEventModule, wingEventSeverity, wingEventMsg, wingEventSourceAddr,
				wingEventSourceHostname }
			STATUS current
			DESCRIPTION
				"Neighbor recovery power change"
				::= { wingTrapsSmrtPrefix 3}


		-- 1.3.6.1.4.1.1916.2.131.50.0.21.0.4
		wingTrapSmrtPowerAdjustment NOTIFICATION-TYPE
			OBJECTS { wingEventMnemonic, wingEventModule, wingEventSeverity, wingEventMsg, wingEventSourceAddr,
				wingEventSourceHostname }
			STATUS current
			DESCRIPTION
				"Radio power adjustment"
				::= { wingTrapsSmrtPrefix 4}


		-- 1.3.6.1.4.1.1916.2.131.50.0.21.0.5
		wingTrapSmrtInterferenceRecovery NOTIFICATION-TYPE
			OBJECTS { wingEventMnemonic, wingEventModule, wingEventSeverity, wingEventMsg, wingEventSourceAddr,
				wingEventSourceHostname }
			STATUS current
			DESCRIPTION
				"Interference recovery"
				::= { wingTrapsSmrtPrefix 5}


		-- 1.3.6.1.4.1.1916.2.131.50.0.21.0.6
		wingTrapSmrtRootRecovery NOTIFICATION-TYPE
			OBJECTS { wingEventMnemonic, wingEventModule, wingEventSeverity, wingEventMsg, wingEventSourceAddr,
				wingEventSourceHostname }
			STATUS current
			DESCRIPTION
				"Meshpoint root  recovery"
				::= { wingTrapsSmrtPrefix 6}


		-- 1.3.6.1.4.1.1916.2.131.50.0.21.0.7
		wingTrapSmrtCovHoleRecovery NOTIFICATION-TYPE
			OBJECTS { wingEventMnemonic, wingEventModule, wingEventSeverity, wingEventMsg, wingEventSourceAddr,
				wingEventSourceHostname }
			STATUS current
			DESCRIPTION
				"Coverage hole recovery"
				::= { wingTrapsSmrtPrefix 7}


		-- 1.3.6.1.4.1.1916.2.131.50.0.21.0.8
		wingTrapSmrtCovHoleRecoveryDone NOTIFICATION-TYPE
			OBJECTS { wingEventMnemonic, wingEventModule, wingEventSeverity, wingEventMsg, wingEventSourceAddr,
				wingEventSourceHostname }
			STATUS current
			DESCRIPTION
				"Coverage hole recovery done"
				::= { wingTrapsSmrtPrefix 8}


		-- 1.3.6.1.4.1.1916.2.131.50.0.21.0.9
		wingTrapSmrtConfigCleared NOTIFICATION-TYPE
			OBJECTS { wingEventMnemonic, wingEventModule, wingEventSeverity, wingEventMsg, wingEventSourceAddr,
				wingEventSourceHostname }
			STATUS current
			DESCRIPTION
				"Smart-rf configuration cleared"
				::= { wingTrapsSmrtPrefix 9}


		-- 1.3.6.1.4.1.1916.2.131.50.0.21.0.10
		wingTrapSmrtChannelChange NOTIFICATION-TYPE
			OBJECTS { wingEventMnemonic, wingEventModule, wingEventSeverity, wingEventMsg, wingEventSourceAddr,
				wingEventSourceHostname }
			STATUS current
			DESCRIPTION
				"Channel change"
				::= { wingTrapsSmrtPrefix 10}


--smtpnot module
		--1.3.6.1.4.1.1916.2.131.50.0.22
		wingTrapsSmtpnot OBJECT IDENTIFIER ::= { wingNotifications 22 }


		--1.3.6.1.4.1.1916.2.131.50.0.22.0
		wingTrapsSmtpnotPrefix OBJECT IDENTIFIER ::= { wingTrapsSmtpnot 0 }


		-- 1.3.6.1.4.1.1916.2.131.50.0.22.0.1
		wingTrapSmtpnotSmtpauth NOTIFICATION-TYPE
			OBJECTS { wingEventMnemonic, wingEventModule, wingEventSeverity, wingEventMsg, wingEventSourceAddr,
				wingEventSourceHostname }
			STATUS current
			DESCRIPTION
				"Event smtpauth"
				::= { wingTrapsSmtpnotPrefix 1}


		-- 1.3.6.1.4.1.1916.2.131.50.0.22.0.2
		wingTrapSmtpnotNet NOTIFICATION-TYPE
			OBJECTS { wingEventMnemonic, wingEventModule, wingEventSeverity, wingEventMsg, wingEventSourceAddr,
				wingEventSourceHostname }
			STATUS current
			DESCRIPTION
				"Event net"
				::= { wingTrapsSmtpnotPrefix 2}


		-- 1.3.6.1.4.1.1916.2.131.50.0.22.0.3
		wingTrapSmtpnotSmtpinfo NOTIFICATION-TYPE
			OBJECTS { wingEventMnemonic, wingEventModule, wingEventSeverity, wingEventMsg, wingEventSourceAddr,
				wingEventSourceHostname }
			STATUS current
			DESCRIPTION
				"Event smtpinfo"
				::= { wingTrapsSmtpnotPrefix 3}


		-- 1.3.6.1.4.1.1916.2.131.50.0.22.0.4
		wingTrapSmtpnotCfg NOTIFICATION-TYPE
			OBJECTS { wingEventMnemonic, wingEventModule, wingEventSeverity, wingEventMsg, wingEventSourceAddr,
				wingEventSourceHostname }
			STATUS current
			DESCRIPTION
				"Event cfg"
				::= { wingTrapsSmtpnotPrefix 4}


		-- 1.3.6.1.4.1.1916.2.131.50.0.22.0.5
		wingTrapSmtpnotCfginc NOTIFICATION-TYPE
			OBJECTS { wingEventMnemonic, wingEventModule, wingEventSeverity, wingEventMsg, wingEventSourceAddr,
				wingEventSourceHostname }
			STATUS current
			DESCRIPTION
				"Event cfginc"
				::= { wingTrapsSmtpnotPrefix 5}


		-- 1.3.6.1.4.1.1916.2.131.50.0.22.0.6
		wingTrapSmtpnotSmtperr NOTIFICATION-TYPE
			OBJECTS { wingEventMnemonic, wingEventModule, wingEventSeverity, wingEventMsg, wingEventSourceAddr,
				wingEventSourceHostname }
			STATUS current
			DESCRIPTION
				"Event smtperr"
				::= { wingTrapsSmtpnotPrefix 6}


		-- 1.3.6.1.4.1.1916.2.131.50.0.22.0.7
		wingTrapSmtpnotProto NOTIFICATION-TYPE
			OBJECTS { wingEventMnemonic, wingEventModule, wingEventSeverity, wingEventMsg, wingEventSourceAddr,
				wingEventSourceHostname }
			STATUS current
			DESCRIPTION
				"Event proto"
				::= { wingTrapsSmtpnotPrefix 7}


--System module
		--1.3.6.1.4.1.1916.2.131.50.0.23
		wingTrapsSystem OBJECT IDENTIFIER ::= { wingNotifications 23 }


		--1.3.6.1.4.1.1916.2.131.50.0.23.0
		wingTrapsSystemPrefix OBJECT IDENTIFIER ::= { wingTrapsSystem 0 }


		-- 1.3.6.1.4.1.1916.2.131.50.0.23.0.1
		wingTrapSystemPanic NOTIFICATION-TYPE
			OBJECTS { wingEventMnemonic, wingEventModule, wingEventSeverity, wingEventMsg, wingEventSourceAddr,
				wingEventSourceHostname }
			STATUS current
			DESCRIPTION
				"Event panic"
				::= { wingTrapsSystemPrefix 1}


		-- 1.3.6.1.4.1.1916.2.131.50.0.23.0.2
		wingTrapSystemHttpErr NOTIFICATION-TYPE
			OBJECTS { wingEventMnemonic, wingEventModule, wingEventSeverity, wingEventMsg, wingEventSourceAddr,
				wingEventSourceHostname }
			STATUS current
			DESCRIPTION
				"Web server did not start"
				::= { wingTrapsSystemPrefix 2}


		-- 1.3.6.1.4.1.1916.2.131.50.0.23.0.3
		wingTrapSystemProcStop NOTIFICATION-TYPE
			OBJECTS { wingEventMnemonic, wingEventModule, wingEventSeverity, wingEventMsg, wingEventSourceAddr,
				wingEventSourceHostname }
			STATUS current
			DESCRIPTION
				"Stopping process"
				::= { wingTrapsSystemPrefix 3}


		-- 1.3.6.1.4.1.1916.2.131.50.0.23.0.4
		wingTrapSystemClockReset NOTIFICATION-TYPE
			OBJECTS { wingEventMnemonic, wingEventModule, wingEventSeverity, wingEventMsg, wingEventSourceAddr,
				wingEventSourceHostname }
			STATUS current
			DESCRIPTION
				"System clock reset"
				::= { wingTrapsSystemPrefix 4}


		-- 1.3.6.1.4.1.1916.2.131.50.0.23.0.5
		wingTrapSystemUiUserAuthFail NOTIFICATION-TYPE
			OBJECTS { wingEventMnemonic, wingEventModule, wingEventSeverity, wingEventMsg, wingEventSourceAddr,
				wingEventSourceHostname }
			STATUS current
			DESCRIPTION
				"GUI user authentication failed"
				::= { wingTrapsSystemPrefix 5}


		-- 1.3.6.1.4.1.1916.2.131.50.0.23.0.6
		wingTrapSystemUiUserAuthSuccess NOTIFICATION-TYPE
			OBJECTS { wingEventMnemonic, wingEventModule, wingEventSeverity, wingEventMsg, wingEventSourceAddr,
				wingEventSourceHostname }
			STATUS current
			DESCRIPTION
				"GUI user authentication successful"
				::= { wingTrapsSystemPrefix 6}


		-- 1.3.6.1.4.1.1916.2.131.50.0.23.0.7
		wingTrapSystemLogin NOTIFICATION-TYPE
			OBJECTS { wingEventMnemonic, wingEventModule, wingEventSeverity, wingEventMsg, wingEventSourceAddr,
				wingEventSourceHostname }
			STATUS current
			DESCRIPTION
				"Successful login"
				::= { wingTrapsSystemPrefix 7}


		-- 1.3.6.1.4.1.1916.2.131.50.0.23.0.8
		wingTrapSystemLoginFail NOTIFICATION-TYPE
			OBJECTS { wingEventMnemonic, wingEventModule, wingEventSeverity, wingEventMsg, wingEventSourceAddr,
				wingEventSourceHostname }
			STATUS current
			DESCRIPTION
				"Failed login attempt - user authentication failed"
				::= { wingTrapsSystemPrefix 8}


		-- 1.3.6.1.4.1.1916.2.131.50.0.23.0.9
		wingTrapSystemLoginFailAccess NOTIFICATION-TYPE
			OBJECTS { wingEventMnemonic, wingEventModule, wingEventSeverity, wingEventMsg, wingEventSourceAddr,
				wingEventSourceHostname }
			STATUS current
			DESCRIPTION
				"Failed login attempt - access violation"
				::= { wingTrapsSystemPrefix 9}


		-- 1.3.6.1.4.1.1916.2.131.50.0.23.0.10
		wingTrapSystemLoginFailBadRole NOTIFICATION-TYPE
			OBJECTS { wingEventMnemonic, wingEventModule, wingEventSeverity, wingEventMsg, wingEventSourceAddr,
				wingEventSourceHostname }
			STATUS current
			DESCRIPTION
				"Failed login attempt - no such user role"
				::= { wingTrapsSystemPrefix 10}


		-- 1.3.6.1.4.1.1916.2.131.50.0.23.0.11
		wingTrapSystemLogout NOTIFICATION-TYPE
			OBJECTS { wingEventMnemonic, wingEventModule, wingEventSeverity, wingEventMsg, wingEventSourceAddr,
				wingEventSourceHostname }
			STATUS current
			DESCRIPTION
				"Logout event"
				::= { wingTrapsSystemPrefix 11}


		-- 1.3.6.1.4.1.1916.2.131.50.0.23.0.12
		wingTrapSystemServerUnreachable NOTIFICATION-TYPE
			OBJECTS { wingEventMnemonic, wingEventModule, wingEventSeverity, wingEventMsg, wingEventSourceAddr,
				wingEventSourceHostname }
			STATUS current
			DESCRIPTION
				"Event server-unreachable"
				::= { wingTrapsSystemPrefix 12}


		-- 1.3.6.1.4.1.1916.2.131.50.0.23.0.13
		wingTrapSystemSystemAutoupEnable NOTIFICATION-TYPE
			OBJECTS { wingEventMnemonic, wingEventModule, wingEventSeverity, wingEventMsg, wingEventSourceAddr,
				wingEventSourceHostname }
			STATUS current
			DESCRIPTION
				"Auto upgrade module is enabled"
				::= { wingTrapsSystemPrefix 13}


		-- 1.3.6.1.4.1.1916.2.131.50.0.23.0.14
		wingTrapSystemSystemAutoupDisable NOTIFICATION-TYPE
			OBJECTS { wingEventMnemonic, wingEventModule, wingEventSeverity, wingEventMsg, wingEventSourceAddr,
				wingEventSourceHostname }
			STATUS current
			DESCRIPTION
				"Auto upgrade module is disabled"
				::= { wingTrapsSystemPrefix 14}


		-- 1.3.6.1.4.1.1916.2.131.50.0.23.0.15
		wingTrapSystemGuestUserExp NOTIFICATION-TYPE
			OBJECTS { wingEventMnemonic, wingEventModule, wingEventSeverity, wingEventMsg, wingEventSourceAddr,
				wingEventSourceHostname }
			STATUS current
			DESCRIPTION
				"Guest user purging"
				::= { wingTrapsSystemPrefix 15}


--Wireless IPS module
		--1.3.6.1.4.1.1916.2.131.50.0.24
		wingTrapsWips OBJECT IDENTIFIER ::= { wingNotifications 24 }


		--1.3.6.1.4.1.1916.2.131.50.0.24.0
		wingTrapsWipsPrefix OBJECT IDENTIFIER ::= { wingTrapsWips 0 }


		-- 1.3.6.1.4.1.1916.2.131.50.0.24.0.1
		wingTrapWipsWipsEvent NOTIFICATION-TYPE
			OBJECTS { wingEventMnemonic, wingEventModule, wingEventSeverity, wingEventMsg, wingEventSourceAddr,
				wingEventSourceHostname }
			STATUS current
			DESCRIPTION
				"WIPS event triggered"
				::= { wingTrapsWipsPrefix 1}


		-- 1.3.6.1.4.1.1916.2.131.50.0.24.0.2
		wingTrapWipsWipsClientBlacklisted NOTIFICATION-TYPE
			OBJECTS { wingEventMnemonic, wingEventModule, wingEventSeverity, wingEventMsg, wingEventSourceAddr,
				wingEventSourceHostname }
			STATUS current
			DESCRIPTION
				"Client blacklisted by WIPS"
				::= { wingTrapsWipsPrefix 2}


		-- 1.3.6.1.4.1.1916.2.131.50.0.24.0.3
		wingTrapWipsWipsClientRemBlacklist NOTIFICATION-TYPE
			OBJECTS { wingEventMnemonic, wingEventModule, wingEventSeverity, wingEventMsg, wingEventSourceAddr,
				wingEventSourceHostname }
			STATUS current
			DESCRIPTION
				"Client cleared from WIPS blacklist"
				::= { wingTrapsWipsPrefix 3}


--802.1X Authentication
		--1.3.6.1.4.1.1916.2.131.50.0.25
		wingTrapsDot1x OBJECT IDENTIFIER ::= { wingNotifications 25 }


		--1.3.6.1.4.1.1916.2.131.50.0.25.0
		wingTrapsDot1xPrefix OBJECT IDENTIFIER ::= { wingTrapsDot1x 0 }


		-- 1.3.6.1.4.1.1916.2.131.50.0.25.0.1
		wingTrapDot1xDot1xSuccess NOTIFICATION-TYPE
			OBJECTS { wingEventMnemonic, wingEventModule, wingEventSeverity, wingEventMsg, wingEventSourceAddr,
				wingEventSourceHostname }
			STATUS current
			DESCRIPTION
				"Event dot1x-success"
				::= { wingTrapsDot1xPrefix 1}


		-- 1.3.6.1.4.1.1916.2.131.50.0.25.0.2
		wingTrapDot1xDot1xFailed NOTIFICATION-TYPE
			OBJECTS { wingEventMnemonic, wingEventModule, wingEventSeverity, wingEventMsg, wingEventSourceAddr,
				wingEventSourceHostname }
			STATUS current
			DESCRIPTION
				"EAP authentication failure"
				::= { wingTrapsDot1xPrefix 2}



		
		-- 1.3.6.1.4.1.1916.2.131.50.1
		wingObjects OBJECT IDENTIFIER ::= { wingMIB 1 }

		
		-- 1.3.6.1.4.1.1916.2.131.50.1.1
		wingSysoids OBJECT IDENTIFIER ::= { wingObjects 1 }

		
		-- 1.3.6.1.4.1.1916.2.131.50.1.1.1
		wingSysoidAp4511 OBJECT-IDENTITY
			STATUS current
			DESCRIPTION 
				"AP4511 system object identifier"
			::= { wingSysoids 1 }

		
		-- 1.3.6.1.4.1.1916.2.131.50.1.1.2
		wingSysoidAp4521 OBJECT-IDENTITY
			STATUS current
			DESCRIPTION 
				"AP4521 system object identifier"
			::= { wingSysoids 2 }

		
		-- 1.3.6.1.4.1.1916.2.131.50.1.1.4
		wingSysoidAp4532 OBJECT-IDENTITY
			STATUS current
			DESCRIPTION 
				"AP4532 system object identifier"
			::= { wingSysoids 4 }

		
		-- 1.3.6.1.4.1.1916.2.131.50.1.1.8
		wingSysoidAp4760 OBJECT-IDENTITY
			STATUS current
			DESCRIPTION 
				"AP4760 system object identifier"
			::= { wingSysoids 8 }

		
		-- 1.3.6.1.4.1.1916.2.131.50.1.1.10
		wingSysoidAp4600 OBJECT-IDENTITY
			STATUS current
			DESCRIPTION 
				"AP4600 system object identifier"
			::= { wingSysoids 10 }

		
		-- 1.3.6.1.4.1.1916.2.131.50.1.1.11
		wingSysoidAp4021 OBJECT-IDENTITY
			STATUS current
			DESCRIPTION 
				"AP4021 system object identifier"
			::= { wingSysoids 11 }

		
		-- 1.3.6.1.4.1.1916.2.131.50.1.1.12
		wingSysoidAp4022 OBJECT-IDENTITY
			STATUS current
			DESCRIPTION 
				"AP4022 system object identifier"
			::= { wingSysoids 12 }

		
		-- 1.3.6.1.4.1.1916.2.131.50.1.1.13
		wingSysoidAp4522 OBJECT-IDENTITY
			STATUS current
			DESCRIPTION 
				"AP4522 system object identifier"
			::= { wingSysoids 13 }

		
		-- 1.3.6.1.4.1.1916.2.131.50.1.1.20
		wingSysoidAp4832 OBJECT-IDENTITY
			STATUS current
			DESCRIPTION 
				"AP4832 system object identifier"
			::= { wingSysoids 20 }

		
		-- 1.3.6.1.4.1.1916.2.131.50.1.1.25
		wingSysoidAp6562 OBJECT-IDENTITY
			STATUS current
			DESCRIPTION 
				"AP6562 system object identifier"
			::= { wingSysoids 25 }

		
		-- 1.3.6.1.4.1.1916.2.131.50.1.1.27
		wingSysoidNx9510 OBJECT-IDENTITY
			STATUS current
			DESCRIPTION 
				"NX9510 system object identifier"
			::= { wingSysoids 27 }

		
		-- 1.3.6.1.4.1.1916.2.131.50.1.2
		wingNotificationsObjects OBJECT IDENTIFIER ::= { wingObjects 2 }

		
		-- 1.3.6.1.4.1.1916.2.131.50.1.2.1
		wingEvent OBJECT IDENTIFIER ::= { wingNotificationsObjects 1 }

		
		-- 1.3.6.1.4.1.1916.2.131.50.1.2.1.1
		wingEventMnemonic OBJECT-TYPE
			SYNTAX DisplayString
			MAX-ACCESS accessible-for-notify
			STATUS current
			DESCRIPTION
				"Event mnemonic."
			::= { wingEvent 1 }

		
		-- 1.3.6.1.4.1.1916.2.131.50.1.2.1.2
		wingEventModule OBJECT-TYPE
			SYNTAX DisplayString
			MAX-ACCESS accessible-for-notify
			STATUS current
			DESCRIPTION
				"The module that generated the event."
			::= { wingEvent 2 }

		
		-- 1.3.6.1.4.1.1916.2.131.50.1.2.1.3
		wingEventSeverity OBJECT-TYPE
			SYNTAX INTEGER
				{
				emergency(0),
				alert(1),
				critical(2),
				error(3),
				warning(4),
				notice(5),
				information(6),
				debug(7)
				}
			MAX-ACCESS accessible-for-notify
			STATUS current
			DESCRIPTION
				"Severity of the event."
			::= { wingEvent 3 }

		
		-- 1.3.6.1.4.1.1916.2.131.50.1.2.1.4
		wingEventMsg OBJECT-TYPE
			SYNTAX DisplayString
			MAX-ACCESS accessible-for-notify
			STATUS current
			DESCRIPTION
				"Formatted message for the event."
			::= { wingEvent 4 }

		
		-- 1.3.6.1.4.1.1916.2.131.50.1.2.1.5
		wingEventSourceAddr OBJECT-TYPE
			SYNTAX MacAddress
			MAX-ACCESS accessible-for-notify
			STATUS current
			DESCRIPTION
				"Address of the device that generated the event."
			::= { wingEvent 5 }

		
		-- 1.3.6.1.4.1.1916.2.131.50.1.2.1.6
		wingEventSourceHostname OBJECT-TYPE
			SYNTAX DisplayString
			MAX-ACCESS accessible-for-notify
			STATUS current
			DESCRIPTION
				"Hostname of the device that generated the event."
			::= { wingEvent 6 }

		
		-- 1.3.6.1.4.1.1916.2.131.50.1.3
		wingConfig OBJECT IDENTIFIER ::= { wingObjects 3 }

		
-- Extensions to mib-2.system
		-- 1.3.6.1.4.1.1916.2.131.50.1.3.1
		wingCfgSys OBJECT IDENTIFIER ::= { wingConfig 1 }

		
		-- 1.3.6.1.4.1.1916.2.131.50.1.3.1.5
		wingConfigSysMacAddr OBJECT-TYPE
			SYNTAX DisplayString
			MAX-ACCESS read-only
			STATUS current
			DESCRIPTION
				"MAC address of the system.
				
				XPath: /wing-config/device[mac='self']/mac"
			::= { wingCfgSys 5 }

		
-- System commit parameters
		-- 1.3.6.1.4.1.1916.2.131.50.1.3.1.6
		wingCfgSysCommit OBJECT IDENTIFIER ::= { wingCfgSys 6 }

		
		-- 1.3.6.1.4.1.1916.2.131.50.1.3.1.6.1
		wingCfgSysCommitLastError OBJECT-TYPE
			SYNTAX DisplayString
			MAX-ACCESS read-only
			STATUS current
			DESCRIPTION
				"A short while after a successful SNMP set operation,
				the system does an automatic commit. The automatic commit
				may fail for reasons including invalid values.
				
				This object contains the error message from
				the last automatic commit.
				
				Be sure to check this object after a few SNMP set operations
				to make sure that the commit is successful.
				
				In case of error, clear the error by setting the object(s)
				corresponding to the failed configuration item(s) with
				the correct values."
			::= { wingCfgSysCommit 1 }

		
		-- 1.3.6.1.4.1.1916.2.131.50.1.3.1.7
		wingCfgSysRunningConfigChecksum OBJECT-TYPE
			SYNTAX DisplayString
			MAX-ACCESS read-only
			STATUS current
			DESCRIPTION
				"MD5 checksum of system:running-config.
				
				XPath: /wing-stats/device/self/config-checksum"
			::= { wingCfgSys 7 }

		
-- /wing-config/version
		-- 1.3.6.1.4.1.1916.2.131.50.1.3.2
		wingCfgVersion OBJECT IDENTIFIER ::= { wingConfig 2 }

		
		-- 1.3.6.1.4.1.1916.2.131.50.1.3.2.1
		wingCfgVersionVal OBJECT-TYPE
			SYNTAX DisplayString
			MAX-ACCESS read-only
			STATUS current
			DESCRIPTION
				"Version of configuration
				
				XPath: /wing-config/version[name=default]/version"
			::= { wingCfgVersion 1 }

		
-- /wing-config/password_encryption
		-- 1.3.6.1.4.1.1916.2.131.50.1.3.3
		wingCfgPasswordEnc OBJECT IDENTIFIER ::= { wingConfig 3 }

		
		-- 1.3.6.1.4.1.1916.2.131.50.1.3.3.1
		wingCfgPasswordEncVal OBJECT-TYPE
			SYNTAX OCTET STRING
			MAX-ACCESS read-only
			STATUS current
			DESCRIPTION
				"sha256 digest as a hex string of the passphrase used to
				encrypt passwords in the configuration or
				zero length string when encryption is disabled.
				
				XPath: /wing-config/password_encryption[name=default]/password_encryption"
			::= { wingCfgPasswordEnc 1 }

		
-- /wing-config/password_encryption/_set_pe_
		-- 1.3.6.1.4.1.1916.2.131.50.1.3.3.2
		wingCfgPasswordEncSet OBJECT IDENTIFIER ::= { wingCfgPasswordEnc 2 }

		
		-- 1.3.6.1.4.1.1916.2.131.50.1.3.3.2.1
		wingCfgPasswordEncSetOldPassphrase OBJECT-TYPE
			SYNTAX DisplayString
			MAX-ACCESS read-write
			STATUS current
			DESCRIPTION
				"This object is used to encrypt passwords in the configuration.
				To set encryption passphrase with validation this object
				must be set with the current passphrase.
				
				This object is write-only, read simply returns zero length
				string.
				
				XPath: /wing-config/password_encryption[name=default]/_set_pe_/old_pwd"
			::= { wingCfgPasswordEncSet 1 }

		
		-- 1.3.6.1.4.1.1916.2.131.50.1.3.3.2.2
		wingCfgPasswordEncSetNewPassphrase OBJECT-TYPE
			SYNTAX DisplayString
			MAX-ACCESS read-write
			STATUS current
			DESCRIPTION
				"This object is used to encrypt passwords in the configuration.
				To set encryption passphrase with validation this object
				must be set with the new passphrase or an empty string
				to indicate no encryption.
				
				The current passphrase must be set in the previous object
				before setting object.
				
				This object is write-only, read simply returns zero length
				string.
				
				XPath: /wing-config/password_encryption[name=default]/_set_pe_/new_pwd"
			::= { wingCfgPasswordEncSet 2 }

		
-- /wing-config/wlan
		-- 1.3.6.1.4.1.1916.2.131.50.1.3.4
		wingCfgWlan OBJECT IDENTIFIER ::= { wingConfig 4 }

		
		-- 1.3.6.1.4.1.1916.2.131.50.1.3.4.1
		wingCfgWlanTable OBJECT-TYPE
			SYNTAX SEQUENCE OF WingCfgWlanEntry
			MAX-ACCESS not-accessible
			STATUS current
			DESCRIPTION
				"Configuration parameters of a Wireless LAN.
				
				/wing-config/wlan"
			::= { wingCfgWlan 1 }

		
		-- 1.3.6.1.4.1.1916.2.131.50.1.3.4.1.1
		wingCfgWlanEntry OBJECT-TYPE
			SYNTAX WingCfgWlanEntry
			MAX-ACCESS not-accessible
			STATUS current
			DESCRIPTION
				"An entry in the table."
			INDEX { wingCfgWlanName }
			::= { wingCfgWlanTable 1 }

		
		WingCfgWlanEntry ::=
			SEQUENCE { 
				wingCfgWlanName
					WingIdentifier,
				wingCfgWlanShutdown
					TruthValue,
				wingCfgWlanSsid
					DisplayString,
				wingCfgWlanDescr
					DisplayString,
				wingCfgWlanEncType
					DisplayString,
				wingCfgWlanAuthType
					DisplayString,
				wingCfgWlanCaptivePortalEnforcement
					DisplayString,
				wingCfgWlanClientPower
					Unsigned32,
				wingCfgWlanNasId
					DisplayString,
				wingCfgWlanNasPortId
					DisplayString,
				wingCfgWlanBroadcastSsid
					TruthValue,
				wingCfgWlanAnswerBroadcastProbes
					TruthValue,
				wingCfgWlanClientClientCommunication
					TruthValue,
				wingCfgWlanHoldTime
					Unsigned32,
				wingCfgWlanInactivityTimeout
					Unsigned32,
				wingCfgWlanCredCacheAgeout
					Unsigned32,
				wingCfgWlanVlanCacheAgeout
					Unsigned32,
				wingCfgWlanMaxFirewallSessions
					Unsigned32,
				wingCfgWlanReauth
					Unsigned32,
				wingCfgWlanPmfMode
					DisplayString,
				wingCfgWlanPmfSaQueryTimeout
					Unsigned32,
				wingCfgWlanPmfSaQueryAttempts
					Unsigned32,
				wingCfgWlanWpaWpa2Psk
					DisplayString,
				wingCfgWlanWpaWpa2ExcludeWpa2Tkip
					TruthValue,
				wingCfgWlanWpaWpa2KeyRotationUnicast
					Unsigned32,
				wingCfgWlanWpaWpa2KeyRotationBroadcast
					Unsigned32,
				wingCfgWlanWpaWpa2PmkCaching
					TruthValue,
				wingCfgWlanWpaWpa2OpmkCaching
					TruthValue,
				wingCfgWlanWpaWpa2Preauth
					TruthValue,
				wingCfgWlanWpaWpa2TkipCntrmeasHoldTime
					Unsigned32,
				wingCfgWlanWep64TransmitKey
					Unsigned32,
				wingCfgWlanWep128TransmitKey
					Unsigned32,
				wingCfgWlanRadiusAssignedVlans
					TruthValue,
				wingCfgWlanRadiusDynamicAuthorization
					TruthValue,
				wingCfgWlanAccountingRadius
					TruthValue,
				wingCfgWlanMotoExtnMoveCmd
					TruthValue,
				wingCfgWlanMotoExtnSmartScan
					TruthValue,
				wingCfgWlanMotoExtnWmmLoadBalance
					TruthValue,
				wingCfgWlanMotoExtnSymbolLoadInfo
					TruthValue,
				wingCfgWlanClientLoadBal
					TruthValue,
				wingCfgWlanClientLoadBalSingleBandClients5ghz
					TruthValue,
				wingCfgWlanClientLoadBalSingleBandClients24ghz
					TruthValue,
				wingCfgWlanClientLoadBalMaxProbeReq24ghz
					Unsigned32,
				wingCfgWlanClientLoadBalMaxProbeReq5ghz
					Unsigned32,
				wingCfgWlanClientLoadBalProbeReqIntvl5ghz
					Unsigned32,
				wingCfgWlanClientLoadBalProbeReqIntvl24ghz
					Unsigned32,
				wingCfgWlanClientLoadBalBandDiscoveryIntvl
					Unsigned32,
				wingCfgWlanClientLoadBalCapabilityAgeoutTime
					Unsigned32,
				wingCfgWlanQosPolicy
					WingIdentifier,
				wingCfgWlanAaaPolicy
					WingIdentifier,
				wingCfgWlanCaptivePortal
					WingIdentifier,
				wingCfgWlanAssocAcl
					WingIdentifier,
				wingCfgWlanIpInAcl
					WingIdentifier,
				wingCfgWlanMacInAcl
					WingIdentifier,
				wingCfgWlanIpOutAcl
					WingIdentifier,
				wingCfgWlanMacOutAcl
					WingIdentifier,
				wingCfgWlanArpTrust
					TruthValue,
				wingCfgWlanDhcpTrust
					TruthValue,
				wingCfgWlanArpHeaderMismatchValidation
					TruthValue,
				wingCfgWlanServiceAllowHtOnly
					TruthValue,
				wingCfgWlanEnforceDhcp
					TruthValue,
				wingCfgWlanProxyArpMode
					DisplayString,
				wingCfgWlanBroadcastDhcpValidateOffer
					TruthValue
			 }

		-- 1.3.6.1.4.1.1916.2.131.50.1.3.4.1.1.1
		wingCfgWlanName OBJECT-TYPE
			SYNTAX WingIdentifier
			MAX-ACCESS read-only
			STATUS current
			DESCRIPTION
				"
				
				XPath: /wing-config/wlan[name=key1]/name"
			::= { wingCfgWlanEntry 1 }

		
		-- 1.3.6.1.4.1.1916.2.131.50.1.3.4.1.1.3
		wingCfgWlanShutdown OBJECT-TYPE
			SYNTAX TruthValue
			MAX-ACCESS read-write
			STATUS current
			DESCRIPTION
				"
				
				XPath: /wing-config/wlan[name=key1]/shutdown"
			DEFVAL { false }
			::= { wingCfgWlanEntry 3 }

		
		-- 1.3.6.1.4.1.1916.2.131.50.1.3.4.1.1.4
		wingCfgWlanSsid OBJECT-TYPE
			SYNTAX DisplayString (SIZE (1..32))
			MAX-ACCESS read-write
			STATUS current
			DESCRIPTION
				"Service Set Identifier for this WLAN.
				
				XPath: /wing-config/wlan[name=key1]/ssid"
			::= { wingCfgWlanEntry 4 }

		
		-- 1.3.6.1.4.1.1916.2.131.50.1.3.4.1.1.5
		wingCfgWlanDescr OBJECT-TYPE
			SYNTAX DisplayString (SIZE (1..64))
			MAX-ACCESS read-write
			STATUS current
			DESCRIPTION
				"Descriptive text about this WLAN.
				
				XPath: /wing-config/wlan[name=key1]/description"
			::= { wingCfgWlanEntry 5 }

		
		-- 1.3.6.1.4.1.1916.2.131.50.1.3.4.1.1.6
		wingCfgWlanEncType OBJECT-TYPE
			SYNTAX DisplayString
			MAX-ACCESS read-write
			STATUS current
			DESCRIPTION
				"
				Values:
				none
				wep64
				wep128
				wep128-keyguard
				keyguard
				tkip
				tkip-ccmp
				ccmp
				
				XPath: /wing-config/wlan[name=key1]/encryption_type"
			DEFVAL { "none" }
			::= { wingCfgWlanEntry 6 }

		
		-- 1.3.6.1.4.1.1916.2.131.50.1.3.4.1.1.7
		wingCfgWlanAuthType OBJECT-TYPE
			SYNTAX DisplayString
			MAX-ACCESS read-write
			STATUS current
			DESCRIPTION
				"
				Values:
				none
				eap
				kerberos
				mac
				eap-psk
				eap-mac
				
				Notes:
				eap-psk authentication-type is only supported with tkip and
				ccmp encryption types
				
				eap-mac authentication-type is only supported with open,  
				wep64, and wep128 encryption types
				
				kerberos authentication-type is only supported with wep and
				keyguard encryption types
				
				XPath: /wing-config/wlan[name=key1]/authentication_type"
			DEFVAL { "none" }
			::= { wingCfgWlanEntry 7 }

		
		-- 1.3.6.1.4.1.1916.2.131.50.1.3.4.1.1.8
		wingCfgWlanCaptivePortalEnforcement OBJECT-TYPE
			SYNTAX DisplayString
			MAX-ACCESS read-write
			STATUS current
			DESCRIPTION
				"
				Values:
				never
				fall-back
				always
				
				Note: fall-back does not apply if authentication-type is
				eap-psk, none, or kerberos
				
				XPath: /wing-config/wlan[name=key1]/captive_portal_enforcement"
			DEFVAL { "never" }
			::= { wingCfgWlanEntry 8 }

		
		-- 1.3.6.1.4.1.1916.2.131.50.1.3.4.1.1.9
		wingCfgWlanClientPower OBJECT-TYPE
			SYNTAX Unsigned32 (0..20)
			UNITS "dBm"
			MAX-ACCESS read-write
			STATUS current
			DESCRIPTION
				"Transmit power indicated to wireless clients for transmission.
				
				XPath: /wing-config/wlan[name=key1]/wireless_client_power"
			DEFVAL { 20 }
			::= { wingCfgWlanEntry 9 }

		
		-- 1.3.6.1.4.1.1916.2.131.50.1.3.4.1.1.10
		wingCfgWlanNasId OBJECT-TYPE
			SYNTAX DisplayString (SIZE (0..253))
			MAX-ACCESS read-write
			STATUS current
			DESCRIPTION
				"The RADIUS NAS-Identifier attribute which typically
				identifies the AP/Controller where the Radius message
				originates.
				
				XPath: /wing-config/wlan[name=key1]/nas_identifier"
			DEFVAL { "" }
			::= { wingCfgWlanEntry 10 }

		
		-- 1.3.6.1.4.1.1916.2.131.50.1.3.4.1.1.11
		wingCfgWlanNasPortId OBJECT-TYPE
			SYNTAX DisplayString (SIZE (0..253))
			MAX-ACCESS read-write
			STATUS current
			DESCRIPTION
				"The RADIUS NAS-Port-Id attribute which typically identifiers
				the port of the device where the RADIUS messages originates.
				
				XPath: /wing-config/wlan[name=key1]/nas_port_id"
			DEFVAL { "" }
			::= { wingCfgWlanEntry 11 }

		
		-- 1.3.6.1.4.1.1916.2.131.50.1.3.4.1.1.12
		wingCfgWlanBroadcastSsid OBJECT-TYPE
			SYNTAX TruthValue
			MAX-ACCESS read-write
			STATUS current
			DESCRIPTION
				"Do not advertise the SSID of the WLAN in the beacon.
				
				XPath: /wing-config/wlan[name=key1]/broadcast_ssid"
			DEFVAL { true }
			::= { wingCfgWlanEntry 12 }

		
		-- 1.3.6.1.4.1.1916.2.131.50.1.3.4.1.1.13
		wingCfgWlanAnswerBroadcastProbes OBJECT-TYPE
			SYNTAX TruthValue
			MAX-ACCESS read-write
			STATUS current
			DESCRIPTION
				"Include this WLAN when responding to probe requests that
				do not specify an SSID.
				
				XPath: /wing-config/wlan[name=key1]/answer_broadcast_probes"
			DEFVAL { true }
			::= { wingCfgWlanEntry 13 }

		
		-- 1.3.6.1.4.1.1916.2.131.50.1.3.4.1.1.14
		wingCfgWlanClientClientCommunication OBJECT-TYPE
			SYNTAX TruthValue
			MAX-ACCESS read-write
			STATUS current
			DESCRIPTION
				"Disallow switching of frames from one Wireless Client to
				another on this WLAN.
				
				XPath: /wing-config/wlan[name=key1]/client_client_communication"
			DEFVAL { true }
			::= { wingCfgWlanEntry 14 }

		
		-- 1.3.6.1.4.1.1916.2.131.50.1.3.4.1.1.15
		wingCfgWlanHoldTime OBJECT-TYPE
			SYNTAX Unsigned32 (1..300)
			UNITS "seconds"
			MAX-ACCESS read-write
			STATUS current
			DESCRIPTION
				"User credentials and firewall flow state information
				is cached for this much time when the user roams away.
				
				XPath: /wing-config/wlan[name=key1]/hold_time"
			DEFVAL { 30 }
			::= { wingCfgWlanEntry 15 }

		
		-- 1.3.6.1.4.1.1916.2.131.50.1.3.4.1.1.16
		wingCfgWlanInactivityTimeout OBJECT-TYPE
			SYNTAX Unsigned32 (60..86400)
			UNITS "seconds"
			MAX-ACCESS read-write
			STATUS current
			DESCRIPTION
				"If a frame is not received from a Wireless Client for this
				amount of time, the Wireless Client is disassociated.
				
				XPath: /wing-config/wlan[name=key1]/inactivity_timeout"
			DEFVAL { 1800 }
			::= { wingCfgWlanEntry 16 }

		
		-- 1.3.6.1.4.1.1916.2.131.50.1.3.4.1.1.17
		wingCfgWlanCredCacheAgeout OBJECT-TYPE
			SYNTAX Unsigned32 (60..86400)
			UNITS "seconds"
			MAX-ACCESS read-write
			STATUS current
			DESCRIPTION
				"User keys are cached for this time interval across
				associations
				
				XPath: /wing-config/wlan[name=key1]/credcache_ageout"
			DEFVAL { 86400 }
			::= { wingCfgWlanEntry 17 }

		
		-- 1.3.6.1.4.1.1916.2.131.50.1.3.4.1.1.18
		wingCfgWlanVlanCacheAgeout OBJECT-TYPE
			SYNTAX Unsigned32 (60..86400)
			UNITS "seconds"
			MAX-ACCESS read-write
			STATUS current
			DESCRIPTION
				"User vlan information is cached for this time interval
				across associations
				
				XPath: /wing-config/wlan[name=key1]/vlancache_ageout"
			DEFVAL { 3600 }
			::= { wingCfgWlanEntry 18 }

		
		-- 1.3.6.1.4.1.1916.2.131.50.1.3.4.1.1.19
		wingCfgWlanMaxFirewallSessions OBJECT-TYPE
			SYNTAX Unsigned32 (10..10000)
			MAX-ACCESS read-write
			STATUS current
			DESCRIPTION
				"Maximum firewall flows per Wireless Client.
				
				XPath: /wing-config/wlan[name=key1]/max_firewall_sessions"
			::= { wingCfgWlanEntry 19 }

		
		-- 1.3.6.1.4.1.1916.2.131.50.1.3.4.1.1.20
		wingCfgWlanReauth OBJECT-TYPE
			SYNTAX Unsigned32 (30..86400)
			MAX-ACCESS read-write
			STATUS current
			DESCRIPTION
				"
				
				XPath: /wing-config/wlan[name=key1]/reauthentication"
			::= { wingCfgWlanEntry 20 }

		
		-- 1.3.6.1.4.1.1916.2.131.50.1.3.4.1.1.21
		wingCfgWlanPmfMode OBJECT-TYPE
			SYNTAX DisplayString
			MAX-ACCESS read-write
			STATUS current
			DESCRIPTION
				"
				Values:
				disabled
				optional
				mandatory
				
				XPath: /wing-config/wlan[name=key1]/pmf_mode"
			DEFVAL { "disabled" }
			::= { wingCfgWlanEntry 21 }

		
		-- 1.3.6.1.4.1.1916.2.131.50.1.3.4.1.1.22
		wingCfgWlanPmfSaQueryTimeout OBJECT-TYPE
			SYNTAX Unsigned32 (100..1000)
			UNITS "milliseconds"
			MAX-ACCESS read-write
			STATUS current
			DESCRIPTION
				"Timeout when waiting for a response to a Security Association
				(SA) Query before resending it.
				
				XPath: /wing-config/wlan[name=key1]/pmf_sa_query_timeout"
			DEFVAL { 201 }
			::= { wingCfgWlanEntry 22 }

		
		-- 1.3.6.1.4.1.1916.2.131.50.1.3.4.1.1.23
		wingCfgWlanPmfSaQueryAttempts OBJECT-TYPE
			SYNTAX Unsigned32 (1..10)
			MAX-ACCESS read-write
			STATUS current
			DESCRIPTION
				"Number of times a Security Association (SA) Query message
				is tried.
				
				XPath: /wing-config/wlan[name=key1]/pmf_sa_query_attempts"
			DEFVAL { 5 }
			::= { wingCfgWlanEntry 23 }

		
		-- 1.3.6.1.4.1.1916.2.131.50.1.3.4.1.1.24
		wingCfgWlanWpaWpa2Psk OBJECT-TYPE
			SYNTAX DisplayString (SIZE (8..64))
			MAX-ACCESS read-write
			STATUS current
			DESCRIPTION
				"
				
				XPath: /wing-config/wlan[name=key1]/wpa_wpa2_psk"
			::= { wingCfgWlanEntry 24 }

		
		-- 1.3.6.1.4.1.1916.2.131.50.1.3.4.1.1.25
		wingCfgWlanWpaWpa2ExcludeWpa2Tkip OBJECT-TYPE
			SYNTAX TruthValue
			MAX-ACCESS read-write
			STATUS current
			DESCRIPTION
				"Exclude the WPA2 version of TKIP and support only WPA-TKIP.
				
				XPath: /wing-config/wlan[name=key1]/wpa_wpa2_exclude_wpa2_tkip"
			DEFVAL { false }
			::= { wingCfgWlanEntry 25 }

		
		-- 1.3.6.1.4.1.1916.2.131.50.1.3.4.1.1.26
		wingCfgWlanWpaWpa2KeyRotationUnicast OBJECT-TYPE
			SYNTAX Unsigned32 (30..86400)
			UNITS "seconds"
			MAX-ACCESS read-write
			STATUS current
			DESCRIPTION
				"
				
				XPath: /wing-config/wlan[name=key1]/wpa_wpa2_key_rotation_unicast"
			::= { wingCfgWlanEntry 26 }

		
		-- 1.3.6.1.4.1.1916.2.131.50.1.3.4.1.1.27
		wingCfgWlanWpaWpa2KeyRotationBroadcast OBJECT-TYPE
			SYNTAX Unsigned32 (30..86400)
			UNITS "seconds"
			MAX-ACCESS read-write
			STATUS current
			DESCRIPTION
				"
				
				XPath: /wing-config/wlan[name=key1]/wpa_wpa2_key_rotation_broadcast"
			::= { wingCfgWlanEntry 27 }

		
		-- 1.3.6.1.4.1.1916.2.131.50.1.3.4.1.1.28
		wingCfgWlanWpaWpa2PmkCaching OBJECT-TYPE
			SYNTAX TruthValue
			MAX-ACCESS read-write
			STATUS current
			DESCRIPTION
				"Enable the user of cached pairwise master keys (fast roaming
				with 802.1X EAP).
				
				XPath: /wing-config/wlan[name=key1]/wpa_wpa2_pmk_caching"
			DEFVAL { true }
			::= { wingCfgWlanEntry 28 }

		
		-- 1.3.6.1.4.1.1916.2.131.50.1.3.4.1.1.29
		wingCfgWlanWpaWpa2OpmkCaching OBJECT-TYPE
			SYNTAX TruthValue
			MAX-ACCESS read-write
			STATUS current
			DESCRIPTION
				"Enable the use of Opportunistic Key Caching (same PMK across
				APs for fast roaming with 802.1X EAP).
				
				XPath: /wing-config/wlan[name=key1]/wpa_wpa2_opmk_caching"
			DEFVAL { true }
			::= { wingCfgWlanEntry 29 }

		
		-- 1.3.6.1.4.1.1916.2.131.50.1.3.4.1.1.30
		wingCfgWlanWpaWpa2Preauth OBJECT-TYPE
			SYNTAX TruthValue
			MAX-ACCESS read-write
			STATUS current
			DESCRIPTION
				"Enable the use of preauthentication (802.11i fast roaming).
				
				XPath: /wing-config/wlan[name=key1]/wpa_wpa2_preauthentication"
			DEFVAL { true }
			::= { wingCfgWlanEntry 30 }

		
		-- 1.3.6.1.4.1.1916.2.131.50.1.3.4.1.1.31
		wingCfgWlanWpaWpa2TkipCntrmeasHoldTime OBJECT-TYPE
			SYNTAX Unsigned32 (0..65535)
			UNITS "seconds"
			MAX-ACCESS read-write
			STATUS current
			DESCRIPTION
				"The amount of time for which a WLAN is disabled when
				TKIP countermeasures are invoked.
				
				XPath: /wing-config/wlan[name=key1]/wpa_wpa2_tkip_cntrmeas_hold_time"
			DEFVAL { 60 }
			::= { wingCfgWlanEntry 31 }

		
		-- 1.3.6.1.4.1.1916.2.131.50.1.3.4.1.1.32
		wingCfgWlanWep64TransmitKey OBJECT-TYPE
			SYNTAX Unsigned32 (1..4)
			MAX-ACCESS read-write
			STATUS current
			DESCRIPTION
				"
				
				XPath: /wing-config/wlan[name=key1]/wep64_transmit_key"
			DEFVAL { 1 }
			::= { wingCfgWlanEntry 32 }

		
		-- 1.3.6.1.4.1.1916.2.131.50.1.3.4.1.1.37
		wingCfgWlanWep128TransmitKey OBJECT-TYPE
			SYNTAX Unsigned32 (1..4)
			MAX-ACCESS read-write
			STATUS current
			DESCRIPTION
				"
				
				XPath: /wing-config/wlan[name=key1]/wep128_transmit_key"
			DEFVAL { 1 }
			::= { wingCfgWlanEntry 37 }

		
		-- 1.3.6.1.4.1.1916.2.131.50.1.3.4.1.1.42
		wingCfgWlanRadiusAssignedVlans OBJECT-TYPE
			SYNTAX TruthValue
			MAX-ACCESS read-write
			STATUS current
			DESCRIPTION
				"Allow users to be assigned to RADIUS server-specified VLANs.
				
				XPath: /wing-config/wlan[name=key1]/radius_assigned_vlans"
			DEFVAL { false }
			::= { wingCfgWlanEntry 42 }

		
		-- 1.3.6.1.4.1.1916.2.131.50.1.3.4.1.1.43
		wingCfgWlanRadiusDynamicAuthorization OBJECT-TYPE
			SYNTAX TruthValue
			MAX-ACCESS read-write
			STATUS current
			DESCRIPTION
				"Enable support for Disconnect and Change of Authorization
				(CoA) messages (RFC5176).
				
				XPath: /wing-config/wlan[name=key1]/radius_dynamic_authorization"
			DEFVAL { false }
			::= { wingCfgWlanEntry 43 }

		
		-- 1.3.6.1.4.1.1916.2.131.50.1.3.4.1.1.44
		wingCfgWlanAccountingRadius OBJECT-TYPE
			SYNTAX TruthValue
			MAX-ACCESS read-write
			STATUS current
			DESCRIPTION
				"802.11 rates supported on the radio for this wlan when
				it is mapped to a 2.4GHz mode radio.
				
				XPath: /wing-config/wlan[name=key1]/accounting_radius"
			DEFVAL { false }
			::= { wingCfgWlanEntry 44 }

		
		-- 1.3.6.1.4.1.1916.2.131.50.1.3.4.1.1.45
		wingCfgWlanMotoExtnMoveCmd OBJECT-TYPE
			SYNTAX TruthValue
			MAX-ACCESS read-write
			STATUS current
			DESCRIPTION
				"
				
				XPath: /wing-config/wlan[name=key1]/moto_extn_move_cmd"
			DEFVAL { false }
			::= { wingCfgWlanEntry 45 }

		
		-- 1.3.6.1.4.1.1916.2.131.50.1.3.4.1.1.46
		wingCfgWlanMotoExtnSmartScan OBJECT-TYPE
			SYNTAX TruthValue
			MAX-ACCESS read-write
			STATUS current
			DESCRIPTION
				"
				
				XPath: /wing-config/wlan[name=key1]/moto_extn_smart_scan"
			DEFVAL { false }
			::= { wingCfgWlanEntry 46 }

		
		-- 1.3.6.1.4.1.1916.2.131.50.1.3.4.1.1.47
		wingCfgWlanMotoExtnWmmLoadBalance OBJECT-TYPE
			SYNTAX TruthValue
			MAX-ACCESS read-write
			STATUS current
			DESCRIPTION
				"
				
				XPath: /wing-config/wlan[name=key1]/moto_extn_wmm_load_balance"
			DEFVAL { false }
			::= { wingCfgWlanEntry 47 }

		
		-- 1.3.6.1.4.1.1916.2.131.50.1.3.4.1.1.48
		wingCfgWlanMotoExtnSymbolLoadInfo OBJECT-TYPE
			SYNTAX TruthValue
			MAX-ACCESS read-write
			STATUS current
			DESCRIPTION
				"
				
				XPath: /wing-config/wlan[name=key1]/moto_extn_symbol_load_info"
			DEFVAL { true }
			::= { wingCfgWlanEntry 48 }

		
		-- 1.3.6.1.4.1.1916.2.131.50.1.3.4.1.1.49
		wingCfgWlanClientLoadBal OBJECT-TYPE
			SYNTAX TruthValue
			MAX-ACCESS read-write
			STATUS current
			DESCRIPTION
				"
				
				XPath: /wing-config/wlan[name=key1]/client_load_balancing"
			DEFVAL { true }
			::= { wingCfgWlanEntry 49 }

		
		-- 1.3.6.1.4.1.1916.2.131.50.1.3.4.1.1.50
		wingCfgWlanClientLoadBalSingleBandClients5ghz OBJECT-TYPE
			SYNTAX TruthValue
			MAX-ACCESS read-write
			STATUS current
			DESCRIPTION
				"
				
				XPath: /wing-config/wlan[name=key1]/client_load_balancing_single_band_clients_5ghz"
			DEFVAL { true }
			::= { wingCfgWlanEntry 50 }

		
		-- 1.3.6.1.4.1.1916.2.131.50.1.3.4.1.1.51
		wingCfgWlanClientLoadBalSingleBandClients24ghz OBJECT-TYPE
			SYNTAX TruthValue
			MAX-ACCESS read-write
			STATUS current
			DESCRIPTION
				"
				
				XPath: /wing-config/wlan[name=key1]/client_load_balancing_single_band_clients_2_4ghz"
			DEFVAL { true }
			::= { wingCfgWlanEntry 51 }

		
		-- 1.3.6.1.4.1.1916.2.131.50.1.3.4.1.1.52
		wingCfgWlanClientLoadBalMaxProbeReq24ghz OBJECT-TYPE
			SYNTAX Unsigned32 (0..10000)
			MAX-ACCESS read-write
			STATUS current
			DESCRIPTION
				"Number of persistent probe requests beyond which the client
				is allowed to associate
				
				XPath: /wing-config/wlan[name=key1]/client_load_balancing_max_probe_req_2_4ghz"
			DEFVAL { 48 }
			::= { wingCfgWlanEntry 52 }

		
		-- 1.3.6.1.4.1.1916.2.131.50.1.3.4.1.1.53
		wingCfgWlanClientLoadBalMaxProbeReq5ghz OBJECT-TYPE
			SYNTAX Unsigned32 (0..10000)
			MAX-ACCESS read-write
			STATUS current
			DESCRIPTION
				"Number of persistent probe requests beyond which the client
				is allowed to associate
				
				XPath: /wing-config/wlan[name=key1]/client_load_balancing_max_probe_req_5ghz"
			DEFVAL { 24 }
			::= { wingCfgWlanEntry 53 }

		
		-- 1.3.6.1.4.1.1916.2.131.50.1.3.4.1.1.54
		wingCfgWlanClientLoadBalProbeReqIntvl5ghz OBJECT-TYPE
			SYNTAX Unsigned32 (0..10000)
			UNITS "seconds"
			MAX-ACCESS read-write
			STATUS current
			DESCRIPTION
				"Interval within which we should receive a minimum number of
				probe requests to allow client association.
				
				XPath: /wing-config/wlan[name=key1]/client_load_balancing_probe_req_intvl_5ghz"
			DEFVAL { 24 }
			::= { wingCfgWlanEntry 54 }

		
		-- 1.3.6.1.4.1.1916.2.131.50.1.3.4.1.1.55
		wingCfgWlanClientLoadBalProbeReqIntvl24ghz OBJECT-TYPE
			SYNTAX Unsigned32 (0..10000)
			UNITS "seconds"
			MAX-ACCESS read-write
			STATUS current
			DESCRIPTION
				"Interval within which we should receive a minimum number of
				probe requests to allow client association.
				
				XPath: /wing-config/wlan[name=key1]/client_load_balancing_probe_req_intvl_2_4ghz"
			DEFVAL { 24 }
			::= { wingCfgWlanEntry 55 }

		
		-- 1.3.6.1.4.1.1916.2.131.50.1.3.4.1.1.56
		wingCfgWlanClientLoadBalBandDiscoveryIntvl OBJECT-TYPE
			SYNTAX Unsigned32 (0..10000)
			UNITS "seconds"
			MAX-ACCESS read-write
			STATUS current
			DESCRIPTION
				"Time to discover client's band capabilties.
				
				XPath: /wing-config/wlan[name=key1]/client_load_balancing_band_discovery_intvl"
			DEFVAL { 24 }
			::= { wingCfgWlanEntry 56 }

		
		-- 1.3.6.1.4.1.1916.2.131.50.1.3.4.1.1.57
		wingCfgWlanClientLoadBalCapabilityAgeoutTime OBJECT-TYPE
			SYNTAX Unsigned32 (0..10000)
			UNITS "seconds"
			MAX-ACCESS read-write
			STATUS current
			DESCRIPTION
				"Time to ageout a client's capabilties from internal tables.
				
				XPath: /wing-config/wlan[name=key1]/client_load_balancing_capability_ageout_time"
			DEFVAL { 24 }
			::= { wingCfgWlanEntry 57 }

		
		-- 1.3.6.1.4.1.1916.2.131.50.1.3.4.1.1.58
		wingCfgWlanQosPolicy OBJECT-TYPE
			SYNTAX WingIdentifier
			MAX-ACCESS read-write
			STATUS current
			DESCRIPTION
				"
				
				XPath: /wing-config/wlan[name=key1]/qos_policy"
			::= { wingCfgWlanEntry 58 }

		
		-- 1.3.6.1.4.1.1916.2.131.50.1.3.4.1.1.59
		wingCfgWlanAaaPolicy OBJECT-TYPE
			SYNTAX WingIdentifier
			MAX-ACCESS read-write
			STATUS current
			DESCRIPTION
				"
				
				XPath: /wing-config/wlan[name=key1]/aaa_policy"
			::= { wingCfgWlanEntry 59 }

		
		-- 1.3.6.1.4.1.1916.2.131.50.1.3.4.1.1.60
		wingCfgWlanCaptivePortal OBJECT-TYPE
			SYNTAX WingIdentifier
			MAX-ACCESS read-write
			STATUS current
			DESCRIPTION
				"
				
				XPath: /wing-config/wlan[name=key1]/captive_portal"
			::= { wingCfgWlanEntry 60 }

		
		-- 1.3.6.1.4.1.1916.2.131.50.1.3.4.1.1.61
		wingCfgWlanAssocAcl OBJECT-TYPE
			SYNTAX WingIdentifier
			MAX-ACCESS read-write
			STATUS current
			DESCRIPTION
				"
				
				XPath: /wing-config/wlan[name=key1]/assoc_acl"
			::= { wingCfgWlanEntry 61 }

		
		-- 1.3.6.1.4.1.1916.2.131.50.1.3.4.1.1.62
		wingCfgWlanIpInAcl OBJECT-TYPE
			SYNTAX WingIdentifier
			MAX-ACCESS read-write
			STATUS current
			DESCRIPTION
				"
				
				XPath: /wing-config/wlan[name=key1]/ip_in_acl"
			::= { wingCfgWlanEntry 62 }

		
		-- 1.3.6.1.4.1.1916.2.131.50.1.3.4.1.1.63
		wingCfgWlanMacInAcl OBJECT-TYPE
			SYNTAX WingIdentifier
			MAX-ACCESS read-write
			STATUS current
			DESCRIPTION
				"
				
				XPath: /wing-config/wlan[name=key1]/mac_in_acl"
			::= { wingCfgWlanEntry 63 }

		
		-- 1.3.6.1.4.1.1916.2.131.50.1.3.4.1.1.64
		wingCfgWlanIpOutAcl OBJECT-TYPE
			SYNTAX WingIdentifier
			MAX-ACCESS read-write
			STATUS current
			DESCRIPTION
				"
				
				XPath: /wing-config/wlan[name=key1]/ip_out_acl"
			::= { wingCfgWlanEntry 64 }

		
		-- 1.3.6.1.4.1.1916.2.131.50.1.3.4.1.1.65
		wingCfgWlanMacOutAcl OBJECT-TYPE
			SYNTAX WingIdentifier
			MAX-ACCESS read-write
			STATUS current
			DESCRIPTION
				"
				
				XPath: /wing-config/wlan[name=key1]/mac_out_acl"
			::= { wingCfgWlanEntry 65 }

		
		-- 1.3.6.1.4.1.1916.2.131.50.1.3.4.1.1.66
		wingCfgWlanArpTrust OBJECT-TYPE
			SYNTAX TruthValue
			MAX-ACCESS read-write
			STATUS current
			DESCRIPTION
				"Trust ARP requests on WLANs.
				
				XPath: /wing-config/wlan[name=key1]/arp_trust"
			DEFVAL { false }
			::= { wingCfgWlanEntry 66 }

		
		-- 1.3.6.1.4.1.1916.2.131.50.1.3.4.1.1.67
		wingCfgWlanDhcpTrust OBJECT-TYPE
			SYNTAX TruthValue
			MAX-ACCESS read-write
			STATUS current
			DESCRIPTION
				"Trust DHCP responses on WLANs.
				
				XPath: /wing-config/wlan[name=key1]/dhcp_trust"
			DEFVAL { false }
			::= { wingCfgWlanEntry 67 }

		
		-- 1.3.6.1.4.1.1916.2.131.50.1.3.4.1.1.68
		wingCfgWlanArpHeaderMismatchValidation OBJECT-TYPE
			SYNTAX TruthValue
			MAX-ACCESS read-write
			STATUS current
			DESCRIPTION
				"Check mismatch for source MAC in ARP header and ethernet header.
				
				XPath: /wing-config/wlan[name=key1]/arp_header_mismatch_validation"
			DEFVAL { true }
			::= { wingCfgWlanEntry 68 }

		
		-- 1.3.6.1.4.1.1916.2.131.50.1.3.4.1.1.69
		wingCfgWlanServiceAllowHtOnly OBJECT-TYPE
			SYNTAX TruthValue
			MAX-ACCESS read-write
			STATUS current
			DESCRIPTION
				"
				
				XPath: /wing-config/wlan[name=key1]/service_allow_ht_only"
			DEFVAL { false }
			::= { wingCfgWlanEntry 69 }

		
		-- 1.3.6.1.4.1.1916.2.131.50.1.3.4.1.1.70
		wingCfgWlanEnforceDhcp OBJECT-TYPE
			SYNTAX TruthValue
			MAX-ACCESS read-write
			STATUS current
			DESCRIPTION
				"
				
				XPath: /wing-config/wlan[name=key1]/enforce_dhcp"
			DEFVAL { false }
			::= { wingCfgWlanEntry 70 }

		
		-- 1.3.6.1.4.1.1916.2.131.50.1.3.4.1.1.71
		wingCfgWlanProxyArpMode OBJECT-TYPE
			SYNTAX DisplayString
			MAX-ACCESS read-write
			STATUS current
			DESCRIPTION
				"
				Values:
				strict
				dynamic
				
				XPath: /wing-config/wlan[name=key1]/proxy_arp_mode"
			DEFVAL { "dynamic" }
			::= { wingCfgWlanEntry 71 }

		
		-- 1.3.6.1.4.1.1916.2.131.50.1.3.4.1.1.72
		wingCfgWlanBroadcastDhcpValidateOffer OBJECT-TYPE
			SYNTAX TruthValue
			MAX-ACCESS read-write
			STATUS current
			DESCRIPTION
				"
				
				XPath: /wing-config/wlan[name=key1]/broadcast_dhcp_validate_offer"
			DEFVAL { false }
			::= { wingCfgWlanEntry 72 }

		
		-- 1.3.6.1.4.1.1916.2.131.50.1.3.4.2
		wingCfgWlanVlanTable OBJECT-TYPE
			SYNTAX SEQUENCE OF WingCfgWlanVlanEntry
			MAX-ACCESS not-accessible
			STATUS current
			DESCRIPTION
				"Configure the VLAN where traffic from this WLAN is mapped.
				
				/wing-config/wlan/vlans"
			::= { wingCfgWlan 2 }

		
		-- 1.3.6.1.4.1.1916.2.131.50.1.3.4.2.1
		wingCfgWlanVlanEntry OBJECT-TYPE
			SYNTAX WingCfgWlanVlanEntry
			MAX-ACCESS not-accessible
			STATUS current
			DESCRIPTION
				"An entry in the table."
			INDEX { wingCfgWlanName, wingCfgWlanVlanId }
			::= { wingCfgWlanVlanTable 1 }

		
		WingCfgWlanVlanEntry ::=
			SEQUENCE { 
				wingCfgWlanVlanId
					Unsigned32,
				wingCfgWlanVlanLimit
					Unsigned32
			 }

		-- 1.3.6.1.4.1.1916.2.131.50.1.3.4.2.1.1
		wingCfgWlanVlanId OBJECT-TYPE
			SYNTAX Unsigned32 (1..4094)
			MAX-ACCESS read-only
			STATUS current
			DESCRIPTION
				"The vlan-id.
				
				XPath: /wing-config/wlan[name=key1]/vlans[vlan=key2]/vlan"
			::= { wingCfgWlanVlanEntry 1 }

		
		-- 1.3.6.1.4.1.1916.2.131.50.1.3.4.2.1.3
		wingCfgWlanVlanLimit OBJECT-TYPE
			SYNTAX Unsigned32 (0..8192)
			MAX-ACCESS read-write
			STATUS current
			DESCRIPTION
				"Limit the number of users on this VLAN.
				
				XPath: /wing-config/wlan[name=key1]/vlans[vlan=key2]/limit"
			::= { wingCfgWlanVlanEntry 3 }

		
		-- 1.3.6.1.4.1.1916.2.131.50.1.3.4.3
		wingCfgWlanKerberosTable OBJECT-TYPE
			SYNTAX SEQUENCE OF WingCfgWlanKerberosEntry
			MAX-ACCESS not-accessible
			STATUS current
			DESCRIPTION
				"
				
				/wing-config/wlan/kerberos"
			::= { wingCfgWlan 3 }

		
		-- 1.3.6.1.4.1.1916.2.131.50.1.3.4.3.1
		wingCfgWlanKerberosEntry OBJECT-TYPE
			SYNTAX WingCfgWlanKerberosEntry
			MAX-ACCESS not-accessible
			STATUS current
			DESCRIPTION
				"An entry in the table."
			INDEX { wingCfgWlanName }
			::= { wingCfgWlanKerberosTable 1 }

		
		WingCfgWlanKerberosEntry ::=
			SEQUENCE { 
				wingCfgWlanKerberosRealm
					DisplayString,
				wingCfgWlanKerberosTimeout
					Unsigned32,
				wingCfgWlanKerberosPassword
					DisplayString,
				wingCfgWlanKerberosPrimaryServer
					DisplayString,
				wingCfgWlanKerberosPrimaryServerPort
					Unsigned32,
				wingCfgWlanKerberosSecondaryServer
					DisplayString,
				wingCfgWlanKerberosSecondaryServerPort
					Unsigned32
			 }

		-- 1.3.6.1.4.1.1916.2.131.50.1.3.4.3.1.1
		wingCfgWlanKerberosRealm OBJECT-TYPE
			SYNTAX DisplayString (SIZE (0..127))
			MAX-ACCESS read-write
			STATUS current
			DESCRIPTION
				"
				
				XPath: /wing-config/wlan[name=key1]/kerberos/realm"
			::= { wingCfgWlanKerberosEntry 1 }

		
		-- 1.3.6.1.4.1.1916.2.131.50.1.3.4.3.1.2
		wingCfgWlanKerberosTimeout OBJECT-TYPE
			SYNTAX Unsigned32 (1..10)
			UNITS "seconds"
			MAX-ACCESS read-write
			STATUS current
			DESCRIPTION
				"
				
				XPath: /wing-config/wlan[name=key1]/kerberos/timeout"
			DEFVAL { 5 }
			::= { wingCfgWlanKerberosEntry 2 }

		
		-- 1.3.6.1.4.1.1916.2.131.50.1.3.4.3.1.3
		wingCfgWlanKerberosPassword OBJECT-TYPE
			SYNTAX DisplayString (SIZE (0..127))
			MAX-ACCESS read-write
			STATUS current
			DESCRIPTION
				"
				
				XPath: /wing-config/wlan[name=key1]/kerberos/password"
			::= { wingCfgWlanKerberosEntry 3 }

		
		-- 1.3.6.1.4.1.1916.2.131.50.1.3.4.3.1.4
		wingCfgWlanKerberosPrimaryServer OBJECT-TYPE
			SYNTAX DisplayString
			MAX-ACCESS read-write
			STATUS current
			DESCRIPTION
				"
				
				XPath: /wing-config/wlan[name=key1]/kerberos/primary_server"
			::= { wingCfgWlanKerberosEntry 4 }

		
		-- 1.3.6.1.4.1.1916.2.131.50.1.3.4.3.1.5
		wingCfgWlanKerberosPrimaryServerPort OBJECT-TYPE
			SYNTAX Unsigned32 (1..65535)
			MAX-ACCESS read-write
			STATUS current
			DESCRIPTION
				"
				
				XPath: /wing-config/wlan[name=key1]/kerberos/primary_server_port"
			DEFVAL { 88 }
			::= { wingCfgWlanKerberosEntry 5 }

		
		-- 1.3.6.1.4.1.1916.2.131.50.1.3.4.3.1.6
		wingCfgWlanKerberosSecondaryServer OBJECT-TYPE
			SYNTAX DisplayString
			MAX-ACCESS read-write
			STATUS current
			DESCRIPTION
				"
				
				XPath: /wing-config/wlan[name=key1]/kerberos/secondary_server"
			::= { wingCfgWlanKerberosEntry 6 }

		
		-- 1.3.6.1.4.1.1916.2.131.50.1.3.4.3.1.7
		wingCfgWlanKerberosSecondaryServerPort OBJECT-TYPE
			SYNTAX Unsigned32 (1..65535)
			MAX-ACCESS read-write
			STATUS current
			DESCRIPTION
				"
				
				XPath: /wing-config/wlan[name=key1]/kerberos/secondary_server_port"
			DEFVAL { 88 }
			::= { wingCfgWlanKerberosEntry 7 }

		
		-- 1.3.6.1.4.1.1916.2.131.50.1.3.4.4
		wingCfgWlanAcctSyslogTable OBJECT-TYPE
			SYNTAX SEQUENCE OF WingCfgWlanAcctSyslogEntry
			MAX-ACCESS not-accessible
			STATUS current
			DESCRIPTION
				"
				
				/wing-config/wlan/accounting_syslog"
			::= { wingCfgWlan 4 }

		
		-- 1.3.6.1.4.1.1916.2.131.50.1.3.4.4.1
		wingCfgWlanAcctSyslogEntry OBJECT-TYPE
			SYNTAX WingCfgWlanAcctSyslogEntry
			MAX-ACCESS not-accessible
			STATUS current
			DESCRIPTION
				"An entry in the table."
			INDEX { wingCfgWlanName }
			::= { wingCfgWlanAcctSyslogTable 1 }

		
		WingCfgWlanAcctSyslogEntry ::=
			SEQUENCE { 
				wingCfgWlanAcctSyslogEnable
					TruthValue,
				wingCfgWlanAcctSyslogHost
					DisplayString,
				wingCfgWlanAcctSyslogPort
					Unsigned32
			 }

		-- 1.3.6.1.4.1.1916.2.131.50.1.3.4.4.1.1
		wingCfgWlanAcctSyslogEnable OBJECT-TYPE
			SYNTAX TruthValue
			MAX-ACCESS read-write
			STATUS current
			DESCRIPTION
				"
				
				XPath: /wing-config/wlan[name=key1]/accounting_syslog/enable"
			DEFVAL { false }
			::= { wingCfgWlanAcctSyslogEntry 1 }

		
		-- 1.3.6.1.4.1.1916.2.131.50.1.3.4.4.1.2
		wingCfgWlanAcctSyslogHost OBJECT-TYPE
			SYNTAX DisplayString
			MAX-ACCESS read-write
			STATUS current
			DESCRIPTION
				"
				
				XPath: /wing-config/wlan[name=key1]/accounting_syslog/host"
			::= { wingCfgWlanAcctSyslogEntry 2 }

		
		-- 1.3.6.1.4.1.1916.2.131.50.1.3.4.4.1.3
		wingCfgWlanAcctSyslogPort OBJECT-TYPE
			SYNTAX Unsigned32
			MAX-ACCESS read-write
			STATUS current
			DESCRIPTION
				"
				
				XPath: /wing-config/wlan[name=key1]/accounting_syslog/port"
			DEFVAL { 514 }
			::= { wingCfgWlanAcctSyslogEntry 3 }

		
		-- 1.3.6.1.4.1.1916.2.131.50.1.3.4.5
		wingCfgWlanClientDenyLimitTable OBJECT-TYPE
			SYNTAX SEQUENCE OF WingCfgWlanClientDenyLimitEntry
			MAX-ACCESS not-accessible
			STATUS current
			DESCRIPTION
				"
				
				/wing-config/wlan/mu_deny_limit"
			::= { wingCfgWlan 5 }

		
		-- 1.3.6.1.4.1.1916.2.131.50.1.3.4.5.1
		wingCfgWlanClientDenyLimitEntry OBJECT-TYPE
			SYNTAX WingCfgWlanClientDenyLimitEntry
			MAX-ACCESS not-accessible
			STATUS current
			DESCRIPTION
				"An entry in the table."
			INDEX { wingCfgWlanName }
			::= { wingCfgWlanClientDenyLimitTable 1 }

		
		WingCfgWlanClientDenyLimitEntry ::=
			SEQUENCE { 
				wingCfgWlanClientDenyLimitThresholdRate
					Unsigned32,
				wingCfgWlanClientDenyLimitAction
					DisplayString,
				wingCfgWlanClientDenyLimitBlacklistAgeout
					Unsigned32
			 }

		-- 1.3.6.1.4.1.1916.2.131.50.1.3.4.5.1.1
		wingCfgWlanClientDenyLimitThresholdRate OBJECT-TYPE
			SYNTAX Unsigned32 (1..1000000)
			UNITS "packets"
			MAX-ACCESS read-write
			STATUS current
			DESCRIPTION
				"
				
				XPath: /wing-config/wlan[name=key1]/mu_deny_limit/threshold_rate"
			::= { wingCfgWlanClientDenyLimitEntry 1 }

		
		-- 1.3.6.1.4.1.1916.2.131.50.1.3.4.5.1.2
		wingCfgWlanClientDenyLimitAction OBJECT-TYPE
			SYNTAX DisplayString
			MAX-ACCESS read-write
			STATUS current
			DESCRIPTION
				"
				Values:
				disassociate
				blacklist
				none
				
				XPath: /wing-config/wlan[name=key1]/mu_deny_limit/action"
			DEFVAL { "none" }
			::= { wingCfgWlanClientDenyLimitEntry 2 }

		
		-- 1.3.6.1.4.1.1916.2.131.50.1.3.4.5.1.3
		wingCfgWlanClientDenyLimitBlacklistAgeout OBJECT-TYPE
			SYNTAX Unsigned32 (0..86400)
			UNITS "seconds"
			MAX-ACCESS read-write
			STATUS current
			DESCRIPTION
				"Specifies the duration for which the mobile unit causing
				this event is black listed.
				
				XPath: /wing-config/wlan[name=key1]/mu_deny_limit/blacklist_ageout"
			::= { wingCfgWlanClientDenyLimitEntry 3 }

		
-- /wing-config/wlan_qos
		-- 1.3.6.1.4.1.1916.2.131.50.1.3.5
		wingCfgWlanQos OBJECT IDENTIFIER ::= { wingConfig 5 }

		
		-- 1.3.6.1.4.1.1916.2.131.50.1.3.5.1
		wingCfgWlanQosTable OBJECT-TYPE
			SYNTAX SEQUENCE OF WingCfgWlanQosEntry
			MAX-ACCESS not-accessible
			STATUS current
			DESCRIPTION
				"Configuration parameters of a wireless LAN QoS profile.
				
				/wing-config/wlan_qos"
			::= { wingCfgWlanQos 1 }

		
		-- 1.3.6.1.4.1.1916.2.131.50.1.3.5.1.1
		wingCfgWlanQosEntry OBJECT-TYPE
			SYNTAX WingCfgWlanQosEntry
			MAX-ACCESS not-accessible
			STATUS current
			DESCRIPTION
				"An entry in the table."
			INDEX { wingCfgWlanQosName }
			::= { wingCfgWlanQosTable 1 }

		
		WingCfgWlanQosEntry ::=
			SEQUENCE { 
				wingCfgWlanQosName
					WingIdentifier,
				wingCfgWlanQosClassification
					DisplayString,
				wingCfgWlanQosNonWmmClassification
					DisplayString,
				wingCfgWlanQosMulticastMaskPrimary
					DisplayString,
				wingCfgWlanQosMulticastMaskSecondary
					DisplayString,
				wingCfgWlanQosMulticastMaskAc
					DisplayString,
				wingCfgWlanQosVoicePrioritization
					TruthValue,
				wingCfgWlanQosSvpPrioritization
					TruthValue,
				wingCfgWlanQosWmmPowerSave
					TruthValue,
				wingCfgWlanQosWmmQbssLoadElement
					TruthValue,
				wingCfgWlanQosWmmBestEffortTxopLimit
					Unsigned32,
				wingCfgWlanQosWmmBestEffortAifsn
					Unsigned32,
				wingCfgWlanQosWmmBestEffortCwMin
					Unsigned32,
				wingCfgWlanQosWmmBestEffortCwMax
					Unsigned32,
				wingCfgWlanQosWmmBackgroundTxopLimit
					Unsigned32,
				wingCfgWlanQosWmmBackgroundAifsn
					Unsigned32,
				wingCfgWlanQosWmmBackgroundCwMin
					Unsigned32,
				wingCfgWlanQosWmmBackgroundCwMax
					Unsigned32,
				wingCfgWlanQosWmmVideoTxopLimit
					Unsigned32,
				wingCfgWlanQosWmmVideoAifsn
					Unsigned32,
				wingCfgWlanQosWmmVideoCwMin
					Unsigned32,
				wingCfgWlanQosWmmVideoCwMax
					Unsigned32,
				wingCfgWlanQosWmmVoiceTxopLimit
					Unsigned32,
				wingCfgWlanQosWmmVoiceAifsn
					Unsigned32,
				wingCfgWlanQosWmmVoiceCwMin
					Unsigned32,
				wingCfgWlanQosWmmVoiceCwMax
					Unsigned32,
				wingCfgWlanQosWlanRlDownEnable
					TruthValue,
				wingCfgWlanQosWlanRlDownRate
					Unsigned32,
				wingCfgWlanQosWlanRlDownBurstSize
					Unsigned32,
				wingCfgWlanQosWlanRlDownThreshBackground
					Unsigned32,
				wingCfgWlanQosWlanRlDownThreshBestEffort
					Unsigned32,
				wingCfgWlanQosWlanRlDownThreshVoice
					Unsigned32,
				wingCfgWlanQosWlanRlDownThreshVideo
					Unsigned32,
				wingCfgWlanQosWlanRlUpEnable
					TruthValue,
				wingCfgWlanQosWlanRlUpRate
					Unsigned32,
				wingCfgWlanQosWlanRlUpBurstSize
					Unsigned32,
				wingCfgWlanQosWlanRlUpThreshBackground
					Unsigned32,
				wingCfgWlanQosWlanRlUpThreshBestEffort
					Unsigned32,
				wingCfgWlanQosWlanRlUpThreshVoice
					Unsigned32,
				wingCfgWlanQosWlanRlUpThreshVideo
					Unsigned32,
				wingCfgWlanQosMuRlDownEnable
					TruthValue,
				wingCfgWlanQosMuRlDownRate
					Unsigned32,
				wingCfgWlanQosMuRlDownBurstSize
					Unsigned32,
				wingCfgWlanQosMuRlDownThreshBackground
					Unsigned32,
				wingCfgWlanQosMuRlDownThreshBestEffort
					Unsigned32,
				wingCfgWlanQosMuRlDownThreshVoice
					Unsigned32,
				wingCfgWlanQosMuRlDownThreshVideo
					Unsigned32,
				wingCfgWlanQosMuRlUpEnable
					TruthValue,
				wingCfgWlanQosMuRlUpRate
					Unsigned32,
				wingCfgWlanQosMuRlUpBurstSize
					Unsigned32,
				wingCfgWlanQosMuRlUpThreshBackground
					Unsigned32,
				wingCfgWlanQosMuRlUpThreshBestEffort
					Unsigned32,
				wingCfgWlanQosMuRlUpThreshVoice
					Unsigned32,
				wingCfgWlanQosMuRlUpThreshVideo
					Unsigned32,
				wingCfgWlanQosQosTrustDscp
					TruthValue,
				wingCfgWlanQosQosTrustWmm
					TruthValue
			 }

		-- 1.3.6.1.4.1.1916.2.131.50.1.3.5.1.1.1
		wingCfgWlanQosName OBJECT-TYPE
			SYNTAX WingIdentifier
			MAX-ACCESS read-only
			STATUS current
			DESCRIPTION
				"
				
				XPath: /wing-config/wlan_qos[name=key1]/name"
			::= { wingCfgWlanQosEntry 1 }

		
		-- 1.3.6.1.4.1.1916.2.131.50.1.3.5.1.1.3
		wingCfgWlanQosClassification OBJECT-TYPE
			SYNTAX DisplayString
			MAX-ACCESS read-write
			STATUS current
			DESCRIPTION
				"How traffic on this WLAN will be classified (relative
				prioritization on the radio).
				
				Values:
				wmm
				voice
				video
				normal
				low
				
				XPath: /wing-config/wlan_qos[name=key1]/classification"
			DEFVAL { "wmm" }
			::= { wingCfgWlanQosEntry 3 }

		
		-- 1.3.6.1.4.1.1916.2.131.50.1.3.5.1.1.4
		wingCfgWlanQosNonWmmClassification OBJECT-TYPE
			SYNTAX DisplayString
			MAX-ACCESS read-write
			STATUS current
			DESCRIPTION
				"Configure how non-wmm client traffic on this WLAN will be
				classified, if the wlan classification is wmm.
				
				Values:
				voice
				video
				normal
				low
				
				XPath: /wing-config/wlan_qos[name=key1]/non_wmm_classification"
			DEFVAL { "normal" }
			::= { wingCfgWlanQosEntry 4 }

		
		-- 1.3.6.1.4.1.1916.2.131.50.1.3.5.1.1.5
		wingCfgWlanQosMulticastMaskPrimary OBJECT-TYPE
			SYNTAX DisplayString (SIZE (35))
			MAX-ACCESS read-write
			STATUS current
			DESCRIPTION
				"Egress multicast mask (matching packets will not be queued
				until DTIM).
				
				XPath: /wing-config/wlan_qos[name=key1]/multicast_mask_primary"
			DEFVAL { "00-00-00-00-00-00/FF-FF-FF-FF-FF-FF" }
			::= { wingCfgWlanQosEntry 5 }

		
		-- 1.3.6.1.4.1.1916.2.131.50.1.3.5.1.1.6
		wingCfgWlanQosMulticastMaskSecondary OBJECT-TYPE
			SYNTAX DisplayString (SIZE (35))
			MAX-ACCESS read-write
			STATUS current
			DESCRIPTION
				"Egress multicast mask (matching packets will not be queued
				until DTIM).
				
				XPath: /wing-config/wlan_qos[name=key1]/multicast_mask_secondary"
			DEFVAL { "00-00-00-00-00-00/FF-FF-FF-FF-FF-FF" }
			::= { wingCfgWlanQosEntry 6 }

		
		-- 1.3.6.1.4.1.1916.2.131.50.1.3.5.1.1.7
		wingCfgWlanQosMulticastMaskAc OBJECT-TYPE
			SYNTAX DisplayString
			MAX-ACCESS read-write
			STATUS current
			DESCRIPTION
				"How traffic that matches the multicast masks will be
				classified (relative prioritization on the radio).
				
				Values:
				voice
				video
				normal
				low
				default
				
				XPath: /wing-config/wlan_qos[name=key1]/multicast_mask_ac"
			DEFVAL { "normal" }
			::= { wingCfgWlanQosEntry 7 }

		
		-- 1.3.6.1.4.1.1916.2.131.50.1.3.5.1.1.8
		wingCfgWlanQosVoicePrioritization OBJECT-TYPE
			SYNTAX TruthValue
			MAX-ACCESS read-write
			STATUS current
			DESCRIPTION
				"Prioritize voice Wireless Clients over other Wireless Clients
				(for non-WMM clients).
				
				XPath: /wing-config/wlan_qos[name=key1]/voice_prioritization"
			DEFVAL { false }
			::= { wingCfgWlanQosEntry 8 }

		
		-- 1.3.6.1.4.1.1916.2.131.50.1.3.5.1.1.9
		wingCfgWlanQosSvpPrioritization OBJECT-TYPE
			SYNTAX TruthValue
			MAX-ACCESS read-write
			STATUS current
			DESCRIPTION
				"Enable Spectralink voice protocol support on this WLAN.
				
				XPath: /wing-config/wlan_qos[name=key1]/svp_prioritization"
			DEFVAL { false }
			::= { wingCfgWlanQosEntry 9 }

		
		-- 1.3.6.1.4.1.1916.2.131.50.1.3.5.1.1.10
		wingCfgWlanQosWmmPowerSave OBJECT-TYPE
			SYNTAX TruthValue
			MAX-ACCESS read-write
			STATUS current
			DESCRIPTION
				"Enable support for WMM Power Save (U-APSD).
				
				XPath: /wing-config/wlan_qos[name=key1]/wmm_power_save"
			DEFVAL { true }
			::= { wingCfgWlanQosEntry 10 }

		
		-- 1.3.6.1.4.1.1916.2.131.50.1.3.5.1.1.11
		wingCfgWlanQosWmmQbssLoadElement OBJECT-TYPE
			SYNTAX TruthValue
			MAX-ACCESS read-write
			STATUS current
			DESCRIPTION
				"Enable support for WMM QBSS Load Information Element in
				beacons and probe responses packets
				
				XPath: /wing-config/wlan_qos[name=key1]/wmm_qbss_load_element"
			DEFVAL { true }
			::= { wingCfgWlanQosEntry 11 }

		
		-- 1.3.6.1.4.1.1916.2.131.50.1.3.5.1.1.12
		wingCfgWlanQosWmmBestEffortTxopLimit OBJECT-TYPE
			SYNTAX Unsigned32 (0..65535)
			MAX-ACCESS read-write
			STATUS current
			DESCRIPTION
				"
				
				XPath: /wing-config/wlan_qos[name=key1]/wmm_best_effort_txop_limit"
			DEFVAL { 0 }
			::= { wingCfgWlanQosEntry 12 }

		
		-- 1.3.6.1.4.1.1916.2.131.50.1.3.5.1.1.13
		wingCfgWlanQosWmmBestEffortAifsn OBJECT-TYPE
			SYNTAX Unsigned32 (2..15)
			MAX-ACCESS read-write
			STATUS current
			DESCRIPTION
				"
				
				XPath: /wing-config/wlan_qos[name=key1]/wmm_best_effort_aifsn"
			DEFVAL { 3 }
			::= { wingCfgWlanQosEntry 13 }

		
		-- 1.3.6.1.4.1.1916.2.131.50.1.3.5.1.1.14
		wingCfgWlanQosWmmBestEffortCwMin OBJECT-TYPE
			SYNTAX Unsigned32 (0..15)
			MAX-ACCESS read-write
			STATUS current
			DESCRIPTION
				"
				
				XPath: /wing-config/wlan_qos[name=key1]/wmm_best_effort_cw_min"
			DEFVAL { 4 }
			::= { wingCfgWlanQosEntry 14 }

		
		-- 1.3.6.1.4.1.1916.2.131.50.1.3.5.1.1.15
		wingCfgWlanQosWmmBestEffortCwMax OBJECT-TYPE
			SYNTAX Unsigned32 (0..15)
			MAX-ACCESS read-write
			STATUS current
			DESCRIPTION
				"
				
				XPath: /wing-config/wlan_qos[name=key1]/wmm_best_effort_cw_max"
			DEFVAL { 10 }
			::= { wingCfgWlanQosEntry 15 }

		
		-- 1.3.6.1.4.1.1916.2.131.50.1.3.5.1.1.16
		wingCfgWlanQosWmmBackgroundTxopLimit OBJECT-TYPE
			SYNTAX Unsigned32 (0..65535)
			MAX-ACCESS read-write
			STATUS current
			DESCRIPTION
				"
				
				XPath: /wing-config/wlan_qos[name=key1]/wmm_background_txop_limit"
			DEFVAL { 0 }
			::= { wingCfgWlanQosEntry 16 }

		
		-- 1.3.6.1.4.1.1916.2.131.50.1.3.5.1.1.17
		wingCfgWlanQosWmmBackgroundAifsn OBJECT-TYPE
			SYNTAX Unsigned32 (2..15)
			MAX-ACCESS read-write
			STATUS current
			DESCRIPTION
				"
				
				XPath: /wing-config/wlan_qos[name=key1]/wmm_background_aifsn"
			DEFVAL { 7 }
			::= { wingCfgWlanQosEntry 17 }

		
		-- 1.3.6.1.4.1.1916.2.131.50.1.3.5.1.1.18
		wingCfgWlanQosWmmBackgroundCwMin OBJECT-TYPE
			SYNTAX Unsigned32 (0..15)
			MAX-ACCESS read-write
			STATUS current
			DESCRIPTION
				"
				
				XPath: /wing-config/wlan_qos[name=key1]/wmm_background_cw_min"
			DEFVAL { 4 }
			::= { wingCfgWlanQosEntry 18 }

		
		-- 1.3.6.1.4.1.1916.2.131.50.1.3.5.1.1.19
		wingCfgWlanQosWmmBackgroundCwMax OBJECT-TYPE
			SYNTAX Unsigned32 (0..15)
			MAX-ACCESS read-write
			STATUS current
			DESCRIPTION
				"
				
				XPath: /wing-config/wlan_qos[name=key1]/wmm_background_cw_max"
			DEFVAL { 10 }
			::= { wingCfgWlanQosEntry 19 }

		
		-- 1.3.6.1.4.1.1916.2.131.50.1.3.5.1.1.20
		wingCfgWlanQosWmmVideoTxopLimit OBJECT-TYPE
			SYNTAX Unsigned32 (0..65535)
			MAX-ACCESS read-write
			STATUS current
			DESCRIPTION
				"
				
				XPath: /wing-config/wlan_qos[name=key1]/wmm_video_txop_limit"
			DEFVAL { 94 }
			::= { wingCfgWlanQosEntry 20 }

		
		-- 1.3.6.1.4.1.1916.2.131.50.1.3.5.1.1.21
		wingCfgWlanQosWmmVideoAifsn OBJECT-TYPE
			SYNTAX Unsigned32 (2..15)
			MAX-ACCESS read-write
			STATUS current
			DESCRIPTION
				"
				
				XPath: /wing-config/wlan_qos[name=key1]/wmm_video_aifsn"
			DEFVAL { 2 }
			::= { wingCfgWlanQosEntry 21 }

		
		-- 1.3.6.1.4.1.1916.2.131.50.1.3.5.1.1.22
		wingCfgWlanQosWmmVideoCwMin OBJECT-TYPE
			SYNTAX Unsigned32 (0..15)
			MAX-ACCESS read-write
			STATUS current
			DESCRIPTION
				"
				
				XPath: /wing-config/wlan_qos[name=key1]/wmm_video_cw_min"
			DEFVAL { 3 }
			::= { wingCfgWlanQosEntry 22 }

		
		-- 1.3.6.1.4.1.1916.2.131.50.1.3.5.1.1.23
		wingCfgWlanQosWmmVideoCwMax OBJECT-TYPE
			SYNTAX Unsigned32 (0..15)
			MAX-ACCESS read-write
			STATUS current
			DESCRIPTION
				"
				
				XPath: /wing-config/wlan_qos[name=key1]/wmm_video_cw_max"
			DEFVAL { 4 }
			::= { wingCfgWlanQosEntry 23 }

		
		-- 1.3.6.1.4.1.1916.2.131.50.1.3.5.1.1.24
		wingCfgWlanQosWmmVoiceTxopLimit OBJECT-TYPE
			SYNTAX Unsigned32 (0..65535)
			MAX-ACCESS read-write
			STATUS current
			DESCRIPTION
				"
				
				XPath: /wing-config/wlan_qos[name=key1]/wmm_voice_txop_limit"
			DEFVAL { 47 }
			::= { wingCfgWlanQosEntry 24 }

		
		-- 1.3.6.1.4.1.1916.2.131.50.1.3.5.1.1.25
		wingCfgWlanQosWmmVoiceAifsn OBJECT-TYPE
			SYNTAX Unsigned32 (2..15)
			MAX-ACCESS read-write
			STATUS current
			DESCRIPTION
				"
				
				XPath: /wing-config/wlan_qos[name=key1]/wmm_voice_aifsn"
			DEFVAL { 2 }
			::= { wingCfgWlanQosEntry 25 }

		
		-- 1.3.6.1.4.1.1916.2.131.50.1.3.5.1.1.26
		wingCfgWlanQosWmmVoiceCwMin OBJECT-TYPE
			SYNTAX Unsigned32 (0..15)
			MAX-ACCESS read-write
			STATUS current
			DESCRIPTION
				"
				
				XPath: /wing-config/wlan_qos[name=key1]/wmm_voice_cw_min"
			DEFVAL { 2 }
			::= { wingCfgWlanQosEntry 26 }

		
		-- 1.3.6.1.4.1.1916.2.131.50.1.3.5.1.1.27
		wingCfgWlanQosWmmVoiceCwMax OBJECT-TYPE
			SYNTAX Unsigned32 (0..15)
			MAX-ACCESS read-write
			STATUS current
			DESCRIPTION
				"
				
				XPath: /wing-config/wlan_qos[name=key1]/wmm_voice_cw_max"
			DEFVAL { 3 }
			::= { wingCfgWlanQosEntry 27 }

		
		-- 1.3.6.1.4.1.1916.2.131.50.1.3.5.1.1.28
		wingCfgWlanQosWlanRlDownEnable OBJECT-TYPE
			SYNTAX TruthValue
			MAX-ACCESS read-write
			STATUS current
			DESCRIPTION
				"Enable downstream (to air) traffic rate limiting on a WLAN.
				
				XPath: /wing-config/wlan_qos[name=key1]/wlan_rl_down_enable"
			DEFVAL { false }
			::= { wingCfgWlanQosEntry 28 }

		
		-- 1.3.6.1.4.1.1916.2.131.50.1.3.5.1.1.29
		wingCfgWlanQosWlanRlDownRate OBJECT-TYPE
			SYNTAX Unsigned32 (50..1000000)
			UNITS "kbps"
			MAX-ACCESS read-write
			STATUS current
			DESCRIPTION
				"Traffic rate for downstream (to air) rate limiting on a WLAN.
				
				XPath: /wing-config/wlan_qos[name=key1]/wlan_rl_down_rate"
			DEFVAL { 5000 }
			::= { wingCfgWlanQosEntry 29 }

		
		-- 1.3.6.1.4.1.1916.2.131.50.1.3.5.1.1.30
		wingCfgWlanQosWlanRlDownBurstSize OBJECT-TYPE
			SYNTAX Unsigned32 (2..1024)
			UNITS "kbytes"
			MAX-ACCESS read-write
			STATUS current
			DESCRIPTION
				"Maximum burst size for downstream (to air) rate limiting
				on a WLAN.
				
				XPath: /wing-config/wlan_qos[name=key1]/wlan_rl_down_burst_size"
			DEFVAL { 320 }
			::= { wingCfgWlanQosEntry 30 }

		
		-- 1.3.6.1.4.1.1916.2.131.50.1.3.5.1.1.31
		wingCfgWlanQosWlanRlDownThreshBackground OBJECT-TYPE
			SYNTAX Unsigned32 (0..100)
			UNITS "%"
			MAX-ACCESS read-write
			STATUS current
			DESCRIPTION
				"Random early detection threshold in % of Maximum burst size
				for low priority traffic (downstream, to air, rate limiting
				on a WLAN).
				
				XPath: /wing-config/wlan_qos[name=key1]/wlan_rl_down_thresh_background"
			DEFVAL { 50 }
			::= { wingCfgWlanQosEntry 31 }

		
		-- 1.3.6.1.4.1.1916.2.131.50.1.3.5.1.1.32
		wingCfgWlanQosWlanRlDownThreshBestEffort OBJECT-TYPE
			SYNTAX Unsigned32 (0..100)
			UNITS "%"
			MAX-ACCESS read-write
			STATUS current
			DESCRIPTION
				"Random early detection threshold in % of Maximum burst size
				for normal priority traffic (downstream, to air, rate limiting
				on a WLAN).
				
				XPath: /wing-config/wlan_qos[name=key1]/wlan_rl_down_thresh_best_effort"
			DEFVAL { 50 }
			::= { wingCfgWlanQosEntry 32 }

		
		-- 1.3.6.1.4.1.1916.2.131.50.1.3.5.1.1.33
		wingCfgWlanQosWlanRlDownThreshVoice OBJECT-TYPE
			SYNTAX Unsigned32 (0..100)
			UNITS "%"
			MAX-ACCESS read-write
			STATUS current
			DESCRIPTION
				"Random early detection threshold in % of Maximum burst size
				for voice traffic (downstream, to air, rate limiting
				on a WLAN).
				
				XPath: /wing-config/wlan_qos[name=key1]/wlan_rl_down_thresh_voice"
			DEFVAL { 0 }
			::= { wingCfgWlanQosEntry 33 }

		
		-- 1.3.6.1.4.1.1916.2.131.50.1.3.5.1.1.34
		wingCfgWlanQosWlanRlDownThreshVideo OBJECT-TYPE
			SYNTAX Unsigned32 (0..100)
			UNITS "%"
			MAX-ACCESS read-write
			STATUS current
			DESCRIPTION
				"Random early detection threshold in % of Maximum burst size
				for video traffic (downstream, to air, rate limiting
				on a WLAN).
				
				XPath: /wing-config/wlan_qos[name=key1]/wlan_rl_down_thresh_video"
			DEFVAL { 25 }
			::= { wingCfgWlanQosEntry 34 }

		
		-- 1.3.6.1.4.1.1916.2.131.50.1.3.5.1.1.35
		wingCfgWlanQosWlanRlUpEnable OBJECT-TYPE
			SYNTAX TruthValue
			MAX-ACCESS read-write
			STATUS current
			DESCRIPTION
				"Enable upstream (from air) traffic rate limiting on a WLAN.
				
				XPath: /wing-config/wlan_qos[name=key1]/wlan_rl_up_enable"
			DEFVAL { false }
			::= { wingCfgWlanQosEntry 35 }

		
		-- 1.3.6.1.4.1.1916.2.131.50.1.3.5.1.1.36
		wingCfgWlanQosWlanRlUpRate OBJECT-TYPE
			SYNTAX Unsigned32 (50..1000000)
			UNITS "kbps"
			MAX-ACCESS read-write
			STATUS current
			DESCRIPTION
				"Traffic rate for upstream (from air) rate limiting on a WLAN.
				
				XPath: /wing-config/wlan_qos[name=key1]/wlan_rl_up_rate"
			DEFVAL { 5000 }
			::= { wingCfgWlanQosEntry 36 }

		
		-- 1.3.6.1.4.1.1916.2.131.50.1.3.5.1.1.37
		wingCfgWlanQosWlanRlUpBurstSize OBJECT-TYPE
			SYNTAX Unsigned32 (2..1024)
			UNITS "kbytes"
			MAX-ACCESS read-write
			STATUS current
			DESCRIPTION
				"Maximum burst size for upstream (from air) rate limiting
				on a WLAN.
				
				XPath: /wing-config/wlan_qos[name=key1]/wlan_rl_up_burst_size"
			DEFVAL { 320 }
			::= { wingCfgWlanQosEntry 37 }

		
		-- 1.3.6.1.4.1.1916.2.131.50.1.3.5.1.1.38
		wingCfgWlanQosWlanRlUpThreshBackground OBJECT-TYPE
			SYNTAX Unsigned32 (0..100)
			UNITS "%"
			MAX-ACCESS read-write
			STATUS current
			DESCRIPTION
				"Random early detection threshold in % of Maximum burst size
				for low priority traffic (upstream, from air, rate limiting
				on a WLAN).
				
				XPath: /wing-config/wlan_qos[name=key1]/wlan_rl_up_thresh_background"
			DEFVAL { 50 }
			::= { wingCfgWlanQosEntry 38 }

		
		-- 1.3.6.1.4.1.1916.2.131.50.1.3.5.1.1.39
		wingCfgWlanQosWlanRlUpThreshBestEffort OBJECT-TYPE
			SYNTAX Unsigned32 (0..100)
			UNITS "%"
			MAX-ACCESS read-write
			STATUS current
			DESCRIPTION
				"Random early detection threshold in % of Maximum burst size
				for normal priority traffic (upstream, from air,
				rate limiting on a WLAN).
				
				XPath: /wing-config/wlan_qos[name=key1]/wlan_rl_up_thresh_best_effort"
			DEFVAL { 50 }
			::= { wingCfgWlanQosEntry 39 }

		
		-- 1.3.6.1.4.1.1916.2.131.50.1.3.5.1.1.40
		wingCfgWlanQosWlanRlUpThreshVoice OBJECT-TYPE
			SYNTAX Unsigned32 (0..100)
			UNITS "%"
			MAX-ACCESS read-write
			STATUS current
			DESCRIPTION
				"Random early detection threshold in % of Maximum burst size
				for voice traffic (upstream, from air, rate limiting
				on a WLAN).
				
				XPath: /wing-config/wlan_qos[name=key1]/wlan_rl_up_thresh_voice"
			DEFVAL { 0 }
			::= { wingCfgWlanQosEntry 40 }

		
		-- 1.3.6.1.4.1.1916.2.131.50.1.3.5.1.1.41
		wingCfgWlanQosWlanRlUpThreshVideo OBJECT-TYPE
			SYNTAX Unsigned32 (0..100)
			UNITS "%"
			MAX-ACCESS read-write
			STATUS current
			DESCRIPTION
				"Random early detection threshold in % of Maximum burst size
				for video traffic (upstream, from air, rate limiting
				on a WLAN).
				
				XPath: /wing-config/wlan_qos[name=key1]/wlan_rl_up_thresh_video"
			DEFVAL { 25 }
			::= { wingCfgWlanQosEntry 41 }

		
		-- 1.3.6.1.4.1.1916.2.131.50.1.3.5.1.1.42
		wingCfgWlanQosMuRlDownEnable OBJECT-TYPE
			SYNTAX TruthValue
			MAX-ACCESS read-write
			STATUS current
			DESCRIPTION
				"Enable downstream (to air) traffic rate limiting for
				Wireless Clients on a WLAN.
				
				XPath: /wing-config/wlan_qos[name=key1]/mu_rl_down_enable"
			DEFVAL { false }
			::= { wingCfgWlanQosEntry 42 }

		
		-- 1.3.6.1.4.1.1916.2.131.50.1.3.5.1.1.43
		wingCfgWlanQosMuRlDownRate OBJECT-TYPE
			SYNTAX Unsigned32 (50..1000000)
			UNITS "kbps"
			MAX-ACCESS read-write
			STATUS current
			DESCRIPTION
				"Traffic rate for downstream (to air) rate limiting for
				Wireless Clients on a WLAN.
				
				XPath: /wing-config/wlan_qos[name=key1]/mu_rl_down_rate"
			DEFVAL { 1000 }
			::= { wingCfgWlanQosEntry 43 }

		
		-- 1.3.6.1.4.1.1916.2.131.50.1.3.5.1.1.44
		wingCfgWlanQosMuRlDownBurstSize OBJECT-TYPE
			SYNTAX Unsigned32 (2..1024)
			UNITS "kbytes"
			MAX-ACCESS read-write
			STATUS current
			DESCRIPTION
				"Maximum burst size for downstream (to air) rate limiting for
				Wireless Clients on a WLAN.
				
				XPath: /wing-config/wlan_qos[name=key1]/mu_rl_down_burst_size"
			DEFVAL { 64 }
			::= { wingCfgWlanQosEntry 44 }

		
		-- 1.3.6.1.4.1.1916.2.131.50.1.3.5.1.1.45
		wingCfgWlanQosMuRlDownThreshBackground OBJECT-TYPE
			SYNTAX Unsigned32 (0..100)
			UNITS "%"
			MAX-ACCESS read-write
			STATUS current
			DESCRIPTION
				"Random early detection threshold in % of Maximum burst size
				for low priority traffic (downstream, to air, rate limiting
				for clients on a WLAN.
				
				XPath: /wing-config/wlan_qos[name=key1]/mu_rl_down_thresh_background"
			DEFVAL { 50 }
			::= { wingCfgWlanQosEntry 45 }

		
		-- 1.3.6.1.4.1.1916.2.131.50.1.3.5.1.1.46
		wingCfgWlanQosMuRlDownThreshBestEffort OBJECT-TYPE
			SYNTAX Unsigned32 (0..100)
			UNITS "%"
			MAX-ACCESS read-write
			STATUS current
			DESCRIPTION
				"Random early detection threshold in % of Maximum burst size
				for low priority traffic (downstream, to air, rate limiting
				for clients on a WLAN).
				
				XPath: /wing-config/wlan_qos[name=key1]/mu_rl_down_thresh_best_effort"
			DEFVAL { 50 }
			::= { wingCfgWlanQosEntry 46 }

		
		-- 1.3.6.1.4.1.1916.2.131.50.1.3.5.1.1.47
		wingCfgWlanQosMuRlDownThreshVoice OBJECT-TYPE
			SYNTAX Unsigned32 (0..100)
			UNITS "%"
			MAX-ACCESS read-write
			STATUS current
			DESCRIPTION
				"Random early detection threshold in % of Maximum burst size
				for voice traffic (downstream, to air, rate limiting for
				clients on a WLAN).
				
				XPath: /wing-config/wlan_qos[name=key1]/mu_rl_down_thresh_voice"
			DEFVAL { 0 }
			::= { wingCfgWlanQosEntry 47 }

		
		-- 1.3.6.1.4.1.1916.2.131.50.1.3.5.1.1.48
		wingCfgWlanQosMuRlDownThreshVideo OBJECT-TYPE
			SYNTAX Unsigned32 (0..100)
			UNITS "%"
			MAX-ACCESS read-write
			STATUS current
			DESCRIPTION
				"Random early detection threshold in % of Maximum burst size
				for video traffic (downstream, to air, rate limiting for
				clients on a WLAN).
				
				XPath: /wing-config/wlan_qos[name=key1]/mu_rl_down_thresh_video"
			DEFVAL { 25 }
			::= { wingCfgWlanQosEntry 48 }

		
		-- 1.3.6.1.4.1.1916.2.131.50.1.3.5.1.1.49
		wingCfgWlanQosMuRlUpEnable OBJECT-TYPE
			SYNTAX TruthValue
			MAX-ACCESS read-write
			STATUS current
			DESCRIPTION
				"Enable upstream (from air) traffic rate limiting for
				Wireless Clients on a WLAN.
				
				XPath: /wing-config/wlan_qos[name=key1]/mu_rl_up_enable"
			DEFVAL { false }
			::= { wingCfgWlanQosEntry 49 }

		
		-- 1.3.6.1.4.1.1916.2.131.50.1.3.5.1.1.50
		wingCfgWlanQosMuRlUpRate OBJECT-TYPE
			SYNTAX Unsigned32 (50..1000000)
			UNITS "kbps"
			MAX-ACCESS read-write
			STATUS current
			DESCRIPTION
				"Traffic rate for upstream (from air) rate limiting for
				Wireless Clients on a WLAN.
				
				XPath: /wing-config/wlan_qos[name=key1]/mu_rl_up_rate"
			DEFVAL { 1000 }
			::= { wingCfgWlanQosEntry 50 }

		
		-- 1.3.6.1.4.1.1916.2.131.50.1.3.5.1.1.51
		wingCfgWlanQosMuRlUpBurstSize OBJECT-TYPE
			SYNTAX Unsigned32 (2..1024)
			UNITS "kbytes"
			MAX-ACCESS read-write
			STATUS current
			DESCRIPTION
				"Maximum burst size for upstream (from air) rate limiting for
				Wireless Clients on a WLAN.
				
				XPath: /wing-config/wlan_qos[name=key1]/mu_rl_up_burst_size"
			DEFVAL { 64 }
			::= { wingCfgWlanQosEntry 51 }

		
		-- 1.3.6.1.4.1.1916.2.131.50.1.3.5.1.1.52
		wingCfgWlanQosMuRlUpThreshBackground OBJECT-TYPE
			SYNTAX Unsigned32 (0..100)
			UNITS "%"
			MAX-ACCESS read-write
			STATUS current
			DESCRIPTION
				"Random early detection threshold in % of Maximum burst size
				for low priority traffic (upstream, from air, rate limiting
				for clients on a WLAN).
				
				XPath: /wing-config/wlan_qos[name=key1]/mu_rl_up_thresh_background"
			DEFVAL { 50 }
			::= { wingCfgWlanQosEntry 52 }

		
		-- 1.3.6.1.4.1.1916.2.131.50.1.3.5.1.1.53
		wingCfgWlanQosMuRlUpThreshBestEffort OBJECT-TYPE
			SYNTAX Unsigned32 (0..100)
			UNITS "%"
			MAX-ACCESS read-write
			STATUS current
			DESCRIPTION
				"Random early detection threshold in % of Maximum burst size
				for normal priority traffic (upstream, from air, rate limiting
				for clients on a WLAN).
				
				XPath: /wing-config/wlan_qos[name=key1]/mu_rl_up_thresh_best_effort"
			DEFVAL { 50 }
			::= { wingCfgWlanQosEntry 53 }

		
		-- 1.3.6.1.4.1.1916.2.131.50.1.3.5.1.1.54
		wingCfgWlanQosMuRlUpThreshVoice OBJECT-TYPE
			SYNTAX Unsigned32 (0..100)
			UNITS "%"
			MAX-ACCESS read-write
			STATUS current
			DESCRIPTION
				"Random early detection threshold in % of Maximum burst size
				for voice traffic (upstream, from air, rate limiting
				for clients on a WLAN).
				
				XPath: /wing-config/wlan_qos[name=key1]/mu_rl_up_thresh_voice"
			DEFVAL { 0 }
			::= { wingCfgWlanQosEntry 54 }

		
		-- 1.3.6.1.4.1.1916.2.131.50.1.3.5.1.1.55
		wingCfgWlanQosMuRlUpThreshVideo OBJECT-TYPE
			SYNTAX Unsigned32 (0..100)
			UNITS "%"
			MAX-ACCESS read-write
			STATUS current
			DESCRIPTION
				"Random early detection threshold in % of Maximum burst size
				for video traffic (upstream, from air, rate limiting
				for clients on a WLAN).
				
				XPath: /wing-config/wlan_qos[name=key1]/mu_rl_up_thresh_video"
			DEFVAL { 25 }
			::= { wingCfgWlanQosEntry 55 }

		
		-- 1.3.6.1.4.1.1916.2.131.50.1.3.5.1.1.56
		wingCfgWlanQosQosTrustDscp OBJECT-TYPE
			SYNTAX TruthValue
			MAX-ACCESS read-write
			STATUS current
			DESCRIPTION
				"Trust IP DSCP values on WLANs.
				
				XPath: /wing-config/wlan_qos[name=key1]/qos_trust_dscp"
			DEFVAL { true }
			::= { wingCfgWlanQosEntry 56 }

		
		-- 1.3.6.1.4.1.1916.2.131.50.1.3.5.1.1.57
		wingCfgWlanQosQosTrustWmm OBJECT-TYPE
			SYNTAX TruthValue
			MAX-ACCESS read-write
			STATUS current
			DESCRIPTION
				"Trust WMM values on WLANs.
				
				XPath: /wing-config/wlan_qos[name=key1]/qos_trust_wmm"
			DEFVAL { true }
			::= { wingCfgWlanQosEntry 57 }

		
		-- 1.3.6.1.4.1.1916.2.131.50.1.3.5.2
		wingCfgWlanQosMcastStreamTable OBJECT-TYPE
			SYNTAX SEQUENCE OF WingCfgWlanQosMcastStreamEntry
			MAX-ACCESS not-accessible
			STATUS current
			DESCRIPTION
				"Configure accelerated multicast streams address and
				forwarding QoS classification
				
				/wing-config/wlan_qos/mcast_stream"
			::= { wingCfgWlanQos 2 }

		
		-- 1.3.6.1.4.1.1916.2.131.50.1.3.5.2.1
		wingCfgWlanQosMcastStreamEntry OBJECT-TYPE
			SYNTAX WingCfgWlanQosMcastStreamEntry
			MAX-ACCESS not-accessible
			STATUS current
			DESCRIPTION
				"An entry in the table."
			INDEX { wingCfgWlanQosName, wingCfgWlanQosMcastStreamAddr }
			::= { wingCfgWlanQosMcastStreamTable 1 }

		
		WingCfgWlanQosMcastStreamEntry ::=
			SEQUENCE { 
				wingCfgWlanQosMcastStreamAddr
					WingIdentifier,
				wingCfgWlanQosMcastStreamPriority
					DisplayString
			 }

		-- 1.3.6.1.4.1.1916.2.131.50.1.3.5.2.1.1
		wingCfgWlanQosMcastStreamAddr OBJECT-TYPE
			SYNTAX WingIdentifier
			MAX-ACCESS read-only
			STATUS current
			DESCRIPTION
				"Multicast IP address of the traffic stream that should be
				selected for accelerated delivery
				
				Note: an IP address of 0.0.0.0 is special, when it is selected
				that can be only entry in this table
								
				Although the type is an IP address, only multicast IP
				addresses (top 4 bits are E: 224.0.0.0 thru 239.255.255.255)
				should be set here.
				
				XPath: /wing-config/wlan_qos[name=key1]/mcast_stream[addr=key2]/addr"
			::= { wingCfgWlanQosMcastStreamEntry 1 }

		
		-- 1.3.6.1.4.1.1916.2.131.50.1.3.5.2.1.3
		wingCfgWlanQosMcastStreamPriority OBJECT-TYPE
			SYNTAX DisplayString
			MAX-ACCESS read-write
			STATUS current
			DESCRIPTION
				"The forwarding qos classification (traffic class)
				
				Values:
				trust
				voice
				video
				best-effort
				background
				
				XPath: /wing-config/wlan_qos[name=key1]/mcast_stream[addr=key2]/priority"
			DEFVAL { "trust" }
			::= { wingCfgWlanQosMcastStreamEntry 3 }

		
-- /wing-config/radio_qos
		-- 1.3.6.1.4.1.1916.2.131.50.1.3.6
		wingCfgRadioQos OBJECT IDENTIFIER ::= { wingConfig 6 }

		
		-- 1.3.6.1.4.1.1916.2.131.50.1.3.6.1
		wingCfgRadioQosTable OBJECT-TYPE
			SYNTAX SEQUENCE OF WingCfgRadioQosEntry
			MAX-ACCESS not-accessible
			STATUS current
			DESCRIPTION
				"Radio QoS profile
				
				/wing-config/radio_qos"
			::= { wingCfgRadioQos 1 }

		
		-- 1.3.6.1.4.1.1916.2.131.50.1.3.6.1.1
		wingCfgRadioQosEntry OBJECT-TYPE
			SYNTAX WingCfgRadioQosEntry
			MAX-ACCESS not-accessible
			STATUS current
			DESCRIPTION
				"An entry in the table."
			INDEX { wingCfgRadioQosName }
			::= { wingCfgRadioQosTable 1 }

		
		WingCfgRadioQosEntry ::=
			SEQUENCE { 
				wingCfgRadioQosName
					WingIdentifier,
				wingCfgRadioQosWmmBestEffortTxopLimit
					Unsigned32,
				wingCfgRadioQosWmmBestEffortAifsn
					Unsigned32,
				wingCfgRadioQosWmmBestEffortCwMin
					Unsigned32,
				wingCfgRadioQosWmmBestEffortCwMax
					Unsigned32,
				wingCfgRadioQosWmmBackgroundTxopLimit
					Unsigned32,
				wingCfgRadioQosWmmBackgroundAifsn
					Unsigned32,
				wingCfgRadioQosWmmBackgroundCwMin
					Unsigned32,
				wingCfgRadioQosWmmBackgroundCwMax
					Unsigned32,
				wingCfgRadioQosWmmVideoTxopLimit
					Unsigned32,
				wingCfgRadioQosWmmVideoAifsn
					Unsigned32,
				wingCfgRadioQosWmmVideoCwMin
					Unsigned32,
				wingCfgRadioQosWmmVideoCwMax
					Unsigned32,
				wingCfgRadioQosWmmVoiceTxopLimit
					Unsigned32,
				wingCfgRadioQosWmmVoiceAifsn
					Unsigned32,
				wingCfgRadioQosWmmVoiceCwMin
					Unsigned32,
				wingCfgRadioQosWmmVoiceCwMax
					Unsigned32,
				wingCfgRadioQosAdmCtrlFirewallDetectedTraffic
					TruthValue,
				wingCfgRadioQosAdmCtrlImplicitTspec
					TruthValue,
				wingCfgRadioQosAdmCtrlVoiceEnable
					TruthValue,
				wingCfgRadioQosAdmCtrlVoiceMaxClients
					Unsigned32,
				wingCfgRadioQosAdmCtrlVoiceMaxRoamedClients
					Unsigned32,
				wingCfgRadioQosAdmCtrlVoiceMaxAirtimePercent
					Unsigned32,
				wingCfgRadioQosAdmCtrlVoiceReservedForRoamPercent
					Unsigned32,
				wingCfgRadioQosAdmCtrlVideoEnable
					TruthValue,
				wingCfgRadioQosAdmCtrlVideoMaxClients
					Unsigned32,
				wingCfgRadioQosAdmCtrlVideoMaxRoamedClients
					Unsigned32,
				wingCfgRadioQosAdmCtrlVideoMaxAirtimePercent
					Unsigned32,
				wingCfgRadioQosAdmCtrlVideoReservedForRoamPercent
					Unsigned32,
				wingCfgRadioQosAdmCtrlBestEffortEnable
					TruthValue,
				wingCfgRadioQosAdmCtrlBestEffortMaxClients
					Unsigned32,
				wingCfgRadioQosAdmCtrlBestEffortMaxRoamedClients
					Unsigned32,
				wingCfgRadioQosAdmCtrlBestEffortMaxAirtimePercent
					Unsigned32,
				wingCfgRadioQosAdmCtrlBestEffortReservedForRoamPercent
					Unsigned32,
				wingCfgRadioQosAdmCtrlBackgroundEnable
					TruthValue,
				wingCfgRadioQosAdmCtrlBackgroundMaxClients
					Unsigned32,
				wingCfgRadioQosAdmCtrlBackgroundMaxRoamedClients
					Unsigned32,
				wingCfgRadioQosAdmCtrlBackgroundMaxAirtimePercent
					Unsigned32,
				wingCfgRadioQosAdmCtrlBackgroundReservedForRoamPercent
					Unsigned32,
				wingCfgRadioQosAccelMcastMaxStreams
					Unsigned32,
				wingCfgRadioQosAccelMcastOverflowPolicy
					DisplayString,
				wingCfgRadioQosAccelMcastMaxClientStreams
					Unsigned32,
				wingCfgRadioQosAccelMcastStreamThreshold
					Unsigned32,
				wingCfgRadioQosAccelMcastClientTimeout
					Unsigned32
			 }

		-- 1.3.6.1.4.1.1916.2.131.50.1.3.6.1.1.1
		wingCfgRadioQosName OBJECT-TYPE
			SYNTAX WingIdentifier
			MAX-ACCESS read-only
			STATUS current
			DESCRIPTION
				"
				
				XPath: /wing-config/radio_qos[name=key1]/name"
			::= { wingCfgRadioQosEntry 1 }

		
		-- 1.3.6.1.4.1.1916.2.131.50.1.3.6.1.1.3
		wingCfgRadioQosWmmBestEffortTxopLimit OBJECT-TYPE
			SYNTAX Unsigned32 (0..65535)
			MAX-ACCESS read-write
			STATUS current
			DESCRIPTION
				"
				
				XPath: /wing-config/radio_qos[name=key1]/wmm_best_effort_txop_limit"
			DEFVAL { 0 }
			::= { wingCfgRadioQosEntry 3 }

		
		-- 1.3.6.1.4.1.1916.2.131.50.1.3.6.1.1.4
		wingCfgRadioQosWmmBestEffortAifsn OBJECT-TYPE
			SYNTAX Unsigned32 (1..15)
			MAX-ACCESS read-write
			STATUS current
			DESCRIPTION
				"
				
				XPath: /wing-config/radio_qos[name=key1]/wmm_best_effort_aifsn"
			DEFVAL { 3 }
			::= { wingCfgRadioQosEntry 4 }

		
		-- 1.3.6.1.4.1.1916.2.131.50.1.3.6.1.1.5
		wingCfgRadioQosWmmBestEffortCwMin OBJECT-TYPE
			SYNTAX Unsigned32 (0..15)
			MAX-ACCESS read-write
			STATUS current
			DESCRIPTION
				"
				
				XPath: /wing-config/radio_qos[name=key1]/wmm_best_effort_cw_min"
			DEFVAL { 4 }
			::= { wingCfgRadioQosEntry 5 }

		
		-- 1.3.6.1.4.1.1916.2.131.50.1.3.6.1.1.6
		wingCfgRadioQosWmmBestEffortCwMax OBJECT-TYPE
			SYNTAX Unsigned32 (0..15)
			MAX-ACCESS read-write
			STATUS current
			DESCRIPTION
				"
				
				XPath: /wing-config/radio_qos[name=key1]/wmm_best_effort_cw_max"
			DEFVAL { 6 }
			::= { wingCfgRadioQosEntry 6 }

		
		-- 1.3.6.1.4.1.1916.2.131.50.1.3.6.1.1.7
		wingCfgRadioQosWmmBackgroundTxopLimit OBJECT-TYPE
			SYNTAX Unsigned32 (0..65535)
			MAX-ACCESS read-write
			STATUS current
			DESCRIPTION
				"
				
				XPath: /wing-config/radio_qos[name=key1]/wmm_background_txop_limit"
			DEFVAL { 0 }
			::= { wingCfgRadioQosEntry 7 }

		
		-- 1.3.6.1.4.1.1916.2.131.50.1.3.6.1.1.8
		wingCfgRadioQosWmmBackgroundAifsn OBJECT-TYPE
			SYNTAX Unsigned32 (1..15)
			MAX-ACCESS read-write
			STATUS current
			DESCRIPTION
				"
				
				XPath: /wing-config/radio_qos[name=key1]/wmm_background_aifsn"
			DEFVAL { 7 }
			::= { wingCfgRadioQosEntry 8 }

		
		-- 1.3.6.1.4.1.1916.2.131.50.1.3.6.1.1.9
		wingCfgRadioQosWmmBackgroundCwMin OBJECT-TYPE
			SYNTAX Unsigned32 (0..15)
			MAX-ACCESS read-write
			STATUS current
			DESCRIPTION
				"
				
				XPath: /wing-config/radio_qos[name=key1]/wmm_background_cw_min"
			DEFVAL { 4 }
			::= { wingCfgRadioQosEntry 9 }

		
		-- 1.3.6.1.4.1.1916.2.131.50.1.3.6.1.1.10
		wingCfgRadioQosWmmBackgroundCwMax OBJECT-TYPE
			SYNTAX Unsigned32 (0..15)
			MAX-ACCESS read-write
			STATUS current
			DESCRIPTION
				"
				
				XPath: /wing-config/radio_qos[name=key1]/wmm_background_cw_max"
			DEFVAL { 10 }
			::= { wingCfgRadioQosEntry 10 }

		
		-- 1.3.6.1.4.1.1916.2.131.50.1.3.6.1.1.11
		wingCfgRadioQosWmmVideoTxopLimit OBJECT-TYPE
			SYNTAX Unsigned32 (0..65535)
			MAX-ACCESS read-write
			STATUS current
			DESCRIPTION
				"
				
				XPath: /wing-config/radio_qos[name=key1]/wmm_video_txop_limit"
			DEFVAL { 94 }
			::= { wingCfgRadioQosEntry 11 }

		
		-- 1.3.6.1.4.1.1916.2.131.50.1.3.6.1.1.12
		wingCfgRadioQosWmmVideoAifsn OBJECT-TYPE
			SYNTAX Unsigned32 (1..15)
			MAX-ACCESS read-write
			STATUS current
			DESCRIPTION
				"
				
				XPath: /wing-config/radio_qos[name=key1]/wmm_video_aifsn"
			DEFVAL { 1 }
			::= { wingCfgRadioQosEntry 12 }

		
		-- 1.3.6.1.4.1.1916.2.131.50.1.3.6.1.1.13
		wingCfgRadioQosWmmVideoCwMin OBJECT-TYPE
			SYNTAX Unsigned32 (0..15)
			MAX-ACCESS read-write
			STATUS current
			DESCRIPTION
				"
				
				XPath: /wing-config/radio_qos[name=key1]/wmm_video_cw_min"
			DEFVAL { 3 }
			::= { wingCfgRadioQosEntry 13 }

		
		-- 1.3.6.1.4.1.1916.2.131.50.1.3.6.1.1.14
		wingCfgRadioQosWmmVideoCwMax OBJECT-TYPE
			SYNTAX Unsigned32 (0..15)
			MAX-ACCESS read-write
			STATUS current
			DESCRIPTION
				"
				
				XPath: /wing-config/radio_qos[name=key1]/wmm_video_cw_max"
			DEFVAL { 4 }
			::= { wingCfgRadioQosEntry 14 }

		
		-- 1.3.6.1.4.1.1916.2.131.50.1.3.6.1.1.15
		wingCfgRadioQosWmmVoiceTxopLimit OBJECT-TYPE
			SYNTAX Unsigned32 (0..65535)
			MAX-ACCESS read-write
			STATUS current
			DESCRIPTION
				"
				
				XPath: /wing-config/radio_qos[name=key1]/wmm_voice_txop_limit"
			DEFVAL { 47 }
			::= { wingCfgRadioQosEntry 15 }

		
		-- 1.3.6.1.4.1.1916.2.131.50.1.3.6.1.1.16
		wingCfgRadioQosWmmVoiceAifsn OBJECT-TYPE
			SYNTAX Unsigned32 (1..15)
			MAX-ACCESS read-write
			STATUS current
			DESCRIPTION
				"
				
				XPath: /wing-config/radio_qos[name=key1]/wmm_voice_aifsn"
			DEFVAL { 1 }
			::= { wingCfgRadioQosEntry 16 }

		
		-- 1.3.6.1.4.1.1916.2.131.50.1.3.6.1.1.17
		wingCfgRadioQosWmmVoiceCwMin OBJECT-TYPE
			SYNTAX Unsigned32 (0..15)
			MAX-ACCESS read-write
			STATUS current
			DESCRIPTION
				"
				
				XPath: /wing-config/radio_qos[name=key1]/wmm_voice_cw_min"
			DEFVAL { 2 }
			::= { wingCfgRadioQosEntry 17 }

		
		-- 1.3.6.1.4.1.1916.2.131.50.1.3.6.1.1.18
		wingCfgRadioQosWmmVoiceCwMax OBJECT-TYPE
			SYNTAX Unsigned32 (0..15)
			MAX-ACCESS read-write
			STATUS current
			DESCRIPTION
				"
				
				XPath: /wing-config/radio_qos[name=key1]/wmm_voice_cw_max"
			DEFVAL { 3 }
			::= { wingCfgRadioQosEntry 18 }

		
		-- 1.3.6.1.4.1.1916.2.131.50.1.3.6.1.1.19
		wingCfgRadioQosAdmCtrlFirewallDetectedTraffic OBJECT-TYPE
			SYNTAX TruthValue
			MAX-ACCESS read-write
			STATUS current
			DESCRIPTION
				"Enforce admission control for traffic whose access category
				is detected by the firewall ALG (e.g. SIP voice calls).
				Could result in rejected calls
				
				XPath: /wing-config/radio_qos[name=key1]/admission_control_firewall_detected_traffic"
			DEFVAL { true }
			::= { wingCfgRadioQosEntry 19 }

		
		-- 1.3.6.1.4.1.1916.2.131.50.1.3.6.1.1.20
		wingCfgRadioQosAdmCtrlImplicitTspec OBJECT-TYPE
			SYNTAX TruthValue
			MAX-ACCESS read-write
			STATUS current
			DESCRIPTION
				"Enforce admission control for clients that do not support
				WMM-TSPEC but are accessing admission controlled
				access categories. Could result in downgraded traffic
				
				XPath: /wing-config/radio_qos[name=key1]/admission_control_implicit_tspec"
			DEFVAL { true }
			::= { wingCfgRadioQosEntry 20 }

		
		-- 1.3.6.1.4.1.1916.2.131.50.1.3.6.1.1.21
		wingCfgRadioQosAdmCtrlVoiceEnable OBJECT-TYPE
			SYNTAX TruthValue
			MAX-ACCESS read-write
			STATUS current
			DESCRIPTION
				"Enable Voice access category admission control.
				
				XPath: /wing-config/radio_qos[name=key1]/admission_control_voice_enable"
			DEFVAL { false }
			::= { wingCfgRadioQosEntry 21 }

		
		-- 1.3.6.1.4.1.1916.2.131.50.1.3.6.1.1.22
		wingCfgRadioQosAdmCtrlVoiceMaxClients OBJECT-TYPE
			SYNTAX Unsigned32 (0..256)
			MAX-ACCESS read-write
			STATUS current
			DESCRIPTION
				"Maximum number of non-roamed wireless clients admitted.
				
				XPath: /wing-config/radio_qos[name=key1]/admission_control_voice_max_mus"
			DEFVAL { 100 }
			::= { wingCfgRadioQosEntry 22 }

		
		-- 1.3.6.1.4.1.1916.2.131.50.1.3.6.1.1.23
		wingCfgRadioQosAdmCtrlVoiceMaxRoamedClients OBJECT-TYPE
			SYNTAX Unsigned32 (0..256)
			MAX-ACCESS read-write
			STATUS current
			DESCRIPTION
				"Maximum number of additional roamed wireless clients admitted.
				
				XPath: /wing-config/radio_qos[name=key1]/admission_control_voice_max_roamed_mus"
			DEFVAL { 10 }
			::= { wingCfgRadioQosEntry 23 }

		
		-- 1.3.6.1.4.1.1916.2.131.50.1.3.6.1.1.24
		wingCfgRadioQosAdmCtrlVoiceMaxAirtimePercent OBJECT-TYPE
			SYNTAX Unsigned32 (0..150)
			MAX-ACCESS read-write
			STATUS current
			DESCRIPTION
				"Maximum percentage of airtime for this access category for
				non-roamed wireless clients.
				
				XPath: /wing-config/radio_qos[name=key1]/admission_control_voice_max_airtime_percent"
			DEFVAL { 75 }
			::= { wingCfgRadioQosEntry 24 }

		
		-- 1.3.6.1.4.1.1916.2.131.50.1.3.6.1.1.25
		wingCfgRadioQosAdmCtrlVoiceReservedForRoamPercent OBJECT-TYPE
			SYNTAX Unsigned32 (0..150)
			MAX-ACCESS read-write
			STATUS current
			DESCRIPTION
				"Additional percentage of air time allocated exclusively for
				roamed wireless clients.
				
				XPath: /wing-config/radio_qos[name=key1]/admission_control_voice_reserved_for_roam_percent"
			DEFVAL { 10 }
			::= { wingCfgRadioQosEntry 25 }

		
		-- 1.3.6.1.4.1.1916.2.131.50.1.3.6.1.1.26
		wingCfgRadioQosAdmCtrlVideoEnable OBJECT-TYPE
			SYNTAX TruthValue
			MAX-ACCESS read-write
			STATUS current
			DESCRIPTION
				"Enable Video access category admission control.
				
				XPath: /wing-config/radio_qos[name=key1]/admission_control_video_enable"
			DEFVAL { false }
			::= { wingCfgRadioQosEntry 26 }

		
		-- 1.3.6.1.4.1.1916.2.131.50.1.3.6.1.1.27
		wingCfgRadioQosAdmCtrlVideoMaxClients OBJECT-TYPE
			SYNTAX Unsigned32 (0..256)
			MAX-ACCESS read-write
			STATUS current
			DESCRIPTION
				"Maximum number of non-roamed wireless clients admitted.
				
				XPath: /wing-config/radio_qos[name=key1]/admission_control_video_max_mus"
			DEFVAL { 100 }
			::= { wingCfgRadioQosEntry 27 }

		
		-- 1.3.6.1.4.1.1916.2.131.50.1.3.6.1.1.28
		wingCfgRadioQosAdmCtrlVideoMaxRoamedClients OBJECT-TYPE
			SYNTAX Unsigned32 (0..256)
			MAX-ACCESS read-write
			STATUS current
			DESCRIPTION
				"Maximum number of additional roamed wireless clients admitted.
				
				XPath: /wing-config/radio_qos[name=key1]/admission_control_video_max_roamed_mus"
			DEFVAL { 10 }
			::= { wingCfgRadioQosEntry 28 }

		
		-- 1.3.6.1.4.1.1916.2.131.50.1.3.6.1.1.29
		wingCfgRadioQosAdmCtrlVideoMaxAirtimePercent OBJECT-TYPE
			SYNTAX Unsigned32 (0..150)
			MAX-ACCESS read-write
			STATUS current
			DESCRIPTION
				"Maximum percentage of airtime for this access category for
				non-roamed wireless clients.
				
				XPath: /wing-config/radio_qos[name=key1]/admission_control_video_max_airtime_percent"
			DEFVAL { 75 }
			::= { wingCfgRadioQosEntry 29 }

		
		-- 1.3.6.1.4.1.1916.2.131.50.1.3.6.1.1.30
		wingCfgRadioQosAdmCtrlVideoReservedForRoamPercent OBJECT-TYPE
			SYNTAX Unsigned32 (0..150)
			MAX-ACCESS read-write
			STATUS current
			DESCRIPTION
				"Additional percentage of air time allocated exclusively for
				roamed wireless clients.
				
				XPath: /wing-config/radio_qos[name=key1]/admission_control_video_reserved_for_roam_percent"
			DEFVAL { 10 }
			::= { wingCfgRadioQosEntry 30 }

		
		-- 1.3.6.1.4.1.1916.2.131.50.1.3.6.1.1.31
		wingCfgRadioQosAdmCtrlBestEffortEnable OBJECT-TYPE
			SYNTAX TruthValue
			MAX-ACCESS read-write
			STATUS current
			DESCRIPTION
				"Enable Best Effort access category admission control.
				
				XPath: /wing-config/radio_qos[name=key1]/admission_control_best_effort_enable"
			DEFVAL { false }
			::= { wingCfgRadioQosEntry 31 }

		
		-- 1.3.6.1.4.1.1916.2.131.50.1.3.6.1.1.32
		wingCfgRadioQosAdmCtrlBestEffortMaxClients OBJECT-TYPE
			SYNTAX Unsigned32 (0..256)
			MAX-ACCESS read-write
			STATUS current
			DESCRIPTION
				"Maximum number of non-roamed wireless clients admitted.
				
				XPath: /wing-config/radio_qos[name=key1]/admission_control_best_effort_max_mus"
			DEFVAL { 100 }
			::= { wingCfgRadioQosEntry 32 }

		
		-- 1.3.6.1.4.1.1916.2.131.50.1.3.6.1.1.33
		wingCfgRadioQosAdmCtrlBestEffortMaxRoamedClients OBJECT-TYPE
			SYNTAX Unsigned32 (0..256)
			MAX-ACCESS read-write
			STATUS current
			DESCRIPTION
				"Maximum number of additional roamed wireless clients admitted.
				
				XPath: /wing-config/radio_qos[name=key1]/admission_control_best_effort_max_roamed_mus"
			DEFVAL { 10 }
			::= { wingCfgRadioQosEntry 33 }

		
		-- 1.3.6.1.4.1.1916.2.131.50.1.3.6.1.1.34
		wingCfgRadioQosAdmCtrlBestEffortMaxAirtimePercent OBJECT-TYPE
			SYNTAX Unsigned32 (0..150)
			MAX-ACCESS read-write
			STATUS current
			DESCRIPTION
				"Maximum percentage of airtime for this access category for
				non-roamed wireless clients.
				
				XPath: /wing-config/radio_qos[name=key1]/admission_control_best_effort_max_airtime_percent"
			DEFVAL { 75 }
			::= { wingCfgRadioQosEntry 34 }

		
		-- 1.3.6.1.4.1.1916.2.131.50.1.3.6.1.1.35
		wingCfgRadioQosAdmCtrlBestEffortReservedForRoamPercent OBJECT-TYPE
			SYNTAX Unsigned32 (0..150)
			MAX-ACCESS read-write
			STATUS current
			DESCRIPTION
				"Additional percentage of air time allocated exclusively for
				roamed wireless clients.
				
				XPath: /wing-config/radio_qos[name=key1]/admission_control_best_effort_reserved_for_roam_percent"
			DEFVAL { 10 }
			::= { wingCfgRadioQosEntry 35 }

		
		-- 1.3.6.1.4.1.1916.2.131.50.1.3.6.1.1.36
		wingCfgRadioQosAdmCtrlBackgroundEnable OBJECT-TYPE
			SYNTAX TruthValue
			MAX-ACCESS read-write
			STATUS current
			DESCRIPTION
				"Enable Background access category admission control.
				
				XPath: /wing-config/radio_qos[name=key1]/admission_control_background_enable"
			DEFVAL { false }
			::= { wingCfgRadioQosEntry 36 }

		
		-- 1.3.6.1.4.1.1916.2.131.50.1.3.6.1.1.37
		wingCfgRadioQosAdmCtrlBackgroundMaxClients OBJECT-TYPE
			SYNTAX Unsigned32 (0..256)
			MAX-ACCESS read-write
			STATUS current
			DESCRIPTION
				"Maximum number of non-roamed wireless clients admitted.
				
				XPath: /wing-config/radio_qos[name=key1]/admission_control_background_max_mus"
			DEFVAL { 100 }
			::= { wingCfgRadioQosEntry 37 }

		
		-- 1.3.6.1.4.1.1916.2.131.50.1.3.6.1.1.38
		wingCfgRadioQosAdmCtrlBackgroundMaxRoamedClients OBJECT-TYPE
			SYNTAX Unsigned32 (0..256)
			MAX-ACCESS read-write
			STATUS current
			DESCRIPTION
				"Maximum number of additional roamed wireless clients admitted.
				
				XPath: /wing-config/radio_qos[name=key1]/admission_control_background_max_roamed_mus"
			DEFVAL { 10 }
			::= { wingCfgRadioQosEntry 38 }

		
		-- 1.3.6.1.4.1.1916.2.131.50.1.3.6.1.1.39
		wingCfgRadioQosAdmCtrlBackgroundMaxAirtimePercent OBJECT-TYPE
			SYNTAX Unsigned32 (0..150)
			MAX-ACCESS read-write
			STATUS current
			DESCRIPTION
				"Maximum percentage of airtime for this access category for
				non-roamed wireless clients.
				
				XPath: /wing-config/radio_qos[name=key1]/admission_control_background_max_airtime_percent"
			DEFVAL { 75 }
			::= { wingCfgRadioQosEntry 39 }

		
		-- 1.3.6.1.4.1.1916.2.131.50.1.3.6.1.1.40
		wingCfgRadioQosAdmCtrlBackgroundReservedForRoamPercent OBJECT-TYPE
			SYNTAX Unsigned32 (0..150)
			MAX-ACCESS read-write
			STATUS current
			DESCRIPTION
				"Additional percentage of air time allocated exclusively for
				roamed wireless clients.
				
				XPath: /wing-config/radio_qos[name=key1]/admission_control_background_reserved_for_roam_percent"
			DEFVAL { 10 }
			::= { wingCfgRadioQosEntry 40 }

		
		-- 1.3.6.1.4.1.1916.2.131.50.1.3.6.1.1.41
		wingCfgRadioQosAccelMcastMaxStreams OBJECT-TYPE
			SYNTAX Unsigned32 (0..256)
			MAX-ACCESS read-write
			STATUS current
			DESCRIPTION
				"Maximum number of accelerated multicast streams per radio.
				
				XPath: /wing-config/radio_qos[name=key1]/accelerated_multicast_max_streams"
			DEFVAL { 25 }
			::= { wingCfgRadioQosEntry 41 }

		
		-- 1.3.6.1.4.1.1916.2.131.50.1.3.6.1.1.42
		wingCfgRadioQosAccelMcastOverflowPolicy OBJECT-TYPE
			SYNTAX DisplayString
			MAX-ACCESS read-write
			STATUS current
			DESCRIPTION
				"Policy for what to do when more then the maximum number of
				accelerated multicast streams become active: Revert to
				non-accelerated multicast or reject new streams.
				
				Values:
				revert
				reject
				
				XPath: /wing-config/radio_qos[name=key1]/accelerated_multicast_overflow_policy"
			DEFVAL { "reject" }
			::= { wingCfgRadioQosEntry 42 }

		
		-- 1.3.6.1.4.1.1916.2.131.50.1.3.6.1.1.43
		wingCfgRadioQosAccelMcastMaxClientStreams OBJECT-TYPE
			SYNTAX Unsigned32 (1..4)
			MAX-ACCESS read-write
			STATUS current
			DESCRIPTION
				"Maximum number of accelerated multicast streams per
				wireless client.
				
				XPath: /wing-config/radio_qos[name=key1]/accelerated_multicast_max_client_streams"
			DEFVAL { 2 }
			::= { wingCfgRadioQosEntry 43 }

		
		-- 1.3.6.1.4.1.1916.2.131.50.1.3.6.1.1.44
		wingCfgRadioQosAccelMcastStreamThreshold OBJECT-TYPE
			SYNTAX Unsigned32 (1..500)
			MAX-ACCESS read-write
			STATUS current
			DESCRIPTION
				"Packets per second threshold for a multicast stream to
				qualify for accelerated multicast in case the multicast
				address was not explicitly configured.
				
				XPath: /wing-config/radio_qos[name=key1]/accelerated_multicast_stream_threshold"
			DEFVAL { 25 }
			::= { wingCfgRadioQosEntry 44 }

		
		-- 1.3.6.1.4.1.1916.2.131.50.1.3.6.1.1.45
		wingCfgRadioQosAccelMcastClientTimeout OBJECT-TYPE
			SYNTAX Unsigned32 (5..6000)
			MAX-ACCESS read-write
			STATUS current
			DESCRIPTION
				"Number of seconds between reJOINING of a wireless client to
				an accelerated multicast stream. Client may be removed if it
				does not respond to a request during that time.
				
				XPath: /wing-config/radio_qos[name=key1]/accelerated_multicast_client_timeout"
			DEFVAL { 60 }
			::= { wingCfgRadioQosEntry 45 }

		
-- /wing-config/aaa_policy
		-- 1.3.6.1.4.1.1916.2.131.50.1.3.7
		wingCfgAaa OBJECT IDENTIFIER ::= { wingConfig 7 }

		
		-- 1.3.6.1.4.1.1916.2.131.50.1.3.7.1
		wingCfgAaaTable OBJECT-TYPE
			SYNTAX SEQUENCE OF WingCfgAaaEntry
			MAX-ACCESS not-accessible
			STATUS current
			DESCRIPTION
				"AAA policy
				
				/wing-config/aaa_policy"
			::= { wingCfgAaa 1 }

		
		-- 1.3.6.1.4.1.1916.2.131.50.1.3.7.1.1
		wingCfgAaaEntry OBJECT-TYPE
			SYNTAX WingCfgAaaEntry
			MAX-ACCESS not-accessible
			STATUS current
			DESCRIPTION
				"An entry in the table."
			INDEX { wingCfgAaaName }
			::= { wingCfgAaaTable 1 }

		
		WingCfgAaaEntry ::=
			SEQUENCE { 
				wingCfgAaaName
					WingIdentifier,
				wingCfgAaaServerPoolingMode
					DisplayString,
				wingCfgAaaMacAddrFormat
					DisplayString,
				wingCfgAaaMacAddrCase
					DisplayString,
				wingCfgAaaMacAddrAttributes
					DisplayString,
				wingCfgAaaEapClientTimeout
					Unsigned32,
				wingCfgAaaEapClientAttempts
					Unsigned32,
				wingCfgAaaEapClientRetryFactor
					Unsigned32,
				wingCfgAaaEapClientIdReqTimeout
					Unsigned32,
				wingCfgAaaAuthProtocol
					DisplayString,
				wingCfgAaaAccountingType
					DisplayString,
				wingCfgAaaInterimAccountingInterval
					Unsigned32,
				wingCfgAaaNacList
					WingIdentifier
			 }

		-- 1.3.6.1.4.1.1916.2.131.50.1.3.7.1.1.1
		wingCfgAaaName OBJECT-TYPE
			SYNTAX WingIdentifier
			MAX-ACCESS read-only
			STATUS current
			DESCRIPTION
				"The user-defined name of the AAA policy.
				
				XPath: /wing-config/aaa_policy[name=key1]/name"
			::= { wingCfgAaaEntry 1 }

		
		-- 1.3.6.1.4.1.1916.2.131.50.1.3.7.1.1.3
		wingCfgAaaServerPoolingMode OBJECT-TYPE
			SYNTAX DisplayString
			MAX-ACCESS read-write
			STATUS current
			DESCRIPTION
				"Controls how requests are transmitted across RADIUS servers.
				Failover implies working down the list of servers if any
				server is unresponsive. load-balanced implies use of all
				servers, transmitting requests in a round-robin fashion.
				
				Values:
				failover
				load-balance
				
				XPath: /wing-config/aaa_policy[name=key1]/server_pooling_mode"
			DEFVAL { "failover" }
			::= { wingCfgAaaEntry 3 }

		
		-- 1.3.6.1.4.1.1916.2.131.50.1.3.7.1.1.4
		wingCfgAaaMacAddrFormat OBJECT-TYPE
			SYNTAX DisplayString
			MAX-ACCESS read-write
			STATUS current
			DESCRIPTION
				"Configure the format in which the MAC address is packed
				in the RADIUS request packets
				(AABBCCDDEEFF/AA:BB:CC:DD:EE:FF/AA-BB-CC-DD-EE-FF/
				AABB.CCDD.EEFF/AABBCC-DDEEFF).
				
				Values:
				no-delim
				pair-colon
				pair-hyphen
				quad-dot
				middle-hyphen
				
				XPath: /wing-config/aaa_policy[name=key1]/mac_address_format/format"
			DEFVAL { "pair-hyphen" }
			::= { wingCfgAaaEntry 4 }

		
		-- 1.3.6.1.4.1.1916.2.131.50.1.3.7.1.1.5
		wingCfgAaaMacAddrCase OBJECT-TYPE
			SYNTAX DisplayString
			MAX-ACCESS read-write
			STATUS current
			DESCRIPTION
				"whether the MAC address is filled in upper case
				(AA-BB-CC-DD-EE-FF) or lower case (aa-bb-cc-dd-ee-ff)
				
				Values:
				upper
				lower
				
				XPath: /wing-config/aaa_policy[name=key1]/mac_address_format/case"
			DEFVAL { "upper" }
			::= { wingCfgAaaEntry 5 }

		
		-- 1.3.6.1.4.1.1916.2.131.50.1.3.7.1.1.6
		wingCfgAaaMacAddrAttributes OBJECT-TYPE
			SYNTAX DisplayString
			MAX-ACCESS read-write
			STATUS current
			DESCRIPTION
				"whether this format specified applies only to the
				username/password in mac-auth, or for all attributes that
				include a mac address, such as calling-station-id,
				called-station-id etc
				
				Values:
				username-password
				all
				
				XPath: /wing-config/aaa_policy[name=key1]/mac_address_format/attributes"
			DEFVAL { "username-password" }
			::= { wingCfgAaaEntry 6 }

		
		-- 1.3.6.1.4.1.1916.2.131.50.1.3.7.1.1.7
		wingCfgAaaEapClientTimeout OBJECT-TYPE
			SYNTAX Unsigned32 (1..60)
			UNITS "seconds"
			MAX-ACCESS read-write
			STATUS current
			DESCRIPTION
				"The amount of time after which an EAP request towards a
				Wireless Client is retried.
				
				XPath: /wing-config/aaa_policy[name=key1]/eap_mu_timeout"
			DEFVAL { 3 }
			::= { wingCfgAaaEntry 7 }

		
		-- 1.3.6.1.4.1.1916.2.131.50.1.3.7.1.1.8
		wingCfgAaaEapClientAttempts OBJECT-TYPE
			SYNTAX Unsigned32 (1..10)
			MAX-ACCESS read-write
			STATUS current
			DESCRIPTION
				"The number of times an EAP request is transmitted towards
				a Wireless Client before giving up.
				
				XPath: /wing-config/aaa_policy[name=key1]/eap_mu_attempts"
			DEFVAL { 3 }
			::= { wingCfgAaaEntry 8 }

		
		-- 1.3.6.1.4.1.1916.2.131.50.1.3.7.1.1.9
		wingCfgAaaEapClientRetryFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /wing-config/aaa_policy[name=key1]/eap_mu_retry_factor"
			DEFVAL { 100 }
			::= { wingCfgAaaEntry 9 }

		
		-- 1.3.6.1.4.1.1916.2.131.50.1.3.7.1.1.10
		wingCfgAaaEapClientIdReqTimeout OBJECT-TYPE
			SYNTAX Unsigned32 (1..60)
			UNITS "seconds"
			MAX-ACCESS read-write
			STATUS current
			DESCRIPTION
				"The amount of time after which an EAP-ID-Request towards a
				Wireless Client is retried.
				
				XPath: /wing-config/aaa_policy[name=key1]/eap_mu_id_req_timeout"
			DEFVAL { 10 }
			::= { wingCfgAaaEntry 10 }

		
		-- 1.3.6.1.4.1.1916.2.131.50.1.3.7.1.1.11
		wingCfgAaaAuthProtocol OBJECT-TYPE
			SYNTAX DisplayString
			MAX-ACCESS read-write
			STATUS current
			DESCRIPTION
				"The authentication protocol (Password Authentication Protocol
				or Challenge Handshake Authentication Protocol) to use when
				the server is used for any non-EAP authentication.
				
				Values:
				pap
				chap
				
				XPath: /wing-config/aaa_policy[name=key1]/authentication_protocol"
			DEFVAL { "pap" }
			::= { wingCfgAaaEntry 11 }

		
		-- 1.3.6.1.4.1.1916.2.131.50.1.3.7.1.1.12
		wingCfgAaaAccountingType OBJECT-TYPE
			SYNTAX DisplayString
			MAX-ACCESS read-write
			STATUS current
			DESCRIPTION
				"Control the type of RADIUS Accounting request packets that
				are to be generated.
				
				Values:
				stop-only
				start-stop
				start-interim-stop
				
				XPath: /wing-config/aaa_policy[name=key1]/accounting_type"
			DEFVAL { "start-stop" }
			::= { wingCfgAaaEntry 12 }

		
		-- 1.3.6.1.4.1.1916.2.131.50.1.3.7.1.1.13
		wingCfgAaaInterimAccountingInterval OBJECT-TYPE
			SYNTAX Unsigned32 (60..3600)
			UNITS "seconds"
			MAX-ACCESS read-write
			STATUS current
			DESCRIPTION
				"The periodicity of the interim accounting requests.
				
				XPath: /wing-config/aaa_policy[name=key1]/interim_accounting_interval"
			DEFVAL { 1800 }
			::= { wingCfgAaaEntry 13 }

		
		-- 1.3.6.1.4.1.1916.2.131.50.1.3.7.1.1.14
		wingCfgAaaNacList OBJECT-TYPE
			SYNTAX WingIdentifier
			MAX-ACCESS read-write
			STATUS current
			DESCRIPTION
				"Filter to include or exclude certain Wireless Clients from
				network access control.
				
				XPath: /wing-config/aaa_policy[name=key1]/nac_list"
			::= { wingCfgAaaEntry 14 }

		
		-- 1.3.6.1.4.1.1916.2.131.50.1.3.7.2
		wingCfgAaaAuthSrvrTable OBJECT-TYPE
			SYNTAX SEQUENCE OF WingCfgAaaAuthSrvrEntry
			MAX-ACCESS not-accessible
			STATUS current
			DESCRIPTION
				"
				
				/wing-config/aaa_policy/auth_srvr"
			::= { wingCfgAaa 2 }

		
		-- 1.3.6.1.4.1.1916.2.131.50.1.3.7.2.1
		wingCfgAaaAuthSrvrEntry OBJECT-TYPE
			SYNTAX WingCfgAaaAuthSrvrEntry
			MAX-ACCESS not-accessible
			STATUS current
			DESCRIPTION
				"An entry in the table."
			INDEX { wingCfgAaaName, wingCfgAaaAuthSrvrIdx }
			::= { wingCfgAaaAuthSrvrTable 1 }

		
		WingCfgAaaAuthSrvrEntry ::=
			SEQUENCE { 
				wingCfgAaaAuthSrvrIdx
					Unsigned32,
				wingCfgAaaAuthSrvrType
					DisplayString,
				wingCfgAaaAuthSrvrHost
					DisplayString,
				wingCfgAaaAuthSrvrSecret
					DisplayString,
				wingCfgAaaAuthSrvrPort
					Unsigned32,
				wingCfgAaaAuthSrvrTimeout
					Unsigned32,
				wingCfgAaaAuthSrvrAttempts
					Unsigned32,
				wingCfgAaaAuthSrvrProxyMode
					DisplayString,
				wingCfgAaaAuthSrvrNaiRouting
					TruthValue,
				wingCfgAaaAuthSrvrRealmType
					DisplayString,
				wingCfgAaaAuthSrvrRealm
					DisplayString,
				wingCfgAaaAuthSrvrStripRealm
					TruthValue,
				wingCfgAaaAuthSrvrRetryTimeoutFactor
					Unsigned32,
				wingCfgAaaAuthSrvrNacEnable
					TruthValue,
				wingCfgAaaAuthSrvrDscp
					Unsigned32
			 }

		-- 1.3.6.1.4.1.1916.2.131.50.1.3.7.2.1.1
		wingCfgAaaAuthSrvrIdx OBJECT-TYPE
			SYNTAX Unsigned32 (1..6)
			MAX-ACCESS read-only
			STATUS current
			DESCRIPTION
				"The index into the list of servers.
				
				XPath: /wing-config/aaa_policy[name=key1]/auth_srvr[server_idx=key2]/server_idx"
			::= { wingCfgAaaAuthSrvrEntry 1 }

		
		-- 1.3.6.1.4.1.1916.2.131.50.1.3.7.2.1.3
		wingCfgAaaAuthSrvrType OBJECT-TYPE
			SYNTAX DisplayString
			MAX-ACCESS read-write
			STATUS current
			DESCRIPTION
				"The type of RADIUS server to use
				
				Values:
				host
				onboard-self
				onboard-controller
				
				Note: If the type is onboard-self or onboard-controller only
				then host, secret, port, and proxy-mode need be specified.
				Otherwise these parameters are not applicable.
				
				XPath: /wing-config/aaa_policy[name=key1]/auth_srvr[server_idx=key2]/server_type"
			DEFVAL { "host" }
			::= { wingCfgAaaAuthSrvrEntry 3 }

		
		-- 1.3.6.1.4.1.1916.2.131.50.1.3.7.2.1.4
		wingCfgAaaAuthSrvrHost OBJECT-TYPE
			SYNTAX DisplayString
			MAX-ACCESS read-write
			STATUS current
			DESCRIPTION
				"The hostname or IP address of the RADIUS server.
				
				XPath: /wing-config/aaa_policy[name=key1]/auth_srvr[server_idx=key2]/host"
			::= { wingCfgAaaAuthSrvrEntry 4 }

		
		-- 1.3.6.1.4.1.1916.2.131.50.1.3.7.2.1.5
		wingCfgAaaAuthSrvrSecret OBJECT-TYPE
			SYNTAX DisplayString (SIZE (0..127))
			MAX-ACCESS read-write
			STATUS current
			DESCRIPTION
				"The shared secret between the RADIUS server and the Controller/AP.
				
				XPath: /wing-config/aaa_policy[name=key1]/auth_srvr[server_idx=key2]/secret"
			DEFVAL { "" }
			::= { wingCfgAaaAuthSrvrEntry 5 }

		
		-- 1.3.6.1.4.1.1916.2.131.50.1.3.7.2.1.6
		wingCfgAaaAuthSrvrPort OBJECT-TYPE
			SYNTAX Unsigned32 (1..65535)
			MAX-ACCESS read-write
			STATUS current
			DESCRIPTION
				"The UDP port number where the RADIUS server is listening.
				
				XPath: /wing-config/aaa_policy[name=key1]/auth_srvr[server_idx=key2]/port"
			DEFVAL { 1812 }
			::= { wingCfgAaaAuthSrvrEntry 6 }

		
		-- 1.3.6.1.4.1.1916.2.131.50.1.3.7.2.1.7
		wingCfgAaaAuthSrvrTimeout OBJECT-TYPE
			SYNTAX Unsigned32 (1..60)
			UNITS "seconds"
			MAX-ACCESS read-write
			STATUS current
			DESCRIPTION
				"The timeout in seconds after which the request to
				the RADIUS server will be retried.
				
				XPath: /wing-config/aaa_policy[name=key1]/auth_srvr[server_idx=key2]/timeout"
			DEFVAL { 3 }
			::= { wingCfgAaaAuthSrvrEntry 7 }

		
		-- 1.3.6.1.4.1.1916.2.131.50.1.3.7.2.1.8
		wingCfgAaaAuthSrvrAttempts OBJECT-TYPE
			SYNTAX Unsigned32 (1..10)
			MAX-ACCESS read-write
			STATUS current
			DESCRIPTION
				"The number of times a request is sent towards a RADIUS server
				before giving up.
				
				XPath: /wing-config/aaa_policy[name=key1]/auth_srvr[server_idx=key2]/attempts"
			DEFVAL { 3 }
			::= { wingCfgAaaAuthSrvrEntry 8 }

		
		-- 1.3.6.1.4.1.1916.2.131.50.1.3.7.2.1.9
		wingCfgAaaAuthSrvrProxyMode OBJECT-TYPE
			SYNTAX DisplayString
			MAX-ACCESS read-write
			STATUS current
			DESCRIPTION
				"Specfies whether the request is transmitted directly to
				the server or proxied through either the Controller or
				the RF Domain Manager.
				
				Values:
				none
				through-controller
				through-rf-domain-manager
				
				XPath: /wing-config/aaa_policy[name=key1]/auth_srvr[server_idx=key2]/proxy_mode"
			DEFVAL { "none" }
			::= { wingCfgAaaAuthSrvrEntry 9 }

		
		-- 1.3.6.1.4.1.1916.2.131.50.1.3.7.2.1.10
		wingCfgAaaAuthSrvrNaiRouting OBJECT-TYPE
			SYNTAX TruthValue
			MAX-ACCESS read-write
			STATUS current
			DESCRIPTION
				"Whether this RADIUS server is to be selected based on part of
				the username (Network-Access-Identifier).
				
				XPath: /wing-config/aaa_policy[name=key1]/auth_srvr[server_idx=key2]/nai_routing"
			DEFVAL { false }
			::= { wingCfgAaaAuthSrvrEntry 10 }

		
		-- 1.3.6.1.4.1.1916.2.131.50.1.3.7.2.1.11
		wingCfgAaaAuthSrvrRealmType OBJECT-TYPE
			SYNTAX DisplayString
			MAX-ACCESS read-write
			STATUS current
			DESCRIPTION
				"Whether the prefix or the suffix of the username should be
				matched to the realm.
				
				Values:
				prefix
				suffix
				
				XPath: /wing-config/aaa_policy[name=key1]/auth_srvr[server_idx=key2]/realm_type"
			DEFVAL { "prefix" }
			::= { wingCfgAaaAuthSrvrEntry 11 }

		
		-- 1.3.6.1.4.1.1916.2.131.50.1.3.7.2.1.12
		wingCfgAaaAuthSrvrRealm OBJECT-TYPE
			SYNTAX DisplayString (SIZE (0..64))
			MAX-ACCESS read-write
			STATUS current
			DESCRIPTION
				"If the part of the username matches this string, this server
				is selected for authentication.
				
				XPath: /wing-config/aaa_policy[name=key1]/auth_srvr[server_idx=key2]/realm"
			DEFVAL { "" }
			::= { wingCfgAaaAuthSrvrEntry 12 }

		
		-- 1.3.6.1.4.1.1916.2.131.50.1.3.7.2.1.13
		wingCfgAaaAuthSrvrStripRealm OBJECT-TYPE
			SYNTAX TruthValue
			MAX-ACCESS read-write
			STATUS current
			DESCRIPTION
				"Configures whether the realm is stripped from the username
				before the request is forwarded to a server.
				
				XPath: /wing-config/aaa_policy[name=key1]/auth_srvr[server_idx=key2]/strip_realm"
			DEFVAL { false }
			::= { wingCfgAaaAuthSrvrEntry 13 }

		
		-- 1.3.6.1.4.1.1916.2.131.50.1.3.7.2.1.14
		wingCfgAaaAuthSrvrRetryTimeoutFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /wing-config/aaa_policy[name=key1]/auth_srvr[server_idx=key2]/retry_timeout_factor"
			DEFVAL { 100 }
			::= { wingCfgAaaAuthSrvrEntry 14 }

		
		-- 1.3.6.1.4.1.1916.2.131.50.1.3.7.2.1.15
		wingCfgAaaAuthSrvrNacEnable OBJECT-TYPE
			SYNTAX TruthValue
			MAX-ACCESS read-write
			STATUS current
			DESCRIPTION
				"Enable Network Access Control (NAC) on this RADIUS server.
				
				XPath: /wing-config/aaa_policy[name=key1]/auth_srvr[server_idx=key2]/nac_enable"
			DEFVAL { false }
			::= { wingCfgAaaAuthSrvrEntry 15 }

		
		-- 1.3.6.1.4.1.1916.2.131.50.1.3.7.2.1.16
		wingCfgAaaAuthSrvrDscp OBJECT-TYPE
			SYNTAX Unsigned32 (0..63)
			MAX-ACCESS read-write
			STATUS current
			DESCRIPTION
				"Configures the packet priority in request packets sent to
				the RADIUS server
				
				XPath: /wing-config/aaa_policy[name=key1]/auth_srvr[server_idx=key2]/dscp"
			DEFVAL { 46 }
			::= { wingCfgAaaAuthSrvrEntry 16 }

		
		-- 1.3.6.1.4.1.1916.2.131.50.1.3.7.3
		wingCfgAaaAcctSrvrTable OBJECT-TYPE
			SYNTAX SEQUENCE OF WingCfgAaaAcctSrvrEntry
			MAX-ACCESS not-accessible
			STATUS current
			DESCRIPTION
				"
				
				/wing-config/aaa_policy/acct_srvr"
			::= { wingCfgAaa 3 }

		
		-- 1.3.6.1.4.1.1916.2.131.50.1.3.7.3.1
		wingCfgAaaAcctSrvrEntry OBJECT-TYPE
			SYNTAX WingCfgAaaAcctSrvrEntry
			MAX-ACCESS not-accessible
			STATUS current
			DESCRIPTION
				"An entry in the table."
			INDEX { wingCfgAaaName, wingCfgAaaAcctSrvrIdx }
			::= { wingCfgAaaAcctSrvrTable 1 }

		
		WingCfgAaaAcctSrvrEntry ::=
			SEQUENCE { 
				wingCfgAaaAcctSrvrIdx
					Unsigned32,
				wingCfgAaaAcctSrvrType
					DisplayString,
				wingCfgAaaAcctSrvrHost
					DisplayString,
				wingCfgAaaAcctSrvrSecret
					DisplayString,
				wingCfgAaaAcctSrvrPort
					Unsigned32,
				wingCfgAaaAcctSrvrTimeout
					Unsigned32,
				wingCfgAaaAcctSrvrAttempts
					Unsigned32,
				wingCfgAaaAcctSrvrProxyMode
					DisplayString,
				wingCfgAaaAcctSrvrNaiRouting
					TruthValue,
				wingCfgAaaAcctSrvrRealmType
					DisplayString,
				wingCfgAaaAcctSrvrRealm
					DisplayString,
				wingCfgAaaAcctSrvrStripRealm
					TruthValue,
				wingCfgAaaAcctSrvrRetryTimeoutFactor
					Unsigned32,
				wingCfgAaaAcctSrvrDscp
					Unsigned32
			 }

		-- 1.3.6.1.4.1.1916.2.131.50.1.3.7.3.1.1
		wingCfgAaaAcctSrvrIdx OBJECT-TYPE
			SYNTAX Unsigned32 (1..6)
			MAX-ACCESS read-only
			STATUS current
			DESCRIPTION
				"The index into the list of servers.
				
				XPath: /wing-config/aaa_policy[name=key1]/acct_srvr[server_idx=key2]/server_idx"
			::= { wingCfgAaaAcctSrvrEntry 1 }

		
		-- 1.3.6.1.4.1.1916.2.131.50.1.3.7.3.1.3
		wingCfgAaaAcctSrvrType OBJECT-TYPE
			SYNTAX DisplayString
			MAX-ACCESS read-write
			STATUS current
			DESCRIPTION
				"The type of RADIUS server to use
				
				Values:
				host
				onboard-self
				onboard-controller
				
				Note:
				If the type is onboard-self or onboard-controller only then
				host, secret, port, and proxy-mode need be specified.
				Otherwise these parameters are not applicable.
				
				XPath: /wing-config/aaa_policy[name=key1]/acct_srvr[server_idx=key2]/server_type"
			DEFVAL { "host" }
			::= { wingCfgAaaAcctSrvrEntry 3 }

		
		-- 1.3.6.1.4.1.1916.2.131.50.1.3.7.3.1.4
		wingCfgAaaAcctSrvrHost OBJECT-TYPE
			SYNTAX DisplayString
			MAX-ACCESS read-write
			STATUS current
			DESCRIPTION
				"The hostname or IP address of the RADIUS server.
				
				XPath: /wing-config/aaa_policy[name=key1]/acct_srvr[server_idx=key2]/host"
			::= { wingCfgAaaAcctSrvrEntry 4 }

		
		-- 1.3.6.1.4.1.1916.2.131.50.1.3.7.3.1.5
		wingCfgAaaAcctSrvrSecret OBJECT-TYPE
			SYNTAX DisplayString (SIZE (0..127))
			MAX-ACCESS read-write
			STATUS current
			DESCRIPTION
				"The shared secret between the RADIUS server and
				the Controller/AP.
				
				XPath: /wing-config/aaa_policy[name=key1]/acct_srvr[server_idx=key2]/secret"
			DEFVAL { "" }
			::= { wingCfgAaaAcctSrvrEntry 5 }

		
		-- 1.3.6.1.4.1.1916.2.131.50.1.3.7.3.1.6
		wingCfgAaaAcctSrvrPort OBJECT-TYPE
			SYNTAX Unsigned32 (1..65535)
			MAX-ACCESS read-write
			STATUS current
			DESCRIPTION
				"The UDP port number where the RADIUS server is listening.
				
				XPath: /wing-config/aaa_policy[name=key1]/acct_srvr[server_idx=key2]/port"
			DEFVAL { 1813 }
			::= { wingCfgAaaAcctSrvrEntry 6 }

		
		-- 1.3.6.1.4.1.1916.2.131.50.1.3.7.3.1.7
		wingCfgAaaAcctSrvrTimeout OBJECT-TYPE
			SYNTAX Unsigned32 (1..60)
			UNITS "seconds"
			MAX-ACCESS read-write
			STATUS current
			DESCRIPTION
				"The timeout in seconds after which the request to
				the RADIUS server will be retried.
				
				XPath: /wing-config/aaa_policy[name=key1]/acct_srvr[server_idx=key2]/timeout"
			DEFVAL { 5 }
			::= { wingCfgAaaAcctSrvrEntry 7 }

		
		-- 1.3.6.1.4.1.1916.2.131.50.1.3.7.3.1.8
		wingCfgAaaAcctSrvrAttempts OBJECT-TYPE
			SYNTAX Unsigned32 (1..10)
			MAX-ACCESS read-write
			STATUS current
			DESCRIPTION
				"The number of times a request is sent towards a RADIUS server
				before giving up.
				
				XPath: /wing-config/aaa_policy[name=key1]/acct_srvr[server_idx=key2]/attempts"
			DEFVAL { 3 }
			::= { wingCfgAaaAcctSrvrEntry 8 }

		
		-- 1.3.6.1.4.1.1916.2.131.50.1.3.7.3.1.9
		wingCfgAaaAcctSrvrProxyMode OBJECT-TYPE
			SYNTAX DisplayString
			MAX-ACCESS read-write
			STATUS current
			DESCRIPTION
				"Specfies whether the request is transmitted directly to
				the server or proxied through either the Controller or
				the RF Domain Manager.
				
				Values:
				none
				through-controller
				through-rf-domain-manager
				
				XPath: /wing-config/aaa_policy[name=key1]/acct_srvr[server_idx=key2]/proxy_mode"
			DEFVAL { "none" }
			::= { wingCfgAaaAcctSrvrEntry 9 }

		
		-- 1.3.6.1.4.1.1916.2.131.50.1.3.7.3.1.10
		wingCfgAaaAcctSrvrNaiRouting OBJECT-TYPE
			SYNTAX TruthValue
			MAX-ACCESS read-write
			STATUS current
			DESCRIPTION
				"Whether this RADIUS server is to be selected based on part of
				the username (Network-Access-Identifier).
				
				XPath: /wing-config/aaa_policy[name=key1]/acct_srvr[server_idx=key2]/nai_routing"
			DEFVAL { false }
			::= { wingCfgAaaAcctSrvrEntry 10 }

		
		-- 1.3.6.1.4.1.1916.2.131.50.1.3.7.3.1.11
		wingCfgAaaAcctSrvrRealmType OBJECT-TYPE
			SYNTAX DisplayString
			MAX-ACCESS read-write
			STATUS current
			DESCRIPTION
				"Whether the prefix or the suffix of the username should be
				matched to the realm.
				
				Values:
				prefix
				suffix
				
				XPath: /wing-config/aaa_policy[name=key1]/acct_srvr[server_idx=key2]/realm_type"
			DEFVAL { "prefix" }
			::= { wingCfgAaaAcctSrvrEntry 11 }

		
		-- 1.3.6.1.4.1.1916.2.131.50.1.3.7.3.1.12
		wingCfgAaaAcctSrvrRealm OBJECT-TYPE
			SYNTAX DisplayString (SIZE (0..64))
			MAX-ACCESS read-write
			STATUS current
			DESCRIPTION
				"If a part of the username (prefix or suffix depending on
				realm_type) matches this parameter this server is selected
				for authentication.
				
				XPath: /wing-config/aaa_policy[name=key1]/acct_srvr[server_idx=key2]/realm"
			DEFVAL { "" }
			::= { wingCfgAaaAcctSrvrEntry 12 }

		
		-- 1.3.6.1.4.1.1916.2.131.50.1.3.7.3.1.13
		wingCfgAaaAcctSrvrStripRealm OBJECT-TYPE
			SYNTAX TruthValue
			MAX-ACCESS read-write
			STATUS current
			DESCRIPTION
				"Configures whether the realm is stripped from the username
				before the request is forwarded to a server.
				
				XPath: /wing-config/aaa_policy[name=key1]/acct_srvr[server_idx=key2]/strip_realm"
			DEFVAL { false }
			::= { wingCfgAaaAcctSrvrEntry 13 }

		
		-- 1.3.6.1.4.1.1916.2.131.50.1.3.7.3.1.14
		wingCfgAaaAcctSrvrRetryTimeoutFactor OBJECT-TYPE
			SYNTAX Unsigned32 (50..200)
			MAX-ACCESS read-write
			STATUS current
			DESCRIPTION
				"Configures the scaling of the retransmission attempts.
				Timeout at each attempt is a function of this retry_timeout
				factor and the attempt number. 100 implies a constant timeout
				on each retry, smaller values indicate more aggressive
				(shorter) timeouts, larger numbers indicate more conservative
				(larger) timeouts on each successive attempt.
				
				XPath: /wing-config/aaa_policy[name=key1]/acct_srvr[server_idx=key2]/retry_timeout_factor"
			DEFVAL { 100 }
			::= { wingCfgAaaAcctSrvrEntry 14 }

		
		-- 1.3.6.1.4.1.1916.2.131.50.1.3.7.3.1.15
		wingCfgAaaAcctSrvrDscp OBJECT-TYPE
			SYNTAX Unsigned32 (0..63)
			MAX-ACCESS read-write
			STATUS current
			DESCRIPTION
				"Configures the packet priority in request packets sent to
				the RADIUS server
				
				XPath: /wing-config/aaa_policy[name=key1]/acct_srvr[server_idx=key2]/dscp"
			DEFVAL { 34 }
			::= { wingCfgAaaAcctSrvrEntry 15 }

		
-- /wing-config/assoc_acl
		-- 1.3.6.1.4.1.1916.2.131.50.1.3.8
		wingCfgAssocAcl OBJECT IDENTIFIER ::= { wingConfig 8 }

		
		-- 1.3.6.1.4.1.1916.2.131.50.1.3.8.1
		wingCfgAssocAclTable OBJECT-TYPE
			SYNTAX SEQUENCE OF WingCfgAssocAclEntry
			MAX-ACCESS not-accessible
			STATUS current
			DESCRIPTION
				"Association ACL
				
				/wing-config/assoc_acl"
			::= { wingCfgAssocAcl 1 }

		
		-- 1.3.6.1.4.1.1916.2.131.50.1.3.8.1.1
		wingCfgAssocAclEntry OBJECT-TYPE
			SYNTAX WingCfgAssocAclEntry
			MAX-ACCESS not-accessible
			STATUS current
			DESCRIPTION
				"An entry in the table."
			INDEX { wingCfgAssocAclName }
			::= { wingCfgAssocAclTable 1 }

		
		WingCfgAssocAclEntry ::=
			SEQUENCE { 
				wingCfgAssocAclName
					WingIdentifier
			 }

		-- 1.3.6.1.4.1.1916.2.131.50.1.3.8.1.1.1
		wingCfgAssocAclName OBJECT-TYPE
			SYNTAX WingIdentifier
			MAX-ACCESS read-only
			STATUS current
			DESCRIPTION
				"The name of the Association ACL policy.
				
				XPath: /wing-config/assoc_acl[name=key1]/name"
			::= { wingCfgAssocAclEntry 1 }

		
		-- 1.3.6.1.4.1.1916.2.131.50.1.3.8.2
		wingCfgAssocAclRuleTable OBJECT-TYPE
			SYNTAX SEQUENCE OF WingCfgAssocAclRuleEntry
			MAX-ACCESS not-accessible
			STATUS current
			DESCRIPTION
				"
				
				/wing-config/assoc_acl/rule"
			::= { wingCfgAssocAcl 2 }

		
		-- 1.3.6.1.4.1.1916.2.131.50.1.3.8.2.1
		wingCfgAssocAclRuleEntry OBJECT-TYPE
			SYNTAX WingCfgAssocAclRuleEntry
			MAX-ACCESS not-accessible
			STATUS current
			DESCRIPTION
				"An entry in the table."
			INDEX { wingCfgAssocAclName, wingCfgAssocAclRulePrecedence }
			::= { wingCfgAssocAclRuleTable 1 }

		
		WingCfgAssocAclRuleEntry ::=
			SEQUENCE { 
				wingCfgAssocAclRulePrecedence
					Unsigned32,
				wingCfgAssocAclRulePermit
					TruthValue,
				wingCfgAssocAclRuleMac0
					MacAddress,
				wingCfgAssocAclRuleMac1
					MacAddress
			 }

		-- 1.3.6.1.4.1.1916.2.131.50.1.3.8.2.1.1
		wingCfgAssocAclRulePrecedence OBJECT-TYPE
			SYNTAX Unsigned32 (1..1000)
			MAX-ACCESS read-only
			STATUS current
			DESCRIPTION
				"The index/precedence of a particular rule. Rules are matched
				in order of increasing precedence.
				
				XPath: /wing-config/assoc_acl[name=key1]/rule[precedence=key2]/precedence"
			::= { wingCfgAssocAclRuleEntry 1 }

		
		-- 1.3.6.1.4.1.1916.2.131.50.1.3.8.2.1.3
		wingCfgAssocAclRulePermit OBJECT-TYPE
			SYNTAX TruthValue
			MAX-ACCESS read-write
			STATUS current
			DESCRIPTION
				"Configure whether to disallow access if a MAC matches
				this rule, or to fall through to the next rule.
				
				XPath: /wing-config/assoc_acl[name=key1]/rule[precedence=key2]/permit"
			DEFVAL { false }
			::= { wingCfgAssocAclRuleEntry 3 }

		
		-- 1.3.6.1.4.1.1916.2.131.50.1.3.8.2.1.4
		wingCfgAssocAclRuleMac0 OBJECT-TYPE
			SYNTAX MacAddress
			MAX-ACCESS read-write
			STATUS current
			DESCRIPTION
				"The starting MAC address in the range of MACs that apply to
				this rule.
				
				XPath: /wing-config/assoc_acl[name=key1]/rule[precedence=key2]/mac0"
			DEFVAL { '000000000000'h }
			::= { wingCfgAssocAclRuleEntry 4 }

		
		-- 1.3.6.1.4.1.1916.2.131.50.1.3.8.2.1.5
		wingCfgAssocAclRuleMac1 OBJECT-TYPE
			SYNTAX MacAddress
			MAX-ACCESS read-write
			STATUS current
			DESCRIPTION
				"The ending MAC address in the range of MACs that apply to
				this rule.
				
				XPath: /wing-config/assoc_acl[name=key1]/rule[precedence=key2]/mac1"
			DEFVAL { 'FFFFFFFFFFFF'h }
			::= { wingCfgAssocAclRuleEntry 5 }

		
-- /wing-config/smart_rf_policy
		-- 1.3.6.1.4.1.1916.2.131.50.1.3.9
		wingCfgSmartRf OBJECT IDENTIFIER ::= { wingConfig 9 }

		
		-- 1.3.6.1.4.1.1916.2.131.50.1.3.9.1
		wingCfgSmartRfTable OBJECT-TYPE
			SYNTAX SEQUENCE OF WingCfgSmartRfEntry
			MAX-ACCESS not-accessible
			STATUS current
			DESCRIPTION
				"Configuration parameters of a wireless Smart-RF profile
				
				/wing-config/smart_rf_policy"
			::= { wingCfgSmartRf 1 }

		
		-- 1.3.6.1.4.1.1916.2.131.50.1.3.9.1.1
		wingCfgSmartRfEntry OBJECT-TYPE
			SYNTAX WingCfgSmartRfEntry
			MAX-ACCESS not-accessible
			STATUS current
			DESCRIPTION
				"An entry in the table."
			INDEX { wingCfgSmartRfName }
			::= { wingCfgSmartRfTable 1 }

		
		WingCfgSmartRfEntry ::=
			SEQUENCE { 
				wingCfgSmartRfName
					WingIdentifier,
				wingCfgSmartRfEnable
					TruthValue,
				wingCfgSmartRfSensitivity
					DisplayString,
				wingCfgSmartRfAutoAssignSensor
					TruthValue,
				wingCfgSmartRfMinPowerA
					Unsigned32,
				wingCfgSmartRfMaxPowerA
					Unsigned32,
				wingCfgSmartRfMinPowerBg
					Unsigned32,
				wingCfgSmartRfMaxPowerBg
					Unsigned32,
				wingCfgSmartRfChannelWidthA
					DisplayString,
				wingCfgSmartRfChannelWidthBg
					DisplayString,
				wingCfgSmartRfGroupByArea
					TruthValue,
				wingCfgSmartRfGroupByFloor
					TruthValue,
				wingCfgSmartRfSmartOcsMonitoring
					TruthValue,
				wingCfgSmartRfOcsDurationA
					Unsigned32,
				wingCfgSmartRfOcsDurationBg
					Unsigned32,
				wingCfgSmartRfOcsFrequencyA
					Unsigned32,
				wingCfgSmartRfOcsFrequencyBg
					Unsigned32,
				wingCfgSmartRfOcsSampleCountA
					Unsigned32,
				wingCfgSmartRfOcsSampleCountBg
					Unsigned32,
				wingCfgSmartRfOcsExtendedScanFrequencyA
					Unsigned32,
				wingCfgSmartRfOcsExtendedScanFrequencyBg
					Unsigned32,
				wingCfgSmartRfOcsVoiceAwareA
					DisplayString,
				wingCfgSmartRfOcsVoiceAwareBg
					DisplayString,
				wingCfgSmartRfOcsPspAwareA
					DisplayString,
				wingCfgSmartRfOcsPspAwareBg
					DisplayString,
				wingCfgSmartRfInterferenceRecovery
					TruthValue,
				wingCfgSmartRfIrNoise
					TruthValue,
				wingCfgSmartRfIrInterference
					TruthValue,
				wingCfgSmartRfIrClientThreshold
					Unsigned32,
				wingCfgSmartRfIrChannelSwitchDeltaA
					Unsigned32,
				wingCfgSmartRfIrChannelSwitchDeltaBg
					Unsigned32,
				wingCfgSmartRfNeighborRecovery
					TruthValue,
				wingCfgSmartRfNrPowerThresholdA
					Integer32,
				wingCfgSmartRfNrPowerThresholdBg
					Integer32,
				wingCfgSmartRfCoverageHoleRecovery
					TruthValue,
				wingCfgSmartRfChrIntervalA
					Unsigned32,
				wingCfgSmartRfChrIntervalBg
					Unsigned32,
				wingCfgSmartRfChrCovIntervalA
					Unsigned32,
				wingCfgSmartRfChrCovIntervalBg
					Unsigned32,
				wingCfgSmartRfChrSnrThresholdA
					Unsigned32,
				wingCfgSmartRfChrSnrThresholdBg
					Unsigned32,
				wingCfgSmartRfChrClientThresholdA
					Unsigned32,
				wingCfgSmartRfChrClientThresholdBg
					Unsigned32,
				wingCfgSmartRfChannelHoldTime
					Unsigned32,
				wingCfgSmartRfPowerHoldTime
					Unsigned32,
				wingCfgSmartRfOcsMeshpointA
					DisplayString,
				wingCfgSmartRfOcsMeshpointBg
					DisplayString
			 }

		-- 1.3.6.1.4.1.1916.2.131.50.1.3.9.1.1.1
		wingCfgSmartRfName OBJECT-TYPE
			SYNTAX WingIdentifier
			MAX-ACCESS read-only
			STATUS current
			DESCRIPTION
				"
				
				XPath: /wing-config/smart_rf_policy[name=key1]/name"
			::= { wingCfgSmartRfEntry 1 }

		
		-- 1.3.6.1.4.1.1916.2.131.50.1.3.9.1.1.3
		wingCfgSmartRfEnable OBJECT-TYPE
			SYNTAX TruthValue
			MAX-ACCESS read-write
			STATUS current
			DESCRIPTION
				"
				
				XPath: /wing-config/smart_rf_policy[name=key1]/enable"
			DEFVAL { false }
			::= { wingCfgSmartRfEntry 3 }

		
		-- 1.3.6.1.4.1.1916.2.131.50.1.3.9.1.1.4
		wingCfgSmartRfSensitivity OBJECT-TYPE
			SYNTAX DisplayString
			MAX-ACCESS read-write
			STATUS current
			DESCRIPTION
				"choose smart-rf sensitivity settings, modifies configuration
				parameters to preset values.
				
				Values:
				low
				medium
				high
				custom
				
				XPath: /wing-config/smart_rf_policy[name=key1]/sensitivity"
			DEFVAL { "medium" }
			::= { wingCfgSmartRfEntry 4 }

		
		-- 1.3.6.1.4.1.1916.2.131.50.1.3.9.1.1.5
		wingCfgSmartRfAutoAssignSensor OBJECT-TYPE
			SYNTAX TruthValue
			MAX-ACCESS read-write
			STATUS current
			DESCRIPTION
				"smart-rf automatically assigns optimal sensors for wips and
				rogue ap detection.
				
				XPath: /wing-config/smart_rf_policy[name=key1]/auto_assign_sensor"
			DEFVAL { false }
			::= { wingCfgSmartRfEntry 5 }

		
		-- 1.3.6.1.4.1.1916.2.131.50.1.3.9.1.1.6
		wingCfgSmartRfMinPowerA OBJECT-TYPE
			SYNTAX Unsigned32 (1..20)
			UNITS "dBm"
			MAX-ACCESS read-write
			STATUS current
			DESCRIPTION
				"Minimum assignable power on 5GHz radios
				
				XPath: /wing-config/smart_rf_policy[name=key1]/min_power_a"
			DEFVAL { 4 }
			::= { wingCfgSmartRfEntry 6 }

		
		-- 1.3.6.1.4.1.1916.2.131.50.1.3.9.1.1.7
		wingCfgSmartRfMaxPowerA OBJECT-TYPE
			SYNTAX Unsigned32 (1..20)
			UNITS "dBm"
			MAX-ACCESS read-write
			STATUS current
			DESCRIPTION
				"Maximum assignable power on 5GHz radios
				
				XPath: /wing-config/smart_rf_policy[name=key1]/max_power_a"
			DEFVAL { 17 }
			::= { wingCfgSmartRfEntry 7 }

		
		-- 1.3.6.1.4.1.1916.2.131.50.1.3.9.1.1.8
		wingCfgSmartRfMinPowerBg OBJECT-TYPE
			SYNTAX Unsigned32 (1..20)
			UNITS "dBm"
			MAX-ACCESS read-write
			STATUS current
			DESCRIPTION
				"Minimum assignable power on 2.4GHz radios
				
				XPath: /wing-config/smart_rf_policy[name=key1]/min_power_bg"
			DEFVAL { 4 }
			::= { wingCfgSmartRfEntry 8 }

		
		-- 1.3.6.1.4.1.1916.2.131.50.1.3.9.1.1.9
		wingCfgSmartRfMaxPowerBg OBJECT-TYPE
			SYNTAX Unsigned32 (1..20)
			UNITS "dBm"
			MAX-ACCESS read-write
			STATUS current
			DESCRIPTION
				"Maximum assignable power on 2.4GHz radios
				
				XPath: /wing-config/smart_rf_policy[name=key1]/max_power_bg"
			DEFVAL { 17 }
			::= { wingCfgSmartRfEntry 9 }

		
		-- 1.3.6.1.4.1.1916.2.131.50.1.3.9.1.1.10
		wingCfgSmartRfChannelWidthA OBJECT-TYPE
			SYNTAX DisplayString
			MAX-ACCESS read-write
			STATUS current
			DESCRIPTION
				"Channel width that Smart-RF should assign to 5GHz radios
				
				Values:
				20MHz
				40MHz
				auto
				
				XPath: /wing-config/smart_rf_policy[name=key1]/channel_width_a"
			DEFVAL { "40MHz" }
			::= { wingCfgSmartRfEntry 10 }

		
		-- 1.3.6.1.4.1.1916.2.131.50.1.3.9.1.1.11
		wingCfgSmartRfChannelWidthBg OBJECT-TYPE
			SYNTAX DisplayString
			MAX-ACCESS read-write
			STATUS current
			DESCRIPTION
				"Channel width that Smart-RF should assign to 2.4GHz radios
				
				Values:
				20MHz
				40MHz
				auto
				
				XPath: /wing-config/smart_rf_policy[name=key1]/channel_width_bg"
			DEFVAL { "20MHz" }
			::= { wingCfgSmartRfEntry 11 }

		
		-- 1.3.6.1.4.1.1916.2.131.50.1.3.9.1.1.12
		wingCfgSmartRfGroupByArea OBJECT-TYPE
			SYNTAX TruthValue
			MAX-ACCESS read-write
			STATUS current
			DESCRIPTION
				"Perform grouping of radios by area.
				
				XPath: /wing-config/smart_rf_policy[name=key1]/group_by_area"
			DEFVAL { false }
			::= { wingCfgSmartRfEntry 12 }

		
		-- 1.3.6.1.4.1.1916.2.131.50.1.3.9.1.1.13
		wingCfgSmartRfGroupByFloor OBJECT-TYPE
			SYNTAX TruthValue
			MAX-ACCESS read-write
			STATUS current
			DESCRIPTION
				"Perform grouping of radios by floor.
				
				XPath: /wing-config/smart_rf_policy[name=key1]/group_by_floor"
			DEFVAL { false }
			::= { wingCfgSmartRfEntry 13 }

		
		-- 1.3.6.1.4.1.1916.2.131.50.1.3.9.1.1.14
		wingCfgSmartRfSmartOcsMonitoring OBJECT-TYPE
			SYNTAX TruthValue
			MAX-ACCESS read-write
			STATUS current
			DESCRIPTION
				"Perform off channel scanning to perform recoveries.
				
				XPath: /wing-config/smart_rf_policy[name=key1]/smart_ocs_monitoring"
			DEFVAL { true }
			::= { wingCfgSmartRfEntry 14 }

		
		-- 1.3.6.1.4.1.1916.2.131.50.1.3.9.1.1.15
		wingCfgSmartRfOcsDurationA OBJECT-TYPE
			SYNTAX Unsigned32 (20..150)
			UNITS "milliseconds"
			MAX-ACCESS read-write
			STATUS current
			DESCRIPTION
				"Duration in milliseconds to spend off-channel for 5GHz radios.
				
				XPath: /wing-config/smart_rf_policy[name=key1]/ocs_duration_a"
			DEFVAL { 50 }
			::= { wingCfgSmartRfEntry 15 }

		
		-- 1.3.6.1.4.1.1916.2.131.50.1.3.9.1.1.16
		wingCfgSmartRfOcsDurationBg OBJECT-TYPE
			SYNTAX Unsigned32 (20..150)
			UNITS "milliseconds"
			MAX-ACCESS read-write
			STATUS current
			DESCRIPTION
				"Duration in milliseconds to spend off-channel for
				2.4GHz radios.
				
				XPath: /wing-config/smart_rf_policy[name=key1]/ocs_duration_bg"
			DEFVAL { 50 }
			::= { wingCfgSmartRfEntry 16 }

		
		-- 1.3.6.1.4.1.1916.2.131.50.1.3.9.1.1.17
		wingCfgSmartRfOcsFrequencyA OBJECT-TYPE
			SYNTAX Unsigned32 (1..120)
			UNITS "seconds"
			MAX-ACCESS read-write
			STATUS current
			DESCRIPTION
				"Frequency at which off channel scanning has to be performed
				for 5GHz radios.
				
				XPath: /wing-config/smart_rf_policy[name=key1]/ocs_frequency_a"
			DEFVAL { 6 }
			::= { wingCfgSmartRfEntry 17 }

		
		-- 1.3.6.1.4.1.1916.2.131.50.1.3.9.1.1.18
		wingCfgSmartRfOcsFrequencyBg OBJECT-TYPE
			SYNTAX Unsigned32 (1..120)
			UNITS "seconds"
			MAX-ACCESS read-write
			STATUS current
			DESCRIPTION
				"Frequency at which off channel scanning has to be performed
				for 2.4GHz radios.
				
				XPath: /wing-config/smart_rf_policy[name=key1]/ocs_frequency_bg"
			DEFVAL { 6 }
			::= { wingCfgSmartRfEntry 18 }

		
		-- 1.3.6.1.4.1.1916.2.131.50.1.3.9.1.1.19
		wingCfgSmartRfOcsSampleCountA OBJECT-TYPE
			SYNTAX Unsigned32 (1..15)
			MAX-ACCESS read-write
			STATUS current
			DESCRIPTION
				"Number of samples to take during off channel scan for
				5GHz radios.
				
				XPath: /wing-config/smart_rf_policy[name=key1]/ocs_sample_count_a"
			DEFVAL { 5 }
			::= { wingCfgSmartRfEntry 19 }

		
		-- 1.3.6.1.4.1.1916.2.131.50.1.3.9.1.1.20
		wingCfgSmartRfOcsSampleCountBg OBJECT-TYPE
			SYNTAX Unsigned32 (1..15)
			MAX-ACCESS read-write
			STATUS current
			DESCRIPTION
				"Number of samples to take during off channel scan for
				2.4GHz radios.
				
				XPath: /wing-config/smart_rf_policy[name=key1]/ocs_sample_count_bg"
			DEFVAL { 5 }
			::= { wingCfgSmartRfEntry 20 }

		
		-- 1.3.6.1.4.1.1916.2.131.50.1.3.9.1.1.21
		wingCfgSmartRfOcsExtendedScanFrequencyA OBJECT-TYPE
			SYNTAX Unsigned32 (0..50)
			MAX-ACCESS read-write
			STATUS current
			DESCRIPTION
				"Frequency at which an extended scan has to be performed on
				5GHz radios instead of a normal neighbor only scan.
				
				XPath: /wing-config/smart_rf_policy[name=key1]/ocs_extended_scan_frequency_a"
			DEFVAL { 5 }
			::= { wingCfgSmartRfEntry 21 }

		
		-- 1.3.6.1.4.1.1916.2.131.50.1.3.9.1.1.22
		wingCfgSmartRfOcsExtendedScanFrequencyBg OBJECT-TYPE
			SYNTAX Unsigned32 (0..50)
			MAX-ACCESS read-write
			STATUS current
			DESCRIPTION
				"Frequency at which an extended scan has to be performed on
				2.4GHz radios instead of a normal neighbor only scan.
				
				XPath: /wing-config/smart_rf_policy[name=key1]/ocs_extended_scan_frequency_bg"
			DEFVAL { 5 }
			::= { wingCfgSmartRfEntry 22 }

		
		-- 1.3.6.1.4.1.1916.2.131.50.1.3.9.1.1.23
		wingCfgSmartRfOcsVoiceAwareA OBJECT-TYPE
			SYNTAX DisplayString
			MAX-ACCESS read-write
			STATUS current
			DESCRIPTION
				"Voice awareness setting during off channel scan for
				5GHz radios
				
				Values:
				dynamic
				strict
				disable
				
				XPath: /wing-config/smart_rf_policy[name=key1]/ocs_voice_aware_a"
			DEFVAL { "dynamic" }
			::= { wingCfgSmartRfEntry 23 }

		
		-- 1.3.6.1.4.1.1916.2.131.50.1.3.9.1.1.24
		wingCfgSmartRfOcsVoiceAwareBg OBJECT-TYPE
			SYNTAX DisplayString
			MAX-ACCESS read-write
			STATUS current
			DESCRIPTION
				"Voice awareness setting during off channel scan for
				2.4GHz radios
				
				Values:
				dynamic
				strict
				disable
				
				XPath: /wing-config/smart_rf_policy[name=key1]/ocs_voice_aware_bg"
			DEFVAL { "dynamic" }
			::= { wingCfgSmartRfEntry 24 }

		
		-- 1.3.6.1.4.1.1916.2.131.50.1.3.9.1.1.25
		wingCfgSmartRfOcsPspAwareA OBJECT-TYPE
			SYNTAX DisplayString
			MAX-ACCESS read-write
			STATUS current
			DESCRIPTION
				"PSP awareness setting during off channel scan for 5GHz radios
				
				Values:
				dynamic
				strict
				disable
				
				XPath: /wing-config/smart_rf_policy[name=key1]/ocs_psp_aware_a"
			DEFVAL { "dynamic" }
			::= { wingCfgSmartRfEntry 25 }

		
		-- 1.3.6.1.4.1.1916.2.131.50.1.3.9.1.1.26
		wingCfgSmartRfOcsPspAwareBg OBJECT-TYPE
			SYNTAX DisplayString
			MAX-ACCESS read-write
			STATUS current
			DESCRIPTION
				"PSP awareness setting during off channel scan for
				2.4GHz radios
				
				Values:
				dynamic
				strict
				disable
				
				XPath: /wing-config/smart_rf_policy[name=key1]/ocs_psp_aware_bg"
			DEFVAL { "dynamic" }
			::= { wingCfgSmartRfEntry 26 }

		
		-- 1.3.6.1.4.1.1916.2.131.50.1.3.9.1.1.27
		wingCfgSmartRfInterferenceRecovery OBJECT-TYPE
			SYNTAX TruthValue
			MAX-ACCESS read-write
			STATUS current
			DESCRIPTION
				"Recover issues due to excessive noise and interference.
				
				XPath: /wing-config/smart_rf_policy[name=key1]/interference_recovery"
			DEFVAL { true }
			::= { wingCfgSmartRfEntry 27 }

		
		-- 1.3.6.1.4.1.1916.2.131.50.1.3.9.1.1.28
		wingCfgSmartRfIrNoise OBJECT-TYPE
			SYNTAX TruthValue
			MAX-ACCESS read-write
			STATUS current
			DESCRIPTION
				"Take noise into consideration while performing interference
				recovery.
				
				XPath: /wing-config/smart_rf_policy[name=key1]/ir_noise"
			DEFVAL { true }
			::= { wingCfgSmartRfEntry 28 }

		
		-- 1.3.6.1.4.1.1916.2.131.50.1.3.9.1.1.29
		wingCfgSmartRfIrInterference OBJECT-TYPE
			SYNTAX TruthValue
			MAX-ACCESS read-write
			STATUS current
			DESCRIPTION
				"Take external interference into consideration while performing
				interference recovery.
				
				XPath: /wing-config/smart_rf_policy[name=key1]/ir_interference"
			DEFVAL { true }
			::= { wingCfgSmartRfEntry 29 }

		
		-- 1.3.6.1.4.1.1916.2.131.50.1.3.9.1.1.30
		wingCfgSmartRfIrClientThreshold OBJECT-TYPE
			SYNTAX Unsigned32 (1..255)
			MAX-ACCESS read-write
			STATUS current
			DESCRIPTION
				"Number of associated clients after which channel change due to
				interference recovery is not allowed.
				
				XPath: /wing-config/smart_rf_policy[name=key1]/ir_client_threshold"
			DEFVAL { 50 }
			::= { wingCfgSmartRfEntry 30 }

		
		-- 1.3.6.1.4.1.1916.2.131.50.1.3.9.1.1.31
		wingCfgSmartRfIrChannelSwitchDeltaA OBJECT-TYPE
			SYNTAX Unsigned32 (5..35)
			UNITS "dBm"
			MAX-ACCESS read-write
			STATUS current
			DESCRIPTION
				"Difference in interference between current channel and
				the best possible channel to perform a channel switch on
				5GHz radios
				
				XPath: /wing-config/smart_rf_policy[name=key1]/ir_channel_switch_delta_a"
			DEFVAL { 20 }
			::= { wingCfgSmartRfEntry 31 }

		
		-- 1.3.6.1.4.1.1916.2.131.50.1.3.9.1.1.32
		wingCfgSmartRfIrChannelSwitchDeltaBg OBJECT-TYPE
			SYNTAX Unsigned32 (5..35)
			UNITS "dBm"
			MAX-ACCESS read-write
			STATUS current
			DESCRIPTION
				"Difference in interference between current channel and
				the best possible channel to perform a channel switch on
				2.4GHz radios
				
				XPath: /wing-config/smart_rf_policy[name=key1]/ir_channel_switch_delta_bg"
			DEFVAL { 20 }
			::= { wingCfgSmartRfEntry 32 }

		
		-- 1.3.6.1.4.1.1916.2.131.50.1.3.9.1.1.33
		wingCfgSmartRfNeighborRecovery OBJECT-TYPE
			SYNTAX TruthValue
			MAX-ACCESS read-write
			STATUS current
			DESCRIPTION
				"Recover issues due to faulty neighbor radios.
				
				XPath: /wing-config/smart_rf_policy[name=key1]/neighbor_recovery"
			DEFVAL { true }
			::= { wingCfgSmartRfEntry 33 }

		
		-- 1.3.6.1.4.1.1916.2.131.50.1.3.9.1.1.34
		wingCfgSmartRfNrPowerThresholdA OBJECT-TYPE
			SYNTAX Integer32 (-85..-55)
			UNITS "dBm"
			MAX-ACCESS read-write
			STATUS current
			DESCRIPTION
				"Power threshold to be used while performing neighbor recovery
				on 5GHz radios.
				
				XPath: /wing-config/smart_rf_policy[name=key1]/nr_power_threshold_a"
			DEFVAL { -70 }
			::= { wingCfgSmartRfEntry 34 }

		
		-- 1.3.6.1.4.1.1916.2.131.50.1.3.9.1.1.35
		wingCfgSmartRfNrPowerThresholdBg OBJECT-TYPE
			SYNTAX Integer32 (-85..-55)
			UNITS "dBm"
			MAX-ACCESS read-write
			STATUS current
			DESCRIPTION
				"Power threshold to be used while performing neighbor recovery
				on 2.4GHz radios.
				
				XPath: /wing-config/smart_rf_policy[name=key1]/nr_power_threshold_bg"
			DEFVAL { -70 }
			::= { wingCfgSmartRfEntry 35 }

		
		-- 1.3.6.1.4.1.1916.2.131.50.1.3.9.1.1.36
		wingCfgSmartRfCoverageHoleRecovery OBJECT-TYPE
			SYNTAX TruthValue
			MAX-ACCESS read-write
			STATUS current
			DESCRIPTION
				"Recover from coverage hole.
				
				XPath: /wing-config/smart_rf_policy[name=key1]/coverage_hole_recovery"
			DEFVAL { true }
			::= { wingCfgSmartRfEntry 36 }

		
		-- 1.3.6.1.4.1.1916.2.131.50.1.3.9.1.1.37
		wingCfgSmartRfChrIntervalA OBJECT-TYPE
			SYNTAX Unsigned32 (1..120)
			UNITS "seconds"
			MAX-ACCESS read-write
			STATUS current
			DESCRIPTION
				"Interval at which coverage-hole-recovery should be performed
				for 5GHz radios.
				
				XPath: /wing-config/smart_rf_policy[name=key1]/chr_interval_a"
			DEFVAL { 30 }
			::= { wingCfgSmartRfEntry 37 }

		
		-- 1.3.6.1.4.1.1916.2.131.50.1.3.9.1.1.38
		wingCfgSmartRfChrIntervalBg OBJECT-TYPE
			SYNTAX Unsigned32 (1..120)
			UNITS "seconds"
			MAX-ACCESS read-write
			STATUS current
			DESCRIPTION
				"Interval at which coverage-hole-recovery should be performed
				for 2.4GHz radios.
				
				XPath: /wing-config/smart_rf_policy[name=key1]/chr_interval_bg"
			DEFVAL { 30 }
			::= { wingCfgSmartRfEntry 38 }

		
		-- 1.3.6.1.4.1.1916.2.131.50.1.3.9.1.1.39
		wingCfgSmartRfChrCovIntervalA OBJECT-TYPE
			SYNTAX Unsigned32 (1..120)
			UNITS "seconds"
			MAX-ACCESS read-write
			STATUS current
			DESCRIPTION
				"Interval at which coverage-hole-recovery should be performed
				after coverage hole is discovered for 5GHz radios.
				
				XPath: /wing-config/smart_rf_policy[name=key1]/chr_cov_interval_a"
			DEFVAL { 10 }
			::= { wingCfgSmartRfEntry 39 }

		
		-- 1.3.6.1.4.1.1916.2.131.50.1.3.9.1.1.40
		wingCfgSmartRfChrCovIntervalBg OBJECT-TYPE
			SYNTAX Unsigned32 (1..120)
			UNITS "seconds"
			MAX-ACCESS read-write
			STATUS current
			DESCRIPTION
				"Interval at which coverage-hole-recovery should be performed
				after coverage hole is discovered for 2.4GHz radios.
				
				XPath: /wing-config/smart_rf_policy[name=key1]/chr_cov_interval_bg"
			DEFVAL { 10 }
			::= { wingCfgSmartRfEntry 40 }

		
		-- 1.3.6.1.4.1.1916.2.131.50.1.3.9.1.1.41
		wingCfgSmartRfChrSnrThresholdA OBJECT-TYPE
			SYNTAX Unsigned32 (1..75)
			UNITS "dB"
			MAX-ACCESS read-write
			STATUS current
			DESCRIPTION
				"The signal to noise ratio below which coverage recovery is
				initiated for 5GHz radios.
				
				XPath: /wing-config/smart_rf_policy[name=key1]/chr_snr_threshold_a"
			DEFVAL { 20 }
			::= { wingCfgSmartRfEntry 41 }

		
		-- 1.3.6.1.4.1.1916.2.131.50.1.3.9.1.1.42
		wingCfgSmartRfChrSnrThresholdBg OBJECT-TYPE
			SYNTAX Unsigned32 (1..75)
			UNITS "dB"
			MAX-ACCESS read-write
			STATUS current
			DESCRIPTION
				"The signal to noise ratio below which coverage recovery is
				initiated for 2.4GHz radios.
				
				XPath: /wing-config/smart_rf_policy[name=key1]/chr_snr_threshold_bg"
			DEFVAL { 20 }
			::= { wingCfgSmartRfEntry 42 }

		
		-- 1.3.6.1.4.1.1916.2.131.50.1.3.9.1.1.43
		wingCfgSmartRfChrClientThresholdA OBJECT-TYPE
			SYNTAX Unsigned32 (1..255)
			MAX-ACCESS read-write
			STATUS current
			DESCRIPTION
				"Minimum number of clients below SNR threhold required for
				coverage hole recovery on 5GHz radios.
				
				XPath: /wing-config/smart_rf_policy[name=key1]/chr_client_threshold_a"
			DEFVAL { 1 }
			::= { wingCfgSmartRfEntry 43 }

		
		-- 1.3.6.1.4.1.1916.2.131.50.1.3.9.1.1.44
		wingCfgSmartRfChrClientThresholdBg OBJECT-TYPE
			SYNTAX Unsigned32 (1..255)
			MAX-ACCESS read-write
			STATUS current
			DESCRIPTION
				"Minimum number of clients below SNR threhold required for
				coverage hole recovery on 2.4GHz radios.
				
				XPath: /wing-config/smart_rf_policy[name=key1]/chr_client_threshold_bg"
			DEFVAL { 1 }
			::= { wingCfgSmartRfEntry 44 }

		
		-- 1.3.6.1.4.1.1916.2.131.50.1.3.9.1.1.45
		wingCfgSmartRfChannelHoldTime OBJECT-TYPE
			SYNTAX Unsigned32 (0..86400)
			UNITS "seconds"
			MAX-ACCESS read-write
			STATUS current
			DESCRIPTION
				"The minimum time between two channel changes on a radio
				during interference recovery.
				
				XPath: /wing-config/smart_rf_policy[name=key1]/channel_hold_time"
			DEFVAL { 3600 }
			::= { wingCfgSmartRfEntry 45 }

		
		-- 1.3.6.1.4.1.1916.2.131.50.1.3.9.1.1.46
		wingCfgSmartRfPowerHoldTime OBJECT-TYPE
			SYNTAX Unsigned32 (0..3600)
			UNITS "seconds"
			MAX-ACCESS read-write
			STATUS current
			DESCRIPTION
				"The minimum time between two power changes on a radio during
				neighbor recovery.
				
				XPath: /wing-config/smart_rf_policy[name=key1]/power_hold_time"
			DEFVAL { 0 }
			::= { wingCfgSmartRfEntry 46 }

		
		-- 1.3.6.1.4.1.1916.2.131.50.1.3.9.1.1.47
		wingCfgSmartRfOcsMeshpointA OBJECT-TYPE
			SYNTAX DisplayString (SIZE (1..64))
			MAX-ACCESS read-write
			STATUS current
			DESCRIPTION
				"Meshpoint to be monitored during off channel scan for 5GHz radios
				
				XPath: /wing-config/smart_rf_policy[name=key1]/ocs_meshpoint_a"
			::= { wingCfgSmartRfEntry 47 }

		
		-- 1.3.6.1.4.1.1916.2.131.50.1.3.9.1.1.48
		wingCfgSmartRfOcsMeshpointBg OBJECT-TYPE
			SYNTAX DisplayString (SIZE (1..64))
			MAX-ACCESS read-write
			STATUS current
			DESCRIPTION
				"Meshpoint to be monitored during off channel scan for 2.4GHz radios
				
				XPath: /wing-config/smart_rf_policy[name=key1]/ocs_meshpoint_bg"
			::= { wingCfgSmartRfEntry 48 }

		
-- /wing-config/captive_portal
		-- 1.3.6.1.4.1.1916.2.131.50.1.3.10
		wingCfgCaptPrtl OBJECT IDENTIFIER ::= { wingConfig 10 }

		
		-- 1.3.6.1.4.1.1916.2.131.50.1.3.10.1
		wingCfgCaptPrtlTable OBJECT-TYPE
			SYNTAX SEQUENCE OF WingCfgCaptPrtlEntry
			MAX-ACCESS not-accessible
			STATUS current
			DESCRIPTION
				"Configuration parameters of a WLAN/VLAN captive portal
				authentication profile
				
				/wing-config/captive_portal"
			::= { wingCfgCaptPrtl 1 }

		
		-- 1.3.6.1.4.1.1916.2.131.50.1.3.10.1.1
		wingCfgCaptPrtlEntry OBJECT-TYPE
			SYNTAX WingCfgCaptPrtlEntry
			MAX-ACCESS not-accessible
			STATUS current
			DESCRIPTION
				"An entry in the table."
			INDEX { wingCfgCaptPrtlName }
			::= { wingCfgCaptPrtlTable 1 }

		
		WingCfgCaptPrtlEntry ::=
			SEQUENCE { 
				wingCfgCaptPrtlName
					WingIdentifier,
				wingCfgCaptPrtlAccessType
					DisplayString,
				wingCfgCaptPrtlAccessTime
					Unsigned32,
				wingCfgCaptPrtlCustomAuthInfo
					DisplayString,
				wingCfgCaptPrtlConnectionMode
					DisplayString,
				wingCfgCaptPrtlInactivityTimeout
					Unsigned32,
				wingCfgCaptPrtlServer
					DisplayString,
				wingCfgCaptPrtlServerMode
					DisplayString,
				wingCfgCaptPrtlSimultaneousUsers
					Unsigned32,
				wingCfgCaptPrtlTermsAgreement
					TruthValue,
				wingCfgCaptPrtlWebpageLocation
					DisplayString,
				wingCfgCaptPrtlAccountingRadius
					TruthValue,
				wingCfgCaptPrtlAaaPolicy
					WingIdentifier,
				wingCfgCaptPrtlDnsWhitelist
					WingIdentifier
			 }

		-- 1.3.6.1.4.1.1916.2.131.50.1.3.10.1.1.1
		wingCfgCaptPrtlName OBJECT-TYPE
			SYNTAX WingIdentifier
			MAX-ACCESS read-only
			STATUS current
			DESCRIPTION
				"
				
				XPath: /wing-config/captive_portal[name=key1]/name"
			::= { wingCfgCaptPrtlEntry 1 }

		
		-- 1.3.6.1.4.1.1916.2.131.50.1.3.10.1.1.3
		wingCfgCaptPrtlAccessType OBJECT-TYPE
			SYNTAX DisplayString
			MAX-ACCESS read-write
			STATUS current
			DESCRIPTION
				"Access type of this captive portal
				
				Values:
				no-auth
				logging
				custom-auth-radius
				radius
				
				XPath: /wing-config/captive_portal[name=key1]/access_type"
			DEFVAL { "radius" }
			::= { wingCfgCaptPrtlEntry 3 }

		
		-- 1.3.6.1.4.1.1916.2.131.50.1.3.10.1.1.4
		wingCfgCaptPrtlAccessTime OBJECT-TYPE
			SYNTAX Unsigned32 (30..10080)
			UNITS "minutes"
			MAX-ACCESS read-write
			STATUS current
			DESCRIPTION
				"Allowed access time for the client. Used when there is
				no session time value in RADIUS response.
				
				XPath: /wing-config/captive_portal[name=key1]/access_time"
			DEFVAL { 1440 }
			::= { wingCfgCaptPrtlEntry 4 }

		
		-- 1.3.6.1.4.1.1916.2.131.50.1.3.10.1.1.5
		wingCfgCaptPrtlCustomAuthInfo OBJECT-TYPE
			SYNTAX DisplayString (SIZE (32))
			MAX-ACCESS read-write
			STATUS current
			DESCRIPTION
				"Custom user information used for RADIUS lookup/logging when
				access-type custom-auth-radius/logging is configured.
				
				XPath: /wing-config/captive_portal[name=key1]/custom_auth_info"
			::= { wingCfgCaptPrtlEntry 5 }

		
		-- 1.3.6.1.4.1.1916.2.131.50.1.3.10.1.1.6
		wingCfgCaptPrtlConnectionMode OBJECT-TYPE
			SYNTAX DisplayString
			MAX-ACCESS read-write
			STATUS current
			DESCRIPTION
				"
				Values:
				http
				https
				
				XPath: /wing-config/captive_portal[name=key1]/connection_mode"
			DEFVAL { "http" }
			::= { wingCfgCaptPrtlEntry 6 }

		
		-- 1.3.6.1.4.1.1916.2.131.50.1.3.10.1.1.7
		wingCfgCaptPrtlInactivityTimeout OBJECT-TYPE
			SYNTAX Unsigned32 (300..1800)
			UNITS "seconds"
			MAX-ACCESS read-write
			STATUS current
			DESCRIPTION
				"If a frame is not received from client for this
				amount of time, then current session will be removed.
				
				XPath: /wing-config/captive_portal[name=key1]/inactivity_timeout"
			DEFVAL { 600 }
			::= { wingCfgCaptPrtlEntry 7 }

		
		-- 1.3.6.1.4.1.1916.2.131.50.1.3.10.1.1.8
		wingCfgCaptPrtlServer OBJECT-TYPE
			SYNTAX DisplayString
			MAX-ACCESS read-write
			STATUS current
			DESCRIPTION
				"Device(s) hosting the captive portal service, Address of
				controller or access point for centralized mode,
				Virtual hostname of controller(s) in case of
				centralized-controller mode
				
				XPath: /wing-config/captive_portal[name=key1]/server"
			::= { wingCfgCaptPrtlEntry 8 }

		
		-- 1.3.6.1.4.1.1916.2.131.50.1.3.10.1.1.9
		wingCfgCaptPrtlServerMode OBJECT-TYPE
			SYNTAX DisplayString
			MAX-ACCESS read-write
			STATUS current
			DESCRIPTION
				"In centralized/centralized-controller mode, the configured
				server is used as the captive portal server.  In self mode,
				the device serving the WLAN is used as the
				captive portal server.
				
				Values:
				self
				centralized
				centralized-controller
				
				XPath: /wing-config/captive_portal[name=key1]/server_mode"
			DEFVAL { "self" }
			::= { wingCfgCaptPrtlEntry 9 }

		
		-- 1.3.6.1.4.1.1916.2.131.50.1.3.10.1.1.10
		wingCfgCaptPrtlSimultaneousUsers OBJECT-TYPE
			SYNTAX Unsigned32 (1..8192)
			MAX-ACCESS read-write
			STATUS current
			DESCRIPTION
				"Number of MAC addresses that are allowed to use a username at
				the same time.
				
				XPath: /wing-config/captive_portal[name=key1]/simultaneous-users"
			::= { wingCfgCaptPrtlEntry 10 }

		
		-- 1.3.6.1.4.1.1916.2.131.50.1.3.10.1.1.11
		wingCfgCaptPrtlTermsAgreement OBJECT-TYPE
			SYNTAX TruthValue
			MAX-ACCESS read-write
			STATUS current
			DESCRIPTION
				"Combined with any access type, terms needs to be included in
				agreement page
				
				XPath: /wing-config/captive_portal[name=key1]/terms_agreement"
			DEFVAL { false }
			::= { wingCfgCaptPrtlEntry 11 }

		
		-- 1.3.6.1.4.1.1916.2.131.50.1.3.10.1.1.12
		wingCfgCaptPrtlWebpageLocation OBJECT-TYPE
			SYNTAX DisplayString
			MAX-ACCESS read-write
			STATUS current
			DESCRIPTION
				"
				Values:
				internal
				external
				advanced
				
				XPath: /wing-config/captive_portal[name=key1]/webpage_location"
			DEFVAL { "internal" }
			::= { wingCfgCaptPrtlEntry 12 }

		
		-- 1.3.6.1.4.1.1916.2.131.50.1.3.10.1.1.13
		wingCfgCaptPrtlAccountingRadius OBJECT-TYPE
			SYNTAX TruthValue
			MAX-ACCESS read-write
			STATUS current
			DESCRIPTION
				"
				
				XPath: /wing-config/captive_portal[name=key1]/accounting_radius"
			DEFVAL { false }
			::= { wingCfgCaptPrtlEntry 13 }

		
		-- 1.3.6.1.4.1.1916.2.131.50.1.3.10.1.1.14
		wingCfgCaptPrtlAaaPolicy OBJECT-TYPE
			SYNTAX WingIdentifier
			MAX-ACCESS read-write
			STATUS current
			DESCRIPTION
				"
				
				XPath: /wing-config/captive_portal[name=key1]/aaa_policy"
			::= { wingCfgCaptPrtlEntry 14 }

		
		-- 1.3.6.1.4.1.1916.2.131.50.1.3.10.1.1.15
		wingCfgCaptPrtlDnsWhitelist OBJECT-TYPE
			SYNTAX WingIdentifier
			MAX-ACCESS read-write
			STATUS current
			DESCRIPTION
				"
				
				XPath: /wing-config/captive_portal[name=key1]/dns_whitelist"
			::= { wingCfgCaptPrtlEntry 15 }

		
		-- 1.3.6.1.4.1.1916.2.131.50.1.3.10.4
		wingCfgCaptPrtlAcctSyslogTable OBJECT-TYPE
			SYNTAX SEQUENCE OF WingCfgCaptPrtlAcctSyslogEntry
			MAX-ACCESS not-accessible
			STATUS current
			DESCRIPTION
				"
				
				/wing-config/captive_portal"
			::= { wingCfgCaptPrtl 4 }

		
		-- 1.3.6.1.4.1.1916.2.131.50.1.3.10.4.1
		wingCfgCaptPrtlAcctSyslogEntry OBJECT-TYPE
			SYNTAX WingCfgCaptPrtlAcctSyslogEntry
			MAX-ACCESS not-accessible
			STATUS current
			DESCRIPTION
				"An entry in the table."
			INDEX { wingCfgCaptPrtlName }
			::= { wingCfgCaptPrtlAcctSyslogTable 1 }

		
		WingCfgCaptPrtlAcctSyslogEntry ::=
			SEQUENCE { 
				wingCfgCaptPrtlAcctSyslogEnable
					TruthValue,
				wingCfgCaptPrtlAcctSyslogHost
					DisplayString,
				wingCfgCaptPrtlAcctSyslogPort
					Unsigned32
			 }

		-- 1.3.6.1.4.1.1916.2.131.50.1.3.10.4.1.1
		wingCfgCaptPrtlAcctSyslogEnable OBJECT-TYPE
			SYNTAX TruthValue
			MAX-ACCESS read-write
			STATUS current
			DESCRIPTION
				"
				
				XPath: /wing-config/captive_portal[name=key1]/accounting_syslog/enable"
			DEFVAL { false }
			::= { wingCfgCaptPrtlAcctSyslogEntry 1 }

		
		-- 1.3.6.1.4.1.1916.2.131.50.1.3.10.4.1.2
		wingCfgCaptPrtlAcctSyslogHost OBJECT-TYPE
			SYNTAX DisplayString
			MAX-ACCESS read-write
			STATUS current
			DESCRIPTION
				"
				
				XPath: /wing-config/captive_portal[name=key1]/accounting_syslog/host"
			::= { wingCfgCaptPrtlAcctSyslogEntry 2 }

		
		-- 1.3.6.1.4.1.1916.2.131.50.1.3.10.4.1.3
		wingCfgCaptPrtlAcctSyslogPort OBJECT-TYPE
			SYNTAX Unsigned32 (1..65535)
			MAX-ACCESS read-write
			STATUS current
			DESCRIPTION
				"
				
				XPath: /wing-config/captive_portal[name=key1]/accounting_syslog/port"
			DEFVAL { 514 }
			::= { wingCfgCaptPrtlAcctSyslogEntry 3 }

		
-- /wing-config/dns_whitelist
		-- 1.3.6.1.4.1.1916.2.131.50.1.3.11
		wingCfgDnsWhitelist OBJECT IDENTIFIER ::= { wingConfig 11 }

		
		-- 1.3.6.1.4.1.1916.2.131.50.1.3.11.1
		wingCfgDnsWhitelistTable OBJECT-TYPE
			SYNTAX SEQUENCE OF WingCfgDnsWhitelistEntry
			MAX-ACCESS not-accessible
			STATUS current
			DESCRIPTION
				"Whitelisted hostname and domainname entries.
				
				/wing-config/dns_whitelist"
			::= { wingCfgDnsWhitelist 1 }

		
		-- 1.3.6.1.4.1.1916.2.131.50.1.3.11.1.1
		wingCfgDnsWhitelistEntry OBJECT-TYPE
			SYNTAX WingCfgDnsWhitelistEntry
			MAX-ACCESS not-accessible
			STATUS current
			DESCRIPTION
				"An entry in the table."
			INDEX { wingCfgDnsWhitelistName }
			::= { wingCfgDnsWhitelistTable 1 }

		
		WingCfgDnsWhitelistEntry ::=
			SEQUENCE { 
				wingCfgDnsWhitelistName
					WingIdentifier
			 }

		-- 1.3.6.1.4.1.1916.2.131.50.1.3.11.1.1.1
		wingCfgDnsWhitelistName OBJECT-TYPE
			SYNTAX WingIdentifier
			MAX-ACCESS read-only
			STATUS current
			DESCRIPTION
				"
				
				XPath: /wing-config/dns_whitelist[name=key1]/name"
			::= { wingCfgDnsWhitelistEntry 1 }

		
		-- 1.3.6.1.4.1.1916.2.131.50.1.3.11.2
		wingCfgDnsWhitelistInstTable OBJECT-TYPE
			SYNTAX SEQUENCE OF WingCfgDnsWhitelistInstEntry
			MAX-ACCESS not-accessible
			STATUS current
			DESCRIPTION
				"
				
				/wing-config/dns_whitelist/entry"
			::= { wingCfgDnsWhitelist 2 }

		
		-- 1.3.6.1.4.1.1916.2.131.50.1.3.11.2.1
		wingCfgDnsWhitelistInstEntry OBJECT-TYPE
			SYNTAX WingCfgDnsWhitelistInstEntry
			MAX-ACCESS not-accessible
			STATUS current
			DESCRIPTION
				"An entry in the table."
			INDEX { wingCfgDnsWhitelistName, wingCfgDnsWhitelistInstName }
			::= { wingCfgDnsWhitelistInstTable 1 }

		
		WingCfgDnsWhitelistInstEntry ::=
			SEQUENCE { 
				wingCfgDnsWhitelistInstName
					WingIdentifier,
				wingCfgDnsWhitelistInstSuffix
					TruthValue
			 }

		-- 1.3.6.1.4.1.1916.2.131.50.1.3.11.2.1.1
		wingCfgDnsWhitelistInstName OBJECT-TYPE
			SYNTAX WingIdentifier
			MAX-ACCESS read-only
			STATUS current
			DESCRIPTION
				"Hostname or Domain Name or IP address.
				
				XPath: /wing-config/dns_whitelist[name=key1]/entry[entry=key2]/entry"
			::= { wingCfgDnsWhitelistInstEntry 1 }

		
		-- 1.3.6.1.4.1.1916.2.131.50.1.3.11.2.1.3
		wingCfgDnsWhitelistInstSuffix OBJECT-TYPE
			SYNTAX TruthValue
			MAX-ACCESS read-write
			STATUS current
			DESCRIPTION
				"Match any hostname or domainname including this entry
				as suffix.
				
				XPath: /wing-config/dns_whitelist[name=key1]/entry[entry=key2]/suffix"
			DEFVAL { false }
			::= { wingCfgDnsWhitelistInstEntry 3 }

		
-- /wing-config/ip_acl
		-- 1.3.6.1.4.1.1916.2.131.50.1.3.12
		wingCfgIpAcl OBJECT IDENTIFIER ::= { wingConfig 12 }

		
		-- 1.3.6.1.4.1.1916.2.131.50.1.3.12.1
		wingCfgIpAclTable OBJECT-TYPE
			SYNTAX SEQUENCE OF WingCfgIpAclEntry
			MAX-ACCESS not-accessible
			STATUS current
			DESCRIPTION
				"
				
				/wing-config/ip_acl"
			::= { wingCfgIpAcl 1 }

		
		-- 1.3.6.1.4.1.1916.2.131.50.1.3.12.1.1
		wingCfgIpAclEntry OBJECT-TYPE
			SYNTAX WingCfgIpAclEntry
			MAX-ACCESS not-accessible
			STATUS current
			DESCRIPTION
				"An entry in the table."
			INDEX { wingCfgIpAclName }
			::= { wingCfgIpAclTable 1 }

		
		WingCfgIpAclEntry ::=
			SEQUENCE { 
				wingCfgIpAclName
					WingIdentifier
			 }

		-- 1.3.6.1.4.1.1916.2.131.50.1.3.12.1.1.1
		wingCfgIpAclName OBJECT-TYPE
			SYNTAX WingIdentifier
			MAX-ACCESS read-only
			STATUS current
			DESCRIPTION
				"
				
				XPath: /wing-config/ip_acl[name=key1]/name"
			::= { wingCfgIpAclEntry 1 }

		
		-- 1.3.6.1.4.1.1916.2.131.50.1.3.12.2
		wingCfgIpAclRuleTable OBJECT-TYPE
			SYNTAX SEQUENCE OF WingCfgIpAclRuleEntry
			MAX-ACCESS not-accessible
			STATUS current
			DESCRIPTION
				"
				
				/wing-config/ip_acl/ip_rules"
			::= { wingCfgIpAcl 2 }

		
		-- 1.3.6.1.4.1.1916.2.131.50.1.3.12.2.1
		wingCfgIpAclRuleEntry OBJECT-TYPE
			SYNTAX WingCfgIpAclRuleEntry
			MAX-ACCESS not-accessible
			STATUS current
			DESCRIPTION
				"An entry in the table."
			INDEX { wingCfgIpAclName, wingCfgIpAclRulePrecedence }
			::= { wingCfgIpAclRuleTable 1 }

		
		WingCfgIpAclRuleEntry ::=
			SEQUENCE { 
				wingCfgIpAclRulePrecedence
					Unsigned32,
				wingCfgIpAclRuleAllow
					DisplayString,
				wingCfgIpAclRulePriorityField
					DisplayString,
				wingCfgIpAclRuleMarkDscp
					Unsigned32,
				wingCfgIpAclRuleMark8021p
					Unsigned32,
				wingCfgIpAclRuleDescription
					DisplayString,
				wingCfgIpAclRuleProtocol
					Unsigned32,
				wingCfgIpAclRuleSip
					DisplayString,
				wingCfgIpAclRuleDip
					DisplayString
			 }

		-- 1.3.6.1.4.1.1916.2.131.50.1.3.12.2.1.1
		wingCfgIpAclRulePrecedence OBJECT-TYPE
			SYNTAX Unsigned32 (1..5000)
			MAX-ACCESS read-only
			STATUS current
			DESCRIPTION
				"The precedence number for the Access Control Entry (ACE).
				1 is the highest precedence rule and 5000 is the lowest
				precedence rule.
				
				XPath: /wing-config/ip_acl[name=key1]/ip_rules[precedence=key2]/precedence"
			::= { wingCfgIpAclRuleEntry 1 }

		
		-- 1.3.6.1.4.1.1916.2.131.50.1.3.12.2.1.3
		wingCfgIpAclRuleAllow OBJECT-TYPE
			SYNTAX DisplayString
			MAX-ACCESS read-write
			STATUS current
			DESCRIPTION
				"
				Values:
				deny
				permit
				
				XPath: /wing-config/ip_acl[name=key1]/ip_rules[precedence=key2]/allow"
			DEFVAL { "deny" }
			::= { wingCfgIpAclRuleEntry 3 }

		
		-- 1.3.6.1.4.1.1916.2.131.50.1.3.12.2.1.4
		wingCfgIpAclRulePriorityField OBJECT-TYPE
			SYNTAX DisplayString
			MAX-ACCESS read-write
			STATUS current
			DESCRIPTION
				"
				Values:
				8021p
				dscp
				
				XPath: /wing-config/ip_acl[name=key1]/ip_rules[precedence=key2]/priority_field"
			DEFVAL { "dscp" }
			::= { wingCfgIpAclRuleEntry 4 }

		
		-- 1.3.6.1.4.1.1916.2.131.50.1.3.12.2.1.5
		wingCfgIpAclRuleMarkDscp OBJECT-TYPE
			SYNTAX Unsigned32 (0..63)
			MAX-ACCESS read-write
			STATUS current
			DESCRIPTION
				"Modify DSCP TOS bits in IP header.
				
				XPath: /wing-config/ip_acl[name=key1]/ip_rules[precedence=key2]/mark_dscp"
			::= { wingCfgIpAclRuleEntry 5 }

		
		-- 1.3.6.1.4.1.1916.2.131.50.1.3.12.2.1.6
		wingCfgIpAclRuleMark8021p OBJECT-TYPE
			SYNTAX Unsigned32 (0..7)
			MAX-ACCESS read-write
			STATUS current
			DESCRIPTION
				"Modify 802.1p VLAN user priority
				
				XPath: /wing-config/ip_acl[name=key1]/ip_rules[precedence=key2]/mark_8021p"
			::= { wingCfgIpAclRuleEntry 6 }

		
		-- 1.3.6.1.4.1.1916.2.131.50.1.3.12.2.1.7
		wingCfgIpAclRuleDescription OBJECT-TYPE
			SYNTAX DisplayString (SIZE (0..128))
			MAX-ACCESS read-write
			STATUS current
			DESCRIPTION
				"
				
				XPath: /wing-config/ip_acl[name=key1]/ip_rules[precedence=key2]/description"
			::= { wingCfgIpAclRuleEntry 7 }

		
		-- 1.3.6.1.4.1.1916.2.131.50.1.3.12.2.1.8
		wingCfgIpAclRuleProtocol OBJECT-TYPE
			SYNTAX Unsigned32 (0..254)
			MAX-ACCESS read-write
			STATUS current
			DESCRIPTION
				"configure ip, tcp, udp, igmp, icmp, gre, ospf, vrrp, igp,
				eigrp protocols or any protocol number
				
				XPath: /wing-config/ip_acl[name=key1]/ip_rules[precedence=key2]/protocol"
			::= { wingCfgIpAclRuleEntry 8 }

		
		-- 1.3.6.1.4.1.1916.2.131.50.1.3.12.2.1.9
		wingCfgIpAclRuleSip OBJECT-TYPE
			SYNTAX DisplayString
			MAX-ACCESS read-write
			STATUS current
			DESCRIPTION
				"configure host/network, for host configuration,
				network mask /32 has to be specified
				
				XPath: /wing-config/ip_acl[name=key1]/ip_rules[precedence=key2]/sip"
			::= { wingCfgIpAclRuleEntry 9 }

		
		-- 1.3.6.1.4.1.1916.2.131.50.1.3.12.2.1.10
		wingCfgIpAclRuleDip OBJECT-TYPE
			SYNTAX DisplayString
			MAX-ACCESS read-write
			STATUS current
			DESCRIPTION
				"configure host/network, for host configuration,
				network mask /32 has to be specified
				
				XPath: /wing-config/ip_acl[name=key1]/ip_rules[precedence=key2]/dip"
			::= { wingCfgIpAclRuleEntry 10 }

		
-- /wing-config/mac_acl
		-- 1.3.6.1.4.1.1916.2.131.50.1.3.13
		wingCfgMacAcl OBJECT IDENTIFIER ::= { wingConfig 13 }

		
		-- 1.3.6.1.4.1.1916.2.131.50.1.3.13.1
		wingCfgMacAclTable OBJECT-TYPE
			SYNTAX SEQUENCE OF WingCfgMacAclEntry
			MAX-ACCESS not-accessible
			STATUS current
			DESCRIPTION
				"
				
				/wing-config/mac_acl"
			::= { wingCfgMacAcl 1 }

		
		-- 1.3.6.1.4.1.1916.2.131.50.1.3.13.1.1
		wingCfgMacAclEntry OBJECT-TYPE
			SYNTAX WingCfgMacAclEntry
			MAX-ACCESS not-accessible
			STATUS current
			DESCRIPTION
				"An entry in the table."
			INDEX { wingCfgMacAclName }
			::= { wingCfgMacAclTable 1 }

		
		WingCfgMacAclEntry ::=
			SEQUENCE { 
				wingCfgMacAclName
					WingIdentifier
			 }

		-- 1.3.6.1.4.1.1916.2.131.50.1.3.13.1.1.1
		wingCfgMacAclName OBJECT-TYPE
			SYNTAX WingIdentifier
			MAX-ACCESS read-only
			STATUS current
			DESCRIPTION
				"
				
				XPath: /wing-config/mac_acl[name=key1]/name"
			::= { wingCfgMacAclEntry 1 }

		
		-- 1.3.6.1.4.1.1916.2.131.50.1.3.13.2
		wingCfgMacAclRuleTable OBJECT-TYPE
			SYNTAX SEQUENCE OF WingCfgMacAclRuleEntry
			MAX-ACCESS not-accessible
			STATUS current
			DESCRIPTION
				"
				
				/wing-config/mac_acl/mac_rules"
			::= { wingCfgMacAcl 2 }

		
		-- 1.3.6.1.4.1.1916.2.131.50.1.3.13.2.1
		wingCfgMacAclRuleEntry OBJECT-TYPE
			SYNTAX WingCfgMacAclRuleEntry
			MAX-ACCESS not-accessible
			STATUS current
			DESCRIPTION
				"An entry in the table."
			INDEX { wingCfgMacAclName, wingCfgMacAclRulePrecedence }
			::= { wingCfgMacAclRuleTable 1 }

		
		WingCfgMacAclRuleEntry ::=
			SEQUENCE { 
				wingCfgMacAclRulePrecedence
					Unsigned32,
				wingCfgMacAclRuleAllow
					DisplayString,
				wingCfgMacAclRulePriorityField
					DisplayString,
				wingCfgMacAclRuleMarkDscp
					Unsigned32,
				wingCfgMacAclRuleMark8021p
					Unsigned32,
				wingCfgMacAclRuleDescription
					DisplayString,
				wingCfgMacAclRuleSmac
					MacAddress,
				wingCfgMacAclRuleSmacMask
					MacAddress,
				wingCfgMacAclRuleDmac
					MacAddress,
				wingCfgMacAclRuleDmacMask
					MacAddress,
				wingCfgMacAclRuleMatchVlan
					Unsigned32,
				wingCfgMacAclRuleMatchDot1p
					Unsigned32,
				wingCfgMacAclRuleMatchType
					DisplayString
			 }

		-- 1.3.6.1.4.1.1916.2.131.50.1.3.13.2.1.1
		wingCfgMacAclRulePrecedence OBJECT-TYPE
			SYNTAX Unsigned32 (1..5000)
			MAX-ACCESS read-only
			STATUS current
			DESCRIPTION
				"The precedence number for the Access Control Entry (ACE).
				1 is the highest precedence rule and 5000 is the lowest
				precedence rule.
				
				XPath: /wing-config/mac_acl[name=key1]/mac_rules[precedence=key2]/precedence"
			::= { wingCfgMacAclRuleEntry 1 }

		
		-- 1.3.6.1.4.1.1916.2.131.50.1.3.13.2.1.3
		wingCfgMacAclRuleAllow OBJECT-TYPE
			SYNTAX DisplayString
			MAX-ACCESS read-write
			STATUS current
			DESCRIPTION
				"
				Values:
				deny
				permit
				
				XPath: /wing-config/mac_acl[name=key1]/mac_rules[precedence=key2]/allow"
			DEFVAL { "deny" }
			::= { wingCfgMacAclRuleEntry 3 }

		
		-- 1.3.6.1.4.1.1916.2.131.50.1.3.13.2.1.4
		wingCfgMacAclRulePriorityField OBJECT-TYPE
			SYNTAX DisplayString
			MAX-ACCESS read-write
			STATUS current
			DESCRIPTION
				"
				Values:
				8021p
				dscp
				
				XPath: /wing-config/mac_acl[name=key1]/mac_rules[precedence=key2]/priority_field"
			DEFVAL { "dscp" }
			::= { wingCfgMacAclRuleEntry 4 }

		
		-- 1.3.6.1.4.1.1916.2.131.50.1.3.13.2.1.5
		wingCfgMacAclRuleMarkDscp OBJECT-TYPE
			SYNTAX Unsigned32 (0..63)
			MAX-ACCESS read-write
			STATUS current
			DESCRIPTION
				"Modify DSCP TOS bits in IP header.
				
				XPath: /wing-config/mac_acl[name=key1]/mac_rules[precedence=key2]/mark_dscp"
			::= { wingCfgMacAclRuleEntry 5 }

		
		-- 1.3.6.1.4.1.1916.2.131.50.1.3.13.2.1.6
		wingCfgMacAclRuleMark8021p OBJECT-TYPE
			SYNTAX Unsigned32 (0..7)
			MAX-ACCESS read-write
			STATUS current
			DESCRIPTION
				"Modify 802.1p VLAN user priority
				
				XPath: /wing-config/mac_acl[name=key1]/mac_rules[precedence=key2]/mark_8021p"
			::= { wingCfgMacAclRuleEntry 6 }

		
		-- 1.3.6.1.4.1.1916.2.131.50.1.3.13.2.1.7
		wingCfgMacAclRuleDescription OBJECT-TYPE
			SYNTAX DisplayString (SIZE (0..128))
			MAX-ACCESS read-write
			STATUS current
			DESCRIPTION
				"
				
				XPath: /wing-config/mac_acl[name=key1]/mac_rules[precedence=key2]/description"
			::= { wingCfgMacAclRuleEntry 7 }

		
		-- 1.3.6.1.4.1.1916.2.131.50.1.3.13.2.1.8
		wingCfgMacAclRuleSmac OBJECT-TYPE
			SYNTAX MacAddress
			MAX-ACCESS read-write
			STATUS current
			DESCRIPTION
				"
				
				XPath: /wing-config/mac_acl[name=key1]/mac_rules[precedence=key2]/smac"
			::= { wingCfgMacAclRuleEntry 8 }

		
		-- 1.3.6.1.4.1.1916.2.131.50.1.3.13.2.1.9
		wingCfgMacAclRuleSmacMask OBJECT-TYPE
			SYNTAX MacAddress
			MAX-ACCESS read-write
			STATUS current
			DESCRIPTION
				"
				
				XPath: /wing-config/mac_acl[name=key1]/mac_rules[precedence=key2]/smac_mask"
			DEFVAL { 'FFFFFFFFFFFF'h }
			::= { wingCfgMacAclRuleEntry 9 }

		
		-- 1.3.6.1.4.1.1916.2.131.50.1.3.13.2.1.10
		wingCfgMacAclRuleDmac OBJECT-TYPE
			SYNTAX MacAddress
			MAX-ACCESS read-write
			STATUS current
			DESCRIPTION
				"
				
				XPath: /wing-config/mac_acl[name=key1]/mac_rules[precedence=key2]/dmac"
			::= { wingCfgMacAclRuleEntry 10 }

		
		-- 1.3.6.1.4.1.1916.2.131.50.1.3.13.2.1.11
		wingCfgMacAclRuleDmacMask OBJECT-TYPE
			SYNTAX MacAddress
			MAX-ACCESS read-write
			STATUS current
			DESCRIPTION
				"
				
				XPath: /wing-config/mac_acl[name=key1]/mac_rules[precedence=key2]/dmac_mask"
			DEFVAL { 'FFFFFFFFFFFF'h }
			::= { wingCfgMacAclRuleEntry 11 }

		
		-- 1.3.6.1.4.1.1916.2.131.50.1.3.13.2.1.12
		wingCfgMacAclRuleMatchVlan OBJECT-TYPE
			SYNTAX Unsigned32 (1..4094)
			MAX-ACCESS read-write
			STATUS current
			DESCRIPTION
				"
				
				XPath: /wing-config/mac_acl[name=key1]/mac_rules[precedence=key2]/match_vlan"
			::= { wingCfgMacAclRuleEntry 12 }

		
		-- 1.3.6.1.4.1.1916.2.131.50.1.3.13.2.1.13
		wingCfgMacAclRuleMatchDot1p OBJECT-TYPE
			SYNTAX Unsigned32 (0..7)
			MAX-ACCESS read-write
			STATUS current
			DESCRIPTION
				"8021.p priority to match
				
				XPath: /wing-config/mac_acl[name=key1]/mac_rules[precedence=key2]/match_dot1p"
			::= { wingCfgMacAclRuleEntry 13 }

		
		-- 1.3.6.1.4.1.1916.2.131.50.1.3.13.2.1.14
		wingCfgMacAclRuleMatchType OBJECT-TYPE
			SYNTAX DisplayString (SIZE (0..16))
			MAX-ACCESS read-write
			STATUS current
			DESCRIPTION
				"ethertype protocol to match, can be one of the following
				strings:
				ip|ipv6 | arp | wisp | mint | 8021q | rarp | aarp | 
				appletalk | ipx |  <1-65535>
				
				XPath: /wing-config/mac_acl[name=key1]/mac_rules[precedence=key2]/match_type"
			::= { wingCfgMacAclRuleEntry 14 }

		
-- /wing-config/wips_policy
		-- 1.3.6.1.4.1.1916.2.131.50.1.3.14
		wingCfgWips OBJECT IDENTIFIER ::= { wingConfig 14 }

		
		-- 1.3.6.1.4.1.1916.2.131.50.1.3.14.1
		wingCfgWipsTable OBJECT-TYPE
			SYNTAX SEQUENCE OF WingCfgWipsEntry
			MAX-ACCESS not-accessible
			STATUS current
			DESCRIPTION
				"
				
				/wing-config/wips_policy"
			::= { wingCfgWips 1 }

		
		-- 1.3.6.1.4.1.1916.2.131.50.1.3.14.1.1
		wingCfgWipsEntry OBJECT-TYPE
			SYNTAX WingCfgWipsEntry
			MAX-ACCESS not-accessible
			STATUS current
			DESCRIPTION
				"An entry in the table."
			INDEX { wingCfgWipsName }
			::= { wingCfgWipsTable 1 }

		
		WingCfgWipsEntry ::=
			SEQUENCE { 
				wingCfgWipsName
					WingIdentifier,
				wingCfgWipsEnable
					TruthValue,
				wingCfgWipsHistoryThrottleDuration
					Unsigned32,
				wingCfgWipsApDetection
					TruthValue,
				wingCfgWipsApDetectionAgeout
					Unsigned32,
				wingCfgWipsApDetectionWaitTime
					Unsigned32,
				wingCfgWipsDeviceCategorization
					WingIdentifier
			 }

		-- 1.3.6.1.4.1.1916.2.131.50.1.3.14.1.1.1
		wingCfgWipsName OBJECT-TYPE
			SYNTAX WingIdentifier
			MAX-ACCESS read-only
			STATUS current
			DESCRIPTION
				"
				
				XPath: /wing-config/wips_policy[name=key1]/name"
			::= { wingCfgWipsEntry 1 }

		
		-- 1.3.6.1.4.1.1916.2.131.50.1.3.14.1.1.3
		wingCfgWipsEnable OBJECT-TYPE
			SYNTAX TruthValue
			MAX-ACCESS read-write
			STATUS current
			DESCRIPTION
				"Specifies if the given wips policy is enabled or not
				
				XPath: /wing-config/wips_policy[name=key1]/enable"
			DEFVAL { true }
			::= { wingCfgWipsEntry 3 }

		
		-- 1.3.6.1.4.1.1916.2.131.50.1.3.14.1.1.4
		wingCfgWipsHistoryThrottleDuration OBJECT-TYPE
			SYNTAX Unsigned32 (30..86400)
			UNITS "seconds"
			MAX-ACCESS read-write
			STATUS current
			DESCRIPTION
				"The duration for which event duplicates are not stored in history.
				
				XPath: /wing-config/wips_policy[name=key1]/history_throttle_duration"
			DEFVAL { 120 }
			::= { wingCfgWipsEntry 4 }

		
		-- 1.3.6.1.4.1.1916.2.131.50.1.3.14.1.1.5
		wingCfgWipsApDetection OBJECT-TYPE
			SYNTAX TruthValue
			MAX-ACCESS read-write
			STATUS current
			DESCRIPTION
				"enable Rogue AP detection
				
				XPath: /wing-config/wips_policy[name=key1]/ap_detection"
			DEFVAL { false }
			::= { wingCfgWipsEntry 5 }

		
		-- 1.3.6.1.4.1.1916.2.131.50.1.3.14.1.1.6
		wingCfgWipsApDetectionAgeout OBJECT-TYPE
			SYNTAX Unsigned32 (30..86400)
			UNITS "seconds"
			MAX-ACCESS read-write
			STATUS current
			DESCRIPTION
				"ageout time for rogue APs
				
				XPath: /wing-config/wips_policy[name=key1]/ap_detection_ageout"
			DEFVAL { 300 }
			::= { wingCfgWipsEntry 6 }

		
		-- 1.3.6.1.4.1.1916.2.131.50.1.3.14.1.1.7
		wingCfgWipsApDetectionWaitTime OBJECT-TYPE
			SYNTAX Unsigned32 (10..600)
			UNITS "seconds"
			MAX-ACCESS read-write
			STATUS current
			DESCRIPTION
				"wait time to determine before an AP is identified as rogue
				
				XPath: /wing-config/wips_policy[name=key1]/ap_detection_wait_time"
			DEFVAL { 60 }
			::= { wingCfgWipsEntry 7 }

		
		-- 1.3.6.1.4.1.1916.2.131.50.1.3.14.1.1.8
		wingCfgWipsDeviceCategorization OBJECT-TYPE
			SYNTAX WingIdentifier
			MAX-ACCESS read-write
			STATUS current
			DESCRIPTION
				"
				
				XPath: /wing-config/wips_policy[name=key1]/device_categorization"
			::= { wingCfgWipsEntry 8 }

		
-- /wing-config/dhcp_server_policy
		-- 1.3.6.1.4.1.1916.2.131.50.1.3.15
		wingCfgDhcpSvr OBJECT IDENTIFIER ::= { wingConfig 15 }

		
		-- 1.3.6.1.4.1.1916.2.131.50.1.3.15.1
		wingCfgDhcpSvrTable OBJECT-TYPE
			SYNTAX SEQUENCE OF WingCfgDhcpSvrEntry
			MAX-ACCESS not-accessible
			STATUS current
			DESCRIPTION
				"User definition for the on-board DHCP server.
				
				/wing-config/dhcp_server_policy"
			::= { wingCfgDhcpSvr 1 }

		
		-- 1.3.6.1.4.1.1916.2.131.50.1.3.15.1.1
		wingCfgDhcpSvrEntry OBJECT-TYPE
			SYNTAX WingCfgDhcpSvrEntry
			MAX-ACCESS not-accessible
			STATUS current
			DESCRIPTION
				"An entry in the table."
			INDEX { wingCfgDhcpSvrName }
			::= { wingCfgDhcpSvrTable 1 }

		
		WingCfgDhcpSvrEntry ::=
			SEQUENCE { 
				wingCfgDhcpSvrName
					WingIdentifier,
				wingCfgDhcpSvrIgnoreBootp
					TruthValue,
				wingCfgDhcpSvrPingInterval
					Unsigned32
			 }

		-- 1.3.6.1.4.1.1916.2.131.50.1.3.15.1.1.1
		wingCfgDhcpSvrName OBJECT-TYPE
			SYNTAX WingIdentifier
			MAX-ACCESS read-only
			STATUS current
			DESCRIPTION
				"
				
				XPath: /wing-config/dhcp_server_policy[name=key1]/name"
			::= { wingCfgDhcpSvrEntry 1 }

		
		-- 1.3.6.1.4.1.1916.2.131.50.1.3.15.1.1.3
		wingCfgDhcpSvrIgnoreBootp OBJECT-TYPE
			SYNTAX TruthValue
			MAX-ACCESS read-write
			STATUS current
			DESCRIPTION
				"Configure DHCP server to ignore BOOTP requests.
				
				XPath: /wing-config/dhcp_server_policy[name=key1]/ignore_bootp"
			DEFVAL { false }
			::= { wingCfgDhcpSvrEntry 3 }

		
		-- 1.3.6.1.4.1.1916.2.131.50.1.3.15.1.1.4
		wingCfgDhcpSvrPingInterval OBJECT-TYPE
			SYNTAX Unsigned32 (1..10)
			UNITS "seconds"
			MAX-ACCESS read-write
			STATUS current
			DESCRIPTION
				"Ping timeout interval.
				
				XPath: /wing-config/dhcp_server_policy[name=key1]/dhcpSvrPingInterval"
			DEFVAL { 1 }
			::= { wingCfgDhcpSvrEntry 4 }

		
		-- 1.3.6.1.4.1.1916.2.131.50.1.3.15.2
		wingCfgDhcpSvrClassTable OBJECT-TYPE
			SYNTAX SEQUENCE OF WingCfgDhcpSvrClassEntry
			MAX-ACCESS not-accessible
			STATUS current
			DESCRIPTION
				"
				
				/wing-config/dhcp_server_policy/dhcp_class"
			::= { wingCfgDhcpSvr 2 }

		
		-- 1.3.6.1.4.1.1916.2.131.50.1.3.15.2.1
		wingCfgDhcpSvrClassEntry OBJECT-TYPE
			SYNTAX WingCfgDhcpSvrClassEntry
			MAX-ACCESS not-accessible
			STATUS current
			DESCRIPTION
				"An entry in the table."
			INDEX { wingCfgDhcpSvrName, wingCfgDhcpSvrClassName }
			::= { wingCfgDhcpSvrClassTable 1 }

		
		WingCfgDhcpSvrClassEntry ::=
			SEQUENCE { 
				wingCfgDhcpSvrClassName
					WingIdentifier,
				wingCfgDhcpSvrClassMultipleUserClass
					TruthValue
			 }

		-- 1.3.6.1.4.1.1916.2.131.50.1.3.15.2.1.1
		wingCfgDhcpSvrClassName OBJECT-TYPE
			SYNTAX WingIdentifier
			MAX-ACCESS read-only
			STATUS current
			DESCRIPTION
				"
				
				XPath: /wing-config/dhcp_server_policy[name=key1]/dhcp_class[name=key2]/name"
			::= { wingCfgDhcpSvrClassEntry 1 }

		
		-- 1.3.6.1.4.1.1916.2.131.50.1.3.15.2.1.3
		wingCfgDhcpSvrClassMultipleUserClass OBJECT-TYPE
			SYNTAX TruthValue
			MAX-ACCESS read-write
			STATUS current
			DESCRIPTION
				"Enable multiple user class option.
				
				XPath: /wing-config/dhcp_server_policy[name=key1]/dhcp_class[name=key2]/multiple_user_class"
			DEFVAL { false }
			::= { wingCfgDhcpSvrClassEntry 3 }

		
		-- 1.3.6.1.4.1.1916.2.131.50.1.3.15.3
		wingCfgDhcpSvrOptionTable OBJECT-TYPE
			SYNTAX SEQUENCE OF WingCfgDhcpSvrOptionEntry
			MAX-ACCESS not-accessible
			STATUS current
			DESCRIPTION
				"Define an option; the value is assigned inside the pool.
				
				/wing-config/dhcp_server_policy/dhcp_options"
			::= { wingCfgDhcpSvr 3 }

		
		-- 1.3.6.1.4.1.1916.2.131.50.1.3.15.3.1
		wingCfgDhcpSvrOptionEntry OBJECT-TYPE
			SYNTAX WingCfgDhcpSvrOptionEntry
			MAX-ACCESS not-accessible
			STATUS current
			DESCRIPTION
				"An entry in the table."
			INDEX { wingCfgDhcpSvrName, wingCfgDhcpSvrOptionName }
			::= { wingCfgDhcpSvrOptionTable 1 }

		
		WingCfgDhcpSvrOptionEntry ::=
			SEQUENCE { 
				wingCfgDhcpSvrOptionName
					WingIdentifier,
				wingCfgDhcpSvrOptionCode
					Unsigned32,
				wingCfgDhcpSvrOptionType
					DisplayString
			 }

		-- 1.3.6.1.4.1.1916.2.131.50.1.3.15.3.1.1
		wingCfgDhcpSvrOptionName OBJECT-TYPE
			SYNTAX WingIdentifier
			MAX-ACCESS read-only
			STATUS current
			DESCRIPTION
				"
				
				XPath: /wing-config/dhcp_server_policy[name=key1]/dhcp_options[name=key2]/name"
			::= { wingCfgDhcpSvrOptionEntry 1 }

		
		-- 1.3.6.1.4.1.1916.2.131.50.1.3.15.3.1.3
		wingCfgDhcpSvrOptionCode OBJECT-TYPE
			SYNTAX Unsigned32 (0..254)
			MAX-ACCESS read-write
			STATUS current
			DESCRIPTION
				"
				
				XPath: /wing-config/dhcp_server_policy[name=key1]/dhcp_options[name=key2]/code"
			::= { wingCfgDhcpSvrOptionEntry 3 }

		
		-- 1.3.6.1.4.1.1916.2.131.50.1.3.15.3.1.4
		wingCfgDhcpSvrOptionType OBJECT-TYPE
			SYNTAX DisplayString
			MAX-ACCESS read-write
			STATUS current
			DESCRIPTION
				"
				Values:
				ip
				ascii
				hexstring
				
				XPath: /wing-config/dhcp_server_policy[name=key1]/dhcp_options[name=key2]/type"
			::= { wingCfgDhcpSvrOptionEntry 4 }

		
		-- 1.3.6.1.4.1.1916.2.131.50.1.3.15.4
		wingCfgDhcpSvrPoolTable OBJECT-TYPE
			SYNTAX SEQUENCE OF WingCfgDhcpSvrPoolEntry
			MAX-ACCESS not-accessible
			STATUS current
			DESCRIPTION
				"
				
				/wing-config/dhcp_server_policy/dhcp_pools"
			::= { wingCfgDhcpSvr 4 }

		
		-- 1.3.6.1.4.1.1916.2.131.50.1.3.15.4.1
		wingCfgDhcpSvrPoolEntry OBJECT-TYPE
			SYNTAX WingCfgDhcpSvrPoolEntry
			MAX-ACCESS not-accessible
			STATUS current
			DESCRIPTION
				"An entry in the table."
			INDEX { wingCfgDhcpSvrName, wingCfgDhcpSvrPoolName }
			::= { wingCfgDhcpSvrPoolTable 1 }

		
		WingCfgDhcpSvrPoolEntry ::=
			SEQUENCE { 
				wingCfgDhcpSvrPoolName
					WingIdentifier,
				wingCfgDhcpSvrPoolNetwork
					DisplayString,
				wingCfgDhcpSvrPoolDomainName
					DisplayString,
				wingCfgDhcpSvrPoolNetbiosNodeType
					DisplayString,
				wingCfgDhcpSvrPoolBootfile
					DisplayString,
				wingCfgDhcpSvrPoolLeaseTime
					Unsigned32,
				wingCfgDhcpSvrPoolBootpNextServer
					DisplayString,
				wingCfgDhcpSvrPoolUpdateDns
					DisplayString,
				wingCfgDhcpSvrPoolDdnsDomainName
					DisplayString,
				wingCfgDhcpSvrPoolDdnsTtl
					Unsigned32,
				wingCfgDhcpSvrPoolDdnsMultiUserClass
					TruthValue,
				wingCfgDhcpSvrPoolUnicastEnable
					TruthValue
			 }

		-- 1.3.6.1.4.1.1916.2.131.50.1.3.15.4.1.1
		wingCfgDhcpSvrPoolName OBJECT-TYPE
			SYNTAX WingIdentifier
			MAX-ACCESS read-only
			STATUS current
			DESCRIPTION
				"Name of the IP pool from which IP addresses can be issued to
				DHCP client requests.
				
				XPath: /wing-config/dhcp_server_policy[name=key1]/dhcp_pools[name=key2]/name"
			::= { wingCfgDhcpSvrPoolEntry 1 }

		
		-- 1.3.6.1.4.1.1916.2.131.50.1.3.15.4.1.3
		wingCfgDhcpSvrPoolNetwork OBJECT-TYPE
			SYNTAX DisplayString
			MAX-ACCESS read-write
			STATUS current
			DESCRIPTION
				"Network address for the clients.
				
				XPath: /wing-config/dhcp_server_policy[name=key1]/dhcp_pools[name=key2]/network"
			::= { wingCfgDhcpSvrPoolEntry 3 }

		
		-- 1.3.6.1.4.1.1916.2.131.50.1.3.15.4.1.4
		wingCfgDhcpSvrPoolDomainName OBJECT-TYPE
			SYNTAX DisplayString (SIZE (1..255))
			MAX-ACCESS read-write
			STATUS current
			DESCRIPTION
				"
				
				XPath: /wing-config/dhcp_server_policy[name=key1]/dhcp_pools[name=key2]/domain_name"
			::= { wingCfgDhcpSvrPoolEntry 4 }

		
		-- 1.3.6.1.4.1.1916.2.131.50.1.3.15.4.1.5
		wingCfgDhcpSvrPoolNetbiosNodeType OBJECT-TYPE
			SYNTAX DisplayString
			MAX-ACCESS read-write
			STATUS current
			DESCRIPTION
				"
				Values:
				undefined
				broadcast
				peer-to-peer
				mixed
				hybrid
				
				XPath: /wing-config/dhcp_server_policy[name=key1]/dhcp_pools[name=key2]/netbios_node_type"
			DEFVAL { "undefined" }
			::= { wingCfgDhcpSvrPoolEntry 5 }

		
		-- 1.3.6.1.4.1.1916.2.131.50.1.3.15.4.1.6
		wingCfgDhcpSvrPoolBootfile OBJECT-TYPE
			SYNTAX DisplayString
			MAX-ACCESS read-write
			STATUS current
			DESCRIPTION
				"
				
				XPath: /wing-config/dhcp_server_policy[name=key1]/dhcp_pools[name=key2]/bootfile"
			::= { wingCfgDhcpSvrPoolEntry 6 }

		
		-- 1.3.6.1.4.1.1916.2.131.50.1.3.15.4.1.7
		wingCfgDhcpSvrPoolLeaseTime OBJECT-TYPE
			SYNTAX Unsigned32 (1..31622399)
			UNITS "seconds"
			MAX-ACCESS read-write
			STATUS current
			DESCRIPTION
				"The time an IP address is reserved for re-connection after
				its last use.  Address lease time ranges from 1 second to
				1 year (or infinite if unset).
				
				XPath: /wing-config/dhcp_server_policy[name=key1]/dhcp_pools[name=key2]/lease_time"
			DEFVAL { 86400 }
			::= { wingCfgDhcpSvrPoolEntry 7 }

		
		-- 1.3.6.1.4.1.1916.2.131.50.1.3.15.4.1.8
		wingCfgDhcpSvrPoolBootpNextServer OBJECT-TYPE
			SYNTAX DisplayString
			MAX-ACCESS read-write
			STATUS current
			DESCRIPTION
				"Next server in the boot process.
				
				XPath: /wing-config/dhcp_server_policy[name=key1]/dhcp_pools[name=key2]/bootp_next_server"
			::= { wingCfgDhcpSvrPoolEntry 8 }

		
		-- 1.3.6.1.4.1.1916.2.131.50.1.3.15.4.1.9
		wingCfgDhcpSvrPoolUpdateDns OBJECT-TYPE
			SYNTAX DisplayString
			MAX-ACCESS read-write
			STATUS current
			DESCRIPTION
				"
				Values:
				noUpdate
				serverUpdate
				clientUpdate
				
				XPath: /wing-config/dhcp_server_policy[name=key1]/dhcp_pools[name=key2]/update_dns"
			DEFVAL { "noUpdate" }
			::= { wingCfgDhcpSvrPoolEntry 9 }

		
		-- 1.3.6.1.4.1.1916.2.131.50.1.3.15.4.1.10
		wingCfgDhcpSvrPoolDdnsDomainName OBJECT-TYPE
			SYNTAX DisplayString
			MAX-ACCESS read-write
			STATUS current
			DESCRIPTION
				"Domain name used for DDNS Updates.
				
				XPath: /wing-config/dhcp_server_policy[name=key1]/dhcp_pools[name=key2]/ddns_domain_name"
			::= { wingCfgDhcpSvrPoolEntry 10 }

		
		-- 1.3.6.1.4.1.1916.2.131.50.1.3.15.4.1.11
		wingCfgDhcpSvrPoolDdnsTtl OBJECT-TYPE
			SYNTAX Unsigned32 (1..864000)
			MAX-ACCESS read-write
			STATUS current
			DESCRIPTION
				"Time-to-Live (TTL) value used for DDNS updates.
				
				XPath: /wing-config/dhcp_server_policy[name=key1]/dhcp_pools[name=key2]/ddns_ttl"
			::= { wingCfgDhcpSvrPoolEntry 11 }

		
		-- 1.3.6.1.4.1.1916.2.131.50.1.3.15.4.1.12
		wingCfgDhcpSvrPoolDdnsMultiUserClass OBJECT-TYPE
			SYNTAX TruthValue
			MAX-ACCESS read-write
			STATUS current
			DESCRIPTION
				"Enable/disable DDNS multi user class.
				
				XPath: /wing-config/dhcp_server_policy[name=key1]/dhcp_pools[name=key2]/ddns_multi_user_class"
			DEFVAL { false }
			::= { wingCfgDhcpSvrPoolEntry 12 }

		
		-- 1.3.6.1.4.1.1916.2.131.50.1.3.15.4.1.13
		wingCfgDhcpSvrPoolUnicastEnable OBJECT-TYPE
			SYNTAX TruthValue
			MAX-ACCESS read-write
			STATUS current
			DESCRIPTION
				"Enable unicast for DHCP Offer and ACK.
				
				XPath: /wing-config/dhcp_server_policy[name=key1]/dhcp_pools[name=key2]/unicast_enable"
			DEFVAL { false }
			::= { wingCfgDhcpSvrPoolEntry 13 }

		
-- /wing-config/profile
		-- 1.3.6.1.4.1.1916.2.131.50.1.3.16
		wingCfgProf OBJECT IDENTIFIER ::= { wingConfig 16 }

		
		-- 1.3.6.1.4.1.1916.2.131.50.1.3.16.1
		wingCfgProfTable OBJECT-TYPE
			SYNTAX SEQUENCE OF WingCfgProfEntry
			MAX-ACCESS not-accessible
			STATUS current
			DESCRIPTION
				"
				
				/wing-config/profile"
			::= { wingCfgProf 1 }

		
		-- 1.3.6.1.4.1.1916.2.131.50.1.3.16.1.1
		wingCfgProfEntry OBJECT-TYPE
			SYNTAX WingCfgProfEntry
			MAX-ACCESS not-accessible
			STATUS current
			DESCRIPTION
				"An entry in the table."
			INDEX { wingCfgProfName }
			::= { wingCfgProfTable 1 }

		
		WingCfgProfEntry ::=
			SEQUENCE { 
				wingCfgProfName
					WingIdentifier,
				wingCfgProfType
					DisplayString,
				wingCfgProfDomainLookup
					TruthValue,
				wingCfgProfDomainName
					DisplayString,
				wingCfgProfArpTimeout
					Unsigned32,
				wingCfgProfApIpAddr
					DisplayString,
				wingCfgProfAutoConfUpdate
					TruthValue,
				wingCfgProfAutoFwUpdate
					TruthValue,
				wingCfgProfAutoupgradeCount
					Unsigned32,
				wingCfgProfServiceWatchdog
					TruthValue,
				wingCfgProfRadiusServerPolicy
					WingIdentifier,
				wingCfgProfDhcpServerPolicy
					WingIdentifier,
				wingCfgProfManagementPolicy
					WingIdentifier,
				wingCfgProfFirewallPolicy
					WingIdentifier,
				wingCfgProfAdvancedWipsPolicy
					WingIdentifier,
				wingCfgProfRolePolicy
					WingIdentifier,
				wingCfgProfAdoptionPolicy
					WingIdentifier,
				wingCfgProfBridgingPolicy
					WingIdentifier,
				wingCfgProfEventSystemPolicy
					WingIdentifier,
				wingCfgProfRoutingPolicy
					WingIdentifier,
				wingCfgProfRfDomainMgrCapable
					TruthValue,
				wingCfgProfRfDomainMgrPriority
					Unsigned32,
				wingCfgProfDhcpcSendHostname
					TruthValue,
				wingCfgProfDhcpcPersistentLease
					TruthValue,
				wingCfgProfDnsServerForward
					TruthValue,
				wingCfgProfBridgeAgingTime
					Unsigned32,
				wingCfgProfLogging
					TruthValue,
				wingCfgProfAggregationTime
					Unsigned32,
				wingCfgProfConsole
					DisplayString,
				wingCfgProfBuffered
					DisplayString,
				wingCfgProfSyslog
					DisplayString,
				wingCfgProfFacility
					DisplayString,
				wingCfgProfEvents
					TruthValue,
				wingCfgProfEventsForward
					TruthValue,
				wingCfgProfLed
					TruthValue,
				wingCfgProfRemoteLogging
					DisplayString,
				wingCfgProfPowerConfig3afOption
					DisplayString,
				wingCfgProfPowerConfig3atOption
					DisplayString,
				wingCfgProfPowerConfigMode
					DisplayString,
				wingCfgProfCriticalResourcePolicy
					WingIdentifier,
				wingCfgProfControllerApSupported
					TruthValue,
				wingCfgProfControllerVlan
					Unsigned32,
				wingCfgProfControllerGroup
					DisplayString,
				wingCfgProfPreferredControllerGroup
					DisplayString,
				wingCfgProfIpRouting
					TruthValue,
				wingCfgProfLearnStagingConfig
					TruthValue,
				wingCfgProfTunnelController
					DisplayString,
				wingCfgProfPreferredTunnelController
					DisplayString,
				wingCfgProfDot1xSysAuthCtrl
					TruthValue,
				wingCfgProfDot1xGuestVlanCtrl
					TruthValue,
				wingCfgProfDot1xAaaPolicy
					WingIdentifier
			 }

		-- 1.3.6.1.4.1.1916.2.131.50.1.3.16.1.1.1
		wingCfgProfName OBJECT-TYPE
			SYNTAX WingIdentifier
			MAX-ACCESS read-only
			STATUS current
			DESCRIPTION
				"
				
				XPath: /wing-config/profile[name=key1]/name"
			::= { wingCfgProfEntry 1 }

		
		-- 1.3.6.1.4.1.1916.2.131.50.1.3.16.1.1.3
		wingCfgProfType OBJECT-TYPE
			SYNTAX DisplayString
			MAX-ACCESS read-write
			STATUS current
			DESCRIPTION
				"
				Values:
				NX9000
				WM3700
				WM3600
				WM3400
				AP4700
				AP4600
				AP4021
				AP4521
				AP4511
				AP4532
				
				XPath: /wing-config/profile[name=key1]/type"
			::= { wingCfgProfEntry 3 }

		
		-- 1.3.6.1.4.1.1916.2.131.50.1.3.16.1.1.4
		wingCfgProfDomainLookup OBJECT-TYPE
			SYNTAX TruthValue
			MAX-ACCESS read-write
			STATUS current
			DESCRIPTION
				"Domain name lookup (DNS resolution) services
				
				XPath: /wing-config/profile[name=key1]/domain_lookup"
			DEFVAL { true }
			::= { wingCfgProfEntry 4 }

		
		-- 1.3.6.1.4.1.1916.2.131.50.1.3.16.1.1.5
		wingCfgProfDomainName OBJECT-TYPE
			SYNTAX DisplayString (SIZE (0..64))
			MAX-ACCESS read-write
			STATUS current
			DESCRIPTION
				"Default domain-name to be used when resolving DNS names
				
				XPath: /wing-config/profile[name=key1]/domain_name"
			DEFVAL { "" }
			::= { wingCfgProfEntry 5 }

		
		-- 1.3.6.1.4.1.1916.2.131.50.1.3.16.1.1.6
		wingCfgProfArpTimeout OBJECT-TYPE
			SYNTAX Unsigned32 (15..86400)
			UNITS "seconds"
			MAX-ACCESS read-write
			STATUS current
			DESCRIPTION
				"ARP entry timeout
				
				XPath: /wing-config/profile[name=key1]/arp_timeout"
			DEFVAL { 3600 }
			::= { wingCfgProfEntry 6 }

		
		-- 1.3.6.1.4.1.1916.2.131.50.1.3.16.1.1.7
		wingCfgProfApIpAddr OBJECT-TYPE
			SYNTAX DisplayString
			MAX-ACCESS read-write
			STATUS current
			DESCRIPTION
				"Ip address for legacy AP adoption.
				
				XPath: /wing-config/profile[name=key1]/ap_ip_address"
			::= { wingCfgProfEntry 7 }

		
		-- 1.3.6.1.4.1.1916.2.131.50.1.3.16.1.1.8
		wingCfgProfAutoConfUpdate OBJECT-TYPE
			SYNTAX TruthValue
			MAX-ACCESS read-write
			STATUS current
			DESCRIPTION
				"Autoinstall configuration update from external location based
				on DHCP options.
				
				XPath: /wing-config/profile[name=key1]/auto_conf_update"
			DEFVAL { false }
			::= { wingCfgProfEntry 8 }

		
		-- 1.3.6.1.4.1.1916.2.131.50.1.3.16.1.1.9
		wingCfgProfAutoFwUpdate OBJECT-TYPE
			SYNTAX TruthValue
			MAX-ACCESS read-write
			STATUS current
			DESCRIPTION
				"Autoinstall firmware upgrade from external location based on
				DHCP options.
				
				XPath: /wing-config/profile[name=key1]/auto_fw_update"
			DEFVAL { false }
			::= { wingCfgProfEntry 9 }

		
		-- 1.3.6.1.4.1.1916.2.131.50.1.3.16.1.1.11
		wingCfgProfAutoupgradeCount OBJECT-TYPE
			SYNTAX Unsigned32 (1..20)
			UNITS "APs"
			MAX-ACCESS read-write
			STATUS current
			DESCRIPTION
				"The number of APs that can be upgraded concurrently.
				
				XPath: /wing-config/profile[name=key1]/autoupgrade_count"
			DEFVAL { 10 }
			::= { wingCfgProfEntry 11 }

		
		-- 1.3.6.1.4.1.1916.2.131.50.1.3.16.1.1.12
		wingCfgProfServiceWatchdog OBJECT-TYPE
			SYNTAX TruthValue
			MAX-ACCESS read-write
			STATUS current
			DESCRIPTION
				"
				
				XPath: /wing-config/profile[name=key1]/service_watchdog"
			DEFVAL { true }
			::= { wingCfgProfEntry 12 }

		
		-- 1.3.6.1.4.1.1916.2.131.50.1.3.16.1.1.13
		wingCfgProfRadiusServerPolicy OBJECT-TYPE
			SYNTAX WingIdentifier
			MAX-ACCESS read-write
			STATUS current
			DESCRIPTION
				"
				
				XPath: /wing-config/profile[name=key1]/radius_server_policy"
			::= { wingCfgProfEntry 13 }

		
		-- 1.3.6.1.4.1.1916.2.131.50.1.3.16.1.1.14
		wingCfgProfDhcpServerPolicy OBJECT-TYPE
			SYNTAX WingIdentifier
			MAX-ACCESS read-write
			STATUS current
			DESCRIPTION
				"
				
				XPath: /wing-config/profile[name=key1]/dhcp_server_policy"
			::= { wingCfgProfEntry 14 }

		
		-- 1.3.6.1.4.1.1916.2.131.50.1.3.16.1.1.15
		wingCfgProfManagementPolicy OBJECT-TYPE
			SYNTAX WingIdentifier
			MAX-ACCESS read-write
			STATUS current
			DESCRIPTION
				"
				
				XPath: /wing-config/profile[name=key1]/management_policy"
			::= { wingCfgProfEntry 15 }

		
		-- 1.3.6.1.4.1.1916.2.131.50.1.3.16.1.1.16
		wingCfgProfFirewallPolicy OBJECT-TYPE
			SYNTAX WingIdentifier
			MAX-ACCESS read-write
			STATUS current
			DESCRIPTION
				"
				
				XPath: /wing-config/profile[name=key1]/firewall_policy"
			::= { wingCfgProfEntry 16 }

		
		-- 1.3.6.1.4.1.1916.2.131.50.1.3.16.1.1.17
		wingCfgProfAdvancedWipsPolicy OBJECT-TYPE
			SYNTAX WingIdentifier
			MAX-ACCESS read-write
			STATUS current
			DESCRIPTION
				"
				
				XPath: /wing-config/profile[name=key1]/advanced_wips_policy"
			::= { wingCfgProfEntry 17 }

		
		-- 1.3.6.1.4.1.1916.2.131.50.1.3.16.1.1.18
		wingCfgProfRolePolicy OBJECT-TYPE
			SYNTAX WingIdentifier
			MAX-ACCESS read-write
			STATUS current
			DESCRIPTION
				"
				
				XPath: /wing-config/profile[name=key1]/role_policy"
			::= { wingCfgProfEntry 18 }

		
		-- 1.3.6.1.4.1.1916.2.131.50.1.3.16.1.1.19
		wingCfgProfAdoptionPolicy OBJECT-TYPE
			SYNTAX WingIdentifier
			MAX-ACCESS read-write
			STATUS current
			DESCRIPTION
				"
				
				XPath: /wing-config/profile[name=key1]/adoption_policy"
			::= { wingCfgProfEntry 19 }

		
		-- 1.3.6.1.4.1.1916.2.131.50.1.3.16.1.1.20
		wingCfgProfBridgingPolicy OBJECT-TYPE
			SYNTAX WingIdentifier
			MAX-ACCESS read-write
			STATUS current
			DESCRIPTION
				"
				
				XPath: /wing-config/profile[name=key1]/bridging_policy"
			::= { wingCfgProfEntry 20 }

		
		-- 1.3.6.1.4.1.1916.2.131.50.1.3.16.1.1.21
		wingCfgProfEventSystemPolicy OBJECT-TYPE
			SYNTAX WingIdentifier
			MAX-ACCESS read-write
			STATUS current
			DESCRIPTION
				"
				
				XPath: /wing-config/profile[name=key1]/event_system_policy"
			::= { wingCfgProfEntry 21 }

		
		-- 1.3.6.1.4.1.1916.2.131.50.1.3.16.1.1.22
		wingCfgProfRoutingPolicy OBJECT-TYPE
			SYNTAX WingIdentifier
			MAX-ACCESS read-write
			STATUS current
			DESCRIPTION
				"
				
				XPath: /wing-config/profile[name=key1]/routing_policy"
			::= { wingCfgProfEntry 22 }

		
		-- 1.3.6.1.4.1.1916.2.131.50.1.3.16.1.1.23
		wingCfgProfRfDomainMgrCapable OBJECT-TYPE
			SYNTAX TruthValue
			MAX-ACCESS read-write
			STATUS current
			DESCRIPTION
				"whether this device is capable of being the rf-domain manager
				within a particular rf-domain
				
				XPath: /wing-config/profile[name=key1]/rf_domain_mgr_capable"
			DEFVAL { true }
			::= { wingCfgProfEntry 23 }

		
		-- 1.3.6.1.4.1.1916.2.131.50.1.3.16.1.1.24
		wingCfgProfRfDomainMgrPriority OBJECT-TYPE
			SYNTAX Unsigned32 (1..255)
			MAX-ACCESS read-write
			STATUS current
			DESCRIPTION
				"The priority of this device compared to others in becoming
				an rf-domain manager. A larger value indicates a
				higher priority is given to the device in
				the rf-domain manager election process
				
				XPath: /wing-config/profile[name=key1]/rf_domain_mgr_priority"
			::= { wingCfgProfEntry 24 }

		
		-- 1.3.6.1.4.1.1916.2.131.50.1.3.16.1.1.25
		wingCfgProfDhcpcSendHostname OBJECT-TYPE
			SYNTAX TruthValue
			MAX-ACCESS read-write
			STATUS current
			DESCRIPTION
				"Include hostname in DHCP request.
				
				XPath: /wing-config/profile[name=key1]/dhcpc_send_hostname"
			DEFVAL { true }
			::= { wingCfgProfEntry 25 }

		
		-- 1.3.6.1.4.1.1916.2.131.50.1.3.16.1.1.26
		wingCfgProfDhcpcPersistentLease OBJECT-TYPE
			SYNTAX TruthValue
			MAX-ACCESS read-write
			STATUS current
			DESCRIPTION
				"Retain last lease across reboot if DHCP server is unreachable
				
				XPath: /wing-config/profile[name=key1]/dhcpc_persistent_lease"
			DEFVAL { true }
			::= { wingCfgProfEntry 26 }

		
		-- 1.3.6.1.4.1.1916.2.131.50.1.3.16.1.1.27
		wingCfgProfDnsServerForward OBJECT-TYPE
			SYNTAX TruthValue
			MAX-ACCESS read-write
			STATUS current
			DESCRIPTION
				"
				
				XPath: /wing-config/profile[name=key1]/dns_server_forward"
			DEFVAL { false }
			::= { wingCfgProfEntry 27 }

		
		-- 1.3.6.1.4.1.1916.2.131.50.1.3.16.1.1.28
		wingCfgProfBridgeAgingTime OBJECT-TYPE
			SYNTAX Unsigned32 (0 | 10..1000000)
			UNITS "seconds"
			MAX-ACCESS read-write
			STATUS current
			DESCRIPTION
				"Aging time from 10 sec to 1000000 sec or disabled (when value=0).
				
				XPath: /wing-config/profile[name=key1]/bridge_aging_time"
			DEFVAL { 300 }
			::= { wingCfgProfEntry 28 }

		
		-- 1.3.6.1.4.1.1916.2.131.50.1.3.16.1.1.29
		wingCfgProfLogging OBJECT-TYPE
			SYNTAX TruthValue
			MAX-ACCESS read-write
			STATUS current
			DESCRIPTION
				"Enable logging of system messages.
				
				XPath: /wing-config/profile[name=key1]/logging"
			DEFVAL { false }
			::= { wingCfgProfEntry 29 }

		
		-- 1.3.6.1.4.1.1916.2.131.50.1.3.16.1.1.30
		wingCfgProfAggregationTime OBJECT-TYPE
			SYNTAX Unsigned32 (0..60)
			UNITS "seconds"
			MAX-ACCESS read-write
			STATUS current
			DESCRIPTION
				"Set number of seconds for aggregating repeated messages.
				
				XPath: /wing-config/profile[name=key1]/aggregation_time"
			DEFVAL { 0 }
			::= { wingCfgProfEntry 30 }

		
		-- 1.3.6.1.4.1.1916.2.131.50.1.3.16.1.1.31
		wingCfgProfConsole OBJECT-TYPE
			SYNTAX DisplayString
			MAX-ACCESS read-write
			STATUS current
			DESCRIPTION
				"Set console logging level.
				
				Values:
				emergencies
				alerts
				critical
				errors
				warnings
				notifications
				informational
				debugging
				none
				
				XPath: /wing-config/profile[name=key1]/console"
			DEFVAL { "warnings" }
			::= { wingCfgProfEntry 31 }

		
		-- 1.3.6.1.4.1.1916.2.131.50.1.3.16.1.1.32
		wingCfgProfBuffered OBJECT-TYPE
			SYNTAX DisplayString
			MAX-ACCESS read-write
			STATUS current
			DESCRIPTION
				"Set buffered logging level.
				
				Values:
				emergencies
				alerts
				critical
				errors
				warnings
				notifications
				informational
				debugging
				none
				
				XPath: /wing-config/profile[name=key1]/buffered"
			DEFVAL { "warnings" }
			::= { wingCfgProfEntry 32 }

		
		-- 1.3.6.1.4.1.1916.2.131.50.1.3.16.1.1.33
		wingCfgProfSyslog OBJECT-TYPE
			SYNTAX DisplayString
			MAX-ACCESS read-write
			STATUS current
			DESCRIPTION
				"Set syslog logging level.
				
				Values:
				emergencies
				alerts
				critical
				errors
				warnings
				notifications
				informational
				debugging
				none
				
				XPath: /wing-config/profile[name=key1]/syslog"
			DEFVAL { "warnings" }
			::= { wingCfgProfEntry 33 }

		
		-- 1.3.6.1.4.1.1916.2.131.50.1.3.16.1.1.34
		wingCfgProfFacility OBJECT-TYPE
			SYNTAX DisplayString
			MAX-ACCESS read-write
			STATUS current
			DESCRIPTION
				"Syslog facility for log messages sent to syslog server.
				
				Values:
				local0
				local1
				local2
				local3
				local4
				local5
				local6
				local7
				
				XPath: /wing-config/profile[name=key1]/facility"
			DEFVAL { "local7" }
			::= { wingCfgProfEntry 34 }

		
		-- 1.3.6.1.4.1.1916.2.131.50.1.3.16.1.1.35
		wingCfgProfEvents OBJECT-TYPE
			SYNTAX TruthValue
			MAX-ACCESS read-write
			STATUS current
			DESCRIPTION
				"Enable generation of system events.
				
				XPath: /wing-config/profile[name=key1]/events"
			DEFVAL { true }
			::= { wingCfgProfEntry 35 }

		
		-- 1.3.6.1.4.1.1916.2.131.50.1.3.16.1.1.36
		wingCfgProfEventsForward OBJECT-TYPE
			SYNTAX TruthValue
			MAX-ACCESS read-write
			STATUS current
			DESCRIPTION
				"Enable forwarding of system events to a controller or
				cluster member.
				
				XPath: /wing-config/profile[name=key1]/events_forward"
			DEFVAL { true }
			::= { wingCfgProfEntry 36 }

		
		-- 1.3.6.1.4.1.1916.2.131.50.1.3.16.1.1.37
		wingCfgProfLed OBJECT-TYPE
			SYNTAX TruthValue
			MAX-ACCESS read-write
			STATUS current
			DESCRIPTION
				"Turn on/off LEDs on the AP.
				
				XPath: /wing-config/profile[name=key1]/led"
			DEFVAL { true }
			::= { wingCfgProfEntry 37 }

		
		-- 1.3.6.1.4.1.1916.2.131.50.1.3.16.1.1.38
		wingCfgProfRemoteLogging OBJECT-TYPE
			SYNTAX DisplayString
			MAX-ACCESS read-write
			STATUS current
			DESCRIPTION
				"Set logging level for forwarding of log messages to
				controller.
				
				Values:
				emergencies
				alerts
				critical
				errors
				warnings
				notifications
				informational
				debugging
				none
				
				XPath: /wing-config/profile[name=key1]/remote_logging"
			DEFVAL { "errors" }
			::= { wingCfgProfEntry 38 }

		
		-- 1.3.6.1.4.1.1916.2.131.50.1.3.16.1.1.39
		wingCfgProfPowerConfig3afOption OBJECT-TYPE
			SYNTAX DisplayString
			MAX-ACCESS read-write
			STATUS current
			DESCRIPTION
				"
				Values:
				range
				throughput
				
				XPath: /wing-config/profile[name=key1]/power_config_3af_option"
			DEFVAL { "throughput" }
			::= { wingCfgProfEntry 39 }

		
		-- 1.3.6.1.4.1.1916.2.131.50.1.3.16.1.1.40
		wingCfgProfPowerConfig3atOption OBJECT-TYPE
			SYNTAX DisplayString
			MAX-ACCESS read-write
			STATUS current
			DESCRIPTION
				"
				Values:
				range
				throughput
				
				XPath: /wing-config/profile[name=key1]/power_config_3at_option"
			DEFVAL { "throughput" }
			::= { wingCfgProfEntry 40 }

		
		-- 1.3.6.1.4.1.1916.2.131.50.1.3.16.1.1.41
		wingCfgProfPowerConfigMode OBJECT-TYPE
			SYNTAX DisplayString
			MAX-ACCESS read-write
			STATUS current
			DESCRIPTION
				"If power mode is 3af then ap will come up in 3af config
				no matter what power level is.
				
				Values:
				auto
				3af
				
				XPath: /wing-config/profile[name=key1]/power_config_mode"
			DEFVAL { "auto" }
			::= { wingCfgProfEntry 41 }

		
		-- 1.3.6.1.4.1.1916.2.131.50.1.3.16.1.1.42
		wingCfgProfCriticalResourcePolicy OBJECT-TYPE
			SYNTAX WingIdentifier
			MAX-ACCESS read-write
			STATUS current
			DESCRIPTION
				"
				
				XPath: /wing-config/profile[name=key1]/critical_resource_policy"
			::= { wingCfgProfEntry 42 }

		
		-- 1.3.6.1.4.1.1916.2.131.50.1.3.16.1.1.43
		wingCfgProfControllerApSupported OBJECT-TYPE
			SYNTAX TruthValue
			MAX-ACCESS read-write
			STATUS current
			DESCRIPTION
				"Enable/Disable Controller-AP.
				
				XPath: /wing-config/profile[name=key1]/controller_ap_supported"
			DEFVAL { false }
			::= { wingCfgProfEntry 43 }

		
		-- 1.3.6.1.4.1.1916.2.131.50.1.3.16.1.1.44
		wingCfgProfControllerVlan OBJECT-TYPE
			SYNTAX Unsigned32 (1..4094)
			MAX-ACCESS read-write
			STATUS current
			DESCRIPTION
				"VLAN on which a controller is reachable
				
				XPath: /wing-config/profile[name=key1]/controller_vlan"
			::= { wingCfgProfEntry 44 }

		
		-- 1.3.6.1.4.1.1916.2.131.50.1.3.16.1.1.45
		wingCfgProfControllerGroup OBJECT-TYPE
			SYNTAX DisplayString (SIZE (64))
			MAX-ACCESS read-write
			STATUS current
			DESCRIPTION
				"Controller group this controller belongs to
				
				XPath: /wing-config/profile[name=key1]/controller_group"
			::= { wingCfgProfEntry 45 }

		
		-- 1.3.6.1.4.1.1916.2.131.50.1.3.16.1.1.46
		wingCfgProfPreferredControllerGroup OBJECT-TYPE
			SYNTAX DisplayString (SIZE (64))
			MAX-ACCESS read-write
			STATUS current
			DESCRIPTION
				"Controller group this system will prefer for adoption
				
				XPath: /wing-config/profile[name=key1]/preferred_controller_group"
			::= { wingCfgProfEntry 46 }

		
		-- 1.3.6.1.4.1.1916.2.131.50.1.3.16.1.1.47
		wingCfgProfIpRouting OBJECT-TYPE
			SYNTAX TruthValue
			MAX-ACCESS read-write
			STATUS current
			DESCRIPTION
				"IP Routing
				
				XPath: /wing-config/profile[name=key1]/ip_routing"
			DEFVAL { true }
			::= { wingCfgProfEntry 47 }

		
		-- 1.3.6.1.4.1.1916.2.131.50.1.3.16.1.1.48
		wingCfgProfLearnStagingConfig OBJECT-TYPE
			SYNTAX TruthValue
			MAX-ACCESS read-write
			STATUS current
			DESCRIPTION
				"Learn and save network configuration of new devices that
				come for adoption
				
				XPath: /wing-config/profile[name=key1]/learn_staging_config"
			DEFVAL { true }
			::= { wingCfgProfEntry 48 }

		
		-- 1.3.6.1.4.1.1916.2.131.50.1.3.16.1.1.49
		wingCfgProfTunnelController OBJECT-TYPE
			SYNTAX DisplayString
			MAX-ACCESS read-write
			STATUS current
			DESCRIPTION
				"Name of this tunneled-wlan-controller.
				
				XPath: /wing-config/profile[name=key1]/tunnel_controller"
			::= { wingCfgProfEntry 49 }

		
		-- 1.3.6.1.4.1.1916.2.131.50.1.3.16.1.1.50
		wingCfgProfPreferredTunnelController OBJECT-TYPE
			SYNTAX DisplayString
			MAX-ACCESS read-write
			STATUS current
			DESCRIPTION
				"Controller this AP will prefer to tunnel tunnelled-wlan a.k.a extended-vlan traffic to.
				
				XPath: /wing-config/profile[name=key1]/preferred_tunnel_controller"
			::= { wingCfgProfEntry 50 }

		
		-- 1.3.6.1.4.1.1916.2.131.50.1.3.16.1.1.51
		wingCfgProfDot1xSysAuthCtrl OBJECT-TYPE
			SYNTAX TruthValue
			MAX-ACCESS read-write
			STATUS current
			DESCRIPTION
				"Globally enable 802.1x authentication
				
				XPath: /wing-config/profile[name=key1]/dot1x_sys_auth_ctrl"
			DEFVAL { false }
			::= { wingCfgProfEntry 51 }

		
		-- 1.3.6.1.4.1.1916.2.131.50.1.3.16.1.1.52
		wingCfgProfDot1xGuestVlanCtrl OBJECT-TYPE
			SYNTAX TruthValue
			MAX-ACCESS read-write
			STATUS current
			DESCRIPTION
				"Globally enable 802.1x guest vlans
				
				XPath: /wing-config/profile[name=key1]/dot1x_guest_vlan_ctrl"
			DEFVAL { false }
			::= { wingCfgProfEntry 52 }

		
		-- 1.3.6.1.4.1.1916.2.131.50.1.3.16.1.1.53
		wingCfgProfDot1xAaaPolicy OBJECT-TYPE
			SYNTAX WingIdentifier
			MAX-ACCESS read-write
			STATUS current
			DESCRIPTION
				"AAA Authentication policy for 802.1x Authentication
				
				XPath: /wing-config/profile[name=key1]/dot1x_aaa_policy"
			::= { wingCfgProfEntry 53 }

		
-- /wing-config/profile/interface
		-- 1.3.6.1.4.1.1916.2.131.50.1.3.16.2
		wingCfgProfIf OBJECT IDENTIFIER ::= { wingCfgProf 2 }

		
		-- 1.3.6.1.4.1.1916.2.131.50.1.3.16.2.1
		wingCfgProfIfTable OBJECT-TYPE
			SYNTAX SEQUENCE OF WingCfgProfIfEntry
			MAX-ACCESS not-accessible
			STATUS current
			DESCRIPTION
				"
				
				/wing-config/profile/interface"
			::= { wingCfgProfIf 1 }

		
		-- 1.3.6.1.4.1.1916.2.131.50.1.3.16.2.1.1
		wingCfgProfIfEntry OBJECT-TYPE
			SYNTAX WingCfgProfIfEntry
			MAX-ACCESS not-accessible
			STATUS current
			DESCRIPTION
				"An entry in the table."
			INDEX { wingCfgProfName, wingCfgProfIfName }
			::= { wingCfgProfIfTable 1 }

		
		WingCfgProfIfEntry ::=
			SEQUENCE { 
				wingCfgProfIfName
					WingIdentifier,
				wingCfgProfIfDescription
					DisplayString,
				wingCfgProfIfType
					DisplayString,
				wingCfgProfIfShutdown
					TruthValue,
				wingCfgProfIfIpInAcl
					WingIdentifier,
				wingCfgProfIfMacInAcl
					WingIdentifier
			 }

		-- 1.3.6.1.4.1.1916.2.131.50.1.3.16.2.1.1.1
		wingCfgProfIfName OBJECT-TYPE
			SYNTAX WingIdentifier
			MAX-ACCESS read-only
			STATUS current
			DESCRIPTION
				"
				
				XPath: /wing-config/profile[name=key1]/interface[name=key2]/name"
			::= { wingCfgProfIfEntry 1 }

		
		-- 1.3.6.1.4.1.1916.2.131.50.1.3.16.2.1.1.3
		wingCfgProfIfDescription OBJECT-TYPE
			SYNTAX DisplayString
			MAX-ACCESS read-write
			STATUS current
			DESCRIPTION
				"
				
				XPath: /wing-config/profile[name=key1]/interface[name=key2]/description"
			::= { wingCfgProfIfEntry 3 }

		
		-- 1.3.6.1.4.1.1916.2.131.50.1.3.16.2.1.1.4
		wingCfgProfIfType OBJECT-TYPE
			SYNTAX DisplayString
			MAX-ACCESS read-write
			STATUS current
			DESCRIPTION
				"Type of the network interface
				
				Values:
				ethernet
				vlan
				radio
				port_channel
				wwan
				
				XPath: /wing-config/profile[name=key1]/interface[name=key2]/type"
			::= { wingCfgProfIfEntry 4 }

		
		-- 1.3.6.1.4.1.1916.2.131.50.1.3.16.2.1.1.5
		wingCfgProfIfShutdown OBJECT-TYPE
			SYNTAX TruthValue
			MAX-ACCESS read-write
			STATUS current
			DESCRIPTION
				"
				
				XPath: /wing-config/profile[name=key1]/interface[name=key2]/shutdown"
			DEFVAL { false }
			::= { wingCfgProfIfEntry 5 }

		
		-- 1.3.6.1.4.1.1916.2.131.50.1.3.16.2.1.1.6
		wingCfgProfIfIpInAcl OBJECT-TYPE
			SYNTAX WingIdentifier
			MAX-ACCESS read-write
			STATUS current
			DESCRIPTION
				"
				
				XPath: /wing-config/profile[name=key1]/interface[name=key2]/ip_in_acl"
			::= { wingCfgProfIfEntry 6 }

		
		-- 1.3.6.1.4.1.1916.2.131.50.1.3.16.2.1.1.7
		wingCfgProfIfMacInAcl OBJECT-TYPE
			SYNTAX WingIdentifier
			MAX-ACCESS read-write
			STATUS current
			DESCRIPTION
				"
				
				XPath: /wing-config/profile[name=key1]/interface[name=key2]/mac_in_acl"
			::= { wingCfgProfIfEntry 7 }

		
		-- 1.3.6.1.4.1.1916.2.131.50.1.3.16.2.2
		wingCfgProfIfEthTable OBJECT-TYPE
			SYNTAX SEQUENCE OF WingCfgProfIfEthEntry
			MAX-ACCESS not-accessible
			STATUS current
			DESCRIPTION
				"
				
				/wing-config/profile/interface"
			::= { wingCfgProfIf 2 }

		
		-- 1.3.6.1.4.1.1916.2.131.50.1.3.16.2.2.1
		wingCfgProfIfEthEntry OBJECT-TYPE
			SYNTAX WingCfgProfIfEthEntry
			MAX-ACCESS not-accessible
			STATUS current
			DESCRIPTION
				"An entry in the table."
			INDEX { wingCfgProfName, wingCfgProfIfName }
			::= { wingCfgProfIfEthTable 1 }

		
		WingCfgProfIfEthEntry ::=
			SEQUENCE { 
				wingCfgProfIfEthSpeed
					DisplayString,
				wingCfgProfIfEthDuplex
					DisplayString,
				wingCfgProfIfEthSwitchportMode
					DisplayString,
				wingCfgProfIfEthSwitchportNativeVlan
					Unsigned32,
				wingCfgProfIfEthSwitchportNativeVlanTagged
					TruthValue,
				wingCfgProfIfEthArpTrust
					TruthValue,
				wingCfgProfIfEthDhcpTrust
					TruthValue,
				wingCfgProfIfEthArpHeaderMismatchValidation
					TruthValue,
				wingCfgProfIfEthQosTrustDscp
					TruthValue,
				wingCfgProfIfEthQosTrust802dot1p
					TruthValue,
				wingCfgProfIfEthStaticChannelGroup
					Unsigned32,
				wingCfgProfIfEthPoeSupported
					TruthValue,
				wingCfgProfIfEthPoePower
					TruthValue,
				wingCfgProfIfEthPoeLimit
					Unsigned32,
				wingCfgProfIfEthPoePriority
					DisplayString,
				wingCfgProfIfEthDot1xSupported
					TruthValue,
				wingCfgProfIfEthDot1xEnable
					TruthValue,
				wingCfgProfIfEthDot1xUsername
					DisplayString,
				wingCfgProfIfEthDot1xPassword
					DisplayString,
				wingCfgProfIfEthCdpReceive
					TruthValue,
				wingCfgProfIfEthCdpTransmit
					TruthValue,
				wingCfgProfIfEthLldpReceive
					TruthValue,
				wingCfgProfIfEthLldpTransmit
					TruthValue,
				wingCfgProfIfEthPortChannelLoadBalance
					DisplayString
			 }

		-- 1.3.6.1.4.1.1916.2.131.50.1.3.16.2.2.1.1
		wingCfgProfIfEthSpeed OBJECT-TYPE
			SYNTAX DisplayString
			MAX-ACCESS read-write
			STATUS current
			DESCRIPTION
				"
				Values:
				10
				100
				1000
				auto
				
				XPath: /wing-config/profile[name=key1]/interface[name=key2]/speed"
			DEFVAL { "auto" }
			::= { wingCfgProfIfEthEntry 1 }

		
		-- 1.3.6.1.4.1.1916.2.131.50.1.3.16.2.2.1.2
		wingCfgProfIfEthDuplex OBJECT-TYPE
			SYNTAX DisplayString
			MAX-ACCESS read-write
			STATUS current
			DESCRIPTION
				"
				Values:
				half
				full
				auto
				
				XPath: /wing-config/profile[name=key1]/interface[name=key2]/duplex"
			DEFVAL { "auto" }
			::= { wingCfgProfIfEthEntry 2 }

		
		-- 1.3.6.1.4.1.1916.2.131.50.1.3.16.2.2.1.3
		wingCfgProfIfEthSwitchportMode OBJECT-TYPE
			SYNTAX DisplayString
			MAX-ACCESS read-write
			STATUS current
			DESCRIPTION
				"Mode of the Layer 2 interface.
				
				Values:
				access
				trunk
				
				XPath: /wing-config/profile[name=key1]/interface[name=key2]/switchport/mode"
			DEFVAL { "access" }
			::= { wingCfgProfIfEthEntry 3 }

		
		-- 1.3.6.1.4.1.1916.2.131.50.1.3.16.2.2.1.4
		wingCfgProfIfEthSwitchportNativeVlan OBJECT-TYPE
			SYNTAX Unsigned32 (1..4094)
			MAX-ACCESS read-write
			STATUS current
			DESCRIPTION
				"Native VLAN for classifying untagged traffic.
				
				XPath: /wing-config/profile[name=key1]/interface[name=key2]/switchport/native_vlan"
			DEFVAL { 1 }
			::= { wingCfgProfIfEthEntry 4 }

		
		-- 1.3.6.1.4.1.1916.2.131.50.1.3.16.2.2.1.5
		wingCfgProfIfEthSwitchportNativeVlanTagged OBJECT-TYPE
			SYNTAX TruthValue
			MAX-ACCESS read-write
			STATUS current
			DESCRIPTION
				"Tag the native VLAN.
				
				XPath: /wing-config/profile[name=key1]/interface[name=key2]/switchport/native_vlan_tagged"
			DEFVAL { false }
			::= { wingCfgProfIfEthEntry 5 }

		
		-- 1.3.6.1.4.1.1916.2.131.50.1.3.16.2.2.1.6
		wingCfgProfIfEthArpTrust OBJECT-TYPE
			SYNTAX TruthValue
			MAX-ACCESS read-write
			STATUS current
			DESCRIPTION
				"Trust ARP request on this port.
				
				XPath: /wing-config/profile[name=key1]/interface[name=key2]/arp_trust"
			DEFVAL { false }
			::= { wingCfgProfIfEthEntry 6 }

		
		-- 1.3.6.1.4.1.1916.2.131.50.1.3.16.2.2.1.7
		wingCfgProfIfEthDhcpTrust OBJECT-TYPE
			SYNTAX TruthValue
			MAX-ACCESS read-write
			STATUS current
			DESCRIPTION
				"Trust DHCP responses on this port
				
				XPath: /wing-config/profile[name=key1]/interface[name=key2]/dhcp_trust"
			DEFVAL { true }
			::= { wingCfgProfIfEthEntry 7 }

		
		-- 1.3.6.1.4.1.1916.2.131.50.1.3.16.2.2.1.8
		wingCfgProfIfEthArpHeaderMismatchValidation OBJECT-TYPE
			SYNTAX TruthValue
			MAX-ACCESS read-write
			STATUS current
			DESCRIPTION
				"Check mismatch for source MAC in ARP header and ethernet header.
				
				XPath: /wing-config/profile[name=key1]/interface[name=key2]/arp_header_mismatch_validation"
			DEFVAL { false }
			::= { wingCfgProfIfEthEntry 8 }

		
		-- 1.3.6.1.4.1.1916.2.131.50.1.3.16.2.2.1.9
		wingCfgProfIfEthQosTrustDscp OBJECT-TYPE
			SYNTAX TruthValue
			MAX-ACCESS read-write
			STATUS current
			DESCRIPTION
				"Trust IP DSCP values on this port.
				
				XPath: /wing-config/profile[name=key1]/interface[name=key2]/qos_trust_dscp"
			DEFVAL { true }
			::= { wingCfgProfIfEthEntry 9 }

		
		-- 1.3.6.1.4.1.1916.2.131.50.1.3.16.2.2.1.10
		wingCfgProfIfEthQosTrust802dot1p OBJECT-TYPE
			SYNTAX TruthValue
			MAX-ACCESS read-write
			STATUS current
			DESCRIPTION
				"Trust 802.1p COS values on this port.
				
				XPath: /wing-config/profile[name=key1]/interface[name=key2]/qos_trust_802dot1p"
			DEFVAL { true }
			::= { wingCfgProfIfEthEntry 10 }

		
		-- 1.3.6.1.4.1.1916.2.131.50.1.3.16.2.2.1.11
		wingCfgProfIfEthStaticChannelGroup OBJECT-TYPE
			SYNTAX Unsigned32 (1..4)
			MAX-ACCESS read-write
			STATUS current
			DESCRIPTION
				"Channel group to which the port belongs.
				
				XPath: /wing-config/profile[name=key1]/interface[name=key2]/static_channel_group"
			::= { wingCfgProfIfEthEntry 11 }

		
		-- 1.3.6.1.4.1.1916.2.131.50.1.3.16.2.2.1.12
		wingCfgProfIfEthPoeSupported OBJECT-TYPE
			SYNTAX TruthValue
			MAX-ACCESS read-write
			STATUS current
			DESCRIPTION
				"POE supported on this port when true.
				
				XPath: /wing-config/profile[name=key1]/interface[name=key2]/poe_supported"
			DEFVAL { false }
			::= { wingCfgProfIfEthEntry 12 }

		
		-- 1.3.6.1.4.1.1916.2.131.50.1.3.16.2.2.1.13
		wingCfgProfIfEthPoePower OBJECT-TYPE
			SYNTAX TruthValue
			MAX-ACCESS read-write
			STATUS current
			DESCRIPTION
				"Enable/Disable POE Power.
				
				XPath: /wing-config/profile[name=key1]/interface[name=key2]/poe_power"
			DEFVAL { true }
			::= { wingCfgProfIfEthEntry 13 }

		
		-- 1.3.6.1.4.1.1916.2.131.50.1.3.16.2.2.1.14
		wingCfgProfIfEthPoeLimit OBJECT-TYPE
			SYNTAX Unsigned32 (0..40)
			UNITS "watts"
			MAX-ACCESS read-write
			STATUS current
			DESCRIPTION
				"
				
				XPath: /wing-config/profile[name=key1]/interface[name=key2]/poe_limit"
			DEFVAL { 0 }
			::= { wingCfgProfIfEthEntry 14 }

		
		-- 1.3.6.1.4.1.1916.2.131.50.1.3.16.2.2.1.15
		wingCfgProfIfEthPoePriority OBJECT-TYPE
			SYNTAX DisplayString
			MAX-ACCESS read-write
			STATUS current
			DESCRIPTION
				"
				Values:
				critical
				high
				low
				
				XPath: /wing-config/profile[name=key1]/interface[name=key2]/poe_priority"
			DEFVAL { "low" }
			::= { wingCfgProfIfEthEntry 15 }

		
		-- 1.3.6.1.4.1.1916.2.131.50.1.3.16.2.2.1.16
		wingCfgProfIfEthDot1xSupported OBJECT-TYPE
			SYNTAX TruthValue
			MAX-ACCESS read-write
			STATUS current
			DESCRIPTION
				"Dot1x supported on port when enabled.
				
				XPath: /wing-config/profile[name=key1]/interface[name=key2]/dot1x_supported"
			DEFVAL { false }
			::= { wingCfgProfIfEthEntry 16 }

		
		-- 1.3.6.1.4.1.1916.2.131.50.1.3.16.2.2.1.17
		wingCfgProfIfEthDot1xEnable OBJECT-TYPE
			SYNTAX TruthValue
			MAX-ACCESS read-write
			STATUS current
			DESCRIPTION
				"
				
				XPath: /wing-config/profile[name=key1]/interface[name=key2]/dot1x/enable"
			DEFVAL { false }
			::= { wingCfgProfIfEthEntry 17 }

		
		-- 1.3.6.1.4.1.1916.2.131.50.1.3.16.2.2.1.18
		wingCfgProfIfEthDot1xUsername OBJECT-TYPE
			SYNTAX DisplayString (SIZE (1..32))
			MAX-ACCESS read-write
			STATUS current
			DESCRIPTION
				"
				
				XPath: /wing-config/profile[name=key1]/interface[name=key2]/dot1x/username"
			::= { wingCfgProfIfEthEntry 18 }

		
		-- 1.3.6.1.4.1.1916.2.131.50.1.3.16.2.2.1.19
		wingCfgProfIfEthDot1xPassword OBJECT-TYPE
			SYNTAX DisplayString
			MAX-ACCESS read-write
			STATUS current
			DESCRIPTION
				"
				
				XPath: /wing-config/profile[name=key1]/interface[name=key2]/dot1x/password"
			::= { wingCfgProfIfEthEntry 19 }

		
		-- 1.3.6.1.4.1.1916.2.131.50.1.3.16.2.2.1.20
		wingCfgProfIfEthCdpReceive OBJECT-TYPE
			SYNTAX TruthValue
			MAX-ACCESS read-write
			STATUS current
			DESCRIPTION
				"Snoop CDP on port
				
				XPath: /wing-config/profile[name=key1]/interface[name=key2]/cdp_receive"
			DEFVAL { true }
			::= { wingCfgProfIfEthEntry 20 }

		
		-- 1.3.6.1.4.1.1916.2.131.50.1.3.16.2.2.1.21
		wingCfgProfIfEthCdpTransmit OBJECT-TYPE
			SYNTAX TruthValue
			MAX-ACCESS read-write
			STATUS current
			DESCRIPTION
				"Transmit CDP packets on port
				
				XPath: /wing-config/profile[name=key1]/interface[name=key2]/cdp_transmit"
			DEFVAL { true }
			::= { wingCfgProfIfEthEntry 21 }

		
		-- 1.3.6.1.4.1.1916.2.131.50.1.3.16.2.2.1.22
		wingCfgProfIfEthLldpReceive OBJECT-TYPE
			SYNTAX TruthValue
			MAX-ACCESS read-write
			STATUS current
			DESCRIPTION
				"Snoop LLDP on port
				
				XPath: /wing-config/profile[name=key1]/interface[name=key2]/lldp_receive"
			DEFVAL { true }
			::= { wingCfgProfIfEthEntry 22 }

		
		-- 1.3.6.1.4.1.1916.2.131.50.1.3.16.2.2.1.23
		wingCfgProfIfEthLldpTransmit OBJECT-TYPE
			SYNTAX TruthValue
			MAX-ACCESS read-write
			STATUS current
			DESCRIPTION
				"Transmit LLDP PDUs on port
				
				XPath: /wing-config/profile[name=key1]/interface[name=key2]/lldp_transmit"
			DEFVAL { true }
			::= { wingCfgProfIfEthEntry 23 }

		
		-- 1.3.6.1.4.1.1916.2.131.50.1.3.16.2.2.1.24
		wingCfgProfIfEthPortChannelLoadBalance OBJECT-TYPE
			SYNTAX DisplayString
			MAX-ACCESS read-write
			STATUS current
			DESCRIPTION
				"
				Values:
				src-dst-ip
				src-dst-mac
				
				XPath: /wing-config/profile[name=key1]/interface[name=key2]/port_channel_load_balance"
			DEFVAL { "src-dst-ip" }
			::= { wingCfgProfIfEthEntry 24 }

		
		-- 1.3.6.1.4.1.1916.2.131.50.1.3.16.2.3
		wingCfgProfIfVlanTable OBJECT-TYPE
			SYNTAX SEQUENCE OF WingCfgProfIfVlanEntry
			MAX-ACCESS not-accessible
			STATUS current
			DESCRIPTION
				"
				
				/wing-config/profile/interface"
			::= { wingCfgProfIf 3 }

		
		-- 1.3.6.1.4.1.1916.2.131.50.1.3.16.2.3.1
		wingCfgProfIfVlanEntry OBJECT-TYPE
			SYNTAX WingCfgProfIfVlanEntry
			MAX-ACCESS not-accessible
			STATUS current
			DESCRIPTION
				"An entry in the table."
			INDEX { wingCfgProfName, wingCfgProfIfName }
			::= { wingCfgProfIfVlanTable 1 }

		
		WingCfgProfIfVlanEntry ::=
			SEQUENCE { 
				wingCfgProfIfVlanVlan
					Unsigned32,
				wingCfgProfIfVlanDhcpcOptAll
					TruthValue,
				wingCfgProfIfVlanNatDirection
					DisplayString,
				wingCfgProfIfVlanCryptoMap
					WingIdentifier,
				wingCfgProfIfVlanDhcpRelayIncoming
					TruthValue,
				wingCfgProfIfVlanOspfAuth
					DisplayString,
				wingCfgProfIfVlanOspfAuthKey
					DisplayString,
				wingCfgProfIfVlanOspfNetworkType
					DisplayString,
				wingCfgProfIfVlanOspfPriority
					Unsigned32
			 }

		-- 1.3.6.1.4.1.1916.2.131.50.1.3.16.2.3.1.1
		wingCfgProfIfVlanVlan OBJECT-TYPE
			SYNTAX Unsigned32 (1..4094)
			MAX-ACCESS read-write
			STATUS current
			DESCRIPTION
				"
				
				XPath: /wing-config/profile[name=key1]/interface[name=key2]/vlan"
			::= { wingCfgProfIfVlanEntry 1 }

		
		-- 1.3.6.1.4.1.1916.2.131.50.1.3.16.2.3.1.2
		wingCfgProfIfVlanDhcpcOptAll OBJECT-TYPE
			SYNTAX TruthValue
			MAX-ACCESS read-write
			STATUS current
			DESCRIPTION
				"Learn default gateway, name servers, domain name on this
				interface.
				
				XPath: /wing-config/profile[name=key1]/interface[name=key2]/dhcpc_opt_all"
			DEFVAL { false }
			::= { wingCfgProfIfVlanEntry 2 }

		
		-- 1.3.6.1.4.1.1916.2.131.50.1.3.16.2.3.1.3
		wingCfgProfIfVlanNatDirection OBJECT-TYPE
			SYNTAX DisplayString
			MAX-ACCESS read-write
			STATUS current
			DESCRIPTION
				"
				
				Values:
				inside
				outside
				none
				
				XPath: /wing-config/profile[name=key1]/interface[name=key2]/nat_direction"
			DEFVAL { "none" }
			::= { wingCfgProfIfVlanEntry 3 }

		
		-- 1.3.6.1.4.1.1916.2.131.50.1.3.16.2.3.1.4
		wingCfgProfIfVlanCryptoMap OBJECT-TYPE
			SYNTAX WingIdentifier
			MAX-ACCESS read-write
			STATUS current
			DESCRIPTION
				"Attach an already configured crypto map to this interface.
				
				XPath: /wing-config/profile[name=key1]/interface[name=key2]/crypto_map"
			::= { wingCfgProfIfVlanEntry 4 }

		
		-- 1.3.6.1.4.1.1916.2.131.50.1.3.16.2.3.1.5
		wingCfgProfIfVlanDhcpRelayIncoming OBJECT-TYPE
			SYNTAX TruthValue
			MAX-ACCESS read-write
			STATUS current
			DESCRIPTION
				"Allow on-board DHCP server to respond to relayed DHCP packets
				on this interface
				
				XPath: /wing-config/profile[name=key1]/interface[name=key2]/dhcp_relay_incoming"
			DEFVAL { false }
			::= { wingCfgProfIfVlanEntry 5 }

		
		-- 1.3.6.1.4.1.1916.2.131.50.1.3.16.2.3.1.6
		wingCfgProfIfVlanOspfAuth OBJECT-TYPE
			SYNTAX DisplayString
			MAX-ACCESS read-write
			STATUS current
			DESCRIPTION
				"OSPF authentication type
				
				Values:
				simple-password,
				message-digest,
                                null,
				none
				
				XPath: /wing-config/profile[name=key1]/interface[name=key2]/ospf_authentication"
			DEFVAL { "none" }
			::= { wingCfgProfIfVlanEntry 6 }

		
		-- 1.3.6.1.4.1.1916.2.131.50.1.3.16.2.3.1.7
		wingCfgProfIfVlanOspfAuthKey OBJECT-TYPE
			SYNTAX DisplayString (SIZE (0..8))
			MAX-ACCESS read-write
			STATUS current
			DESCRIPTION
				"Simple auth key for OSPF.
				
				XPath: /wing-config/profile[name=key1]/interface[name=key2]/ospf_auth_key"
			::= { wingCfgProfIfVlanEntry 7 }

		
		-- 1.3.6.1.4.1.1916.2.131.50.1.3.16.2.3.1.8
		wingCfgProfIfVlanOspfNetworkType OBJECT-TYPE
			SYNTAX DisplayString
			MAX-ACCESS read-write
			STATUS current
			DESCRIPTION
				"
				Values:
				broadcast
				non-broadcast
				point-to-point
				point-to-multipoint
				
				XPath: /wing-config/profile[name=key1]/interface[name=key2]/ospf_network_type"
			DEFVAL { "broadcast" }
			::= { wingCfgProfIfVlanEntry 8 }

		
		-- 1.3.6.1.4.1.1916.2.131.50.1.3.16.2.3.1.9
		wingCfgProfIfVlanOspfPriority OBJECT-TYPE
			SYNTAX Unsigned32 (0..255)
			MAX-ACCESS read-write
			STATUS current
			DESCRIPTION
				"
				XPath: /wing-config/profile[name=key1]/interface[name=key2]/ospf_priority"
			DEFVAL { 0 }
			::= { wingCfgProfIfVlanEntry 9 }

		
		-- 1.3.6.1.4.1.1916.2.131.50.1.3.16.2.6
		wingCfgProfIfRadioTable OBJECT-TYPE
			SYNTAX SEQUENCE OF WingCfgProfIfRadioEntry
			MAX-ACCESS not-accessible
			STATUS current
			DESCRIPTION
				"
				
				/wing-config/profile/interface"
			::= { wingCfgProfIf 6 }

		
		-- 1.3.6.1.4.1.1916.2.131.50.1.3.16.2.6.1
		wingCfgProfIfRadioEntry OBJECT-TYPE
			SYNTAX WingCfgProfIfRadioEntry
			MAX-ACCESS not-accessible
			STATUS current
			DESCRIPTION
				"An entry in the table."
			INDEX { wingCfgProfName, wingCfgProfIfName }
			::= { wingCfgProfIfRadioTable 1 }

		
		WingCfgProfIfRadioEntry ::=
			SEQUENCE { 
				wingCfgProfIfRadioRfMode
					DisplayString,
				wingCfgProfIfRadioChannel
					DisplayString,
				wingCfgProfIfRadioPower
					Unsigned32,
				wingCfgProfIfRadioPlacement
					DisplayString,
				wingCfgProfIfRadioBeaconInterval
					DisplayString,
				wingCfgProfIfRadioRtsThreshold
					Unsigned32,
				wingCfgProfIfRadioOffChannelScan
					TruthValue,
				wingCfgProfIfRadioPreambleShort
					TruthValue,
				wingCfgProfIfRadioGuardInterval
					DisplayString,
				wingCfgProfIfRadioAmpduMode
					DisplayString,
				wingCfgProfIfRadioAmsduMode
					DisplayString,
				wingCfgProfIfRadioRifsMode
					DisplayString,
				wingCfgProfIfRadioAmpduMaxAggrSizeRx
					DisplayString,
				wingCfgProfIfRadioAmpduMaxAggrSizeTx
					Unsigned32,
				wingCfgProfIfRadioAmpduMinSpacing
					DisplayString,
				wingCfgProfIfRadioAntennaMode
					DisplayString,
				wingCfgProfIfRadioNonUnicastForwarding
					DisplayString,
				wingCfgProfIfRadioDynamicChainSelection
					TruthValue,
				wingCfgProfIfRadioLockRfMode
					TruthValue,
				wingCfgProfIfRadioSnifferRedirHost
					DisplayString,
				wingCfgProfIfRadioSnifferRedirChannel
					DisplayString,
				wingCfgProfIfRadioMesh
					DisplayString,
				wingCfgProfIfRadioMeshLinks
					Unsigned32,
				wingCfgProfIfRadioProbeResponseRetry
					TruthValue,
				wingCfgProfIfRadioProbeResponseRate
					DisplayString,
				wingCfgProfIfRadioMaxClients
					Unsigned32,
				wingCfgProfIfRadioRadioTapMode
					DisplayString,
				wingCfgProfIfRadioWirelessClientPower
					Unsigned32,
				wingCfgProfIfRadioLoadBalLfCount
					Unsigned32,
				wingCfgProfIfRadioLoadBalLfThroughput
					Unsigned32,
				wingCfgProfIfRadioLoadBalWmCount
					Unsigned32,
				wingCfgProfIfRadioLoadBalWmTput
					Unsigned32,
				wingCfgProfIfRadioAssocAcl
					WingIdentifier,
				wingCfgProfIfRadioQosPolicy
					WingIdentifier,
                                wingCfgProfIfRadioAntennaDowntilt
                                        TruthValue,
                                wingCfgProfIfRadioExtendedRange
                                        Unsigned32
			 }

		-- 1.3.6.1.4.1.1916.2.131.50.1.3.16.2.6.1.1
		wingCfgProfIfRadioRfMode OBJECT-TYPE
			SYNTAX DisplayString
			MAX-ACCESS read-write
			STATUS current
			DESCRIPTION
				"
				
				Values:
				2.4GHz-wlan
				5GHz-wlan
				sensor
				
				Notes:
				On a WM3400 the radio-mode of radio1 can only be 2.4|sensor.
				radio2 can only be 5|sensor(so the 2.4-wlan and 5-wlan modes
				cant be interchanged) 
				
				On an AP4700 radio3 can only be sensor. It can never be
				2.4-wlan/5-wlan 
				
				XPath: /wing-config/profile[name=key1]/interface[name=key2]/rf_mode"
			::= { wingCfgProfIfRadioEntry 1 }

		
		-- 1.3.6.1.4.1.1916.2.131.50.1.3.16.2.6.1.2
		wingCfgProfIfRadioChannel OBJECT-TYPE
			SYNTAX DisplayString
			MAX-ACCESS read-write
			STATUS current
			DESCRIPTION
				"Channel of operation for this radio.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, 46, and smart
				
				
				When 'rf_mode' is set to '2.4GHz-wlan', valid channels are
				'1' through '14' and 'smart'.
				
				When 'rf_mode' is set to '5GHz-wlan', '1' through '14'
				are not allowed. Rest of the channels (including 'smart' are
				allowed)
				
				When 'rf_mode' is set to 'sensor', 'channel' setting
				is ignored.
				
				XPath: /wing-config/profile[name=key1]/interface[name=key2]/channel"
			DEFVAL { "smart" }
			::= { wingCfgProfIfRadioEntry 2 }

		
		-- 1.3.6.1.4.1.1916.2.131.50.1.3.16.2.6.1.3
		wingCfgProfIfRadioPower OBJECT-TYPE
			SYNTAX Unsigned32 (0..27)
			UNITS "dBm"
			MAX-ACCESS read-write
			STATUS current
			DESCRIPTION
				"Transmit power of the radio.  A setting of 0 indicates
				Smart RF is managing the power.
				
				XPath: /wing-config/profile[name=key1]/interface[name=key2]/power"
			DEFVAL { 20 }
			::= { wingCfgProfIfRadioEntry 3 }

		
		-- 1.3.6.1.4.1.1916.2.131.50.1.3.16.2.6.1.4
		wingCfgProfIfRadioPlacement OBJECT-TYPE
			SYNTAX DisplayString
			MAX-ACCESS read-write
			STATUS current
			DESCRIPTION
				"Location where this radio is operating.
				
				Values:
				indoor
				outdoor
				
				XPath: /wing-config/profile[name=key1]/interface[name=key2]/placement"
			DEFVAL { "indoor" }
			::= { wingCfgProfIfRadioEntry 4 }

		
		-- 1.3.6.1.4.1.1916.2.131.50.1.3.16.2.6.1.5
		wingCfgProfIfRadioBeaconInterval OBJECT-TYPE
			SYNTAX DisplayString
			UNITS "milliseconds"
			MAX-ACCESS read-write
			STATUS current
			DESCRIPTION
				"Interval between radio beacons.
				
				Values:
				50
				100
				200
				
				XPath: /wing-config/profile[name=key1]/interface[name=key2]/beacon_interval"
			DEFVAL { "100" }
			::= { wingCfgProfIfRadioEntry 5 }

		
		-- 1.3.6.1.4.1.1916.2.131.50.1.3.16.2.6.1.6
		wingCfgProfIfRadioRtsThreshold OBJECT-TYPE
			SYNTAX Unsigned32 (1..2347)
			UNITS "bytes"
			MAX-ACCESS read-write
			STATUS current
			DESCRIPTION
				"Ready to Send threshold on this radio.
				
				XPath: /wing-config/profile[name=key1]/interface[name=key2]/rts_threshold"
			DEFVAL { 2347 }
			::= { wingCfgProfIfRadioEntry 6 }

		
		-- 1.3.6.1.4.1.1916.2.131.50.1.3.16.2.6.1.7
		wingCfgProfIfRadioOffChannelScan OBJECT-TYPE
			SYNTAX TruthValue
			MAX-ACCESS read-write
			STATUS current
			DESCRIPTION
				"Enable off-channel scanning on this radio.
				
				XPath: /wing-config/profile[name=key1]/interface[name=key2]/off_channel_scan"
			DEFVAL { false }
			::= { wingCfgProfIfRadioEntry 7 }

		
		-- 1.3.6.1.4.1.1916.2.131.50.1.3.16.2.6.1.8
		wingCfgProfIfRadioPreambleShort OBJECT-TYPE
			SYNTAX TruthValue
			MAX-ACCESS read-write
			STATUS current
			DESCRIPTION
				"Configure use of short preamble.
				
				XPath: /wing-config/profile[name=key1]/interface[name=key2]/preamble_short"
			DEFVAL { false }
			::= { wingCfgProfIfRadioEntry 8 }

		
		-- 1.3.6.1.4.1.1916.2.131.50.1.3.16.2.6.1.9
		wingCfgProfIfRadioGuardInterval OBJECT-TYPE
			SYNTAX DisplayString
			MAX-ACCESS read-write
			STATUS current
			DESCRIPTION
				"802.11n guard interval.
				
				Values:
				any
				long
				
				XPath: /wing-config/profile[name=key1]/interface[name=key2]/guard_interval"
			DEFVAL { "any" }
			::= { wingCfgProfIfRadioEntry 9 }

		
		-- 1.3.6.1.4.1.1916.2.131.50.1.3.16.2.6.1.10
		wingCfgProfIfRadioAmpduMode OBJECT-TYPE
			SYNTAX DisplayString
			MAX-ACCESS read-write
			STATUS current
			DESCRIPTION
				"Mode in which A-MPDU will be supported.
				
				Values:
				tx-only
				rx-only
				tx-rx
				none
				
				XPath: /wing-config/profile[name=key1]/interface[name=key2]/ampdu_mode"
			DEFVAL { "tx-rx" }
			::= { wingCfgProfIfRadioEntry 10 }

		
		-- 1.3.6.1.4.1.1916.2.131.50.1.3.16.2.6.1.11
		wingCfgProfIfRadioAmsduMode OBJECT-TYPE
			SYNTAX DisplayString
			MAX-ACCESS read-write
			STATUS current
			DESCRIPTION
				"Mode in which A-MSDU will be supported.
				
				Values:
				rx-only
				tx-rx
				
				XPath: /wing-config/profile[name=key1]/interface[name=key2]/amsdu_mode"
			DEFVAL { "rx-only" }
			::= { wingCfgProfIfRadioEntry 11 }

		
		-- 1.3.6.1.4.1.1916.2.131.50.1.3.16.2.6.1.12
		wingCfgProfIfRadioRifsMode OBJECT-TYPE
			SYNTAX DisplayString
			MAX-ACCESS read-write
			STATUS current
			DESCRIPTION
				"Modes in which RIFS will be supported.
				
				Values:
				tx-only
				rx-only
				tx-rx
				none
				
				XPath: /wing-config/profile[name=key1]/interface[name=key2]/rifs_mode"
			DEFVAL { "tx-rx" }
			::= { wingCfgProfIfRadioEntry 12 }

		
		-- 1.3.6.1.4.1.1916.2.131.50.1.3.16.2.6.1.13
		wingCfgProfIfRadioAmpduMaxAggrSizeRx OBJECT-TYPE
			SYNTAX DisplayString
			UNITS "bytes"
			MAX-ACCESS read-write
			STATUS current
			DESCRIPTION
				"Advertised maximum limit on A-MPDU aggregated received frames.
				
				Values:
				8191
				16383
				32767
				65535
				
				XPath: /wing-config/profile[name=key1]/interface[name=key2]/ampdu_max_aggr_size_rx"
			DEFVAL { "65535" }
			::= { wingCfgProfIfRadioEntry 13 }

		
		-- 1.3.6.1.4.1.1916.2.131.50.1.3.16.2.6.1.14
		wingCfgProfIfRadioAmpduMaxAggrSizeTx OBJECT-TYPE
			SYNTAX Unsigned32 (0..65535)
			UNITS "bytes"
			MAX-ACCESS read-write
			STATUS current
			DESCRIPTION
				"Limit on A-MPDU aggregated transmitted frames.
				
				XPath: /wing-config/profile[name=key1]/interface[name=key2]/ampdu_max_aggr_size_tx"
			DEFVAL { 65535 }
			::= { wingCfgProfIfRadioEntry 14 }

		
		-- 1.3.6.1.4.1.1916.2.131.50.1.3.16.2.6.1.15
		wingCfgProfIfRadioAmpduMinSpacing OBJECT-TYPE
			SYNTAX DisplayString
			UNITS "microseconds"
			MAX-ACCESS read-write
			STATUS current
			DESCRIPTION
				"Minimum gap between A-MPDU frames (in microseconds).
				
				Values:
				0
				1
				2
				4
				8
				16
				
				XPath: /wing-config/profile[name=key1]/interface[name=key2]/ampdu_min_spacing"
			DEFVAL { "4" }
			::= { wingCfgProfIfRadioEntry 15 }

		
		-- 1.3.6.1.4.1.1916.2.131.50.1.3.16.2.6.1.16
		wingCfgProfIfRadioAntennaMode OBJECT-TYPE
			SYNTAX DisplayString
			MAX-ACCESS read-write
			STATUS current
			DESCRIPTION
				"Number of transmit and receive antennas on the radio. 1x1 implies only the A antenna; 1x3 implies A for Tx and all three for Rx; default depends on the AP type, the type of power (802.3af etc), etc.
				
				Values:
				1x1
				1xALL
				2x2
				default
				
				XPath: /wing-config/profile[name=key1]/interface[name=key2]/antenna_mode"
			DEFVAL { "default" }
			::= { wingCfgProfIfRadioEntry 16 }

		
		-- 1.3.6.1.4.1.1916.2.131.50.1.3.16.2.6.1.17
		wingCfgProfIfRadioNonUnicastForwarding OBJECT-TYPE
			SYNTAX DisplayString
			MAX-ACCESS read-write
			STATUS current
			DESCRIPTION
				"Whether broadcast and multicast packets should always follow
				DTIM, or do so only if some wireless clients are in
				power-save mode.
				
				Values:
				follow-dtim
				power-save-aware
				
				XPath: /wing-config/profile[name=key1]/interface[name=key2]/non_unicast_forwarding"
			DEFVAL { "follow-dtim" }
			::= { wingCfgProfIfRadioEntry 17 }

		
		-- 1.3.6.1.4.1.1916.2.131.50.1.3.16.2.6.1.18
		wingCfgProfIfRadioDynamicChainSelection OBJECT-TYPE
			SYNTAX TruthValue
			MAX-ACCESS read-write
			STATUS current
			DESCRIPTION
				"Whether the radio should dynamically change the number of
				transmit chains used (use a single chain/antenna for frames
				at non-11n data-rates).
				
				XPath: /wing-config/profile[name=key1]/interface[name=key2]/dynamic_chain_selection"
			DEFVAL { false }
			::= { wingCfgProfIfRadioEntry 18 }

		
		-- 1.3.6.1.4.1.1916.2.131.50.1.3.16.2.6.1.19
		wingCfgProfIfRadioLockRfMode OBJECT-TYPE
			SYNTAX TruthValue
			MAX-ACCESS read-write
			STATUS current
			DESCRIPTION
				"Lock Smart RF mode of operation for this radio.
				
				XPath: /wing-config/profile[name=key1]/interface[name=key2]/lock_rf_mode"
			DEFVAL { false }
			::= { wingCfgProfIfRadioEntry 19 }

		
		-- 1.3.6.1.4.1.1916.2.131.50.1.3.16.2.6.1.20
		wingCfgProfIfRadioSnifferRedirHost OBJECT-TYPE
			SYNTAX DisplayString
			MAX-ACCESS read-write
			STATUS current
			DESCRIPTION
				"Address of host to which captured packets are redirected.
				
				XPath: /wing-config/profile[name=key1]/interface[name=key2]/sniffer_redirect/host"
			::= { wingCfgProfIfRadioEntry 20 }

		
		-- 1.3.6.1.4.1.1916.2.131.50.1.3.16.2.6.1.21
		wingCfgProfIfRadioSnifferRedirChannel OBJECT-TYPE
			SYNTAX DisplayString
			MAX-ACCESS read-write
			STATUS current
			DESCRIPTION
				"Channel on which to capture packets.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, and 46
				
				XPath: /wing-config/profile[name=key1]/interface[name=key2]/sniffer_redirect/channel"
			DEFVAL { "1" }
			::= { wingCfgProfIfRadioEntry 21 }

		
		-- 1.3.6.1.4.1.1916.2.131.50.1.3.16.2.6.1.22
		wingCfgProfIfRadioMesh OBJECT-TYPE
			SYNTAX DisplayString
			MAX-ACCESS read-write
			STATUS current
			DESCRIPTION
				"Client operation scans for Mesh Portals, or nodes that have
				connectivity to Portals, and connects through them. 
				Portal operation begins beaconing immediately and accepting
				connections from other Mesh nodes.  Generally the Portal node
				is connected to the wired network.
				
				Values:
				disabled
				portal
				client
				
				XPath: /wing-config/profile[name=key1]/interface[name=key2]/mesh"
			DEFVAL { "disabled" }
			::= { wingCfgProfIfRadioEntry 22 }

		
		-- 1.3.6.1.4.1.1916.2.131.50.1.3.16.2.6.1.23
		wingCfgProfIfRadioMeshLinks OBJECT-TYPE
			SYNTAX Unsigned32 (1..6)
			MAX-ACCESS read-write
			STATUS current
			DESCRIPTION
				"Maximum number of Mesh links that this radio will attempt to
				create.
				
				XPath: /wing-config/profile[name=key1]/interface[name=key2]/mesh_links"
			DEFVAL { 3 }
			::= { wingCfgProfIfRadioEntry 23 }

		
		-- 1.3.6.1.4.1.1916.2.131.50.1.3.16.2.6.1.24
		wingCfgProfIfRadioProbeResponseRetry OBJECT-TYPE
			SYNTAX TruthValue
			MAX-ACCESS read-write
			STATUS current
			DESCRIPTION
				"Whether Probe-Responses are retried on the air if they are
				not acknowledged by the wireless client
				
				XPath: /wing-config/profile[name=key1]/interface[name=key2]/probe_response_retry"
			DEFVAL { true }
			::= { wingCfgProfIfRadioEntry 24 }

		
		-- 1.3.6.1.4.1.1916.2.131.50.1.3.16.2.6.1.25
		wingCfgProfIfRadioProbeResponseRate OBJECT-TYPE
			SYNTAX DisplayString
			MAX-ACCESS read-write
			STATUS current
			DESCRIPTION
				"The data transmission rate used for sending Probe Responses
				
				Values:
				follow-probe-request
				highest-basic
				lowest-basic
				
				XPath: /wing-config/profile[name=key1]/interface[name=key2]/probe_response_rate"
			DEFVAL { "follow-probe-request" }
			::= { wingCfgProfIfRadioEntry 25 }

		
		-- 1.3.6.1.4.1.1916.2.131.50.1.3.16.2.6.1.26
		wingCfgProfIfRadioMaxClients OBJECT-TYPE
			SYNTAX Unsigned32 (0..256)
			MAX-ACCESS read-write
			STATUS current
			DESCRIPTION
				"The maximum number of clients allowed to associate
				with this radio
				
				XPath: /wing-config/profile[name=key1]/interface[name=key2]/max_clients"
			DEFVAL { 256 }
			::= { wingCfgProfIfRadioEntry 26 }

		
		-- 1.3.6.1.4.1.1916.2.131.50.1.3.16.2.6.1.27
		wingCfgProfIfRadioRadioTapMode OBJECT-TYPE
			SYNTAX DisplayString
			MAX-ACCESS read-write
			STATUS current
			DESCRIPTION
				"Radio tap mode of operation
				
				Values:
				off
				inline
				promiscuous
				
				Note:
				Radio tap can be enabled only on wlan radio and in 5.1,
				only when another radio on AP is sensor.
				
				XPath: /wing-config/profile[name=key1]/interface[name=key2]/radio_tap_mode"
			DEFVAL { "off" }
			::= { wingCfgProfIfRadioEntry 27 }

		
		-- 1.3.6.1.4.1.1916.2.131.50.1.3.16.2.6.1.28
		wingCfgProfIfRadioWirelessClientPower OBJECT-TYPE
			SYNTAX Unsigned32 (0..20)
			UNITS "dBm"
			MAX-ACCESS read-write
			STATUS current
			DESCRIPTION
				"Transmit power indicated to wireless clients for transmission.
				
				XPath: /wing-config/profile[name=key1]/interface[name=key2]/wireless_client_power"
			::= { wingCfgProfIfRadioEntry 28 }

		
		-- 1.3.6.1.4.1.1916.2.131.50.1.3.16.2.6.1.29
		wingCfgProfIfRadioLoadBalLfCount OBJECT-TYPE
			SYNTAX Unsigned32 (0..10)
			MAX-ACCESS read-write
			STATUS current
			DESCRIPTION
				"Consider the number of Wireless Clients in determining
				the load on an AP.  High numbers indicate a higher weight
				assigned to the criteria. 0 implies that count is
				not considered.
				
				XPath: /wing-config/profile[name=key1]/interface[name=key2]/load_balance_lf_count"
			DEFVAL { 10 }
			::= { wingCfgProfIfRadioEntry 29 }

		
		-- 1.3.6.1.4.1.1916.2.131.50.1.3.16.2.6.1.30
		wingCfgProfIfRadioLoadBalLfThroughput OBJECT-TYPE
			SYNTAX Unsigned32 (0..10)
			MAX-ACCESS read-write
			STATUS current
			DESCRIPTION
				"Consider the throughput of traffic in determining the load
				on an AP.  High numbers indicate a higher weight assigned
				to the criteria.  0 implies that throughput is not considered.
				
				XPath: /wing-config/profile[name=key1]/interface[name=key2]/load_balance_lf_throughput"
			DEFVAL { 0 }
			::= { wingCfgProfIfRadioEntry 30 }

		
		-- 1.3.6.1.4.1.1916.2.131.50.1.3.16.2.6.1.31
		wingCfgProfIfRadioLoadBalWmCount OBJECT-TYPE
			SYNTAX Unsigned32 (1..255)
			MAX-ACCESS read-write
			STATUS current
			DESCRIPTION
				"The number of clients that can associate with a radio before
				load-balancing would be triggered
				
				XPath: /wing-config/profile[name=key1]/interface[name=key2]/load_balance_wm_count"
			DEFVAL { 10 }
			::= { wingCfgProfIfRadioEntry 31 }

		
		-- 1.3.6.1.4.1.1916.2.131.50.1.3.16.2.6.1.32
		wingCfgProfIfRadioLoadBalWmTput OBJECT-TYPE
			SYNTAX Unsigned32 (1..1000)
			MAX-ACCESS read-write
			STATUS current
			DESCRIPTION
				"When the average throughput of a radio exceeds this threshold
				(in Mbps) load balancing would be triggered
				
				XPath: /wing-config/profile[name=key1]/interface[name=key2]/load_balance_wm_tput_mbps"
			DEFVAL { 10 }
			::= { wingCfgProfIfRadioEntry 32 }

		
		-- 1.3.6.1.4.1.1916.2.131.50.1.3.16.2.6.1.33
		wingCfgProfIfRadioAssocAcl OBJECT-TYPE
			SYNTAX WingIdentifier
			MAX-ACCESS read-write
			STATUS current
			DESCRIPTION
				"
				
				XPath: /wing-config/profile[name=key1]/interface[name=key2]/assoc_acl"
			::= { wingCfgProfIfRadioEntry 33 }

		
		-- 1.3.6.1.4.1.1916.2.131.50.1.3.16.2.6.1.34
		wingCfgProfIfRadioQosPolicy OBJECT-TYPE
			SYNTAX WingIdentifier
			MAX-ACCESS read-write
			STATUS current
			DESCRIPTION
				"
				
				XPath: /wing-config/profile[name=key1]/interface[name=key2]/qos_policy"
			::= { wingCfgProfIfRadioEntry 34 }

                -- 1.3.6.1.4.1.1916.2.131.50.1.3.16.2.6.1.35
                wingCfgProfIfRadioAntennaDowntilt OBJECT-TYPE
                        SYNTAX TruthValue
                        MAX-ACCESS read-write
                        STATUS current
                        DESCRIPTION
                                "Whether the radio should enable ADEPT antenna modes.
 
                                XPath: /wing-config/profile[name=key1]/interface[name=key2]/antenna_downtilt"
                        DEFVAL { false }
                        ::= { wingCfgProfIfRadioEntry 35 }
 
 
                -- 1.3.6.1.4.1.1916.2.131.50.1.3.16.2.6.1.36
                wingCfgProfIfRadioExtendedRange OBJECT-TYPE
                        SYNTAX Unsigned32
                        MAX-ACCESS read-write
                        STATUS current
                        DESCRIPTION
                                "Configure extended rate selection.
			
				Default Value
                                for 2.4 Ghz : 7 Kilometer
                                    5 GHz   : 2 Kilometer
                                XPath: /wing-config/profile[name=key1]/interface[name=key2]/extended_range"
                        DEFVAL { "kilometer" }
                        ::= { wingCfgProfIfRadioEntry 36 }

		-- 1.3.6.1.4.1.1916.2.131.50.1.3.16.2.7
		wingCfgProfIfRadioBssmapTable OBJECT-TYPE
			SYNTAX SEQUENCE OF WingCfgProfIfRadioBssmapEntry
			MAX-ACCESS not-accessible
			STATUS current
			DESCRIPTION
				"
				
				/wing-config/profile/interface/wlanbssmap"
			::= { wingCfgProfIf 7 }

		
		-- 1.3.6.1.4.1.1916.2.131.50.1.3.16.2.7.1
		wingCfgProfIfRadioBssmapEntry OBJECT-TYPE
			SYNTAX WingCfgProfIfRadioBssmapEntry
			MAX-ACCESS not-accessible
			STATUS current
			DESCRIPTION
				"An entry in the table."
			INDEX { wingCfgProfName, wingCfgProfIfName, wingCfgProfIfRadioBssmapWlan }
			::= { wingCfgProfIfRadioBssmapTable 1 }

		
		WingCfgProfIfRadioBssmapEntry ::=
			SEQUENCE { 
				wingCfgProfIfRadioBssmapWlan
					WingIdentifier,
				wingCfgProfIfRadioBssmapBss
					Unsigned32,
				wingCfgProfIfRadioBssmapPrimary
					TruthValue
			 }

		-- 1.3.6.1.4.1.1916.2.131.50.1.3.16.2.7.1.1
		wingCfgProfIfRadioBssmapWlan OBJECT-TYPE
			SYNTAX WingIdentifier
			MAX-ACCESS read-only
			STATUS current
			DESCRIPTION
				"
				
				XPath: /wing-config/profile[name=key1]/interface[name=key2]/wlanbssmap[wlan=key3]/wlan"
			::= { wingCfgProfIfRadioBssmapEntry 1 }

		
		-- 1.3.6.1.4.1.1916.2.131.50.1.3.16.2.7.1.3
		wingCfgProfIfRadioBssmapBss OBJECT-TYPE
			SYNTAX Unsigned32 (1..16)
			MAX-ACCESS read-write
			STATUS current
			DESCRIPTION
				"
				
				XPath: /wing-config/profile[name=key1]/interface[name=key2]/wlanbssmap[wlan=key3]/bss"
			::= { wingCfgProfIfRadioBssmapEntry 3 }

		
		-- 1.3.6.1.4.1.1916.2.131.50.1.3.16.2.7.1.4
		wingCfgProfIfRadioBssmapPrimary OBJECT-TYPE
			SYNTAX TruthValue
			MAX-ACCESS read-write
			STATUS current
			DESCRIPTION
				"
				
				XPath: /wing-config/profile[name=key1]/interface[name=key2]/wlanbssmap[wlan=key3]/primary"
			::= { wingCfgProfIfRadioBssmapEntry 4 }

		
		-- 1.3.6.1.4.1.1916.2.131.50.1.3.16.2.9
		wingCfgProfIfSpanTreeTable OBJECT-TYPE
			SYNTAX SEQUENCE OF WingCfgProfIfSpanTreeEntry
			MAX-ACCESS not-accessible
			STATUS current
			DESCRIPTION
				"Interface Spanning Tree configuration
				
				/wing-config/profile/interface/spanningtree"
			::= { wingCfgProfIf 9 }

		
		-- 1.3.6.1.4.1.1916.2.131.50.1.3.16.2.9.1
		wingCfgProfIfSpanTreeEntry OBJECT-TYPE
			SYNTAX WingCfgProfIfSpanTreeEntry
			MAX-ACCESS not-accessible
			STATUS current
			DESCRIPTION
				"An entry in the table."
			INDEX { wingCfgProfName, wingCfgProfIfName }
			::= { wingCfgProfIfSpanTreeTable 1 }

		
		WingCfgProfIfSpanTreeEntry ::=
			SEQUENCE { 
				wingCfgProfIfSpanTreeLinkType
					DisplayString,
				wingCfgProfIfSpanTreePortfast
					TruthValue,
				wingCfgProfIfSpanTreeEdgeport
					TruthValue,
				wingCfgProfIfSpanTreeBpduguard
					DisplayString,
				wingCfgProfIfSpanTreeBpdufilter
					DisplayString,
				wingCfgProfIfSpanTreePortCiscoInterop
					DisplayString,
				wingCfgProfIfSpanTreeForceVersion
					Unsigned32,
				wingCfgProfIfSpanTreeGuard
					DisplayString
			 }

		-- 1.3.6.1.4.1.1916.2.131.50.1.3.16.2.9.1.1
		wingCfgProfIfSpanTreeLinkType OBJECT-TYPE
			SYNTAX DisplayString
			MAX-ACCESS read-write
			STATUS current
			DESCRIPTION
				"Point-to-point enables rapid transition.  Shared disables
				rapid transition.
				
				Values:
				point-to-point
				shared
				
				XPath: /wing-config/profile[name=key1]/interface[name=key2]/spanningtree/link_type"
			DEFVAL { "point-to-point" }
			::= { wingCfgProfIfSpanTreeEntry 1 }

		
		-- 1.3.6.1.4.1.1916.2.131.50.1.3.16.2.9.1.2
		wingCfgProfIfSpanTreePortfast OBJECT-TYPE
			SYNTAX TruthValue
			MAX-ACCESS read-write
			STATUS current
			DESCRIPTION
				"Enable fast transitions.
				
				XPath: /wing-config/profile[name=key1]/interface[name=key2]/spanningtree/portfast"
			DEFVAL { false }
			::= { wingCfgProfIfSpanTreeEntry 2 }

		
		-- 1.3.6.1.4.1.1916.2.131.50.1.3.16.2.9.1.3
		wingCfgProfIfSpanTreeEdgeport OBJECT-TYPE
			SYNTAX TruthValue
			MAX-ACCESS read-write
			STATUS current
			DESCRIPTION
				"Enable the port as an edge port.
				
				XPath: /wing-config/profile[name=key1]/interface[name=key2]/spanningtree/edgeport"
			DEFVAL { false }
			::= { wingCfgProfIfSpanTreeEntry 3 }

		
		-- 1.3.6.1.4.1.1916.2.131.50.1.3.16.2.9.1.4
		wingCfgProfIfSpanTreeBpduguard OBJECT-TYPE
			SYNTAX DisplayString
			MAX-ACCESS read-write
			STATUS current
			DESCRIPTION
				"Guard the port against reception of BPDUs.
				
				Values:
				none
				enable
				disable
				
				XPath: /wing-config/profile[name=key1]/interface[name=key2]/spanningtree/bpduguard"
			DEFVAL { "none" }
			::= { wingCfgProfIfSpanTreeEntry 4 }

		
		-- 1.3.6.1.4.1.1916.2.131.50.1.3.16.2.9.1.5
		wingCfgProfIfSpanTreeBpdufilter OBJECT-TYPE
			SYNTAX DisplayString
			MAX-ACCESS read-write
			STATUS current
			DESCRIPTION
				"Set the PortFast BPDU filter for the port.  Enabling the BPDU
				filter ensures that PortFast enabled ports do not transmit or
				receive BPDUs.
				
				Values:
				none
				enable
				disable
				
				XPath: /wing-config/profile[name=key1]/interface[name=key2]/spanningtree/bpdufilter"
			DEFVAL { "none" }
			::= { wingCfgProfIfSpanTreeEntry 5 }

		
		-- 1.3.6.1.4.1.1916.2.131.50.1.3.16.2.9.1.6
		wingCfgProfIfSpanTreePortCiscoInterop OBJECT-TYPE
			SYNTAX DisplayString
			MAX-ACCESS read-write
			STATUS current
			DESCRIPTION
				"Enable interoperability with Cisco's version of MSTP,
				which is incompatible with standard MSTP.
				
				Values:
				enable
				disable
				
				XPath: /wing-config/profile[name=key1]/interface[name=key2]/spanningtree/port_cisco_interop"
			DEFVAL { "disable" }
			::= { wingCfgProfIfSpanTreeEntry 6 }

		
		-- 1.3.6.1.4.1.1916.2.131.50.1.3.16.2.9.1.7
		wingCfgProfIfSpanTreeForceVersion OBJECT-TYPE
			SYNTAX Unsigned32 (0..3)
			MAX-ACCESS read-write
			STATUS current
			DESCRIPTION
				"Version identifier where 0=STP, 1=Not Supported, 2=RSTP,
				3=MSTP.
				
				XPath: /wing-config/profile[name=key1]/interface[name=key2]/spanningtree/force_version"
			DEFVAL { 3 }
			::= { wingCfgProfIfSpanTreeEntry 7 }

		
		-- 1.3.6.1.4.1.1916.2.131.50.1.3.16.2.9.1.8
		wingCfgProfIfSpanTreeGuard OBJECT-TYPE
			SYNTAX DisplayString
			MAX-ACCESS read-write
			STATUS current
			DESCRIPTION
				"Setting 'root' disables reception of superior BPDUs.
				
				Values:
				none
				root
				
				XPath: /wing-config/profile[name=key1]/interface[name=key2]/spanningtree/guard"
			DEFVAL { "none" }
			::= { wingCfgProfIfSpanTreeEntry 8 }

		
		-- 1.3.6.1.4.1.1916.2.131.50.1.3.16.2.12
		wingCfgProfIfWwanTable OBJECT-TYPE
			SYNTAX SEQUENCE OF WingCfgProfIfWwanEntry
			MAX-ACCESS not-accessible
			STATUS current
			DESCRIPTION
				"
				
				/wing-config/profile/interface"
			::= { wingCfgProfIf 12 }

		
		-- 1.3.6.1.4.1.1916.2.131.50.1.3.16.2.12.1
		wingCfgProfIfWwanEntry OBJECT-TYPE
			SYNTAX WingCfgProfIfWwanEntry
			MAX-ACCESS not-accessible
			STATUS current
			DESCRIPTION
				"An entry in the table."
			INDEX { wingCfgProfName, wingCfgProfIfName }
			::= { wingCfgProfIfWwanTable 1 }

		
		WingCfgProfIfWwanEntry ::=
			SEQUENCE { 
				wingCfgProfIfWwanApn
					DisplayString,
				wingCfgProfIfWwanAuth
					DisplayString,
				wingCfgProfIfWwanUser
					DisplayString,
				wingCfgProfIfWwanPwd
					DisplayString,
                                wingCfgProfIfWwanDefaultRoutePriority
                                        Unsigned32
			 }

		-- 1.3.6.1.4.1.1916.2.131.50.1.3.16.2.12.1.2
		wingCfgProfIfWwanApn OBJECT-TYPE
			SYNTAX DisplayString (SIZE (0..25))
			MAX-ACCESS read-write
			STATUS current
			DESCRIPTION
				"Access Point Name.
				
				XPath: /wing-config/profile[name=key1]/interface[name=key2]/apn"
			DEFVAL { "" }
			::= { wingCfgProfIfWwanEntry 2 }

		
		-- 1.3.6.1.4.1.1916.2.131.50.1.3.16.2.12.1.3
		wingCfgProfIfWwanAuth OBJECT-TYPE
			SYNTAX DisplayString
			MAX-ACCESS read-write
			STATUS current
			DESCRIPTION
				"Authentication Type.
				
				Values:
				pap,
				chap,
				mschap,
				mschap-v2
				
				XPath: /wing-config/profile[name=key1]/interface[name=key2]/auth"
			DEFVAL { "chap" }
			::= { wingCfgProfIfWwanEntry 3 }

		
		-- 1.3.6.1.4.1.1916.2.131.50.1.3.16.2.12.1.4
		wingCfgProfIfWwanUser OBJECT-TYPE
			SYNTAX DisplayString (SIZE (0..32))
			MAX-ACCESS read-write
			STATUS current
			DESCRIPTION
				"User Name.
				
				XPath: /wing-config/profile[name=key1]/interface[name=key2]/user"
			DEFVAL { "" }
			::= { wingCfgProfIfWwanEntry 4 }

		
		-- 1.3.6.1.4.1.1916.2.131.50.1.3.16.2.12.1.5
		wingCfgProfIfWwanPwd OBJECT-TYPE
			SYNTAX DisplayString (SIZE (0..30))
			MAX-ACCESS read-write
			STATUS current
			DESCRIPTION
				"Password.
				
				XPath: /wing-config/profile[name=key1]/interface[name=key2]/pwd"
			DEFVAL { "" }
			::= { wingCfgProfIfWwanEntry 5 }

		-- 1.3.6.1.4.1.1916.2.131.50.1.3.16.2.12.1.6
                wingCfgProfIfWwanDefaultRoutePriority OBJECT-TYPE
                        SYNTAX Unsigned32 (1..8000)
                        MAX-ACCESS read-write
                        STATUS current
                        DESCRIPTION
                                "Priority for the default route learnt via Wireless WAN

                                XPath: /wing-config/profile[name=key1]/interface[name=key2]/wwan_default_route_priority"
                        DEFVAL { 3000 }
                        ::= { wingCfgProfIfWwanEntry 6 }

		
		-- 1.3.6.1.4.1.1916.2.131.50.1.3.16.2.13
		wingCfgProfIfVlanOspfTable OBJECT-TYPE
			SYNTAX SEQUENCE OF WingCfgProfIfVlanOspfEntry
			MAX-ACCESS not-accessible
			STATUS current
			DESCRIPTION
				"
				
				/wing-config/profile/interface"
			::= { wingCfgProfIf 13 }

		
		-- 1.3.6.1.4.1.1916.2.131.50.1.3.16.2.13.1
		wingCfgProfIfVlanOspfEntry OBJECT-TYPE
			SYNTAX WingCfgProfIfVlanOspfEntry
			MAX-ACCESS not-accessible
			STATUS current
			DESCRIPTION
				"An entry in the table."
			INDEX { wingCfgProfName, wingCfgProfIfName }
			::= { wingCfgProfIfVlanOspfTable 1 }

		
		WingCfgProfIfVlanOspfEntry ::=
			SEQUENCE { 
				wingCfgProfIfVlanOspfOspfAuthentication
					DisplayString,
				wingCfgProfIfVlanOspfOspfAuthKey
					DisplayString,
				wingCfgProfIfVlanOspfOspfPriority
					Unsigned32,
				wingCfgProfIfVlanOspfOspfCost
					Unsigned32,
				wingCfgProfIfVlanOspfOspfBandWidth
					Unsigned32
			 }

		-- 1.3.6.1.4.1.1916.2.131.50.1.3.16.2.13.1.1
		wingCfgProfIfVlanOspfOspfAuthentication OBJECT-TYPE
			SYNTAX DisplayString
			MAX-ACCESS read-write
			STATUS current
			DESCRIPTION
				"OSPF authentication type
				
				Values:
				simple-password,
				message-digest,
                                null,
				none
				
				XPath: /wing-config/profile[name=key1]/interface[name=key2]/ospf_authentication"
			DEFVAL { "none" }
			::= { wingCfgProfIfVlanOspfEntry 1 }

		
		-- 1.3.6.1.4.1.1916.2.131.50.1.3.16.2.13.1.2
		wingCfgProfIfVlanOspfOspfAuthKey OBJECT-TYPE
			SYNTAX DisplayString
			MAX-ACCESS read-write
			STATUS current
			DESCRIPTION
				"Simple auth key for OSPF.
				
				XPath: /wing-config/profile[name=key1]/interface[name=key2]/ospf_auth_key"
			::= { wingCfgProfIfVlanOspfEntry 2 }

		
		-- 1.3.6.1.4.1.1916.2.131.50.1.3.16.2.13.1.3
		wingCfgProfIfVlanOspfOspfPriority OBJECT-TYPE
			SYNTAX Unsigned32 (0..255)
			MAX-ACCESS read-write
			STATUS current
			DESCRIPTION
				"OSPF priority used in DR election
				
				XPath: /wing-config/profile[name=key1]/interface[name=key2]/ospf_priority"
			DEFVAL { 0 }
			::= { wingCfgProfIfVlanOspfEntry 3 }

		
		-- 1.3.6.1.4.1.1916.2.131.50.1.3.16.2.13.1.4
		wingCfgProfIfVlanOspfOspfCost OBJECT-TYPE
			SYNTAX Unsigned32 (1..65535)
			MAX-ACCESS read-write
			STATUS current
			DESCRIPTION
				"Cost of this OSPF interface
				
				XPath: /wing-config/profile[name=key1]/interface[name=key2]/ospf_cost"
			DEFVAL { 10 }
			::= { wingCfgProfIfVlanOspfEntry 4 }

		
		-- 1.3.6.1.4.1.1916.2.131.50.1.3.16.2.13.1.5
		wingCfgProfIfVlanOspfOspfBandWidth OBJECT-TYPE
			SYNTAX Unsigned32 (1..10000000)
			MAX-ACCESS read-write
			STATUS current
			DESCRIPTION
				"Bandwidth of the interface in Kbps.
				
				XPath: /wing-config/profile[name=key1]/interface[name=key2]/bandwidth"
			::= { wingCfgProfIfVlanOspfEntry 5 }

		
		-- 1.3.6.1.4.1.1916.2.131.50.1.3.16.2.14
		wingCfgProfIfVlanOspfMsgDigestTable OBJECT-TYPE
			SYNTAX SEQUENCE OF WingCfgProfIfVlanOspfMsgDigestEntry
			MAX-ACCESS not-accessible
			STATUS current
			DESCRIPTION
				"
				
				/wing-config/profile/interface/ospf_message_digest_key"
			::= { wingCfgProfIf 14 }

		
		-- 1.3.6.1.4.1.1916.2.131.50.1.3.16.2.14.1
		wingCfgProfIfVlanOspfMsgDigestEntry OBJECT-TYPE
			SYNTAX WingCfgProfIfVlanOspfMsgDigestEntry
			MAX-ACCESS not-accessible
			STATUS current
			DESCRIPTION
				"An entry in the table."
			INDEX { wingCfgProfName, wingCfgProfIfName, wingCfgProfIfVlanOspfMsgDigestKeyId }
			::= { wingCfgProfIfVlanOspfMsgDigestTable 1 }

		
		WingCfgProfIfVlanOspfMsgDigestEntry ::=
			SEQUENCE { 
				wingCfgProfIfVlanOspfMsgDigestKeyId
					Unsigned32,
				wingCfgProfIfVlanOspfMsgDigestMessageDigest
					DisplayString
			 }

		-- 1.3.6.1.4.1.1916.2.131.50.1.3.16.2.14.1.1
		wingCfgProfIfVlanOspfMsgDigestKeyId OBJECT-TYPE
			SYNTAX Unsigned32 (1..255)
			MAX-ACCESS read-only
			STATUS current
			DESCRIPTION
				"OSPF message digest auth key ID.
				
				XPath: /wing-config/profile[name=key1]/interface[name=key2]/ospf_message_digest_key[key_id=key3]/key_id"
			::= { wingCfgProfIfVlanOspfMsgDigestEntry 1 }

		
		-- 1.3.6.1.4.1.1916.2.131.50.1.3.16.2.14.1.3
		wingCfgProfIfVlanOspfMsgDigestMessageDigest OBJECT-TYPE
			SYNTAX DisplayString
			MAX-ACCESS read-write
			STATUS current
			DESCRIPTION
				"OSPF message digest key.
				
				XPath: /wing-config/profile[name=key1]/interface[name=key2]/ospf_message_digest_key[key_id=key3]/message_digest"
			::= { wingCfgProfIfVlanOspfMsgDigestEntry 3 }

		
		-- 1.3.6.1.4.1.1916.2.131.50.1.3.16.2.15
		wingCfgProfIfPppoeTable OBJECT-TYPE
			SYNTAX SEQUENCE OF WingCfgProfIfPppoeEntry
			MAX-ACCESS not-accessible
			STATUS current
			DESCRIPTION
				"
				
				/wing-config/profile/interface"
			::= { wingCfgProfIf 15 }

		
		-- 1.3.6.1.4.1.1916.2.131.50.1.3.16.2.15.1
		wingCfgProfIfPppoeEntry OBJECT-TYPE
			SYNTAX WingCfgProfIfPppoeEntry
			MAX-ACCESS not-accessible
			STATUS current
			DESCRIPTION
				"An entry in the table."
			INDEX { wingCfgProfName, wingCfgProfIfName }
			::= { wingCfgProfIfPppoeTable 1 }

		
		WingCfgProfIfPppoeEntry ::=
			SEQUENCE { 
				wingCfgProfIfPppoeAuthType
					DisplayString,
				wingCfgProfIfPppoeIdleTime
					Unsigned32,
				wingCfgProfIfPppoeKeepalive
					TruthValue,
				wingCfgProfIfPppoeUsername
					DisplayString,
				wingCfgProfIfPppoePassword
					DisplayString,
				wingCfgProfIfPppoeService
					DisplayString,
				wingCfgProfIfPppoeLocalnetVlan
					Unsigned32,
				wingCfgProfIfPppoeMtu
					Unsigned32,
				wingCfgProfIfPppoeDefaultRoutePriority
					Unsigned32,
				wingCfgProfIfPppoeIp
					DisplayString
			 }

		-- 1.3.6.1.4.1.1916.2.131.50.1.3.16.2.15.1.1
		wingCfgProfIfPppoeAuthType OBJECT-TYPE
			SYNTAX DisplayString
			MAX-ACCESS read-write
			STATUS current
			DESCRIPTION
				"PPPoE Client authentication type.
				
				Values:
				none,
				chap,
				mschap,
				mschap-v2,
				pap
				
				XPath: /wing-config/profile[name=key1]/interface[name=key2]/auth-type"
			DEFVAL { "pap" }
			::= { wingCfgProfIfPppoeEntry 1 }

		
		-- 1.3.6.1.4.1.1916.2.131.50.1.3.16.2.15.1.2
		wingCfgProfIfPppoeIdleTime OBJECT-TYPE
			SYNTAX Unsigned32 (1..65535)
			UNITS "seconds"
			MAX-ACCESS read-write
			STATUS current
			DESCRIPTION
				"PPPoE client Idle Timeout.
				
				XPath: /wing-config/profile[name=key1]/interface[name=key2]/idle-time"
			DEFVAL { 600 }
			::= { wingCfgProfIfPppoeEntry 2 }

		
		-- 1.3.6.1.4.1.1916.2.131.50.1.3.16.2.15.1.3
		wingCfgProfIfPppoeKeepalive OBJECT-TYPE
			SYNTAX TruthValue
			MAX-ACCESS read-write
			STATUS current
			DESCRIPTION
				"PPPoE client keep-alive mode.
				
				XPath: /wing-config/profile[name=key1]/interface[name=key2]/keepalive"
			DEFVAL { false }
			::= { wingCfgProfIfPppoeEntry 3 }

		
		-- 1.3.6.1.4.1.1916.2.131.50.1.3.16.2.15.1.4
		wingCfgProfIfPppoeUsername OBJECT-TYPE
			SYNTAX DisplayString (SIZE (0..64))
			MAX-ACCESS read-write
			STATUS current
			DESCRIPTION
				"PPPoE client username.
				
				XPath: /wing-config/profile[name=key1]/interface[name=key2]/username"
			DEFVAL { "" }
			::= { wingCfgProfIfPppoeEntry 4 }

		
		-- 1.3.6.1.4.1.1916.2.131.50.1.3.16.2.15.1.5
		wingCfgProfIfPppoePassword OBJECT-TYPE
			SYNTAX DisplayString (SIZE (0..64))
			MAX-ACCESS read-write
			STATUS current
			DESCRIPTION
				"PPPoE client password.
				
				XPath: /wing-config/profile[name=key1]/interface[name=key2]/password"
			DEFVAL { "" }
			::= { wingCfgProfIfPppoeEntry 5 }

		
		-- 1.3.6.1.4.1.1916.2.131.50.1.3.16.2.15.1.6
		wingCfgProfIfPppoeService OBJECT-TYPE
			SYNTAX DisplayString (SIZE (0..128))
			MAX-ACCESS read-write
			STATUS current
			DESCRIPTION
				"PPPoE client service-name.
				
				XPath: /wing-config/profile[name=key1]/interface[name=key2]/service"
			DEFVAL { "" }
			::= { wingCfgProfIfPppoeEntry 6 }

		
		-- 1.3.6.1.4.1.1916.2.131.50.1.3.16.2.15.1.7
		wingCfgProfIfPppoeLocalnetVlan OBJECT-TYPE
			SYNTAX Unsigned32 (1..4094)
			MAX-ACCESS read-write
			STATUS current
			DESCRIPTION
				"PPPoE client local network(vlan) connected to DSL modem.
				
				XPath: /wing-config/profile[name=key1]/interface[name=key2]/localnet_vlan"
			DEFVAL { 1 }
			::= { wingCfgProfIfPppoeEntry 7 }

		
		-- 1.3.6.1.4.1.1916.2.131.50.1.3.16.2.15.1.8
		wingCfgProfIfPppoeMtu OBJECT-TYPE
			SYNTAX Unsigned32 (500..1492)
			MAX-ACCESS read-write
			STATUS current
			DESCRIPTION
				"PPPoE client Maximum Transmission Unit(MTU).
				
				XPath: /wing-config/profile[name=key1]/interface[name=key2]/mtu"
			DEFVAL { 1492 }
			::= { wingCfgProfIfPppoeEntry 8 }

		
		-- 1.3.6.1.4.1.1916.2.131.50.1.3.16.2.15.1.9
		wingCfgProfIfPppoeDefaultRoutePriority OBJECT-TYPE
			SYNTAX Unsigned32 (1..8000)
			MAX-ACCESS read-write
			STATUS current
			DESCRIPTION
				"Priority for the default route learnt via PPPoE
				
				XPath: /wing-config/profile[name=key1]/interface[name=key2]/pppoe_default_route_priority"
			DEFVAL { 2000 }
			::= { wingCfgProfIfPppoeEntry 9 }

		
		-- 1.3.6.1.4.1.1916.2.131.50.1.3.16.2.15.1.10
		wingCfgProfIfPppoeIp OBJECT-TYPE
			SYNTAX DisplayString
			MAX-ACCESS read-write
			STATUS current
			DESCRIPTION
				"PPPoE client IP address.
				
				XPath: /wing-config/profile[name=key1]/interface[name=key2]/ip"
			DEFVAL { "0.0.0.0" }
			::= { wingCfgProfIfPppoeEntry 10 }

		
		-- 1.3.6.1.4.1.1916.2.131.50.1.3.16.2.16
		wingCfgProfIfT1E1Table OBJECT-TYPE
			SYNTAX SEQUENCE OF WingCfgProfIfT1E1Entry
			MAX-ACCESS not-accessible
			STATUS current
			DESCRIPTION
				"T1 or E1 interface (switched interface) configuration.
				
				/wing-config/profile/interface"
			::= { wingCfgProfIf 16 }

		
		-- 1.3.6.1.4.1.1916.2.131.50.1.3.16.2.16.1
		wingCfgProfIfT1E1Entry OBJECT-TYPE
			SYNTAX WingCfgProfIfT1E1Entry
			MAX-ACCESS not-accessible
			STATUS current
			DESCRIPTION
				"An entry in the table."
			INDEX { wingCfgProfName, wingCfgProfIfName }
			::= { wingCfgProfIfT1E1Table 1 }

		
		WingCfgProfIfT1E1Entry ::=
			SEQUENCE { 
				wingCfgProfIfT1E1Media
					DisplayString,
				wingCfgProfIfT1E1ClockMode
					DisplayString,
				wingCfgProfIfT1E1HighImpedance
					DisplayString,
				wingCfgProfIfT1E1LineBuildOut
					DisplayString,
				wingCfgProfIfT1E1LineEncoding
					DisplayString,
				wingCfgProfIfT1E1RxSensitivityLevel
					DisplayString
			 }

		-- 1.3.6.1.4.1.1916.2.131.50.1.3.16.2.16.1.1
		wingCfgProfIfT1E1Media OBJECT-TYPE
			SYNTAX DisplayString
			MAX-ACCESS read-write
			STATUS current
			DESCRIPTION
				"The media type for the physical interface
				
				Values:
				t1
				e1
				
				XPath: /wing-config/profile[name=key1]/interface[name=key2]/media"
			DEFVAL { "t1" }
			::= { wingCfgProfIfT1E1Entry 1 }

		
		-- 1.3.6.1.4.1.1916.2.131.50.1.3.16.2.16.1.2
		wingCfgProfIfT1E1ClockMode OBJECT-TYPE
			SYNTAX DisplayString
			MAX-ACCESS read-write
			STATUS current
			DESCRIPTION
				"The mode for the clock
				
				Values:
				normal
				master
				
				XPath: /wing-config/profile[name=key1]/interface[name=key2]/clock_mode"
			DEFVAL { "normal" }
			::= { wingCfgProfIfT1E1Entry 2 }

		
		-- 1.3.6.1.4.1.1916.2.131.50.1.3.16.2.16.1.3
		wingCfgProfIfT1E1HighImpedance OBJECT-TYPE
			SYNTAX DisplayString
			MAX-ACCESS read-write
			STATUS current
			DESCRIPTION
				"High impedance mode
				
				Values:
				disable
				enable
				
				XPath: /wing-config/profile[name=key1]/interface[name=key2]/high_impedance"
			DEFVAL { "disable" }
			::= { wingCfgProfIfT1E1Entry 3 }

		
		-- 1.3.6.1.4.1.1916.2.131.50.1.3.16.2.16.1.4
		wingCfgProfIfT1E1LineBuildOut OBJECT-TYPE
			SYNTAX DisplayString
			MAX-ACCESS read-write
			STATUS current
			DESCRIPTION
				"Line build out in decibels (dB) or feet (ft)
				
				Values:
				0-110ft
				0dB
				110-220ft
				15dB
				22.5dB
				220-330ft
				330-440ft
				440-550ft
				550-660ft
				7.5dB
				
				XPath: /wing-config/profile[name=key1]/interface[name=key2]/line_build_out"
			DEFVAL { "0dB" }
			::= { wingCfgProfIfT1E1Entry 4 }

		
		-- 1.3.6.1.4.1.1916.2.131.50.1.3.16.2.16.1.5
		wingCfgProfIfT1E1LineEncoding OBJECT-TYPE
			SYNTAX DisplayString
			MAX-ACCESS read-write
			STATUS current
			DESCRIPTION
				"Line encoding type
				
				Values:
				ami
				b8zs
				
				XPath: /wing-config/profile[name=key1]/interface[name=key2]/line_encoding"
			DEFVAL { "b8zs" }
			::= { wingCfgProfIfT1E1Entry 5 }

		
		-- 1.3.6.1.4.1.1916.2.131.50.1.3.16.2.16.1.6
		wingCfgProfIfT1E1RxSensitivityLevel OBJECT-TYPE
			SYNTAX DisplayString
			MAX-ACCESS read-write
			STATUS current
			DESCRIPTION
				"Receive sensitivity level in decibels
				
				Values:
				12dB
				18dB
				30dB
				36dB
				
				XPath: /wing-config/profile[name=key1]/interface[name=key2]/rx_sensitivity_level"
			DEFVAL { "36dB" }
			::= { wingCfgProfIfT1E1Entry 6 }

		
		-- 1.3.6.1.4.1.1916.2.131.50.1.3.16.2.17
		wingCfgProfIfSerialTable OBJECT-TYPE
			SYNTAX SEQUENCE OF WingCfgProfIfSerialEntry
			MAX-ACCESS not-accessible
			STATUS current
			DESCRIPTION
				"Serial interface (virtual interface) configuration.
				
				/wing-config/profile/interface"
			::= { wingCfgProfIf 17 }

		
		-- 1.3.6.1.4.1.1916.2.131.50.1.3.16.2.17.1
		wingCfgProfIfSerialEntry OBJECT-TYPE
			SYNTAX WingCfgProfIfSerialEntry
			MAX-ACCESS not-accessible
			STATUS current
			DESCRIPTION
				"An entry in the table."
			INDEX { wingCfgProfName, wingCfgProfIfName }
			::= { wingCfgProfIfSerialTable 1 }

		
		WingCfgProfIfSerialEntry ::=
			SEQUENCE { 
				wingCfgProfIfSerialAuthentication
					DisplayString,
				wingCfgProfIfSerialEncapsulation
					DisplayString,
				wingCfgProfIfSerialLocalIpAddress
					DisplayString,
				wingCfgProfIfSerialUsername
					DisplayString,
				wingCfgProfIfSerialPassword
					DisplayString,
				wingCfgProfIfSerialRemoteIpSubnet
					DisplayString
			 }

		-- 1.3.6.1.4.1.1916.2.131.50.1.3.16.2.17.1.1
		wingCfgProfIfSerialAuthentication OBJECT-TYPE
			SYNTAX DisplayString
			MAX-ACCESS read-write
			STATUS current
			DESCRIPTION
				"Type of authentication
				
				Values:
				none
				pap
				chap
				
				XPath: /wing-config/profile[name=key1]/interface[name=key2]/authentication"
			DEFVAL { "none" }
			::= { wingCfgProfIfSerialEntry 1 }

		
		-- 1.3.6.1.4.1.1916.2.131.50.1.3.16.2.17.1.2
		wingCfgProfIfSerialEncapsulation OBJECT-TYPE
			SYNTAX DisplayString
			MAX-ACCESS read-write
			STATUS current
			DESCRIPTION
				"The type of traffic that this group handles
				
				Values:
				chdlc
				hdlc
				ppp
				
				XPath: /wing-config/profile[name=key1]/interface[name=key2]/encapsulation"
			DEFVAL { "ppp" }
			::= { wingCfgProfIfSerialEntry 2 }

		
		-- 1.3.6.1.4.1.1916.2.131.50.1.3.16.2.17.1.3
		wingCfgProfIfSerialLocalIpAddress OBJECT-TYPE
			SYNTAX DisplayString
			MAX-ACCESS read-write
			STATUS current
			DESCRIPTION
				"IP address assigned to the local system
				
				XPath: /wing-config/profile[name=key1]/interface[name=key2]/local_ip_address"
			DEFVAL { "" }
			::= { wingCfgProfIfSerialEntry 3 }

		
		-- 1.3.6.1.4.1.1916.2.131.50.1.3.16.2.17.1.4
		wingCfgProfIfSerialUsername OBJECT-TYPE
			SYNTAX DisplayString (SIZE (0..32))
			MAX-ACCESS read-write
			STATUS current
			DESCRIPTION
				"Username provided by the service provider
				
				XPath: /wing-config/profile[name=key1]/interface[name=key2]/username"
			DEFVAL { "" }
			::= { wingCfgProfIfSerialEntry 4 }

		
		-- 1.3.6.1.4.1.1916.2.131.50.1.3.16.2.17.1.5
		wingCfgProfIfSerialPassword OBJECT-TYPE
			SYNTAX DisplayString (SIZE (0..32))
			MAX-ACCESS read-write
			STATUS current
			DESCRIPTION
				"Password provided by the service provider
				
				XPath: /wing-config/profile[name=key1]/interface[name=key2]/password"
			DEFVAL { "" }
			::= { wingCfgProfIfSerialEntry 5 }

		
		-- 1.3.6.1.4.1.1916.2.131.50.1.3.16.2.17.1.6
		wingCfgProfIfSerialRemoteIpSubnet OBJECT-TYPE
			SYNTAX DisplayString
			MAX-ACCESS read-write
			STATUS current
			DESCRIPTION
				"IP subnet assigned to the remote system along with subnet
				in CIDR notation - A.B.C.D/M
				
				XPath: /wing-config/profile[name=key1]/interface[name=key2]/remote_ip_subnet"
			DEFVAL { "" }
			::= { wingCfgProfIfSerialEntry 6 }

		
		-- 1.3.6.1.4.1.1916.2.131.50.1.3.16.2.18
		wingCfgProfIfDot1xAuthTable OBJECT-TYPE
			SYNTAX SEQUENCE OF WingCfgProfIfDot1xAuthEntry
			MAX-ACCESS not-accessible
			STATUS current
			DESCRIPTION
				"
				
				/wing-config/profile/interface"
			::= { wingCfgProfIf 18 }

		
		-- 1.3.6.1.4.1.1916.2.131.50.1.3.16.2.18.1
		wingCfgProfIfDot1xAuthEntry OBJECT-TYPE
			SYNTAX WingCfgProfIfDot1xAuthEntry
			MAX-ACCESS not-accessible
			STATUS current
			DESCRIPTION
				"An entry in the table."
			INDEX { wingCfgProfName, wingCfgProfIfName }
			::= { wingCfgProfIfDot1xAuthTable 1 }

		
		WingCfgProfIfDot1xAuthEntry ::=
			SEQUENCE { 
				wingCfgProfIfDot1xAuthHostMode
					DisplayString,
				wingCfgProfIfDot1xAuthGuestVlan
					Unsigned32,
				wingCfgProfIfDot1xAuthPortControl
					DisplayString,
				wingCfgProfIfDot1xAuthReauthenticate
					TruthValue,
				wingCfgProfIfDot1xAuthMaxReauthCount
					Unsigned32,
				wingCfgProfIfDot1xAuthMaxReq
					Unsigned32,
				wingCfgProfIfDot1xAuthQuietPeriod
					Unsigned32,
				wingCfgProfIfDot1xAuthReauthPeriod
					Unsigned32
			 }

		-- 1.3.6.1.4.1.1916.2.131.50.1.3.16.2.18.1.1
		wingCfgProfIfDot1xAuthHostMode OBJECT-TYPE
			SYNTAX DisplayString
			MAX-ACCESS read-write
			STATUS current
			DESCRIPTION
				"Single or multi-host mode.
				
				Values:
				single-host,
				multi-host
				
				XPath: /wing-config/profile[name=key1]/interface[name=key2]/host_mode"
			DEFVAL { "single-host" }
			::= { wingCfgProfIfDot1xAuthEntry 1 }

		
		-- 1.3.6.1.4.1.1916.2.131.50.1.3.16.2.18.1.2
		wingCfgProfIfDot1xAuthGuestVlan OBJECT-TYPE
			SYNTAX Unsigned32 (1..4094)
			MAX-ACCESS read-write
			STATUS current
			DESCRIPTION
				"Vlan onto which traffic is bridged if port is unauthorized and guest vlan is globally enabled
				
				XPath: /wing-config/profile[name=key1]/interface[name=key2]/guest_vlan"
			::= { wingCfgProfIfDot1xAuthEntry 2 }

		
		-- 1.3.6.1.4.1.1916.2.131.50.1.3.16.2.18.1.3
		wingCfgProfIfDot1xAuthPortControl OBJECT-TYPE
			SYNTAX DisplayString
			MAX-ACCESS read-write
			STATUS current
			DESCRIPTION
				"Set 802.1x port state
				
				Values:
				auto,
				force-authorized,
				force-unauthorized
				
				XPath: /wing-config/profile[name=key1]/interface[name=key2]/port_control"
			DEFVAL { "force-authorized" }
			::= { wingCfgProfIfDot1xAuthEntry 3 }

		
		-- 1.3.6.1.4.1.1916.2.131.50.1.3.16.2.18.1.4
		wingCfgProfIfDot1xAuthReauthenticate OBJECT-TYPE
			SYNTAX TruthValue
			MAX-ACCESS read-write
			STATUS current
			DESCRIPTION
				"Enable 802.1x re-authentication
				
				XPath: /wing-config/profile[name=key1]/interface[name=key2]/reauthenticate"
			DEFVAL { false }
			::= { wingCfgProfIfDot1xAuthEntry 4 }

		
		-- 1.3.6.1.4.1.1916.2.131.50.1.3.16.2.18.1.5
		wingCfgProfIfDot1xAuthMaxReauthCount OBJECT-TYPE
			SYNTAX Unsigned32 (1..10)
			MAX-ACCESS read-write
			STATUS current
			DESCRIPTION
				"Number of reauthentication attempts before a port is moved to unauthorized
				
				XPath: /wing-config/profile[name=key1]/interface[name=key2]/max_reauth_count"
			DEFVAL { 2 }
			::= { wingCfgProfIfDot1xAuthEntry 5 }

		
		-- 1.3.6.1.4.1.1916.2.131.50.1.3.16.2.18.1.6
		wingCfgProfIfDot1xAuthMaxReq OBJECT-TYPE
			SYNTAX Unsigned32 (1..10)
			MAX-ACCESS read-write
			STATUS current
			DESCRIPTION
				"Number of times 802.1x will retry authentication with the Radius Server before giving up and returning failed to the supplicant.
				
				XPath: /wing-config/profile[name=key1]/interface[name=key2]/max_req"
			DEFVAL { 2 }
			::= { wingCfgProfIfDot1xAuthEntry 6 }

		
		-- 1.3.6.1.4.1.1916.2.131.50.1.3.16.2.18.1.7
		wingCfgProfIfDot1xAuthQuietPeriod OBJECT-TYPE
			SYNTAX Unsigned32 (1..65535)
			MAX-ACCESS read-write
			STATUS current
			DESCRIPTION
				"Time in seconds 802.1x will wait after authentication fails
				
				XPath: /wing-config/profile[name=key1]/interface[name=key2]/quiet_period"
			DEFVAL { 60 }
			::= { wingCfgProfIfDot1xAuthEntry 7 }

		
		-- 1.3.6.1.4.1.1916.2.131.50.1.3.16.2.18.1.8
		wingCfgProfIfDot1xAuthReauthPeriod OBJECT-TYPE
			SYNTAX Unsigned32 (1..65535)
			MAX-ACCESS read-write
			STATUS current
			DESCRIPTION
				"Time in seconds until port is reauthenicated
				
				XPath: /wing-config/profile[name=key1]/interface[name=key2]/reauth_period"
			DEFVAL { 60 }
			::= { wingCfgProfIfDot1xAuthEntry 8 }

		
		-- 1.3.6.1.4.1.1916.2.131.50.1.3.16.2.19
		wingCfgProfIfMeshpointBssmapTable OBJECT-TYPE
			SYNTAX SEQUENCE OF WingCfgProfIfMeshpointBssmapEntry
			MAX-ACCESS not-accessible
			STATUS current
			DESCRIPTION
				"
				
				/wing-config/profile/interface/meshpoint"
			::= { wingCfgProfIf 19 }

		
		-- 1.3.6.1.4.1.1916.2.131.50.1.3.16.2.19.1
		wingCfgProfIfMeshpointBssmapEntry OBJECT-TYPE
			SYNTAX WingCfgProfIfMeshpointBssmapEntry
			MAX-ACCESS not-accessible
			STATUS current
			DESCRIPTION
				"An entry in the table."
			INDEX { wingCfgProfName, wingCfgProfIfName, wingCfgProfIfMeshpointBssmapMeshpoint }
			::= { wingCfgProfIfMeshpointBssmapTable 1 }

		
		WingCfgProfIfMeshpointBssmapEntry ::=
			SEQUENCE { 
				wingCfgProfIfMeshpointBssmapMeshpoint
					WingIdentifier,
				wingCfgProfIfMeshpointBssmapBss
					Unsigned32
			 }

		-- 1.3.6.1.4.1.1916.2.131.50.1.3.16.2.19.1.1
		wingCfgProfIfMeshpointBssmapMeshpoint OBJECT-TYPE
			SYNTAX WingIdentifier
			MAX-ACCESS read-write
			STATUS current
			DESCRIPTION
				"
				
				XPath: /wing-config/profile[name=key1]/interface[name=key2]/meshpoint[meshpoint=key3]/meshpoint"
			::= { wingCfgProfIfMeshpointBssmapEntry 1 }

		
		-- 1.3.6.1.4.1.1916.2.131.50.1.3.16.2.19.1.3
		wingCfgProfIfMeshpointBssmapBss OBJECT-TYPE
			SYNTAX Unsigned32 (1..8)
			MAX-ACCESS read-write
			STATUS current
			DESCRIPTION
				"
				
				XPath: /wing-config/profile[name=key1]/interface[name=key2]/meshpoint[meshpoint=key3]/bss"
			::= { wingCfgProfIfMeshpointBssmapEntry 3 }

		
-- /wing-config/profile/route
		-- 1.3.6.1.4.1.1916.2.131.50.1.3.16.5
		wingCfgProfRoute OBJECT IDENTIFIER ::= { wingCfgProf 5 }

		
		-- 1.3.6.1.4.1.1916.2.131.50.1.3.16.5.1
		wingCfgProfRouteTable OBJECT-TYPE
			SYNTAX SEQUENCE OF WingCfgProfRouteEntry
			MAX-ACCESS not-accessible
			STATUS current
			DESCRIPTION
				"Static IPv4 Route Table
				
				/wing-config/profile/route"
			::= { wingCfgProfRoute 1 }

		
		-- 1.3.6.1.4.1.1916.2.131.50.1.3.16.5.1.1
		wingCfgProfRouteEntry OBJECT-TYPE
			SYNTAX WingCfgProfRouteEntry
			MAX-ACCESS not-accessible
			STATUS current
			DESCRIPTION
				"An entry in the table."
			INDEX { wingCfgProfName, wingCfgProfRouteNetwork }
			::= { wingCfgProfRouteTable 1 }

		
		WingCfgProfRouteEntry ::=
			SEQUENCE { 
				wingCfgProfRouteNetwork
					WingIdentifier,
				wingCfgProfRouteGateway
					WingIdentifier
			 }

		-- 1.3.6.1.4.1.1916.2.131.50.1.3.16.5.1.1.1
		wingCfgProfRouteNetwork OBJECT-TYPE
			SYNTAX WingIdentifier
			MAX-ACCESS read-only
			STATUS current
			DESCRIPTION
				"
				
				XPath: /wing-config/profile[name=key1]/route[network=key2]/network"
			::= { wingCfgProfRouteEntry 1 }

		
		-- 1.3.6.1.4.1.1916.2.131.50.1.3.16.5.1.1.3
		wingCfgProfRouteGateway OBJECT-TYPE
			SYNTAX WingIdentifier
			MAX-ACCESS read-only
			STATUS current
			DESCRIPTION
				"
				
				XPath: /wing-config/profile[name=key1]/route[network=key2]/gateway"
			::= { wingCfgProfRouteEntry 3 }

		
-- /wing-config/profile/ntp_server
		-- 1.3.6.1.4.1.1916.2.131.50.1.3.16.6
		wingCfgProfNtpSvr OBJECT IDENTIFIER ::= { wingCfgProf 6 }

		
		-- 1.3.6.1.4.1.1916.2.131.50.1.3.16.6.1
		wingCfgProfNtpSvrTable OBJECT-TYPE
			SYNTAX SEQUENCE OF WingCfgProfNtpSvrEntry
			MAX-ACCESS not-accessible
			STATUS current
			DESCRIPTION
				"
				
				/wing-config/profile/ntp_server"
			::= { wingCfgProfNtpSvr 1 }

		
		-- 1.3.6.1.4.1.1916.2.131.50.1.3.16.6.1.1
		wingCfgProfNtpSvrEntry OBJECT-TYPE
			SYNTAX WingCfgProfNtpSvrEntry
			MAX-ACCESS not-accessible
			STATUS current
			DESCRIPTION
				"An entry in the table."
			INDEX { wingCfgProfName, wingCfgProfNtpSvrServerIp }
			::= { wingCfgProfNtpSvrTable 1 }

		
		WingCfgProfNtpSvrEntry ::=
			SEQUENCE { 
				wingCfgProfNtpSvrServerIp
					WingIdentifier,
				wingCfgProfNtpSvrAuthenkey
					Unsigned32,
				wingCfgProfNtpSvrAutokey
					TruthValue,
				wingCfgProfNtpSvrKeyStr
					DisplayString,
				wingCfgProfNtpSvrPrefer
					TruthValue,
				wingCfgProfNtpSvrVersion
					Unsigned32
			 }

		-- 1.3.6.1.4.1.1916.2.131.50.1.3.16.6.1.1.1
		wingCfgProfNtpSvrServerIp OBJECT-TYPE
			SYNTAX WingIdentifier
			MAX-ACCESS read-only
			STATUS current
			DESCRIPTION
				"ntp server ip address
				
				XPath: /wing-config/profile[name=key1]/ntp_server[serverip=key2]/serverip"
			::= { wingCfgProfNtpSvrEntry 1 }

		
		-- 1.3.6.1.4.1.1916.2.131.50.1.3.16.6.1.1.3
		wingCfgProfNtpSvrAuthenkey OBJECT-TYPE
			SYNTAX Unsigned32 (0..65534)
			MAX-ACCESS read-write
			STATUS current
			DESCRIPTION
				"authentication peer key number
				
				XPath: /wing-config/profile[name=key1]/ntp_server[serverip=key2]/authenkey"
			DEFVAL { 0 }
			::= { wingCfgProfNtpSvrEntry 3 }

		
		-- 1.3.6.1.4.1.1916.2.131.50.1.3.16.6.1.1.4
		wingCfgProfNtpSvrAutokey OBJECT-TYPE
			SYNTAX TruthValue
			MAX-ACCESS read-write
			STATUS current
			DESCRIPTION
				"enable/disable autokey configuration
				
				XPath: /wing-config/profile[name=key1]/ntp_server[serverip=key2]/autokey"
			DEFVAL { false }
			::= { wingCfgProfNtpSvrEntry 4 }

		
		-- 1.3.6.1.4.1.1916.2.131.50.1.3.16.6.1.1.5
		wingCfgProfNtpSvrKeyStr OBJECT-TYPE
			SYNTAX DisplayString (SIZE (64))
			MAX-ACCESS read-write
			STATUS current
			DESCRIPTION
				"authentication key, valid when autokey is false
				
				XPath: /wing-config/profile[name=key1]/ntp_server[serverip=key2]/key_str"
			::= { wingCfgProfNtpSvrEntry 5 }

		
		-- 1.3.6.1.4.1.1916.2.131.50.1.3.16.6.1.1.6
		wingCfgProfNtpSvrPrefer OBJECT-TYPE
			SYNTAX TruthValue
			MAX-ACCESS read-write
			STATUS current
			DESCRIPTION
				"whether this ntp server is preferred or not
				
				XPath: /wing-config/profile[name=key1]/ntp_server[serverip=key2]/prefer"
			DEFVAL { false }
			::= { wingCfgProfNtpSvrEntry 6 }

		
		-- 1.3.6.1.4.1.1916.2.131.50.1.3.16.6.1.1.7
		wingCfgProfNtpSvrVersion OBJECT-TYPE
			SYNTAX Unsigned32 (0..4)
			MAX-ACCESS read-write
			STATUS current
			DESCRIPTION
				"the version number of this ntp server (1-4, 0:ignore)
				
				XPath: /wing-config/profile[name=key1]/ntp_server[serverip=key2]/version"
			DEFVAL { 0 }
			::= { wingCfgProfNtpSvrEntry 7 }

		
-- /wing-config/profile/bridge_vlan
		-- 1.3.6.1.4.1.1916.2.131.50.1.3.16.7
		wingCfgProfBridgeVlan OBJECT IDENTIFIER ::= { wingCfgProf 7 }

		
		-- 1.3.6.1.4.1.1916.2.131.50.1.3.16.7.1
		wingCfgProfBridgeVlanTable OBJECT-TYPE
			SYNTAX SEQUENCE OF WingCfgProfBridgeVlanEntry
			MAX-ACCESS not-accessible
			STATUS current
			DESCRIPTION
				"
				
				/wing-config/profile/bridge_vlan"
			::= { wingCfgProfBridgeVlan 1 }

		
		-- 1.3.6.1.4.1.1916.2.131.50.1.3.16.7.1.1
		wingCfgProfBridgeVlanEntry OBJECT-TYPE
			SYNTAX WingCfgProfBridgeVlanEntry
			MAX-ACCESS not-accessible
			STATUS current
			DESCRIPTION
				"An entry in the table."
			INDEX { wingCfgProfName, wingCfgProfBridgeVlanId }
			::= { wingCfgProfBridgeVlanTable 1 }

		
		WingCfgProfBridgeVlanEntry ::=
			SEQUENCE { 
				wingCfgProfBridgeVlanId
					Unsigned32,
				wingCfgProfBridgeVlanDesc
					DisplayString,
				wingCfgProfBridgeVlanEdgeVlan
					TruthValue,
				wingCfgProfBridgeVlanBridgingMode
					DisplayString,
				wingCfgProfBridgeVlanIpArpTrust
					TruthValue,
				wingCfgProfBridgeVlanIpDhcpTrust
					TruthValue,
				wingCfgProfBridgeVlanTunnelMacOutAcl
					WingIdentifier,
				wingCfgProfBridgeVlanTunnelIpOutAcl
					WingIdentifier
			 }

		-- 1.3.6.1.4.1.1916.2.131.50.1.3.16.7.1.1.1
		wingCfgProfBridgeVlanId OBJECT-TYPE
			SYNTAX Unsigned32 (1..4095)
			MAX-ACCESS read-only
			STATUS current
			DESCRIPTION
				"
				
				XPath: /wing-config/profile[name=key1]/bridge_vlan[vlan=key2]/vlan"
			::= { wingCfgProfBridgeVlanEntry 1 }

		
		-- 1.3.6.1.4.1.1916.2.131.50.1.3.16.7.1.1.3
		wingCfgProfBridgeVlanDesc OBJECT-TYPE
			SYNTAX DisplayString (SIZE (64))
			MAX-ACCESS read-write
			STATUS current
			DESCRIPTION
				"
				
				XPath: /wing-config/profile[name=key1]/bridge_vlan[vlan=key2]/description"
			::= { wingCfgProfBridgeVlanEntry 3 }

		
		-- 1.3.6.1.4.1.1916.2.131.50.1.3.16.7.1.1.4
		wingCfgProfBridgeVlanEdgeVlan OBJECT-TYPE
			SYNTAX TruthValue
			MAX-ACCESS read-write
			STATUS current
			DESCRIPTION
				"
				
				XPath: /wing-config/profile[name=key1]/bridge_vlan[vlan=key2]/edge_vlan"
			DEFVAL { true }
			::= { wingCfgProfBridgeVlanEntry 4 }

		
		-- 1.3.6.1.4.1.1916.2.131.50.1.3.16.7.1.1.5
		wingCfgProfBridgeVlanBridgingMode OBJECT-TYPE
			SYNTAX DisplayString
			MAX-ACCESS read-write
			STATUS current
			DESCRIPTION
				"
				
				Values:
				auto,
				local,
				tunnel,
				isolated-tunnel
				
				XPath: /wing-config/profile[name=key1]/bridge_vlan[vlan=key2]/bridging_mode"
			DEFVAL { "auto" }
			::= { wingCfgProfBridgeVlanEntry 5 }

		
		-- 1.3.6.1.4.1.1916.2.131.50.1.3.16.7.1.1.6
		wingCfgProfBridgeVlanIpArpTrust OBJECT-TYPE
			SYNTAX TruthValue
			MAX-ACCESS read-write
			STATUS current
			DESCRIPTION
				"
				
				XPath: /wing-config/profile[name=key1]/bridge_vlan[vlan=key2]/ip_arp_trust"
			DEFVAL { false }
			::= { wingCfgProfBridgeVlanEntry 6 }

		
		-- 1.3.6.1.4.1.1916.2.131.50.1.3.16.7.1.1.7
		wingCfgProfBridgeVlanIpDhcpTrust OBJECT-TYPE
			SYNTAX TruthValue
			MAX-ACCESS read-write
			STATUS current
			DESCRIPTION
				"
				
				XPath: /wing-config/profile[name=key1]/bridge_vlan[vlan=key2]/ip_dhcp_trust"
			DEFVAL { false }
			::= { wingCfgProfBridgeVlanEntry 7 }

		
		-- 1.3.6.1.4.1.1916.2.131.50.1.3.16.7.1.1.8
		wingCfgProfBridgeVlanTunnelMacOutAcl OBJECT-TYPE
			SYNTAX WingIdentifier
			MAX-ACCESS read-write
			STATUS current
			DESCRIPTION
				"
				
				XPath: /wing-config/profile[name=key1]/bridge_vlan[vlan=key2]/tunnel_mac_out_acl"
			::= { wingCfgProfBridgeVlanEntry 8 }

		
		-- 1.3.6.1.4.1.1916.2.131.50.1.3.16.7.1.1.9
		wingCfgProfBridgeVlanTunnelIpOutAcl OBJECT-TYPE
			SYNTAX WingIdentifier
			MAX-ACCESS read-write
			STATUS current
			DESCRIPTION
				"
				
				XPath: /wing-config/profile[name=key1]/bridge_vlan[vlan=key2]/tunnel_ip_out_acl"
			::= { wingCfgProfBridgeVlanEntry 9 }

		
		-- 1.3.6.1.4.1.1916.2.131.50.1.3.16.7.2
		wingCfgProfBridgeVlanIgsTable OBJECT-TYPE
			SYNTAX SEQUENCE OF WingCfgProfBridgeVlanIgsEntry
			MAX-ACCESS not-accessible
			STATUS current
			DESCRIPTION
				"
				
				/wing-config/profile/bridge_vlan"
			::= { wingCfgProfBridgeVlan 2 }

		
		-- 1.3.6.1.4.1.1916.2.131.50.1.3.16.7.2.1
		wingCfgProfBridgeVlanIgsEntry OBJECT-TYPE
			SYNTAX WingCfgProfBridgeVlanIgsEntry
			MAX-ACCESS not-accessible
			STATUS current
			DESCRIPTION
				"An entry in the table."
			INDEX { wingCfgProfName, wingCfgProfBridgeVlanId }
			::= { wingCfgProfBridgeVlanIgsTable 1 }

		
		WingCfgProfBridgeVlanIgsEntry ::=
			SEQUENCE { 
				wingCfgProfBridgeVlanIgsIpIgs
					TruthValue,
				wingCfgProfBridgeVlanIgsIpIgsQuerier
					TruthValue,
				wingCfgProfBridgeVlanIgsIpIgsQuerierMaxResponseTime
					Unsigned32,
				wingCfgProfBridgeVlanIgsIpIgsQuerierVersion
					Unsigned32,
				wingCfgProfBridgeVlanIgsIpIgsQuerierAddress
					DisplayString,
				wingCfgProfBridgeVlanIgsIpIgsOtherQuerierTimerExpiry
					Unsigned32,
				wingCfgProfBridgeVlanIgsIpIgsForwardUnknownMcast
					TruthValue,
				wingCfgProfBridgeVlanIgsIpIgsMrouterLearnPimDvmrp
					DisplayString
			 }

		-- 1.3.6.1.4.1.1916.2.131.50.1.3.16.7.2.1.1
		wingCfgProfBridgeVlanIgsIpIgs OBJECT-TYPE
			SYNTAX TruthValue
			MAX-ACCESS read-write
			STATUS current
			DESCRIPTION
				"
				
				XPath: /wing-config/profile[name=key1]/bridge_vlan[vlan=key2]/ip_igs"
			DEFVAL { true }
			::= { wingCfgProfBridgeVlanIgsEntry 1 }

		
		-- 1.3.6.1.4.1.1916.2.131.50.1.3.16.7.2.1.2
		wingCfgProfBridgeVlanIgsIpIgsQuerier OBJECT-TYPE
			SYNTAX TruthValue
			MAX-ACCESS read-write
			STATUS current
			DESCRIPTION
				"
				
				XPath: /wing-config/profile[name=key1]/bridge_vlan[vlan=key2]/ip_igs_querier"
			DEFVAL { false }
			::= { wingCfgProfBridgeVlanIgsEntry 2 }

		
		-- 1.3.6.1.4.1.1916.2.131.50.1.3.16.7.2.1.3
		wingCfgProfBridgeVlanIgsIpIgsQuerierMaxResponseTime OBJECT-TYPE
			SYNTAX Unsigned32 (1..25)
			UNITS "seconds"
			MAX-ACCESS read-only
			STATUS current
			DESCRIPTION
				"
				
				XPath: /wing-config/profile[name=key1]/bridge_vlan[vlan=key2]/ip_igs_querier_max_response_time"
			::= { wingCfgProfBridgeVlanIgsEntry 3 }

		
		-- 1.3.6.1.4.1.1916.2.131.50.1.3.16.7.2.1.4
		wingCfgProfBridgeVlanIgsIpIgsQuerierVersion OBJECT-TYPE
			SYNTAX Unsigned32 (1..3)
			MAX-ACCESS read-only
			STATUS current
			DESCRIPTION
				"
				
				XPath: /wing-config/profile[name=key1]/bridge_vlan[vlan=key2]/ip_igs_querier_version"
			::= { wingCfgProfBridgeVlanIgsEntry 4 }

		
		-- 1.3.6.1.4.1.1916.2.131.50.1.3.16.7.2.1.5
		wingCfgProfBridgeVlanIgsIpIgsQuerierAddress OBJECT-TYPE
			SYNTAX DisplayString
			MAX-ACCESS read-write
			STATUS current
			DESCRIPTION
				"
				
				XPath: /wing-config/profile[name=key1]/bridge_vlan[vlan=key2]/ip_igs_querier_address"
			::= { wingCfgProfBridgeVlanIgsEntry 5 }

		
		-- 1.3.6.1.4.1.1916.2.131.50.1.3.16.7.2.1.6
		wingCfgProfBridgeVlanIgsIpIgsOtherQuerierTimerExpiry OBJECT-TYPE
			SYNTAX Unsigned32 (60..300)
			UNITS "seconds"
			MAX-ACCESS read-only
			STATUS current
			DESCRIPTION
				"
				
				XPath: /wing-config/profile[name=key1]/bridge_vlan[vlan=key2]/ip_igs_other_querier_timer_expiry"
			::= { wingCfgProfBridgeVlanIgsEntry 6 }

		
		-- 1.3.6.1.4.1.1916.2.131.50.1.3.16.7.2.1.7
		wingCfgProfBridgeVlanIgsIpIgsForwardUnknownMcast OBJECT-TYPE
			SYNTAX TruthValue
			MAX-ACCESS read-write
			STATUS current
			DESCRIPTION
				"
				
				XPath: /wing-config/profile[name=key1]/bridge_vlan[vlan=key2]/ip_igs_forward_unknown_mcast"
			DEFVAL { false }
			::= { wingCfgProfBridgeVlanIgsEntry 7 }

		
		-- 1.3.6.1.4.1.1916.2.131.50.1.3.16.7.2.1.8
		wingCfgProfBridgeVlanIgsIpIgsMrouterLearnPimDvmrp OBJECT-TYPE
			SYNTAX DisplayString
			MAX-ACCESS read-write
			STATUS current
			DESCRIPTION
				"Interface name. Eg., ge1 radio1 ...
				
				XPath: /wing-config/profile[name=key1]/bridge_vlan[vlan=key2]/ip_igs_mrouter_learn_pim_dvmrp"
			DEFVAL { "pim-dvmrp" }
			::= { wingCfgProfBridgeVlanIgsEntry 8 }

		
--  /wing-config/profile
		-- 1.3.6.1.4.1.1916.2.131.50.1.3.16.8
		wingCfgProfClst OBJECT IDENTIFIER ::= { wingCfgProf 8 }

		
		-- 1.3.6.1.4.1.1916.2.131.50.1.3.16.8.1
		wingCfgProfClstTable OBJECT-TYPE
			SYNTAX SEQUENCE OF WingCfgProfClstEntry
			MAX-ACCESS not-accessible
			STATUS current
			DESCRIPTION
				"SET available only with controller profile
				
				/wing-config/profile"
			::= { wingCfgProfClst 1 }

		
		-- 1.3.6.1.4.1.1916.2.131.50.1.3.16.8.1.1
		wingCfgProfClstEntry OBJECT-TYPE
			SYNTAX WingCfgProfClstEntry
			MAX-ACCESS not-accessible
			STATUS current
			DESCRIPTION
				"An entry in the table."
			INDEX { wingCfgProfName }
			::= { wingCfgProfClstTable 1 }

		
		WingCfgProfClstEntry ::=
			SEQUENCE { 
				wingCfgProfClstClstName
					WingIdentifier,
				wingCfgProfClstClstMemberVlan
					Unsigned32,
				wingCfgProfClstClstMode
					DisplayString,
				wingCfgProfClstClstMasterPriority
					Unsigned32,
				wingCfgProfClstHandleStp
					TruthValue
			 }

		-- 1.3.6.1.4.1.1916.2.131.50.1.3.16.8.1.1.2
		wingCfgProfClstClstName OBJECT-TYPE
			SYNTAX WingIdentifier
			MAX-ACCESS read-write
			STATUS current
			DESCRIPTION
				"SET available only with controller profile
				
				XPath: /wing-config/profile[name=key1]/cluster_name"
			::= { wingCfgProfClstEntry 2 }

		
		-- 1.3.6.1.4.1.1916.2.131.50.1.3.16.8.1.1.3
		wingCfgProfClstClstMemberVlan OBJECT-TYPE
			SYNTAX Unsigned32 (1..4094)
			MAX-ACCESS read-write
			STATUS current
			DESCRIPTION
				"VLAN on which cluster members are reachable
				SET available only with controller profile
				
				XPath: /wing-config/profile[name=key1]/cluster_member_vlan"
			::= { wingCfgProfClstEntry 3 }

		
		-- 1.3.6.1.4.1.1916.2.131.50.1.3.16.8.1.1.4
		wingCfgProfClstClstMode OBJECT-TYPE
			SYNTAX DisplayString
			MAX-ACCESS read-write
			STATUS current
			DESCRIPTION
				"Cluster mode of operation.
				
				Values:
				active,
				standby
				
				SET available only with controller profile
				
				XPath: /wing-config/profile[name=key1]/cluster_mode"
			DEFVAL { "active" }
			::= { wingCfgProfClstEntry 4 }

		
		-- 1.3.6.1.4.1.1916.2.131.50.1.3.16.8.1.1.5
		wingCfgProfClstClstMasterPriority OBJECT-TYPE
			SYNTAX Unsigned32 (1..255)
			MAX-ACCESS read-write
			STATUS current
			DESCRIPTION
				"Cluster master priority, lower value takes precedence
				SET available only with controller profile
				
				XPath: /wing-config/profile[name=key1]/cluster_master_priority"
			DEFVAL { 128 }
			::= { wingCfgProfClstEntry 5 }

		
		-- 1.3.6.1.4.1.1916.2.131.50.1.3.16.8.1.1.6
		wingCfgProfClstHandleStp OBJECT-TYPE
			SYNTAX TruthValue
			MAX-ACCESS read-write
			STATUS current
			DESCRIPTION
				"SET available only with controller profile
				
				XPath: /wing-config/profile[name=key1]/handle_stp"
			DEFVAL { false }
			::= { wingCfgProfClstEntry 6 }

		
-- /wing-config/profile/mint_link_cfg
		-- 1.3.6.1.4.1.1916.2.131.50.1.3.16.9
		wingCfgProfMint OBJECT IDENTIFIER ::= { wingCfgProf 9 }

		
		-- 1.3.6.1.4.1.1916.2.131.50.1.3.16.9.1
		wingCfgProfMintTable OBJECT-TYPE
			SYNTAX SEQUENCE OF WingCfgProfMintEntry
			MAX-ACCESS not-accessible
			STATUS current
			DESCRIPTION
				"
				
				/wing-config/profile/mint_link_cfg"
			::= { wingCfgProfMint 1 }

		
		-- 1.3.6.1.4.1.1916.2.131.50.1.3.16.9.1.1
		wingCfgProfMintEntry OBJECT-TYPE
			SYNTAX WingCfgProfMintEntry
			MAX-ACCESS not-accessible
			STATUS current
			DESCRIPTION
				"An entry in the table."
			INDEX { wingCfgProfName }
			::= { wingCfgProfMintTable 1 }

		
		WingCfgProfMintEntry ::=
			SEQUENCE { 
				wingCfgProfMintLevel1AreaId
					DisplayString,
				wingCfgProfMintSpfLatency
					Unsigned32,
				wingCfgProfMintDisPriorityAdjustment
					Integer32,
				wingCfgProfMintMlcpVlan
					TruthValue,
				wingCfgProfMintMlcpIp
					TruthValue,
				wingCfgProfMintTunnelControllerLoadBalancingLevel1
					TruthValue
			 }

		-- 1.3.6.1.4.1.1916.2.131.50.1.3.16.9.1.1.1
		wingCfgProfMintLevel1AreaId OBJECT-TYPE
			SYNTAX DisplayString
			MAX-ACCESS read-write
			STATUS current
			DESCRIPTION
				"
				
				XPath: /wing-config/profile[name=key1]/mint_link_cfg/mint_level1_area_id"
			::= { wingCfgProfMintEntry 1 }

		
		-- 1.3.6.1.4.1.1916.2.131.50.1.3.16.9.1.1.2
		wingCfgProfMintSpfLatency OBJECT-TYPE
			SYNTAX Unsigned32 (0..60)
			UNITS "seconds"
			MAX-ACCESS read-write
			STATUS current
			DESCRIPTION
				"
				
				XPath: /wing-config/profile[name=key1]/mint_link_cfg/mint_spf_latency"
			::= { wingCfgProfMintEntry 2 }

		
		-- 1.3.6.1.4.1.1916.2.131.50.1.3.16.9.1.1.3
		wingCfgProfMintDisPriorityAdjustment OBJECT-TYPE
			SYNTAX Integer32 (-255..255)
			MAX-ACCESS read-write
			STATUS current
			DESCRIPTION
				"value added to base level DIS priority to influence the DIS election. +1 increases DISiness.
				
				XPath: /wing-config/profile[name=key1]/mint_link_cfg/mint_dis_priority_adjustment"
			DEFVAL { 0 }
			::= { wingCfgProfMintEntry 3 }

		
		-- 1.3.6.1.4.1.1916.2.131.50.1.3.16.9.1.1.4
		wingCfgProfMintMlcpVlan OBJECT-TYPE
			SYNTAX TruthValue
			MAX-ACCESS read-write
			STATUS current
			DESCRIPTION
				"MLCP for automated MiNT VLAN link creation
				
				XPath: /wing-config/profile[name=key1]/mint_link_cfg/mint_mlcp_vlan"
			DEFVAL { true }
			::= { wingCfgProfMintEntry 4 }

		
		-- 1.3.6.1.4.1.1916.2.131.50.1.3.16.9.1.1.5
		wingCfgProfMintMlcpIp OBJECT-TYPE
			SYNTAX TruthValue
			MAX-ACCESS read-write
			STATUS current
			DESCRIPTION
				"MLCP for automated MiNT UDP/IP link creation
				
				XPath: /wing-config/profile[name=key1]/mint_link_cfg/mint_mlcp_ip"
			DEFVAL { true }
			::= { wingCfgProfMintEntry 5 }

		
		-- 1.3.6.1.4.1.1916.2.131.50.1.3.16.9.1.1.6
		wingCfgProfMintTunnelControllerLoadBalancingLevel1 OBJECT-TYPE
			SYNTAX TruthValue
			MAX-ACCESS read-write
			STATUS current
			DESCRIPTION
				"MLCP for automated MiNT UDP/IP link creation
				
				XPath: /wing-config/profile[name=key1]/mint_link_cfg/mint_tunnel_controller_load_balancing_level1"
			::= { wingCfgProfMintEntry 6 }

		
-- /wing-config/profile/dot11_cfg
		-- 1.3.6.1.4.1.1916.2.131.50.1.3.16.10
		wingCfgProfDot11 OBJECT IDENTIFIER ::= { wingCfgProf 10 }

		
		-- 1.3.6.1.4.1.1916.2.131.50.1.3.16.10.1
		wingCfgProfDot11Table OBJECT-TYPE
			SYNTAX SEQUENCE OF WingCfgProfDot11Entry
			MAX-ACCESS not-accessible
			STATUS current
			DESCRIPTION
				"802.11 global parameters for this device.
				
				/wing-config/profile/dot11_cfg"
			::= { wingCfgProfDot11 1 }

		
		-- 1.3.6.1.4.1.1916.2.131.50.1.3.16.10.1.1
		wingCfgProfDot11Entry OBJECT-TYPE
			SYNTAX WingCfgProfDot11Entry
			MAX-ACCESS not-accessible
			STATUS current
			DESCRIPTION
				"An entry in the table."
			INDEX { wingCfgProfName }
			::= { wingCfgProfDot11Table 1 }

		
		WingCfgProfDot11Entry ::=
			SEQUENCE { 
				wingCfgProfDot11WepSharedKeyAuth
					TruthValue,
				wingCfgProfDot11LegacyAutoUpdateAp650
					TruthValue,
				wingCfgProfDot11LegacyAutoUpdateImgAp7131
					DisplayString,
				wingCfgProfDot11LegacyAutoDowngrade
					TruthValue,
				wingCfgProfDot11NasIdentifier
					DisplayString,
				wingCfgProfDot11NasPortId
					DisplayString
			 }

		-- 1.3.6.1.4.1.1916.2.131.50.1.3.16.10.1.1.1
		wingCfgProfDot11WepSharedKeyAuth OBJECT-TYPE
			SYNTAX TruthValue
			MAX-ACCESS read-write
			STATUS current
			DESCRIPTION
				"Whether 802.11 shared key authentication is supported
				with WEP. Note: this method has known security vulnerabilities
				and its use is not recommended unless there are devices
				on the network that are only capable of
				shared-key authentication.
				
				XPath: /wing-config/profile[name=key1]/dot11_cfg/wep_shared_key_auth"
			DEFVAL { false }
			::= { wingCfgProfDot11Entry 1 }

		
		-- 1.3.6.1.4.1.1916.2.131.50.1.3.16.10.1.1.2
		wingCfgProfDot11LegacyAutoUpdateAp650 OBJECT-TYPE
			SYNTAX TruthValue
			MAX-ACCESS read-write
			STATUS current
			DESCRIPTION
				"Whether legacy devices found on the network will automatically
				be updated to supported firmware.
				
				XPath: /wing-config/profile[name=key1]/dot11_cfg/legacy_auto_update_ap650"
			DEFVAL { true }
			::= { wingCfgProfDot11Entry 2 }

		
		-- 1.3.6.1.4.1.1916.2.131.50.1.3.16.10.1.1.3
		wingCfgProfDot11LegacyAutoUpdateImgAp7131 OBJECT-TYPE
			SYNTAX DisplayString (SIZE (0..253))
			MAX-ACCESS read-write
			STATUS current
			DESCRIPTION
				"Path to the AP4700 legacy auto update image.
				
				XPath: /wing-config/profile[name=key1]/dot11_cfg/legacy_auto_update_img_ap7131"
			DEFVAL { "" }
			::= { wingCfgProfDot11Entry 3 }

		
		-- 1.3.6.1.4.1.1916.2.131.50.1.3.16.10.1.1.4
		wingCfgProfDot11LegacyAutoDowngrade OBJECT-TYPE
			SYNTAX TruthValue
			MAX-ACCESS read-write
			STATUS current
			DESCRIPTION
				"Whether the AP4600 will connect to a legacy device and
				downgrade to be compatible with legacy devices.
				
				XPath: /wing-config/profile[name=key1]/dot11_cfg/legacy_auto_downgrade"
			DEFVAL { true }
			::= { wingCfgProfDot11Entry 4 }

		
		-- 1.3.6.1.4.1.1916.2.131.50.1.3.16.10.1.1.5
		wingCfgProfDot11NasIdentifier OBJECT-TYPE
			SYNTAX DisplayString (SIZE (0..253))
			MAX-ACCESS read-write
			STATUS current
			DESCRIPTION
				"The RADIUS NAS-Identifier attribute which typically identifies
				the Access Point or Wireless Controller where the RADIUS
				message originates.
				
				XPath: /wing-config/profile[name=key1]/dot11_cfg/nas_identifier"
			DEFVAL { "" }
			::= { wingCfgProfDot11Entry 5 }

		
		-- 1.3.6.1.4.1.1916.2.131.50.1.3.16.10.1.1.6
		wingCfgProfDot11NasPortId OBJECT-TYPE
			SYNTAX DisplayString (SIZE (0..253))
			MAX-ACCESS read-write
			STATUS current
			DESCRIPTION
				"The RADIUS NAS-Port-Id attribute which typically identifies
				the port of the device where the RADIUS messages originates.
				
				XPath: /wing-config/profile[name=key1]/dot11_cfg/nas_port_id"
			DEFVAL { "" }
			::= { wingCfgProfDot11Entry 6 }

		
-- /wing-config/profile/crl_update_interval
		-- 1.3.6.1.4.1.1916.2.131.50.1.3.16.14
		wingCfgProfCrlUpdate OBJECT IDENTIFIER ::= { wingCfgProf 14 }

		
		-- 1.3.6.1.4.1.1916.2.131.50.1.3.16.14.1
		wingCfgProfCrlUpdateTable OBJECT-TYPE
			SYNTAX SEQUENCE OF WingCfgProfCrlUpdateEntry
			MAX-ACCESS not-accessible
			STATUS current
			DESCRIPTION
				"
				
				/wing-config/profile/crl_update_interval"
			::= { wingCfgProfCrlUpdate 1 }

		
		-- 1.3.6.1.4.1.1916.2.131.50.1.3.16.14.1.1
		wingCfgProfCrlUpdateEntry OBJECT-TYPE
			SYNTAX WingCfgProfCrlUpdateEntry
			MAX-ACCESS not-accessible
			STATUS current
			DESCRIPTION
				"An entry in the table."
			INDEX { wingCfgProfName, wingCfgProfCrlUpdateTrustpoint }
			::= { wingCfgProfCrlUpdateTable 1 }

		
		WingCfgProfCrlUpdateEntry ::=
			SEQUENCE { 
				wingCfgProfCrlUpdateTrustpoint
					WingIdentifier,
				wingCfgProfCrlUpdateUrl
					DisplayString,
				wingCfgProfCrlUpdateInterval
					Unsigned32
			 }

		-- 1.3.6.1.4.1.1916.2.131.50.1.3.16.14.1.1.1
		wingCfgProfCrlUpdateTrustpoint OBJECT-TYPE
			SYNTAX WingIdentifier
			MAX-ACCESS read-only
			STATUS current
			DESCRIPTION
				"
				
				XPath: /wing-config/profile[name=key1]/crl_update_interval[trustpoint=key2]/trustpoint"
			::= { wingCfgProfCrlUpdateEntry 1 }

		
		-- 1.3.6.1.4.1.1916.2.131.50.1.3.16.14.1.1.3
		wingCfgProfCrlUpdateUrl OBJECT-TYPE
			SYNTAX DisplayString
			MAX-ACCESS read-write
			STATUS current
			DESCRIPTION
				"
				
				XPath: /wing-config/profile[name=key1]/crl_update_interval[trustpoint=key2]/url"
			::= { wingCfgProfCrlUpdateEntry 3 }

		
		-- 1.3.6.1.4.1.1916.2.131.50.1.3.16.14.1.1.4
		wingCfgProfCrlUpdateInterval OBJECT-TYPE
			SYNTAX Unsigned32 (1..168)
			UNITS "hour"
			MAX-ACCESS read-write
			STATUS current
			DESCRIPTION
				"
				
				XPath: /wing-config/profile[name=key1]/crl_update_interval[trustpoint=key2]/interval"
			::= { wingCfgProfCrlUpdateEntry 4 }

		
-- /wing-config/profile
		-- 1.3.6.1.4.1.1916.2.131.50.1.3.16.15
		wingCfgProfNat OBJECT IDENTIFIER ::= { wingCfgProf 15 }

		
		-- 1.3.6.1.4.1.1916.2.131.50.1.3.16.15.1
		wingCfgProfNatPoolTable OBJECT-TYPE
			SYNTAX SEQUENCE OF WingCfgProfNatPoolEntry
			MAX-ACCESS not-accessible
			STATUS current
			DESCRIPTION
				"
				
				/wing-config/profile/nat_pool"
			::= { wingCfgProfNat 1 }

		
		-- 1.3.6.1.4.1.1916.2.131.50.1.3.16.15.1.1
		wingCfgProfNatPoolEntry OBJECT-TYPE
			SYNTAX WingCfgProfNatPoolEntry
			MAX-ACCESS not-accessible
			STATUS current
			DESCRIPTION
				"An entry in the table."
			INDEX { wingCfgProfName, wingCfgProfNatPoolName }
			::= { wingCfgProfNatPoolTable 1 }

		
		WingCfgProfNatPoolEntry ::=
			SEQUENCE { 
				wingCfgProfNatPoolName
					WingIdentifier
			 }

		-- 1.3.6.1.4.1.1916.2.131.50.1.3.16.15.1.1.1
		wingCfgProfNatPoolName OBJECT-TYPE
			SYNTAX WingIdentifier
			MAX-ACCESS read-only
			STATUS current
			DESCRIPTION
				"Name of the NAT pool.
				
				XPath: /wing-config/profile[name=key1]/nat_pool[name=key2]/name"
			::= { wingCfgProfNatPoolEntry 1 }

		
		-- 1.3.6.1.4.1.1916.2.131.50.1.3.16.15.2
		wingCfgProfNatPoolAddrTable OBJECT-TYPE
			SYNTAX SEQUENCE OF WingCfgProfNatPoolAddrEntry
			MAX-ACCESS not-accessible
			STATUS current
			DESCRIPTION
				"
				
				/wing-config/profile/nat_pool/address_range"
			::= { wingCfgProfNat 2 }

		
		-- 1.3.6.1.4.1.1916.2.131.50.1.3.16.15.2.1
		wingCfgProfNatPoolAddrEntry OBJECT-TYPE
			SYNTAX WingCfgProfNatPoolAddrEntry
			MAX-ACCESS not-accessible
			STATUS current
			DESCRIPTION
				"An entry in the table."
			INDEX { wingCfgProfName, wingCfgProfNatPoolName, wingCfgProfNatPoolAddrStartIp }
			::= { wingCfgProfNatPoolAddrTable 1 }

		
		WingCfgProfNatPoolAddrEntry ::=
			SEQUENCE { 
				wingCfgProfNatPoolAddrStartIp
					WingIdentifier,
				wingCfgProfNatPoolAddrEndIp
					DisplayString
			 }

		-- 1.3.6.1.4.1.1916.2.131.50.1.3.16.15.2.1.1
		wingCfgProfNatPoolAddrStartIp OBJECT-TYPE
			SYNTAX WingIdentifier
			MAX-ACCESS read-only
			STATUS current
			DESCRIPTION
				"
				
				XPath: /wing-config/profile[name=key1]/nat_pool[name=key2]/address_rage[start_ip=key3]/start_ip"
			::= { wingCfgProfNatPoolAddrEntry 1 }

		
		-- 1.3.6.1.4.1.1916.2.131.50.1.3.16.15.2.1.3
		wingCfgProfNatPoolAddrEndIp OBJECT-TYPE
			SYNTAX DisplayString
			MAX-ACCESS read-write
			STATUS current
			DESCRIPTION
				"
				
				XPath: /wing-config/profile[name=key1]/nat_pool[name=key2]/address_rage[start_ip=key3]/end_ip"
			::= { wingCfgProfNatPoolAddrEntry 3 }

		
		-- 1.3.6.1.4.1.1916.2.131.50.1.3.16.15.7
		wingCfgProfNatBridgeSrcDynamicTable OBJECT-TYPE
			SYNTAX SEQUENCE OF WingCfgProfNatBridgeSrcDynamicEntry
			MAX-ACCESS not-accessible
			STATUS current
			DESCRIPTION
				"Description."
			::= { wingCfgProfNat 7 }

		
		-- 1.3.6.1.4.1.1916.2.131.50.1.3.16.15.7.1
		wingCfgProfNatBridgeSrcDynamicEntry OBJECT-TYPE
			SYNTAX WingCfgProfNatBridgeSrcDynamicEntry
			MAX-ACCESS not-accessible
			STATUS current
			DESCRIPTION
				"An entry in the table."
			INDEX { wingCfgProfName, wingCfgProfNatBridgeSrcDynamicAcl }
			::= { wingCfgProfNatBridgeSrcDynamicTable 1 }

		
		WingCfgProfNatBridgeSrcDynamicEntry ::=
			SEQUENCE { 
				wingCfgProfNatBridgeSrcDynamicAcl
					WingIdentifier
			 }

		-- 1.3.6.1.4.1.1916.2.131.50.1.3.16.15.7.1.1
		wingCfgProfNatBridgeSrcDynamicAcl OBJECT-TYPE
			SYNTAX WingIdentifier
			MAX-ACCESS read-only
			STATUS current
			DESCRIPTION
				"ACL 
				
				XPath: /wing-config/profile[name=key1]/bridge_source_dynamic_nat[acl=key2]/acl"
			::= { wingCfgProfNatBridgeSrcDynamicEntry 1 }

		
		-- 1.3.6.1.4.1.1916.2.131.50.1.3.16.15.8
		wingCfgProfNatBridgeSrcDynamicIfTable OBJECT-TYPE
			SYNTAX SEQUENCE OF WingCfgProfNatBridgeSrcDynamicIfEntry
			MAX-ACCESS not-accessible
			STATUS current
			DESCRIPTION
				"Description."
			::= { wingCfgProfNat 8 }

		
		-- 1.3.6.1.4.1.1916.2.131.50.1.3.16.15.8.1
		wingCfgProfNatBridgeSrcDynamicIfEntry OBJECT-TYPE
			SYNTAX WingCfgProfNatBridgeSrcDynamicIfEntry
			MAX-ACCESS not-accessible
			STATUS current
			DESCRIPTION
				"An entry in the table."
			INDEX { wingCfgProfName, wingCfgProfNatBridgeSrcDynamicAcl, wingCfgProfNatBridgeSrcDynamicIfName }
			::= { wingCfgProfNatBridgeSrcDynamicIfTable 1 }

		
		WingCfgProfNatBridgeSrcDynamicIfEntry ::=
			SEQUENCE { 
				wingCfgProfNatBridgeSrcDynamicIfName
					WingIdentifier,
				wingCfgProfNatBridgeSrcDynamicIfOverloadType
					DisplayString,
				wingCfgProfNatBridgeSrcDynamicIfOverloadIp
					DisplayString,
				wingCfgProfNatBridgeSrcDynamicIfNatPool
					DisplayString
			 }

		-- 1.3.6.1.4.1.1916.2.131.50.1.3.16.15.8.1.1
		wingCfgProfNatBridgeSrcDynamicIfName OBJECT-TYPE
			SYNTAX WingIdentifier
			MAX-ACCESS read-only
			STATUS current
			DESCRIPTION
				"The outgoing layer 3 interface for NAT.
				
				XPath: /wing-config/profile[name=key1]/bridge_source_dynamic_nat[acl=key2]/interface_cfg[interface=key3]/interface"
			::= { wingCfgProfNatBridgeSrcDynamicIfEntry 1 }

		
		-- 1.3.6.1.4.1.1916.2.131.50.1.3.16.15.8.1.3
		wingCfgProfNatBridgeSrcDynamicIfOverloadType OBJECT-TYPE
			SYNTAX DisplayString
			MAX-ACCESS read-write
			STATUS current
			DESCRIPTION
				"Overload Type.
				
				XPath: /wing-config/profile[name=key1]/bridge_source_dynamic_nat[acl=key2]/interface_cfg[interface=key3]/overload_type"
			::= { wingCfgProfNatBridgeSrcDynamicIfEntry 3 }

		
		-- 1.3.6.1.4.1.1916.2.131.50.1.3.16.15.8.1.4
		wingCfgProfNatBridgeSrcDynamicIfOverloadIp OBJECT-TYPE
			SYNTAX DisplayString
			MAX-ACCESS read-write
			STATUS current
			DESCRIPTION
				"Overload IP.
				
				XPath: /wing-config/profile[name=key1]/bridge_source_dynamic_nat[acl=key2]/interface_cfg[interface=key3]/overload_ip"
			::= { wingCfgProfNatBridgeSrcDynamicIfEntry 4 }

		
		-- 1.3.6.1.4.1.1916.2.131.50.1.3.16.15.8.1.5
		wingCfgProfNatBridgeSrcDynamicIfNatPool OBJECT-TYPE
			SYNTAX DisplayString
			MAX-ACCESS read-write
			STATUS current
			DESCRIPTION
				"Nat Pool.
				
				XPath: /wing-config/profile[name=key1]/bridge_source_dynamic_nat[acl=key2]/interface_cfg[interface=key3]/nat_pool"
			::= { wingCfgProfNatBridgeSrcDynamicIfEntry 5 }

		
-- /wing-config/profile
		-- 1.3.6.1.4.1.1916.2.131.50.1.3.16.18
		wingCfgProfVpn OBJECT IDENTIFIER ::= { wingCfgProf 18 }

		
		-- 1.3.6.1.4.1.1916.2.131.50.1.3.16.18.1
		wingCfgProfVpnTable OBJECT-TYPE
			SYNTAX SEQUENCE OF WingCfgProfVpnEntry
			MAX-ACCESS not-accessible
			STATUS current
			DESCRIPTION
				"
				
				/wing-config/profile"
			::= { wingCfgProfVpn 1 }

		
		-- 1.3.6.1.4.1.1916.2.131.50.1.3.16.18.1.1
		wingCfgProfVpnEntry OBJECT-TYPE
			SYNTAX WingCfgProfVpnEntry
			MAX-ACCESS not-accessible
			STATUS current
			DESCRIPTION
				"An entry in the table."
			INDEX { wingCfgProfName }
			::= { wingCfgProfVpnTable 1 }

		
		WingCfgProfVpnEntry ::=
			SEQUENCE { 
				wingCfgProfVpnLifetimeSeconds
					Unsigned32,
				wingCfgProfVpnLifetimeKb
					Unsigned32,
				wingCfgProfVpnIkev1GlobalDpdKeepalive
					Unsigned32,
				wingCfgProfVpnIkev1GlobalDpdRetries
					Unsigned32,
				wingCfgProfVpnIkev1GlobalNatKeepalive
					Unsigned32,
				wingCfgProfVpnIkev2GlobalDpdKeepalive
					Unsigned32,
				wingCfgProfVpnIkev2GlobalDpdRetries
					Unsigned32,
				wingCfgProfVpnIkev2GlobalNatKeepalive
					Unsigned32,
				wingCfgProfVpnCookieChallengeThreshold
					Unsigned32,
				wingCfgProfVpnMaxInNegotiationSa
					Unsigned32,
				wingCfgProfVpnDfBit
					DisplayString
			 }

		-- 1.3.6.1.4.1.1916.2.131.50.1.3.16.18.1.1.1
		wingCfgProfVpnLifetimeSeconds OBJECT-TYPE
			SYNTAX Unsigned32 (120..2147483646)
			UNITS "seconds"
			MAX-ACCESS read-write
			STATUS current
			DESCRIPTION
				"Time-based IPsec security association lifetime.
				
				XPath: /wing-config/profile[name=key1]/lifetime_seconds"
			DEFVAL { 3600 }
			::= { wingCfgProfVpnEntry 1 }

		
		-- 1.3.6.1.4.1.1916.2.131.50.1.3.16.18.1.1.2
		wingCfgProfVpnLifetimeKb OBJECT-TYPE
			SYNTAX Unsigned32 (500..2147483646)
			UNITS "kilobytes"
			MAX-ACCESS read-write
			STATUS current
			DESCRIPTION
				"Data-based IPsec security association lifetime.
				
				XPath: /wing-config/profile[name=key1]/lifetime_kb"
			DEFVAL { 4608000 }
			::= { wingCfgProfVpnEntry 2 }

		
		-- 1.3.6.1.4.1.1916.2.131.50.1.3.16.18.1.1.3
		wingCfgProfVpnIkev1GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /wing-config/profile[name=key1]/ikev1_dpd_keepalive"
			DEFVAL { 30 }
			::= { wingCfgProfVpnEntry 3 }

		
		-- 1.3.6.1.4.1.1916.2.131.50.1.3.16.18.1.1.4
		wingCfgProfVpnIkev1GlobalDpdRetries OBJECT-TYPE
			SYNTAX Unsigned32 (1..100)
			MAX-ACCESS read-write
			STATUS current
			DESCRIPTION
				"Global setting for number of keepalive messages to send before declaring a peer dead.
				
				XPath: /wing-config/profile[name=key1]/ikev1_dpd_retries"
			DEFVAL { 5 }
			::= { wingCfgProfVpnEntry 4 }

		
		-- 1.3.6.1.4.1.1916.2.131.50.1.3.16.18.1.1.5
		wingCfgProfVpnIkev1GlobalNatKeepalive OBJECT-TYPE
			SYNTAX Unsigned32 (10..3600)
			UNITS "seconds"
			MAX-ACCESS read-write
			STATUS current
			DESCRIPTION
				"Global setting for frequency of NAT keepalive messages.
				
				XPath: /wing-config/profile[name=key1]/ikev1_nat_keepalive"
			DEFVAL { 20 }
			::= { wingCfgProfVpnEntry 5 }

		
		-- 1.3.6.1.4.1.1916.2.131.50.1.3.16.18.1.1.6
		wingCfgProfVpnIkev2GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /wing-config/profile[name=key1]/ikev2_dpd_keepalive"
			DEFVAL { 30 }
			::= { wingCfgProfVpnEntry 6 }

		
		-- 1.3.6.1.4.1.1916.2.131.50.1.3.16.18.1.1.7
		wingCfgProfVpnIkev2GlobalDpdRetries OBJECT-TYPE
			SYNTAX Unsigned32 (1..100)
			MAX-ACCESS read-write
			STATUS current
			DESCRIPTION
				"Global setting for number of keepalive messages to send before declaring a peer dead.
				
				XPath: /wing-config/profile[name=key1]/ikev2_dpd_retries"
			DEFVAL { 5 }
			::= { wingCfgProfVpnEntry 7 }

		
		-- 1.3.6.1.4.1.1916.2.131.50.1.3.16.18.1.1.8
		wingCfgProfVpnIkev2GlobalNatKeepalive OBJECT-TYPE
			SYNTAX Unsigned32 (10..3600)
			UNITS "seconds"
			MAX-ACCESS read-write
			STATUS current
			DESCRIPTION
				"Global setting for frequency of NAT keepalive messages.
				
				XPath: /wing-config/profile[name=key1]/ikev2_nat_keepalive"
			DEFVAL { 20 }
			::= { wingCfgProfVpnEntry 8 }

		
		-- 1.3.6.1.4.1.1916.2.131.50.1.3.16.18.1.1.9
		wingCfgProfVpnCookieChallengeThreshold OBJECT-TYPE
			SYNTAX Unsigned32 (1..100)
			MAX-ACCESS read-write
			STATUS current
			DESCRIPTION
				"Number of Half open IKE SA after which cookie challenge mechanism is enabled (IKEv2 only).
				
				XPath: /wing-config/profile[name=key1]/cookie_challenge_threshold"
			DEFVAL { 5 }
			::= { wingCfgProfVpnEntry 9 }

		
		-- 1.3.6.1.4.1.1916.2.131.50.1.3.16.18.1.1.10
		wingCfgProfVpnMaxInNegotiationSa OBJECT-TYPE
			SYNTAX Unsigned32 (1..100)
			MAX-ACCESS read-write
			STATUS current
			DESCRIPTION
				"Maximum allowed half open IKE SAs (IKEv2 only).
				
				XPath: /wing-config/profile[name=key1]/max_in_negotiation_sa"
			DEFVAL { 10 }
			::= { wingCfgProfVpnEntry 10 }

		
		-- 1.3.6.1.4.1.1916.2.131.50.1.3.16.18.1.1.11
		wingCfgProfVpnDfBit OBJECT-TYPE
			SYNTAX DisplayString
			MAX-ACCESS read-write
			STATUS current
			DESCRIPTION
				"Configure DF bit handling for esp encapsulating header
				
				Values:
				clear,
				set,
				copy
				
				XPath: /wing-config/profile[name=key1]/df_bit"
			DEFVAL { "copy" }
			::= { wingCfgProfVpnEntry 11 }

		
		-- 1.3.6.1.4.1.1916.2.131.50.1.3.16.18.2
		wingCfgProfVpnIkev1Table OBJECT-TYPE
			SYNTAX SEQUENCE OF WingCfgProfVpnIkev1Entry
			MAX-ACCESS not-accessible
			STATUS current
			DESCRIPTION
				"
				
				/wing-config/profile/ikev1_policy"
			::= { wingCfgProfVpn 2 }

		
		-- 1.3.6.1.4.1.1916.2.131.50.1.3.16.18.2.1
		wingCfgProfVpnIkev1Entry OBJECT-TYPE
			SYNTAX WingCfgProfVpnIkev1Entry
			MAX-ACCESS not-accessible
			STATUS current
			DESCRIPTION
				"An entry in the table."
			INDEX { wingCfgProfName, wingCfgProfVpnIkev1Name }
			::= { wingCfgProfVpnIkev1Table 1 }

		
		WingCfgProfVpnIkev1Entry ::=
			SEQUENCE { 
				wingCfgProfVpnIkev1Name
					WingIdentifier,
				wingCfgProfVpnIkev1Mode
					DisplayString,
				wingCfgProfVpnIkev1IsakmpLifetime
					Unsigned32,
				wingCfgProfVpnIkev1DpdKeepalive
					Unsigned32,
				wingCfgProfVpnIkev1DpdRetries
					Unsigned32
			 }

		-- 1.3.6.1.4.1.1916.2.131.50.1.3.16.18.2.1.1
		wingCfgProfVpnIkev1Name OBJECT-TYPE
			SYNTAX WingIdentifier
			MAX-ACCESS read-only
			STATUS current
			DESCRIPTION
				"
				
				XPath: /wing-config/profile[name=key1]/ikev1_policy[name=key2]/name"
			::= { wingCfgProfVpnIkev1Entry 1 }

		
		-- 1.3.6.1.4.1.1916.2.131.50.1.3.16.18.2.1.3
		wingCfgProfVpnIkev1Mode OBJECT-TYPE
			SYNTAX DisplayString
			MAX-ACCESS read-write
			STATUS current
			DESCRIPTION
				"IKE version 1 mode of operation (main/aggressive).
				
				Values:
				main,
				aggressive
				
				XPath: /wing-config/profile[name=key1]/ikev1_policy[name=key2]/mode"
			DEFVAL { "main" }
			::= { wingCfgProfVpnIkev1Entry 3 }

		
		-- 1.3.6.1.4.1.1916.2.131.50.1.3.16.18.2.1.4
		wingCfgProfVpnIkev1IsakmpLifetime OBJECT-TYPE
			SYNTAX Unsigned32 (600..2147483646)
			UNITS "seconds"
			MAX-ACCESS read-write
			STATUS current
			DESCRIPTION
				"Lifetime in seconds for IKE Security Association (ISAKMP SA).
				
				XPath: /wing-config/profile[name=key1]/ikev1_policy[name=key2]/isakmp_lifetime"
			DEFVAL { 86400 }
			::= { wingCfgProfVpnIkev1Entry 4 }

		
		-- 1.3.6.1.4.1.1916.2.131.50.1.3.16.18.2.1.5
		wingCfgProfVpnIkev1DpdKeepalive OBJECT-TYPE
			SYNTAX Unsigned32 (10..3600)
			UNITS "seconds"
			MAX-ACCESS read-write
			STATUS current
			DESCRIPTION
				"Frequency of IKE keepalive messages for Dead Peer Detection.
				
				XPath: /wing-config/profile[name=key1]/ikev1_policy[name=key2]/dpd_keepalive"
			DEFVAL { 30 }
			::= { wingCfgProfVpnIkev1Entry 5 }

		
		-- 1.3.6.1.4.1.1916.2.131.50.1.3.16.18.2.1.6
		wingCfgProfVpnIkev1DpdRetries OBJECT-TYPE
			SYNTAX Unsigned32 (1..100)
			MAX-ACCESS read-write
			STATUS current
			DESCRIPTION
				"Number of keepalive messages to send before declaring a peer dead.
				
				XPath: /wing-config/profile[name=key1]/ikev1_policy[name=key2]/dpd_retries"
			DEFVAL { 5 }
			::= { wingCfgProfVpnIkev1Entry 6 }

		
		-- 1.3.6.1.4.1.1916.2.131.50.1.3.16.18.3
		wingCfgProfVpnIkev1IsakmpTable OBJECT-TYPE
			SYNTAX SEQUENCE OF WingCfgProfVpnIkev1IsakmpEntry
			MAX-ACCESS not-accessible
			STATUS current
			DESCRIPTION
				"
				
				/wing-config/profile/ikev1_policy/isakmp_proposal"
			::= { wingCfgProfVpn 3 }

		
		-- 1.3.6.1.4.1.1916.2.131.50.1.3.16.18.3.1
		wingCfgProfVpnIkev1IsakmpEntry OBJECT-TYPE
			SYNTAX WingCfgProfVpnIkev1IsakmpEntry
			MAX-ACCESS not-accessible
			STATUS current
			DESCRIPTION
				"An entry in the table."
			INDEX { wingCfgProfName, wingCfgProfVpnIkev1Name, wingCfgProfVpnIkev1IsakmpName }
			::= { wingCfgProfVpnIkev1IsakmpTable 1 }

		
		WingCfgProfVpnIkev1IsakmpEntry ::=
			SEQUENCE { 
				wingCfgProfVpnIkev1IsakmpName
					WingIdentifier,
				wingCfgProfVpnIkev1IsakmpEncryption
					DisplayString,
				wingCfgProfVpnIkev1IsakmpGroup
					DisplayString,
				wingCfgProfVpnIkev1IsakmpHash
					DisplayString
			 }

		-- 1.3.6.1.4.1.1916.2.131.50.1.3.16.18.3.1.1
		wingCfgProfVpnIkev1IsakmpName OBJECT-TYPE
			SYNTAX WingIdentifier
			MAX-ACCESS read-only
			STATUS current
			DESCRIPTION
				"
				
				XPath: /wing-config/profile[name=key1]/ikev1_policy[name=key2]/isakmp_proposal[name=key3]/name"
			::= { wingCfgProfVpnIkev1IsakmpEntry 1 }

		
		-- 1.3.6.1.4.1.1916.2.131.50.1.3.16.18.3.1.3
		wingCfgProfVpnIkev1IsakmpEncryption OBJECT-TYPE
			SYNTAX DisplayString
			MAX-ACCESS read-write
			STATUS current
			DESCRIPTION
				"Encryption method protecting data transmitted between peers.
				
				Values:
				3des,
				aes,
				aes-192,
				aes-256
				
				XPath: /wing-config/profile[name=key1]/ikev1_policy[name=key2]/isakmp_proposal[name=key3]/encryption"
			DEFVAL { "aes-256" }
			::= { wingCfgProfVpnIkev1IsakmpEntry 3 }

		
		-- 1.3.6.1.4.1.1916.2.131.50.1.3.16.18.3.1.4
		wingCfgProfVpnIkev1IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /wing-config/profile[name=key1]/ikev1_policy[name=key2]/isakmp_proposal[name=key3]/group"
			DEFVAL { "2" }
			::= { wingCfgProfVpnIkev1IsakmpEntry 4 }

		
		-- 1.3.6.1.4.1.1916.2.131.50.1.3.16.18.3.1.5
		wingCfgProfVpnIkev1IsakmpHash OBJECT-TYPE
			SYNTAX DisplayString
			MAX-ACCESS read-write
			STATUS current
			DESCRIPTION
				"Hash algorithm used to ensure data integrity.
				
				Values:
				md5,
				sha
				
				XPath: /wing-config/profile[name=key1]/ikev1_policy[name=key2]/isakmp_proposal[name=key3]/hash"
			DEFVAL { "sha" }
			::= { wingCfgProfVpnIkev1IsakmpEntry 5 }

		
		-- 1.3.6.1.4.1.1916.2.131.50.1.3.16.18.4
		wingCfgProfVpnIkev2Table OBJECT-TYPE
			SYNTAX SEQUENCE OF WingCfgProfVpnIkev2Entry
			MAX-ACCESS not-accessible
			STATUS current
			DESCRIPTION
				"
				
				/wing-config/profile/ikev2_policy"
			::= { wingCfgProfVpn 4 }

		
		-- 1.3.6.1.4.1.1916.2.131.50.1.3.16.18.4.1
		wingCfgProfVpnIkev2Entry OBJECT-TYPE
			SYNTAX WingCfgProfVpnIkev2Entry
			MAX-ACCESS not-accessible
			STATUS current
			DESCRIPTION
				"An entry in the table."
			INDEX { wingCfgProfName, wingCfgProfVpnIkev2Name }
			::= { wingCfgProfVpnIkev2Table 1 }

		
		WingCfgProfVpnIkev2Entry ::=
			SEQUENCE { 
				wingCfgProfVpnIkev2Name
					WingIdentifier,
				wingCfgProfVpnIkev2IsakmpLifetime
					Unsigned32,
				wingCfgProfVpnIkev2DpdKeepalive
					Unsigned32
			 }

		-- 1.3.6.1.4.1.1916.2.131.50.1.3.16.18.4.1.1
		wingCfgProfVpnIkev2Name OBJECT-TYPE
			SYNTAX WingIdentifier
			MAX-ACCESS read-only
			STATUS current
			DESCRIPTION
				"
				
				XPath: /wing-config/profile[name=key1]/ikev2_policy[name=key2]/name"
			::= { wingCfgProfVpnIkev2Entry 1 }

		
		-- 1.3.6.1.4.1.1916.2.131.50.1.3.16.18.4.1.3
		wingCfgProfVpnIkev2IsakmpLifetime OBJECT-TYPE
			SYNTAX Unsigned32 (600..2147483646)
			UNITS "seconds"
			MAX-ACCESS read-write
			STATUS current
			DESCRIPTION
				"Lifetime in seconds for IKE Security Association (ISAKMP SA).
				
				XPath: /wing-config/profile[name=key1]/ikev2_policy[name=key2]/isakmp_lifetime"
			DEFVAL { 86400 }
			::= { wingCfgProfVpnIkev2Entry 3 }

		
		-- 1.3.6.1.4.1.1916.2.131.50.1.3.16.18.4.1.4
		wingCfgProfVpnIkev2DpdKeepalive OBJECT-TYPE
			SYNTAX Unsigned32 (10..3600)
			UNITS "seconds"
			MAX-ACCESS read-write
			STATUS current
			DESCRIPTION
				"Frequency of IKE keepalive messages for Dead Peer Detection.
				
				XPath: /wing-config/profile[name=key1]/ikev2_policy[name=key2]/dpd_keepalive"
			DEFVAL { 10 }
			::= { wingCfgProfVpnIkev2Entry 4 }

		
		-- 1.3.6.1.4.1.1916.2.131.50.1.3.16.18.5
		wingCfgProfVpnIkev2IsakmpTable OBJECT-TYPE
			SYNTAX SEQUENCE OF WingCfgProfVpnIkev2IsakmpEntry
			MAX-ACCESS not-accessible
			STATUS current
			DESCRIPTION
				"
				
				/wing-config/profile/ikev2_policy/isakmp_proposal"
			::= { wingCfgProfVpn 5 }

		
		-- 1.3.6.1.4.1.1916.2.131.50.1.3.16.18.5.1
		wingCfgProfVpnIkev2IsakmpEntry OBJECT-TYPE
			SYNTAX WingCfgProfVpnIkev2IsakmpEntry
			MAX-ACCESS not-accessible
			STATUS current
			DESCRIPTION
				"An entry in the table."
			INDEX { wingCfgProfName, wingCfgProfVpnIkev2Name, wingCfgProfVpnIkev2IsakmpName }
			::= { wingCfgProfVpnIkev2IsakmpTable 1 }

		
		WingCfgProfVpnIkev2IsakmpEntry ::=
			SEQUENCE { 
				wingCfgProfVpnIkev2IsakmpName
					WingIdentifier,
				wingCfgProfVpnIkev2IsakmpEncryption
					DisplayString,
				wingCfgProfVpnIkev2IsakmpGroup
					DisplayString,
				wingCfgProfVpnIkev2IsakmpHash
					DisplayString
			 }

		-- 1.3.6.1.4.1.1916.2.131.50.1.3.16.18.5.1.1
		wingCfgProfVpnIkev2IsakmpName OBJECT-TYPE
			SYNTAX WingIdentifier
			MAX-ACCESS read-only
			STATUS current
			DESCRIPTION
				"
				
				XPath: /wing-config/profile[name=key1]/ikev2_policy[name=key2]/isakmp_proposal[name=key3]/name"
			::= { wingCfgProfVpnIkev2IsakmpEntry 1 }

		
		-- 1.3.6.1.4.1.1916.2.131.50.1.3.16.18.5.1.3
		wingCfgProfVpnIkev2IsakmpEncryption OBJECT-TYPE
			SYNTAX DisplayString
			MAX-ACCESS read-write
			STATUS current
			DESCRIPTION
				"Encryption method protecting data transmitted between peers.
				
				Values:
				3des,
				aes,
				aes-192,
				aes-256
				
				XPath: /wing-config/profile[name=key1]/ikev2_policy[name=key2]/isakmp_proposal[name=key3]/encryption"
			DEFVAL { "aes-256" }
			::= { wingCfgProfVpnIkev2IsakmpEntry 3 }

		
		-- 1.3.6.1.4.1.1916.2.131.50.1.3.16.18.5.1.4
		wingCfgProfVpnIkev2IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /wing-config/profile[name=key1]/ikev2_policy[name=key2]/isakmp_proposal[name=key3]/group"
			DEFVAL { "2" }
			::= { wingCfgProfVpnIkev2IsakmpEntry 4 }

		
		-- 1.3.6.1.4.1.1916.2.131.50.1.3.16.18.5.1.5
		wingCfgProfVpnIkev2IsakmpHash OBJECT-TYPE
			SYNTAX DisplayString
			MAX-ACCESS read-write
			STATUS current
			DESCRIPTION
				"Hash algorithm used to ensure data integrity.
				
				Values:
				md5,
				sha
				
				XPath: /wing-config/profile[name=key1]/ikev2_policy[name=key2]/isakmp_proposal[name=key3]/hash"
			DEFVAL { "sha" }
			::= { wingCfgProfVpnIkev2IsakmpEntry 5 }

		
		-- 1.3.6.1.4.1.1916.2.131.50.1.3.16.18.6
		wingCfgProfVpnIkev1PeerTable OBJECT-TYPE
			SYNTAX SEQUENCE OF WingCfgProfVpnIkev1PeerEntry
			MAX-ACCESS not-accessible
			STATUS current
			DESCRIPTION
				"
				
				/wing-config/profile/ikev1_peer"
			::= { wingCfgProfVpn 6 }

		
		-- 1.3.6.1.4.1.1916.2.131.50.1.3.16.18.6.1
		wingCfgProfVpnIkev1PeerEntry OBJECT-TYPE
			SYNTAX WingCfgProfVpnIkev1PeerEntry
			MAX-ACCESS not-accessible
			STATUS current
			DESCRIPTION
				"An entry in the table."
			INDEX { wingCfgProfName, wingCfgProfVpnIkev1PeerName }
			::= { wingCfgProfVpnIkev1PeerTable 1 }

		
		WingCfgProfVpnIkev1PeerEntry ::=
			SEQUENCE { 
				wingCfgProfVpnIkev1PeerName
					WingIdentifier,
				wingCfgProfVpnIkev1PeerIpType
					DisplayString,
				wingCfgProfVpnIkev1PeerIpValue
					DisplayString,
				wingCfgProfVpnIkev1PeerAuthType
					DisplayString,
				wingCfgProfVpnIkev1PeerAuthKey
					DisplayString,
				wingCfgProfVpnIkev1PeerLocalidType
					DisplayString,
				wingCfgProfVpnIkev1PeerLocalidValue
					DisplayString,
				wingCfgProfVpnIkev1PeerRemoteidType
					DisplayString,
				wingCfgProfVpnIkev1PeerRemoteidValue
					DisplayString,
				wingCfgProfVpnIkev1PeerIkev1Policy
					WingIdentifier
			 }

		-- 1.3.6.1.4.1.1916.2.131.50.1.3.16.18.6.1.1
		wingCfgProfVpnIkev1PeerName OBJECT-TYPE
			SYNTAX WingIdentifier
			MAX-ACCESS read-only
			STATUS current
			DESCRIPTION
				"
				
				XPath: /wing-config/profile[name=key1]/ikev1_peer[name=key2]/name"
			::= { wingCfgProfVpnIkev1PeerEntry 1 }

		
		-- 1.3.6.1.4.1.1916.2.131.50.1.3.16.18.6.1.3
		wingCfgProfVpnIkev1PeerIpType OBJECT-TYPE
			SYNTAX DisplayString
			MAX-ACCESS read-write
			STATUS current
			DESCRIPTION
				"IP address/fqdn of the IPSEC VPN peer for tunnel setup
				
				Values:
				address,
				fqdn
				
				XPath: /wing-config/profile[name=key1]/ikev1_peer[name=key2]/ip/type"
			DEFVAL { "address" }
			::= { wingCfgProfVpnIkev1PeerEntry 3 }

		
		-- 1.3.6.1.4.1.1916.2.131.50.1.3.16.18.6.1.4
		wingCfgProfVpnIkev1PeerIpValue OBJECT-TYPE
			SYNTAX DisplayString (SIZE (1..64))
			MAX-ACCESS read-write
			STATUS current
			DESCRIPTION
				"Peer IP can be specified as either IP or FQDN.
				
				XPath: /wing-config/profile[name=key1]/ikev1_peer[name=key2]/ip/value"
			::= { wingCfgProfVpnIkev1PeerEntry 4 }

		
		-- 1.3.6.1.4.1.1916.2.131.50.1.3.16.18.6.1.5
		wingCfgProfVpnIkev1PeerAuthType OBJECT-TYPE
			SYNTAX DisplayString
			MAX-ACCESS read-write
			STATUS current
			DESCRIPTION
				"
				
				Values:
				psk,
				rsa
				
				XPath: /wing-config/profile[name=key1]/ikev1_peer[name=key2]/authentication/type"
			DEFVAL { "rsa" }
			::= { wingCfgProfVpnIkev1PeerEntry 5 }

		
		-- 1.3.6.1.4.1.1916.2.131.50.1.3.16.18.6.1.6
		wingCfgProfVpnIkev1PeerAuthKey OBJECT-TYPE
			SYNTAX DisplayString (SIZE (8..21))
			MAX-ACCESS read-write
			STATUS current
			DESCRIPTION
				"The shared secret used for peer authentication.
				
				XPath: /wing-config/profile[name=key1]/ikev1_peer[name=key2]/authentication/key"
			::= { wingCfgProfVpnIkev1PeerEntry 6 }

		
		-- 1.3.6.1.4.1.1916.2.131.50.1.3.16.18.6.1.7
		wingCfgProfVpnIkev1PeerLocalidType OBJECT-TYPE
			SYNTAX DisplayString
			MAX-ACCESS read-write
			STATUS current
			DESCRIPTION
				"Local identity to use in IKE exchange with this peer.
				
				Values:
				address,
				dn,
				fqdn,
				email,
				string
				
				XPath: /wing-config/profile[name=key1]/ikev1_peer[name=key2]/localid/localid_type"
			DEFVAL { "'string'" }
			::= { wingCfgProfVpnIkev1PeerEntry 7 }

		
		-- 1.3.6.1.4.1.1916.2.131.50.1.3.16.18.6.1.8
		wingCfgProfVpnIkev1PeerLocalidValue OBJECT-TYPE
			SYNTAX DisplayString (SIZE (1..128))
			MAX-ACCESS read-write
			STATUS current
			DESCRIPTION
				"
				
				XPath: /wing-config/profile[name=key1]/ikev1_peer[name=key2]/localid/localid_value"
			::= { wingCfgProfVpnIkev1PeerEntry 8 }

		
		-- 1.3.6.1.4.1.1916.2.131.50.1.3.16.18.6.1.9
		wingCfgProfVpnIkev1PeerRemoteidType OBJECT-TYPE
			SYNTAX DisplayString
			MAX-ACCESS read-write
			STATUS current
			DESCRIPTION
				"Peer identity of this peer.
				
				Values:
				address,
				dn,
				fqdn,
				email,
				string
				
				XPath: /wing-config/profile[name=key1]/ikev1_peer[name=key2]/remoteid/remoteid_type"
			DEFVAL { "'string'" }
			::= { wingCfgProfVpnIkev1PeerEntry 9 }

		
		-- 1.3.6.1.4.1.1916.2.131.50.1.3.16.18.6.1.10
		wingCfgProfVpnIkev1PeerRemoteidValue OBJECT-TYPE
			SYNTAX DisplayString (SIZE (1..128))
			MAX-ACCESS read-write
			STATUS current
			DESCRIPTION
				"
				
				XPath: /wing-config/profile[name=key1]/ikev1_peer[name=key2]/remoteid/remoteid_value"
			::= { wingCfgProfVpnIkev1PeerEntry 10 }

		
		-- 1.3.6.1.4.1.1916.2.131.50.1.3.16.18.6.1.11
		wingCfgProfVpnIkev1PeerIkev1Policy OBJECT-TYPE
			SYNTAX WingIdentifier
			MAX-ACCESS read-write
			STATUS current
			DESCRIPTION
				"
				
				XPath: /wing-config/profile[name=key1]/ikev1_peer[name=key2]/ikev1_policy"
			::= { wingCfgProfVpnIkev1PeerEntry 11 }

		
		-- 1.3.6.1.4.1.1916.2.131.50.1.3.16.18.7
		wingCfgProfVpnIkev2PeerTable OBJECT-TYPE
			SYNTAX SEQUENCE OF WingCfgProfVpnIkev2PeerEntry
			MAX-ACCESS not-accessible
			STATUS current
			DESCRIPTION
				"
				
				/wing-config/profile/ikev2_peer"
			::= { wingCfgProfVpn 7 }

		
		-- 1.3.6.1.4.1.1916.2.131.50.1.3.16.18.7.1
		wingCfgProfVpnIkev2PeerEntry OBJECT-TYPE
			SYNTAX WingCfgProfVpnIkev2PeerEntry
			MAX-ACCESS not-accessible
			STATUS current
			DESCRIPTION
				"An entry in the table."
			INDEX { wingCfgProfName, wingCfgProfVpnIkev2PeerName }
			::= { wingCfgProfVpnIkev2PeerTable 1 }

		
		WingCfgProfVpnIkev2PeerEntry ::=
			SEQUENCE { 
				wingCfgProfVpnIkev2PeerName
					WingIdentifier,
				wingCfgProfVpnIkev2PeerIpType
					DisplayString,
				wingCfgProfVpnIkev2PeerIpValue
					DisplayString,
				wingCfgProfVpnIkev2PeerLocalAuthType
					DisplayString,
				wingCfgProfVpnIkev2PeerLocalAuthKey
					DisplayString,
				wingCfgProfVpnIkev2PeerRemoteAuthType
					DisplayString,
				wingCfgProfVpnIkev2PeerRemoteAuthKey
					DisplayString,
				wingCfgProfVpnIkev2PeerLocalidType
					DisplayString,
				wingCfgProfVpnIkev2PeerLocalidValue
					DisplayString,
				wingCfgProfVpnIkev2PeerRemoteidType
					DisplayString,
				wingCfgProfVpnIkev2PeerRemoteidValue
					DisplayString,
				wingCfgProfVpnIkev2PeerIkev2Policy
					WingIdentifier
			 }

		-- 1.3.6.1.4.1.1916.2.131.50.1.3.16.18.7.1.1
		wingCfgProfVpnIkev2PeerName OBJECT-TYPE
			SYNTAX WingIdentifier
			MAX-ACCESS read-only
			STATUS current
			DESCRIPTION
				"
				
				XPath: /wing-config/profile[name=key1]/ikev2_peer[name=key2]/name"
			::= { wingCfgProfVpnIkev2PeerEntry 1 }

		
		-- 1.3.6.1.4.1.1916.2.131.50.1.3.16.18.7.1.3
		wingCfgProfVpnIkev2PeerIpType OBJECT-TYPE
			SYNTAX DisplayString
			MAX-ACCESS read-write
			STATUS current
			DESCRIPTION
				"IP address/hostname of the IPSEC VPN peer for tunnel setup
				
				Values:
				address,
				fqdn
				
				XPath: /wing-config/profile[name=key1]/ikev2_peer[name=key2]/ip/type"
			DEFVAL { "address" }
			::= { wingCfgProfVpnIkev2PeerEntry 3 }

		
		-- 1.3.6.1.4.1.1916.2.131.50.1.3.16.18.7.1.4
		wingCfgProfVpnIkev2PeerIpValue OBJECT-TYPE
			SYNTAX DisplayString (SIZE (1..64))
			MAX-ACCESS read-write
			STATUS current
			DESCRIPTION
				"Peer IP can be specified as either IP or FQDN.
				
				XPath: /wing-config/profile[name=key1]/ikev2_peer[name=key2]/ip/value"
			::= { wingCfgProfVpnIkev2PeerEntry 4 }

		
		-- 1.3.6.1.4.1.1916.2.131.50.1.3.16.18.7.1.5
		wingCfgProfVpnIkev2PeerLocalAuthType OBJECT-TYPE
			SYNTAX DisplayString
			MAX-ACCESS read-write
			STATUS current
			DESCRIPTION
				"
				
				Values:
				psk,
				rsa
				
				XPath: /wing-config/profile[name=key1]/ikev2_peer[name=key2]/local_authentication/type"
			DEFVAL { "rsa" }
			::= { wingCfgProfVpnIkev2PeerEntry 5 }

		
		-- 1.3.6.1.4.1.1916.2.131.50.1.3.16.18.7.1.6
		wingCfgProfVpnIkev2PeerLocalAuthKey OBJECT-TYPE
			SYNTAX DisplayString (SIZE (8..21))
			MAX-ACCESS read-write
			STATUS current
			DESCRIPTION
				"The shared secret used for local peer authentication.
				
				XPath: /wing-config/profile[name=key1]/ikev2_peer[name=key2]/local_authentication/key"
			::= { wingCfgProfVpnIkev2PeerEntry 6 }

		
		-- 1.3.6.1.4.1.1916.2.131.50.1.3.16.18.7.1.7
		wingCfgProfVpnIkev2PeerRemoteAuthType OBJECT-TYPE
			SYNTAX DisplayString
			MAX-ACCESS read-write
			STATUS current
			DESCRIPTION
				"
				
				Values:
				psk,
				rsa
				
				XPath: /wing-config/profile[name=key1]/ikev2_peer[name=key2]/remote_authentication/type"
			DEFVAL { "rsa" }
			::= { wingCfgProfVpnIkev2PeerEntry 7 }

		
		-- 1.3.6.1.4.1.1916.2.131.50.1.3.16.18.7.1.8
		wingCfgProfVpnIkev2PeerRemoteAuthKey OBJECT-TYPE
			SYNTAX DisplayString (SIZE (8..21))
			MAX-ACCESS read-write
			STATUS current
			DESCRIPTION
				"The shared secret used for remote peer authentication.
				
				XPath: /wing-config/profile[name=key1]/ikev2_peer[name=key2]/remote_authentication/key"
			::= { wingCfgProfVpnIkev2PeerEntry 8 }

		
		-- 1.3.6.1.4.1.1916.2.131.50.1.3.16.18.7.1.9
		wingCfgProfVpnIkev2PeerLocalidType OBJECT-TYPE
			SYNTAX DisplayString
			MAX-ACCESS read-write
			STATUS current
			DESCRIPTION
				"Local identity to use in IKE exchange with this peer.
				
				Values:
				address,
				dn,
				fqdn,
				email,
				string
				
				XPath: /wing-config/profile[name=key1]/ikev2_peer[name=key2]/localid/localid_type"
			DEFVAL { "'string'" }
			::= { wingCfgProfVpnIkev2PeerEntry 9 }

		
		-- 1.3.6.1.4.1.1916.2.131.50.1.3.16.18.7.1.10
		wingCfgProfVpnIkev2PeerLocalidValue OBJECT-TYPE
			SYNTAX DisplayString (SIZE (1..128))
			MAX-ACCESS read-write
			STATUS current
			DESCRIPTION
				"
				
				XPath: /wing-config/profile[name=key1]/ikev2_peer[name=key2]/localid/localid_value"
			::= { wingCfgProfVpnIkev2PeerEntry 10 }

		
		-- 1.3.6.1.4.1.1916.2.131.50.1.3.16.18.7.1.11
		wingCfgProfVpnIkev2PeerRemoteidType OBJECT-TYPE
			SYNTAX DisplayString
			MAX-ACCESS read-write
			STATUS current
			DESCRIPTION
				"Peer identity of this peer.
				
				Values:
				address,
				dn,
				fqdn,
				email,
				string
				
				XPath: /wing-config/profile[name=key1]/ikev2_peer[name=key2]/remoteid/remoteid_type"
			DEFVAL { "'string'" }
			::= { wingCfgProfVpnIkev2PeerEntry 11 }

		
		-- 1.3.6.1.4.1.1916.2.131.50.1.3.16.18.7.1.12
		wingCfgProfVpnIkev2PeerRemoteidValue OBJECT-TYPE
			SYNTAX DisplayString (SIZE (1..128))
			MAX-ACCESS read-write
			STATUS current
			DESCRIPTION
				"
				
				XPath: /wing-config/profile[name=key1]/ikev2_peer[name=key2]/remoteid/remoteid_value"
			::= { wingCfgProfVpnIkev2PeerEntry 12 }

		
		-- 1.3.6.1.4.1.1916.2.131.50.1.3.16.18.7.1.13
		wingCfgProfVpnIkev2PeerIkev2Policy OBJECT-TYPE
			SYNTAX WingIdentifier
			MAX-ACCESS read-write
			STATUS current
			DESCRIPTION
				"IKEv2 Policy to use with this peer.
				
				XPath: /wing-config/profile[name=key1]/ikev2_peer[name=key2]/ikev2_policy"
			::= { wingCfgProfVpnIkev2PeerEntry 13 }

		
		-- 1.3.6.1.4.1.1916.2.131.50.1.3.16.18.8
		wingCfgProfVpnTransformTable OBJECT-TYPE
			SYNTAX SEQUENCE OF WingCfgProfVpnTransformEntry
			MAX-ACCESS not-accessible
			STATUS current
			DESCRIPTION
				"
				
				/wing-config/profile/ipsec_transform_set"
			::= { wingCfgProfVpn 8 }

		
		-- 1.3.6.1.4.1.1916.2.131.50.1.3.16.18.8.1
		wingCfgProfVpnTransformEntry OBJECT-TYPE
			SYNTAX WingCfgProfVpnTransformEntry
			MAX-ACCESS not-accessible
			STATUS current
			DESCRIPTION
				"An entry in the table."
			INDEX { wingCfgProfName, wingCfgProfVpnTransformName }
			::= { wingCfgProfVpnTransformTable 1 }

		
		WingCfgProfVpnTransformEntry ::=
			SEQUENCE { 
				wingCfgProfVpnTransformName
					WingIdentifier,
				wingCfgProfVpnTransformCipherAlgo
					DisplayString,
				wingCfgProfVpnTransformAuthAlgo
					DisplayString,
				wingCfgProfVpnTransformMode
					DisplayString
			 }

		-- 1.3.6.1.4.1.1916.2.131.50.1.3.16.18.8.1.1
		wingCfgProfVpnTransformName OBJECT-TYPE
			SYNTAX WingIdentifier
			MAX-ACCESS read-only
			STATUS current
			DESCRIPTION
				"
				
				XPath: /wing-config/profile[name=key1]/ipsec_transform_set[name=key2]/name"
			::= { wingCfgProfVpnTransformEntry 1 }

		
		-- 1.3.6.1.4.1.1916.2.131.50.1.3.16.18.8.1.3
		wingCfgProfVpnTransformCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /wing-config/profile[name=key1]/ipsec_transform_set[name=key2]/cipher_algo"
			DEFVAL { "aes-256" }
			::= { wingCfgProfVpnTransformEntry 3 }

		
		-- 1.3.6.1.4.1.1916.2.131.50.1.3.16.18.8.1.4
		wingCfgProfVpnTransformAuthAlgo OBJECT-TYPE
			SYNTAX DisplayString
			MAX-ACCESS read-write
			STATUS current
			DESCRIPTION
				"Authentication scheme used to validate identity.
				
				Values:
				md5-hmac,
				sha-hmac
				
				XPath: /wing-config/profile[name=key1]/ipsec_transform_set[name=key2]/auth_algo"
			DEFVAL { "sha-hmac" }
			::= { wingCfgProfVpnTransformEntry 4 }

		
		-- 1.3.6.1.4.1.1916.2.131.50.1.3.16.18.8.1.5
		wingCfgProfVpnTransformMode OBJECT-TYPE
			SYNTAX DisplayString
			MAX-ACCESS read-write
			STATUS current
			DESCRIPTION
				"IPsec tunnel type - tunnel mode is used for site-to-site vpn and transport mode is used to remote-vpn.
				
				Values:
				tunnel,
				transport
				
				XPath: /wing-config/profile[name=key1]/ipsec_transform_set[name=key2]/mode"
			DEFVAL { "tunnel" }
			::= { wingCfgProfVpnTransformEntry 5 }

		
		-- 1.3.6.1.4.1.1916.2.131.50.1.3.16.18.9
		wingCfgProfVpnCryptoTable OBJECT-TYPE
			SYNTAX SEQUENCE OF WingCfgProfVpnCryptoEntry
			MAX-ACCESS not-accessible
			STATUS current
			DESCRIPTION
				"
				
				/wing-config/profile/crypto_map"
			::= { wingCfgProfVpn 9 }

		
		-- 1.3.6.1.4.1.1916.2.131.50.1.3.16.18.9.1
		wingCfgProfVpnCryptoEntry OBJECT-TYPE
			SYNTAX WingCfgProfVpnCryptoEntry
			MAX-ACCESS not-accessible
			STATUS current
			DESCRIPTION
				"An entry in the table."
			INDEX { wingCfgProfName, wingCfgProfVpnCryptoName }
			::= { wingCfgProfVpnCryptoTable 1 }

		
		WingCfgProfVpnCryptoEntry ::=
			SEQUENCE { 
				wingCfgProfVpnCryptoName
					WingIdentifier
			 }

		-- 1.3.6.1.4.1.1916.2.131.50.1.3.16.18.9.1.1
		wingCfgProfVpnCryptoName OBJECT-TYPE
			SYNTAX WingIdentifier
			MAX-ACCESS read-only
			STATUS current
			DESCRIPTION
				"
				
				XPath: /wing-config/profile[name=key1]/crypto_map[name=key2]/name"
			::= { wingCfgProfVpnCryptoEntry 1 }

		
		-- 1.3.6.1.4.1.1916.2.131.50.1.3.16.18.10
		wingCfgProfVpnCryptoInstTable OBJECT-TYPE
			SYNTAX SEQUENCE OF WingCfgProfVpnCryptoInstEntry
			MAX-ACCESS not-accessible
			STATUS current
			DESCRIPTION
				"
				
				/wing-config/profile/crypto_map/crypto_map_entry"
			::= { wingCfgProfVpn 10 }

		
		-- 1.3.6.1.4.1.1916.2.131.50.1.3.16.18.10.1
		wingCfgProfVpnCryptoInstEntry OBJECT-TYPE
			SYNTAX WingCfgProfVpnCryptoInstEntry
			MAX-ACCESS not-accessible
			STATUS current
			DESCRIPTION
				"An entry in the table."
			INDEX { wingCfgProfName, wingCfgProfVpnCryptoName, wingCfgProfVpnCryptoInstSequence }
			::= { wingCfgProfVpnCryptoInstTable 1 }

		
		WingCfgProfVpnCryptoInstEntry ::=
			SEQUENCE { 
				wingCfgProfVpnCryptoInstSequence
					Unsigned32,
				wingCfgProfVpnCryptoInstType
					DisplayString,
				wingCfgProfVpnCryptoInstIpAcl
					WingIdentifier,
				wingCfgProfVpnCryptoInstTransformSet
					WingIdentifier,
				wingCfgProfVpnCryptoInstLocalip
					DisplayString,
				wingCfgProfVpnCryptoInstPfs
					DisplayString,
				wingCfgProfVpnCryptoInstLifetimeSeconds
					Unsigned32,
				wingCfgProfVpnCryptoInstLifetimeKb
					Unsigned32,
				wingCfgProfVpnCryptoInstRemoteType
					DisplayString,
				wingCfgProfVpnCryptoInstModeconfig
					DisplayString,
				wingCfgProfVpnCryptoInstPeer
					DisplayString,
				wingCfgProfVpnCryptoInstProtocol
					DisplayString,
				wingCfgProfVpnCryptoInstMode
					DisplayString
			 }

		-- 1.3.6.1.4.1.1916.2.131.50.1.3.16.18.10.1.1
		wingCfgProfVpnCryptoInstSequence OBJECT-TYPE
			SYNTAX Unsigned32 (1..1000)
			MAX-ACCESS read-only
			STATUS current
			DESCRIPTION
				"
				
				XPath: /wing-config/profile[name=key1]/crypto_map[name=key2]/crypto_map_entry[sequence=key3]/sequence"
			::= { wingCfgProfVpnCryptoInstEntry 1 }

		
		-- 1.3.6.1.4.1.1916.2.131.50.1.3.16.18.10.1.3
		wingCfgProfVpnCryptoInstType OBJECT-TYPE
			SYNTAX DisplayString
			MAX-ACCESS read-write
			STATUS current
			DESCRIPTION
				"
				
				Values:
				site-to-site-auto,
				remote-vpn,
				site-to-site-manual
				
				XPath: /wing-config/profile[name=key1]/crypto_map[name=key2]/crypto_map_entry[sequence=key3]/type"
			DEFVAL { "site-to-site-auto" }
			::= { wingCfgProfVpnCryptoInstEntry 3 }

		
		-- 1.3.6.1.4.1.1916.2.131.50.1.3.16.18.10.1.4
		wingCfgProfVpnCryptoInstIpAcl OBJECT-TYPE
			SYNTAX WingIdentifier
			MAX-ACCESS read-write
			STATUS current
			DESCRIPTION
				"Access list for traffic that should be protected by IPsec.
				
				XPath: /wing-config/profile[name=key1]/crypto_map[name=key2]/crypto_map_entry[sequence=key3]/ip_acl"
			::= { wingCfgProfVpnCryptoInstEntry 4 }

		
		-- 1.3.6.1.4.1.1916.2.131.50.1.3.16.18.10.1.5
		wingCfgProfVpnCryptoInstTransformSet OBJECT-TYPE
			SYNTAX WingIdentifier
			MAX-ACCESS read-write
			STATUS current
			DESCRIPTION
				"NOTE: This column is valid only if wingCfgProfVpnCryptoInstType sets to site-to-site-auto or remote-vpn
				
				IPsec transform (encryption and hash algorithms) to use.
				
				XPath: /wing-config/profile[name=key1]/crypto_map[name=key2]/crypto_map_entry[sequence=key3]/ipsec_transform_set"
			::= { wingCfgProfVpnCryptoInstEntry 5 }

		
		-- 1.3.6.1.4.1.1916.2.131.50.1.3.16.18.10.1.6
		wingCfgProfVpnCryptoInstLocalip OBJECT-TYPE
			SYNTAX DisplayString
			MAX-ACCESS read-write
			STATUS current
			DESCRIPTION
				"Use this IP as local tunnel endpoint address, instead of the interface IP (Advanced Configuration).
				
				XPath: /wing-config/profile[name=key1]/crypto_map[name=key2]/crypto_map_entry[sequence=key3]/localip"
			::= { wingCfgProfVpnCryptoInstEntry 6 }

		
		-- 1.3.6.1.4.1.1916.2.131.50.1.3.16.18.10.1.7
		wingCfgProfVpnCryptoInstPfs OBJECT-TYPE
			SYNTAX DisplayString
			MAX-ACCESS read-write
			STATUS current
			DESCRIPTION
				"NOTE: This column is valid only if wingCfgProfVpnCryptoInstType sets to site-to-site-auto or remote-vpn
				
				Perfect Forward Secrecy.
				
				Values:
				none,
				2,
				5,
				14
				
				XPath: /wing-config/profile[name=key1]/crypto_map[name=key2]/crypto_map_entry[sequence=key3]/pfs"
			DEFVAL { "none" }
			::= { wingCfgProfVpnCryptoInstEntry 7 }

		
		-- 1.3.6.1.4.1.1916.2.131.50.1.3.16.18.10.1.8
		wingCfgProfVpnCryptoInstLifetimeSeconds OBJECT-TYPE
			SYNTAX Unsigned32 (120..2147483646)
			UNITS "seconds"
			MAX-ACCESS read-write
			STATUS current
			DESCRIPTION
				"Time-based IPsec security association lifetime.
				
				XPath: /wing-config/profile[name=key1]/crypto_map[name=key2]/crypto_map_entry[sequence=key3]/lifetime_seconds"
			::= { wingCfgProfVpnCryptoInstEntry 8 }

		
		-- 1.3.6.1.4.1.1916.2.131.50.1.3.16.18.10.1.9
		wingCfgProfVpnCryptoInstLifetimeKb OBJECT-TYPE
			SYNTAX Unsigned32 (500..2147483646)
			UNITS "kilobytes"
			MAX-ACCESS read-write
			STATUS current
			DESCRIPTION
				"Volume-based IPsec security association lifetime.
				
				XPath: /wing-config/profile[name=key1]/crypto_map[name=key2]/crypto_map_entry[sequence=key3]/lifetime_kb"
			::= { wingCfgProfVpnCryptoInstEntry 9 }

		
		-- 1.3.6.1.4.1.1916.2.131.50.1.3.16.18.10.1.10
		wingCfgProfVpnCryptoInstRemoteType OBJECT-TYPE
			SYNTAX DisplayString
			MAX-ACCESS read-write
			STATUS current
			DESCRIPTION
				"NOTE: This column is valid only if wingCfgProfVpnCryptoInstType sets to remote-vpn
				
				Remote VPN client type.
				
				Values:
				none,
				xauth
				
				XPath: /wing-config/profile[name=key1]/crypto_map[name=key2]/crypto_map_entry[sequence=key3]/remote_type"
			DEFVAL { "xauth" }
			::= { wingCfgProfVpnCryptoInstEntry 10 }

		
		-- 1.3.6.1.4.1.1916.2.131.50.1.3.16.18.10.1.11
		wingCfgProfVpnCryptoInstModeconfig OBJECT-TYPE
			SYNTAX DisplayString
			MAX-ACCESS read-write
			STATUS current
			DESCRIPTION
				"NOTE: This column is valid only if wingCfgProfVpnCryptoInstType sets to remote-vpn
				
				Choose the modeconfig method to use.
				
				Values:
				push,
				pull
				
				XPath: /wing-config/profile[name=key1]/crypto_map[name=key2]/crypto_map_entry[sequence=key3]/modeconfig"
			DEFVAL { "push" }
			::= { wingCfgProfVpnCryptoInstEntry 11 }

		
		-- 1.3.6.1.4.1.1916.2.131.50.1.3.16.18.10.1.12
		wingCfgProfVpnCryptoInstPeer OBJECT-TYPE
			SYNTAX DisplayString
			MAX-ACCESS read-write
			STATUS current
			DESCRIPTION
				"NOTE: This column is valid only if wingCfgProfVpnCryptoInstType sets to site-to-site-manual
				
				Allowed Encryption/Decryption peer.
				
				XPath: /wing-config/profile[name=key1]/crypto_map[name=key2]/crypto_map_entry[sequence=key3]/peer"
			::= { wingCfgProfVpnCryptoInstEntry 12 }

		
		-- 1.3.6.1.4.1.1916.2.131.50.1.3.16.18.10.1.13
		wingCfgProfVpnCryptoInstProtocol OBJECT-TYPE
			SYNTAX DisplayString
			MAX-ACCESS read-write
			STATUS current
			DESCRIPTION
				"NOTE: This column is valid only if wingCfgProfVpnCryptoInstType sets to site-to-site-manual
				
				Procotol to be used to the IPsec tunnel. It can be ESP or AH.
				
				Values:
				ESP,
				AH
				
				XPath: /wing-config/profile[name=key1]/crypto_map[name=key2]/crypto_map_entry[sequence=key3]/protocol"
			DEFVAL { "ESP" }
			::= { wingCfgProfVpnCryptoInstEntry 13 }

		
		-- 1.3.6.1.4.1.1916.2.131.50.1.3.16.18.10.1.14
		wingCfgProfVpnCryptoInstMode OBJECT-TYPE
			SYNTAX DisplayString
			MAX-ACCESS read-write
			STATUS current
			DESCRIPTION
				"NOTE: This column is valid only if wingCfgProfVpnCryptoInstType sets to site-to-site-manual
				
				IPsec tunnel type - tunnel or transport mode.
				
				Values:
				tunnel,
				transport
				
				XPath: /wing-config/profile[name=key1]/crypto_map[name=key2]/crypto_map_entry[sequence=key3]/mode"
			DEFVAL { "tunnel" }
			::= { wingCfgProfVpnCryptoInstEntry 14 }

		
		-- 1.3.6.1.4.1.1916.2.131.50.1.3.16.18.11
		wingCfgProfVpnCryptoInstPeerListTable OBJECT-TYPE
			SYNTAX SEQUENCE OF WingCfgProfVpnCryptoInstPeerListEntry
			MAX-ACCESS not-accessible
			STATUS current
			DESCRIPTION
				"NOTE: Columns under this table are valid only if wingCfgProfVpnCryptoInstType sets to site-to-site-auto or remote-vpn
				
				/wing-config/profile/crypto_map/crypto_map_entry"
			::= { wingCfgProfVpn 11 }

		
		-- 1.3.6.1.4.1.1916.2.131.50.1.3.16.18.11.1
		wingCfgProfVpnCryptoInstPeerListEntry OBJECT-TYPE
			SYNTAX WingCfgProfVpnCryptoInstPeerListEntry
			MAX-ACCESS not-accessible
			STATUS current
			DESCRIPTION
				"An entry in the table."
			INDEX { wingCfgProfName, wingCfgProfVpnCryptoName, wingCfgProfVpnCryptoInstSequence, wingCfgProfVpnCryptoInstPeerListPriority }
			::= { wingCfgProfVpnCryptoInstPeerListTable 1 }

		
		WingCfgProfVpnCryptoInstPeerListEntry ::=
			SEQUENCE { 
				wingCfgProfVpnCryptoInstPeerListPriority
					Unsigned32,
				wingCfgProfVpnCryptoInstPeerListType
					DisplayString,
				wingCfgProfVpnCryptoInstPeerListIkev1Peer
					WingIdentifier,
				wingCfgProfVpnCryptoInstPeerListIkev2Peer
					WingIdentifier
			 }

		-- 1.3.6.1.4.1.1916.2.131.50.1.3.16.18.11.1.1
		wingCfgProfVpnCryptoInstPeerListPriority OBJECT-TYPE
			SYNTAX Unsigned32 (1..3)
			MAX-ACCESS read-only
			STATUS current
			DESCRIPTION
				"List of prioritized redundant peers.
				
				XPath: /wing-config/profile[name=key1]/crypto_map[name=key2]/crypto_map_entry[sequence=key3]/peer_list[priority=key4]/priority"
			::= { wingCfgProfVpnCryptoInstPeerListEntry 1 }

		
		-- 1.3.6.1.4.1.1916.2.131.50.1.3.16.18.11.1.3
		wingCfgProfVpnCryptoInstPeerListType OBJECT-TYPE
			SYNTAX DisplayString
			MAX-ACCESS read-write
			STATUS current
			DESCRIPTION
				"Peer IKE type.
				
				Values:
				ikev1,
				ikev2
				
				XPath: /wing-config/profile[name=key1]/crypto_map[name=key2]/crypto_map_entry[sequence=key3]/peer_list[priority=key4]/type"
			::= { wingCfgProfVpnCryptoInstPeerListEntry 3 }

		
		-- 1.3.6.1.4.1.1916.2.131.50.1.3.16.18.11.1.4
		wingCfgProfVpnCryptoInstPeerListIkev1Peer OBJECT-TYPE
			SYNTAX WingIdentifier
			MAX-ACCESS read-write
			STATUS current
			DESCRIPTION
				"Name of the IKEv1 Peer.
				
				XPath: /wing-config/profile[name=key1]/crypto_map[name=key2]/crypto_map_entry[sequence=key3]/peer_list[priority=key4]/ikev1_peer"
			::= { wingCfgProfVpnCryptoInstPeerListEntry 4 }

		
		-- 1.3.6.1.4.1.1916.2.131.50.1.3.16.18.11.1.5
		wingCfgProfVpnCryptoInstPeerListIkev2Peer OBJECT-TYPE
			SYNTAX WingIdentifier
			MAX-ACCESS read-write
			STATUS current
			DESCRIPTION
				"Name of the IKEv2 Peer.
				
				XPath: /wing-config/profile[name=key1]/crypto_map[name=key2]/crypto_map_entry[sequence=key3]/peer_list[priority=key4]/ikev2_peer"
			::= { wingCfgProfVpnCryptoInstPeerListEntry 5 }

		
		-- 1.3.6.1.4.1.1916.2.131.50.1.3.16.18.12
		wingCfgProfVpnCryptoInstAhSessionTable OBJECT-TYPE
			SYNTAX SEQUENCE OF WingCfgProfVpnCryptoInstAhSessionEntry
			MAX-ACCESS not-accessible
			STATUS current
			DESCRIPTION
				"NOTE: Columns under this table are valid only if wingCfgProfVpnCryptoInstType sets to site-to-site-manual
				
				/wing-config/profile/crypto_map/crypto_map_entry/ah_session_keys"
			::= { wingCfgProfVpn 12 }

		
		-- 1.3.6.1.4.1.1916.2.131.50.1.3.16.18.12.1
		wingCfgProfVpnCryptoInstAhSessionEntry OBJECT-TYPE
			SYNTAX WingCfgProfVpnCryptoInstAhSessionEntry
			MAX-ACCESS not-accessible
			STATUS current
			DESCRIPTION
				"An entry in the table."
			INDEX { wingCfgProfName, wingCfgProfVpnCryptoName, wingCfgProfVpnCryptoInstSequence, wingCfgProfVpnCryptoInstAhSessionDirection }
			::= { wingCfgProfVpnCryptoInstAhSessionTable 1 }

		
		WingCfgProfVpnCryptoInstAhSessionEntry ::=
			SEQUENCE { 
				wingCfgProfVpnCryptoInstAhSessionDirection
					WingIdentifier,
				wingCfgProfVpnCryptoInstAhSessionSpi
					Unsigned32,
				wingCfgProfVpnCryptoInstAhSessionAuth
					DisplayString,
				wingCfgProfVpnCryptoInstAhSessionKey
					OCTET STRING
			 }

		-- 1.3.6.1.4.1.1916.2.131.50.1.3.16.18.12.1.1
		wingCfgProfVpnCryptoInstAhSessionDirection OBJECT-TYPE
			SYNTAX WingIdentifier
			MAX-ACCESS read-only
			STATUS current
			DESCRIPTION
				"Direction of the security association.
				
				Values:
				inbound,
				outbound
				
				XPath: /wing-config/profile[name=key1]/crypto_map[name=key2]/crypto_map_entry[sequence=key3]/ah_session_keys[direction=key4]/direction"
			::= { wingCfgProfVpnCryptoInstAhSessionEntry 1 }

		
		-- 1.3.6.1.4.1.1916.2.131.50.1.3.16.18.12.1.3
		wingCfgProfVpnCryptoInstAhSessionSpi OBJECT-TYPE
			SYNTAX Unsigned32 (256..4294967295)
			MAX-ACCESS read-write
			STATUS current
			DESCRIPTION
				"Security Parameter Index for Security Association.
				This should be unique for all Security Associations.
				
				XPath: /wing-config/profile[name=key1]/crypto_map[name=key2]/crypto_map_entry[sequence=key3]/ah_session_keys[direction=key4]/spi"
			::= { wingCfgProfVpnCryptoInstAhSessionEntry 3 }

		
		-- 1.3.6.1.4.1.1916.2.131.50.1.3.16.18.12.1.4
		wingCfgProfVpnCryptoInstAhSessionAuth OBJECT-TYPE
			SYNTAX DisplayString
			MAX-ACCESS read-write
			STATUS current
			DESCRIPTION
				"Authentication scheme used to validate identity.
				
				Values:
				md5,
				sha
				
				XPath: /wing-config/profile[name=key1]/crypto_map[name=key2]/crypto_map_entry[sequence=key3]/ah_session_keys[direction=key4]/auth_algo"
			DEFVAL { "sha" }
			::= { wingCfgProfVpnCryptoInstAhSessionEntry 4 }

		
		-- 1.3.6.1.4.1.1916.2.131.50.1.3.16.18.12.1.5
		wingCfgProfVpnCryptoInstAhSessionKey OBJECT-TYPE
			SYNTAX OCTET STRING (SIZE (8..512))
			MAX-ACCESS read-write
			STATUS current
			DESCRIPTION
				"Security association key value. The following key lengths
				(in hex characters) are required.ESP-MD5: 32,ESP-SHA: 40.
				
				XPath: /wing-config/profile[name=key1]/crypto_map[name=key2]/crypto_map_entry[sequence=key3]/ah_session_keys[direction=key4]/key"
			::= { wingCfgProfVpnCryptoInstAhSessionEntry 5 }

		
		-- 1.3.6.1.4.1.1916.2.131.50.1.3.16.18.13
		wingCfgProfVpnCryptoInstEspSessionTable OBJECT-TYPE
			SYNTAX SEQUENCE OF WingCfgProfVpnCryptoInstEspSessionEntry
			MAX-ACCESS not-accessible
			STATUS current
			DESCRIPTION
				"NOTE: Columns under this table are valid only if wingCfgProfVpnCryptoInstType sets to site-to-site-manual
				
				/wing-config/profile/crypto_map/crypto_map_entry/esp_session_keys"
			::= { wingCfgProfVpn 13 }

		
		-- 1.3.6.1.4.1.1916.2.131.50.1.3.16.18.13.1
		wingCfgProfVpnCryptoInstEspSessionEntry OBJECT-TYPE
			SYNTAX WingCfgProfVpnCryptoInstEspSessionEntry
			MAX-ACCESS not-accessible
			STATUS current
			DESCRIPTION
				"An entry in the table."
			INDEX { wingCfgProfName, wingCfgProfVpnCryptoName, wingCfgProfVpnCryptoInstSequence, wingCfgProfVpnCryptoInstEspSessionDirection }
			::= { wingCfgProfVpnCryptoInstEspSessionTable 1 }

		
		WingCfgProfVpnCryptoInstEspSessionEntry ::=
			SEQUENCE { 
				wingCfgProfVpnCryptoInstEspSessionDirection
					WingIdentifier,
				wingCfgProfVpnCryptoInstEspSessionSpi
					Unsigned32,
				wingCfgProfVpnCryptoInstEspSessionCipherAlgo
					DisplayString,
				wingCfgProfVpnCryptoInstEspSessionCipherKey
					OCTET STRING,
				wingCfgProfVpnCryptoInstEspSessionAuthAlgo
					DisplayString,
				wingCfgProfVpnCryptoInstEspSessionAuthKey
					OCTET STRING
			 }

		-- 1.3.6.1.4.1.1916.2.131.50.1.3.16.18.13.1.1
		wingCfgProfVpnCryptoInstEspSessionDirection OBJECT-TYPE
			SYNTAX WingIdentifier
			MAX-ACCESS read-only
			STATUS current
			DESCRIPTION
				"
				
				Values:
				inbound,
				outbound
				
				XPath: /wing-config/profile[name=key1]/crypto_map[name=key2]/crypto_map_entry[sequence=key3]/esp_session_keys[direction=key4]/direction"
			::= { wingCfgProfVpnCryptoInstEspSessionEntry 1 }

		
		-- 1.3.6.1.4.1.1916.2.131.50.1.3.16.18.13.1.3
		wingCfgProfVpnCryptoInstEspSessionSpi OBJECT-TYPE
			SYNTAX Unsigned32 (256..4294967295)
			MAX-ACCESS read-write
			STATUS current
			DESCRIPTION
				"Security Parameter Index for Security Association. This should be unique for all Security Associations.
				
				XPath: /wing-config/profile[name=key1]/crypto_map[name=key2]/crypto_map_entry[sequence=key3]/esp_session_keys[direction=key4]/spi"
			::= { wingCfgProfVpnCryptoInstEspSessionEntry 3 }

		
		-- 1.3.6.1.4.1.1916.2.131.50.1.3.16.18.13.1.4
		wingCfgProfVpnCryptoInstEspSessionCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /wing-config/profile[name=key1]/crypto_map[name=key2]/crypto_map_entry[sequence=key3]/esp_session_keys[direction=key4]/cipher_algo"
			DEFVAL { "aes-256" }
			::= { wingCfgProfVpnCryptoInstEspSessionEntry 4 }

		
		-- 1.3.6.1.4.1.1916.2.131.50.1.3.16.18.13.1.5
		wingCfgProfVpnCryptoInstEspSessionCipherKey OBJECT-TYPE
			SYNTAX OCTET STRING (SIZE (8..512))
			MAX-ACCESS read-write
			STATUS current
			DESCRIPTION
				"Security association key value. The following key lengths (in hex characters) are required .ESP-NULL: 0, ESP-DES: 16, ESP-3DES: 48, ESP-AES: 32, ESP-AES-192: 48, ESP-AES-256: 64
				
				XPath: /wing-config/profile[name=key1]/crypto_map[name=key2]/crypto_map_entry[sequence=key3]/esp_session_keys[direction=key4]/cipher_key"
			::= { wingCfgProfVpnCryptoInstEspSessionEntry 5 }

		
		-- 1.3.6.1.4.1.1916.2.131.50.1.3.16.18.13.1.6
		wingCfgProfVpnCryptoInstEspSessionAuthAlgo OBJECT-TYPE
			SYNTAX DisplayString
			MAX-ACCESS read-write
			STATUS current
			DESCRIPTION
				"Authentication scheme used to validate identity.
				
				Values:
				md5,
				sha
				
				XPath: /wing-config/profile[name=key1]/crypto_map[name=key2]/crypto_map_entry[sequence=key3]/esp_session_keys[direction=key4]/auth_algo"
			DEFVAL { "sha" }
			::= { wingCfgProfVpnCryptoInstEspSessionEntry 6 }

		
		-- 1.3.6.1.4.1.1916.2.131.50.1.3.16.18.13.1.7
		wingCfgProfVpnCryptoInstEspSessionAuthKey OBJECT-TYPE
			SYNTAX OCTET STRING (SIZE (8..512))
			MAX-ACCESS read-write
			STATUS current
			DESCRIPTION
				"Security association key value. The following key lengths (in hex characters) are required.ESP-MD5: 32,ESP-SHA: 40.
				
				XPath: /wing-config/profile[name=key1]/crypto_map[name=key2]/crypto_map_entry[sequence=key3]/esp_session_keys[direction=key4]/auth_key"
			::= { wingCfgProfVpnCryptoInstEspSessionEntry 7 }

		
		-- 1.3.6.1.4.1.1916.2.131.50.1.3.16.18.14
		wingCfgProfVpnIkev1RemoteTable OBJECT-TYPE
			SYNTAX SEQUENCE OF WingCfgProfVpnIkev1RemoteEntry
			MAX-ACCESS not-accessible
			STATUS current
			DESCRIPTION
				"
				
				/wing-config/profile/ikev1_remote_vpn"
			::= { wingCfgProfVpn 14 }

		
		-- 1.3.6.1.4.1.1916.2.131.50.1.3.16.18.14.1
		wingCfgProfVpnIkev1RemoteEntry OBJECT-TYPE
			SYNTAX WingCfgProfVpnIkev1RemoteEntry
			MAX-ACCESS not-accessible
			STATUS current
			DESCRIPTION
				"An entry in the table."
			INDEX { wingCfgProfName }
			::= { wingCfgProfVpnIkev1RemoteTable 1 }

		
		WingCfgProfVpnIkev1RemoteEntry ::=
			SEQUENCE { 
				wingCfgProfVpnIkev1RemoteAuthMethod
					DisplayString,
				wingCfgProfVpnIkev1RemoteAaaPolicy
					WingIdentifier,
				wingCfgProfVpnIkev1RemoteIpLocalPool
					DisplayString
			 }

		-- 1.3.6.1.4.1.1916.2.131.50.1.3.16.18.14.1.1
		wingCfgProfVpnIkev1RemoteAuthMethod OBJECT-TYPE
			SYNTAX DisplayString
			MAX-ACCESS read-write
			STATUS current
			DESCRIPTION
				"The authentication method used for Remove VPN client. It can be one of RADIUS or LOCAL.
				
				Values:
				radius,
				local
				
				XPath: /wing-config/profile[name=key1]/ikev1_remote_vpn/auth_method"
			DEFVAL { "local" }
			::= { wingCfgProfVpnIkev1RemoteEntry 1 }

		
		-- 1.3.6.1.4.1.1916.2.131.50.1.3.16.18.14.1.2
		wingCfgProfVpnIkev1RemoteAaaPolicy OBJECT-TYPE
			SYNTAX WingIdentifier
			MAX-ACCESS read-write
			STATUS current
			DESCRIPTION
				"AAA Policy to use for remote VPN clients.
				
				XPath: /wing-config/profile[name=key1]/ikev1_remote_vpn/aaa_policy"
			::= { wingCfgProfVpnIkev1RemoteEntry 2 }

		
		-- 1.3.6.1.4.1.1916.2.131.50.1.3.16.18.14.1.3
		wingCfgProfVpnIkev1RemoteIpLocalPool OBJECT-TYPE
			SYNTAX DisplayString
			MAX-ACCESS read-write
			STATUS current
			DESCRIPTION
				"The virtual IP pool for assigning IP addresses to remote VPN clients.
				
				XPath: /wing-config/profile[name=key1]/ikev1_remote_vpn/ip_local_pool"
			::= { wingCfgProfVpnIkev1RemoteEntry 3 }

		
		-- 1.3.6.1.4.1.1916.2.131.50.1.3.16.18.15
		wingCfgProfVpnIkev1RemoteLocalUsersTable OBJECT-TYPE
			SYNTAX SEQUENCE OF WingCfgProfVpnIkev1RemoteLocalUsersEntry
			MAX-ACCESS not-accessible
			STATUS current
			DESCRIPTION
				"
				
				/wing-config/profile/ikev1_remote_vpn/local_users"
			::= { wingCfgProfVpn 15 }

		
		-- 1.3.6.1.4.1.1916.2.131.50.1.3.16.18.15.1
		wingCfgProfVpnIkev1RemoteLocalUsersEntry OBJECT-TYPE
			SYNTAX WingCfgProfVpnIkev1RemoteLocalUsersEntry
			MAX-ACCESS not-accessible
			STATUS current
			DESCRIPTION
				"An entry in the table."
			INDEX { wingCfgProfName, wingCfgProfVpnIkev1RemoteLocalUsersName }
			::= { wingCfgProfVpnIkev1RemoteLocalUsersTable 1 }

		
		WingCfgProfVpnIkev1RemoteLocalUsersEntry ::=
			SEQUENCE { 
				wingCfgProfVpnIkev1RemoteLocalUsersName
					WingIdentifier,
				wingCfgProfVpnIkev1RemoteLocalUsersPassword
					DisplayString
			 }

		-- 1.3.6.1.4.1.1916.2.131.50.1.3.16.18.15.1.1
		wingCfgProfVpnIkev1RemoteLocalUsersName OBJECT-TYPE
			SYNTAX WingIdentifier
			MAX-ACCESS read-only
			STATUS current
			DESCRIPTION
				"User name
				
				XPath: /wing-config/profile[name=key1]/ikev1_remote_vpn/local_users[name=key2]/name"
			::= { wingCfgProfVpnIkev1RemoteLocalUsersEntry 1 }
-- TODO: Key length may exceed 128 sub-identifiers
-- add leaf with Integer as key to append as the last digit of OID
		
		-- 1.3.6.1.4.1.1916.2.131.50.1.3.16.18.15.1.3
		wingCfgProfVpnIkev1RemoteLocalUsersPassword OBJECT-TYPE
			SYNTAX DisplayString (SIZE (8..21))
			MAX-ACCESS read-write
			STATUS current
			DESCRIPTION
				"The password to authenticate the user.
				
				XPath: /wing-config/profile[name=key1]/ikev1_remote_vpn/local_users[name=key2]/password"
			::= { wingCfgProfVpnIkev1RemoteLocalUsersEntry 3 }

		
		-- 1.3.6.1.4.1.1916.2.131.50.1.3.16.18.16
		wingCfgProfVpnIkev1RemoteWinsTable OBJECT-TYPE
			SYNTAX SEQUENCE OF WingCfgProfVpnIkev1RemoteWinsEntry
			MAX-ACCESS not-accessible
			STATUS current
			DESCRIPTION
				"
				
				/wing-config/profile/ikev1_remote_vpn/wins"
			::= { wingCfgProfVpn 16 }

		
		-- 1.3.6.1.4.1.1916.2.131.50.1.3.16.18.16.1
		wingCfgProfVpnIkev1RemoteWinsEntry OBJECT-TYPE
			SYNTAX WingCfgProfVpnIkev1RemoteWinsEntry
			MAX-ACCESS not-accessible
			STATUS current
			DESCRIPTION
				"An entry in the table."
			INDEX { wingCfgProfName, wingCfgProfVpnIkev1RemoteWinsServerType }
			::= { wingCfgProfVpnIkev1RemoteWinsTable 1 }

		
		WingCfgProfVpnIkev1RemoteWinsEntry ::=
			SEQUENCE { 
				wingCfgProfVpnIkev1RemoteWinsServerType
					WingIdentifier,
				wingCfgProfVpnIkev1RemoteWinsServerIp
					DisplayString
			 }

		-- 1.3.6.1.4.1.1916.2.131.50.1.3.16.18.16.1.1
		wingCfgProfVpnIkev1RemoteWinsServerType OBJECT-TYPE
			SYNTAX WingIdentifier
			MAX-ACCESS read-only
			STATUS current
			DESCRIPTION
				"Primary or Secondary WINS server.
				
				Values:
				primary,
				secondary
				
				XPath: /wing-config/profile[name=key1]/ikev1_remote_vpn/wins[server_type=key2]/server_type"
			::= { wingCfgProfVpnIkev1RemoteWinsEntry 1 }

		
		-- 1.3.6.1.4.1.1916.2.131.50.1.3.16.18.16.1.3
		wingCfgProfVpnIkev1RemoteWinsServerIp OBJECT-TYPE
			SYNTAX DisplayString
			MAX-ACCESS read-write
			STATUS current
			DESCRIPTION
				"
				
				XPath: /wing-config/profile[name=key1]/ikev1_remote_vpn/wins[server_type=key2]/server_ip"
			::= { wingCfgProfVpnIkev1RemoteWinsEntry 3 }

		
		-- 1.3.6.1.4.1.1916.2.131.50.1.3.16.18.17
		wingCfgProfVpnIkev1RemoteNameServerTable OBJECT-TYPE
			SYNTAX SEQUENCE OF WingCfgProfVpnIkev1RemoteNameServerEntry
			MAX-ACCESS not-accessible
			STATUS current
			DESCRIPTION
				"
				
				/wing-config/profile/ikev1_remote_vpn/nameserver"
			::= { wingCfgProfVpn 17 }

		
		-- 1.3.6.1.4.1.1916.2.131.50.1.3.16.18.17.1
		wingCfgProfVpnIkev1RemoteNameServerEntry OBJECT-TYPE
			SYNTAX WingCfgProfVpnIkev1RemoteNameServerEntry
			MAX-ACCESS not-accessible
			STATUS current
			DESCRIPTION
				"An entry in the table."
			INDEX { wingCfgProfName, wingCfgProfVpnIkev1RemoteNameServerType }
			::= { wingCfgProfVpnIkev1RemoteNameServerTable 1 }

		
		WingCfgProfVpnIkev1RemoteNameServerEntry ::=
			SEQUENCE { 
				wingCfgProfVpnIkev1RemoteNameServerType
					WingIdentifier,
				wingCfgProfVpnIkev1RemoteNameServerIp
					DisplayString
			 }

		-- 1.3.6.1.4.1.1916.2.131.50.1.3.16.18.17.1.1
		wingCfgProfVpnIkev1RemoteNameServerType OBJECT-TYPE
			SYNTAX WingIdentifier
			MAX-ACCESS read-only
			STATUS current
			DESCRIPTION
				"Primary or Secondary Name server.
				
				Values:
				primary,
				secondary
				
				XPath: /wing-config/profile[name=key1]/ikev1_remote_vpn/nameserver[server_type=key2]/server_type"
			::= { wingCfgProfVpnIkev1RemoteNameServerEntry 1 }

		
		-- 1.3.6.1.4.1.1916.2.131.50.1.3.16.18.17.1.3
		wingCfgProfVpnIkev1RemoteNameServerIp OBJECT-TYPE
			SYNTAX DisplayString
			MAX-ACCESS read-write
			STATUS current
			DESCRIPTION
				"
				
				XPath: /wing-config/profile[name=key1]/ikev1_remote_vpn/nameserver[server_type=key2]/server_ip"
			::= { wingCfgProfVpnIkev1RemoteNameServerEntry 3 }

		
		-- 1.3.6.1.4.1.1916.2.131.50.1.3.16.18.18
		wingCfgProfVpnIkev2RemoteTable OBJECT-TYPE
			SYNTAX SEQUENCE OF WingCfgProfVpnIkev2RemoteEntry
			MAX-ACCESS not-accessible
			STATUS current
			DESCRIPTION
				"
				
				/wing-config/profile/ikev2_remote_vpn"
			::= { wingCfgProfVpn 18 }

		
		-- 1.3.6.1.4.1.1916.2.131.50.1.3.16.18.18.1
		wingCfgProfVpnIkev2RemoteEntry OBJECT-TYPE
			SYNTAX WingCfgProfVpnIkev2RemoteEntry
			MAX-ACCESS not-accessible
			STATUS current
			DESCRIPTION
				"An entry in the table."
			INDEX { wingCfgProfName }
			::= { wingCfgProfVpnIkev2RemoteTable 1 }

		
		WingCfgProfVpnIkev2RemoteEntry ::=
			SEQUENCE { 
				wingCfgProfVpnIkev2RemoteAuthMethod
					DisplayString,
				wingCfgProfVpnIkev2RemoteAaaPolicy
					WingIdentifier,
				wingCfgProfVpnIkev2RemoteIpLocalPool
					DisplayString,
				wingCfgProfVpnIkev2RemoteDhcpServerType
					DisplayString,
				wingCfgProfVpnIkev2RemoteDhcpServer
					DisplayString,
				wingCfgProfVpnIkev2RemoteDhcpServerGiaddr
					DisplayString,
				wingCfgProfVpnIkev2RemoteNetmask
					DisplayString
			 }

		-- 1.3.6.1.4.1.1916.2.131.50.1.3.16.18.18.1.1
		wingCfgProfVpnIkev2RemoteAuthMethod OBJECT-TYPE
			SYNTAX DisplayString
			MAX-ACCESS read-write
			STATUS current
			DESCRIPTION
				"The authentication method used for Remove VPN client. It can be one of RADIUS or LOCAL.
				
				Values:
				radius,
				local
				
				XPath: /wing-config/profile[name=key1]/ikev2_remote_vpn/auth_method"
			DEFVAL { "local" }
			::= { wingCfgProfVpnIkev2RemoteEntry 1 }

		
		-- 1.3.6.1.4.1.1916.2.131.50.1.3.16.18.18.1.2
		wingCfgProfVpnIkev2RemoteAaaPolicy OBJECT-TYPE
			SYNTAX WingIdentifier
			MAX-ACCESS read-write
			STATUS current
			DESCRIPTION
				"AAA Policy to use for remote VPN clients.
				
				XPath: /wing-config/profile[name=key1]/ikev2_remote_vpn/aaa_policy"
			::= { wingCfgProfVpnIkev2RemoteEntry 2 }

		
		-- 1.3.6.1.4.1.1916.2.131.50.1.3.16.18.18.1.3
		wingCfgProfVpnIkev2RemoteIpLocalPool OBJECT-TYPE
			SYNTAX DisplayString
			MAX-ACCESS read-write
			STATUS current
			DESCRIPTION
				"The virtual IP pool for assigning IP addresses to remote VPN clients.
				
				XPath: /wing-config/profile[name=key1]/ikev2_remote_vpn/ip_local_pool"
			::= { wingCfgProfVpnIkev2RemoteEntry 3 }

		
		-- 1.3.6.1.4.1.1916.2.131.50.1.3.16.18.18.1.4
		wingCfgProfVpnIkev2RemoteDhcpServerType OBJECT-TYPE
			SYNTAX DisplayString
			MAX-ACCESS read-write
			STATUS current
			DESCRIPTION
				"Select DHCP server type as IP or Hostname.
				
				Values:
				address,
				hostname,
				none
				
				XPath: /wing-config/profile[name=key1]/ikev2_remote_vpn/dhcp_server/dhcp_server_type"
			DEFVAL { "'none'" }
			::= { wingCfgProfVpnIkev2RemoteEntry 4 }

		
		-- 1.3.6.1.4.1.1916.2.131.50.1.3.16.18.18.1.5
		wingCfgProfVpnIkev2RemoteDhcpServer OBJECT-TYPE
			SYNTAX DisplayString (SIZE (1..64))
			MAX-ACCESS read-write
			STATUS current
			DESCRIPTION
				"Specify DHCP Server IP or Hostname.
				
				XPath: /wing-config/profile[name=key1]/ikev2_remote_vpn/dhcp_server/dhcp_server"
			::= { wingCfgProfVpnIkev2RemoteEntry 5 }

		
		-- 1.3.6.1.4.1.1916.2.131.50.1.3.16.18.18.1.6
		wingCfgProfVpnIkev2RemoteDhcpServerGiaddr OBJECT-TYPE
			SYNTAX DisplayString
			MAX-ACCESS read-write
			STATUS current
			DESCRIPTION
				"DHCP Relay Agent IP address
				
				XPath: /wing-config/profile[name=key1]/ikev2_remote_vpn/dhcp_server/giaddr"
			::= { wingCfgProfVpnIkev2RemoteEntry 6 }

		
		-- 1.3.6.1.4.1.1916.2.131.50.1.3.16.18.18.1.7
		wingCfgProfVpnIkev2RemoteNetmask OBJECT-TYPE
			SYNTAX DisplayString
			MAX-ACCESS read-write
			STATUS current
			DESCRIPTION
				"Netmask for remote VPN clients (IKEv2 only)
				
				XPath: /wing-config/profile[name=key1]/ikev2_remote_vpn/netmask"
			::= { wingCfgProfVpnIkev2RemoteEntry 7 }

		
		-- 1.3.6.1.4.1.1916.2.131.50.1.3.16.18.19
		wingCfgProfVpnIkev2RemoteLocalUsersTable OBJECT-TYPE
			SYNTAX SEQUENCE OF WingCfgProfVpnIkev2RemoteLocalUsersEntry
			MAX-ACCESS not-accessible
			STATUS current
			DESCRIPTION
				"
				
				/wing-config/profile/ikev2_remote_vpn/local_users"
			::= { wingCfgProfVpn 19 }

		
		-- 1.3.6.1.4.1.1916.2.131.50.1.3.16.18.19.1
		wingCfgProfVpnIkev2RemoteLocalUsersEntry OBJECT-TYPE
			SYNTAX WingCfgProfVpnIkev2RemoteLocalUsersEntry
			MAX-ACCESS not-accessible
			STATUS current
			DESCRIPTION
				"An entry in the table."
			INDEX { wingCfgProfName, wingCfgProfVpnIkev2RemoteLocalUsersName }
			::= { wingCfgProfVpnIkev2RemoteLocalUsersTable 1 }

		
		WingCfgProfVpnIkev2RemoteLocalUsersEntry ::=
			SEQUENCE { 
				wingCfgProfVpnIkev2RemoteLocalUsersName
					WingIdentifier,
				wingCfgProfVpnIkev2RemoteLocalUsersPassword
					DisplayString
			 }

		-- 1.3.6.1.4.1.1916.2.131.50.1.3.16.18.19.1.1
		wingCfgProfVpnIkev2RemoteLocalUsersName OBJECT-TYPE
			SYNTAX WingIdentifier
			MAX-ACCESS read-only
			STATUS current
			DESCRIPTION
				"User name
				
				XPath: /wing-config/profile[name=key1]/ikev2_remote_vpn/local_users[name=key2]/name"
			::= { wingCfgProfVpnIkev2RemoteLocalUsersEntry 1 }
-- TODO: Key length may exceed 128 sub-identifiers
-- add leaf with Integer as key to append as the last digit of OID
		
		-- 1.3.6.1.4.1.1916.2.131.50.1.3.16.18.19.1.3
		wingCfgProfVpnIkev2RemoteLocalUsersPassword OBJECT-TYPE
			SYNTAX DisplayString (SIZE (8..21))
			MAX-ACCESS read-write
			STATUS current
			DESCRIPTION
				"The password to authenticate the user.
				
				XPath: /wing-config/profile[name=key1]/ikev2_remote_vpn/local_users[name=key2]/password"
			::= { wingCfgProfVpnIkev2RemoteLocalUsersEntry 3 }

		
		-- 1.3.6.1.4.1.1916.2.131.50.1.3.16.18.20
		wingCfgProfVpnIkev2RemoteWinsTable OBJECT-TYPE
			SYNTAX SEQUENCE OF WingCfgProfVpnIkev2RemoteWinsEntry
			MAX-ACCESS not-accessible
			STATUS current
			DESCRIPTION
				"
				
				/wing-config/profile/ikev2_remote_vpn/wins"
			::= { wingCfgProfVpn 20 }

		
		-- 1.3.6.1.4.1.1916.2.131.50.1.3.16.18.20.1
		wingCfgProfVpnIkev2RemoteWinsEntry OBJECT-TYPE
			SYNTAX WingCfgProfVpnIkev2RemoteWinsEntry
			MAX-ACCESS not-accessible
			STATUS current
			DESCRIPTION
				"An entry in the table."
			INDEX { wingCfgProfName, wingCfgProfVpnIkev2RemoteWinsServerType }
			::= { wingCfgProfVpnIkev2RemoteWinsTable 1 }

		
		WingCfgProfVpnIkev2RemoteWinsEntry ::=
			SEQUENCE { 
				wingCfgProfVpnIkev2RemoteWinsServerType
					WingIdentifier,
				wingCfgProfVpnIkev2RemoteWinsServerIp
					DisplayString
			 }

		-- 1.3.6.1.4.1.1916.2.131.50.1.3.16.18.20.1.1
		wingCfgProfVpnIkev2RemoteWinsServerType OBJECT-TYPE
			SYNTAX WingIdentifier
			MAX-ACCESS read-only
			STATUS current
			DESCRIPTION
				"Primary or Secondary WINS server.
				
				Values:
				primary,
				secondary
				
				XPath: /wing-config/profile[name=key1]/ikev2_remote_vpn/wins[server_type=key2]/server_type"
			::= { wingCfgProfVpnIkev2RemoteWinsEntry 1 }

		
		-- 1.3.6.1.4.1.1916.2.131.50.1.3.16.18.20.1.3
		wingCfgProfVpnIkev2RemoteWinsServerIp OBJECT-TYPE
			SYNTAX DisplayString
			MAX-ACCESS read-write
			STATUS current
			DESCRIPTION
				"
				
				XPath: /wing-config/profile[name=key1]/ikev2_remote_vpn/wins[server_type=key2]/server_ip"
			::= { wingCfgProfVpnIkev2RemoteWinsEntry 3 }

		
		-- 1.3.6.1.4.1.1916.2.131.50.1.3.16.18.21
		wingCfgProfVpnIkev2RemoteNameServerTable OBJECT-TYPE
			SYNTAX SEQUENCE OF WingCfgProfVpnIkev2RemoteNameServerEntry
			MAX-ACCESS not-accessible
			STATUS current
			DESCRIPTION
				"
				
				/wing-config/profile/ikev2_remote_vpn/nameserver"
			::= { wingCfgProfVpn 21 }

		
		-- 1.3.6.1.4.1.1916.2.131.50.1.3.16.18.21.1
		wingCfgProfVpnIkev2RemoteNameServerEntry OBJECT-TYPE
			SYNTAX WingCfgProfVpnIkev2RemoteNameServerEntry
			MAX-ACCESS not-accessible
			STATUS current
			DESCRIPTION
				"An entry in the table."
			INDEX { wingCfgProfName, wingCfgProfVpnIkev2RemoteNameServerType }
			::= { wingCfgProfVpnIkev2RemoteNameServerTable 1 }

		
		WingCfgProfVpnIkev2RemoteNameServerEntry ::=
			SEQUENCE { 
				wingCfgProfVpnIkev2RemoteNameServerType
					WingIdentifier,
				wingCfgProfVpnIkev2RemoteNameServerIp
					DisplayString
			 }

		-- 1.3.6.1.4.1.1916.2.131.50.1.3.16.18.21.1.1
		wingCfgProfVpnIkev2RemoteNameServerType OBJECT-TYPE
			SYNTAX WingIdentifier
			MAX-ACCESS read-only
			STATUS current
			DESCRIPTION
				"Primary or Secondary Name server.
				
				Values:
				primary,
				secondary
				
				XPath: /wing-config/profile[name=key1]/ikev2_remote_vpn/nameserver[server_type=key2]/server_type"
			::= { wingCfgProfVpnIkev2RemoteNameServerEntry 1 }

		
		-- 1.3.6.1.4.1.1916.2.131.50.1.3.16.18.21.1.3
		wingCfgProfVpnIkev2RemoteNameServerIp OBJECT-TYPE
			SYNTAX DisplayString
			MAX-ACCESS read-write
			STATUS current
			DESCRIPTION
				"
				
				XPath: /wing-config/profile[name=key1]/ikev2_remote_vpn/nameserver[server_type=key2]/server_ip"
			::= { wingCfgProfVpnIkev2RemoteNameServerEntry 3 }

		
		-- 1.3.6.1.4.1.1916.2.131.50.1.3.16.18.22
		wingCfgProfVpnAutoIPSecSecureTable OBJECT-TYPE
			SYNTAX SEQUENCE OF WingCfgProfVpnAutoIPSecSecureEntry
			MAX-ACCESS not-accessible
			STATUS current
			DESCRIPTION
				"Description."
			::= { wingCfgProfVpn 22 }

		
		-- 1.3.6.1.4.1.1916.2.131.50.1.3.16.18.22.1
		wingCfgProfVpnAutoIPSecSecureEntry OBJECT-TYPE
			SYNTAX WingCfgProfVpnAutoIPSecSecureEntry
			MAX-ACCESS not-accessible
			STATUS current
			DESCRIPTION
				"Description."
			INDEX { wingCfgProfName }
			::= { wingCfgProfVpnAutoIPSecSecureTable 1 }

		
		WingCfgProfVpnAutoIPSecSecureEntry ::=
			SEQUENCE { 
				wingCfgProfVpnAutoIPSecSecureGroupId
					OCTET STRING,
				wingCfgProfVpnAutoIPSecSecureGroupIdAuthType
					DisplayString,
				wingCfgProfVpnAutoIPSecSecureGroupIdAuthKey
					DisplayString,
				wingCfgProfVpnAutoIPSecSecureRemoteGWIkeVersion
					DisplayString
			 }

		-- 1.3.6.1.4.1.1916.2.131.50.1.3.16.18.22.1.1
		wingCfgProfVpnAutoIPSecSecureGroupId OBJECT-TYPE
			SYNTAX OCTET STRING (SIZE (1..128))
			MAX-ACCESS read-write
			STATUS current
			DESCRIPTION
				"Group identity to use in IKE exchange for auto ipsec secure peers.
				
				XPath: /wing-config/profile[name=key1]/auto_ipsec_secure/group_id_auth_type_key/groupid_id"
			::= { wingCfgProfVpnAutoIPSecSecureEntry 1 }

		
		-- 1.3.6.1.4.1.1916.2.131.50.1.3.16.18.22.1.2
		wingCfgProfVpnAutoIPSecSecureGroupIdAuthType OBJECT-TYPE
			SYNTAX DisplayString
			MAX-ACCESS read-write
			STATUS current
			DESCRIPTION
				"The authentication type for auto ipsec secure peer authentication.
				
				XPath: /wing-config/profile[name=key1]/auto_ipsec_secure/group_id_auth_type_key/groupid_auth_type"
			::= { wingCfgProfVpnAutoIPSecSecureEntry 2 }

		
		-- 1.3.6.1.4.1.1916.2.131.50.1.3.16.18.22.1.3
		wingCfgProfVpnAutoIPSecSecureGroupIdAuthKey OBJECT-TYPE
			SYNTAX DisplayString (SIZE (8..21))
			MAX-ACCESS read-write
			STATUS current
			DESCRIPTION
				"The shared secret used for auto ipsec secure peer authentication.
				
				XPath: /wing-config/profile[name=key1]/auto_ipsec_secure/group_id_auth_type_key/groupid_auth_key"
			::= { wingCfgProfVpnAutoIPSecSecureEntry 3 }

		
		-- 1.3.6.1.4.1.1916.2.131.50.1.3.16.18.22.1.4
		wingCfgProfVpnAutoIPSecSecureRemoteGWIkeVersion OBJECT-TYPE
			SYNTAX DisplayString
			MAX-ACCESS read-write
			STATUS current
			DESCRIPTION
				"The ike version for auto ipsec secure authentication with ipsec gateway other than controllers.
				
				XPath: /wing-config/profile[name=key1]/auto_ipsec_secure/remotegw_ike_version"
			::= { wingCfgProfVpnAutoIPSecSecureEntry 4 }

		
-- /wing-config/profile/controller_host
		-- 1.3.6.1.4.1.1916.2.131.50.1.3.16.19
		wingCfgProfControllerHost OBJECT IDENTIFIER ::= { wingCfgProf 19 }

		
		-- 1.3.6.1.4.1.1916.2.131.50.1.3.16.19.1
		wingCfgProfControllerHostTable OBJECT-TYPE
			SYNTAX SEQUENCE OF WingCfgProfControllerHostEntry
			MAX-ACCESS not-accessible
			STATUS current
			DESCRIPTION
				"WLAN controller configuration
				
				/wing-config/profile/controller_host"
			::= { wingCfgProfControllerHost 1 }

		
		-- 1.3.6.1.4.1.1916.2.131.50.1.3.16.19.1.1
		wingCfgProfControllerHostEntry OBJECT-TYPE
			SYNTAX WingCfgProfControllerHostEntry
			MAX-ACCESS not-accessible
			STATUS current
			DESCRIPTION
				"An entry in the table."
			INDEX { wingCfgProfName, wingCfgProfControllerHostIndex }
			::= { wingCfgProfControllerHostTable 1 }

		
		WingCfgProfControllerHostEntry ::=
			SEQUENCE { 
				wingCfgProfControllerHostIndex
					WingIdentifier,
				wingCfgProfControllerHostRowStatus
					RowStatus,
				wingCfgProfControllerHostHost
					DisplayString,
				wingCfgProfControllerHostPool
					Unsigned32,
				wingCfgProfControllerHostLevel
					Unsigned32
			 }

		-- 1.3.6.1.4.1.1916.2.131.50.1.3.16.19.1.1.1
		wingCfgProfControllerHostIndex OBJECT-TYPE
			SYNTAX WingIdentifier
			MAX-ACCESS not-accessible
			STATUS current
			DESCRIPTION
				"Key of the table is a string in the following format:
				
				IP address or hostname of controller,Pool,Level"
			::= { wingCfgProfControllerHostEntry 1 }

		
		-- 1.3.6.1.4.1.1916.2.131.50.1.3.16.19.1.1.2
		wingCfgProfControllerHostRowStatus OBJECT-TYPE
			SYNTAX RowStatus
				{
				active(1),
				createAndGo(4),
				destroy(6)
				}
			MAX-ACCESS read-create
			STATUS current
			DESCRIPTION
				"The status of this conceptual row.
				
				XPath: /wing-config/profile[name=key1]/controller_host[controller_entry=key2]/row_status"
			::= { wingCfgProfControllerHostEntry 2 }

		
		-- 1.3.6.1.4.1.1916.2.131.50.1.3.16.19.1.1.3
		wingCfgProfControllerHostHost OBJECT-TYPE
			SYNTAX DisplayString
			MAX-ACCESS read-only
			STATUS current
			DESCRIPTION
				"IP address or hostname of controller.
				
				As this object is indirectly part of the key,
				to change its value the row must be deleted and created with
				the new key.
				
				XPath: /wing-config/profile[name=key1]/controller_host[controller_entry=key2]/host"
			::= { wingCfgProfControllerHostEntry 3 }

		
		-- 1.3.6.1.4.1.1916.2.131.50.1.3.16.19.1.1.4
		wingCfgProfControllerHostPool OBJECT-TYPE
			SYNTAX Unsigned32 (1..2)
			MAX-ACCESS read-only
			STATUS current
			DESCRIPTION
				"Pool this controller belongs to.
				
				As this object is indirectly part of the key,
				to change its value the row must be deleted and created with
				the new key.
				
				XPath: /wing-config/profile[name=key1]/controller_host[controller_entry=key2]/pool"
			DEFVAL { 1 }
			::= { wingCfgProfControllerHostEntry 4 }

		
		-- 1.3.6.1.4.1.1916.2.131.50.1.3.16.19.1.1.5
		wingCfgProfControllerHostLevel OBJECT-TYPE
			SYNTAX Unsigned32 (1..2)
			MAX-ACCESS read-only
			STATUS current
			DESCRIPTION
				"Routing level for controller link.
				
				As this object is indirectly part of the key,
				to change its value the row must be deleted and created with
				the new key.
				
				Values:
				1  Level 1 (local)
				2  Level 2 (inter-site)
				
				XPath: /wing-config/profile[name=key1]/controller_host[controller_entry=key2]/level"
			DEFVAL { 1 }
			::= { wingCfgProfControllerHostEntry 5 }

		
		-- 1.3.6.1.4.1.1916.2.131.50.1.3.16.20
		wingCfgProfDynRoute OBJECT IDENTIFIER ::= { wingCfgProf 20 }

		
		-- 1.3.6.1.4.1.1916.2.131.50.1.3.16.20.1
		wingCfgProfDynRouteOspfTable OBJECT-TYPE
			SYNTAX SEQUENCE OF WingCfgProfDynRouteOspfEntry
			MAX-ACCESS not-accessible
			STATUS current
			DESCRIPTION
				"Route Ospf Table.
				
				/wing-config/profile/dynamic_router_ospf"
			::= { wingCfgProfDynRoute 1 }

		
		-- 1.3.6.1.4.1.1916.2.131.50.1.3.16.20.1.1
		wingCfgProfDynRouteOspfEntry OBJECT-TYPE
			SYNTAX WingCfgProfDynRouteOspfEntry
			MAX-ACCESS not-accessible
			STATUS current
			DESCRIPTION
				"An entry in the table."
			INDEX { wingCfgProfName }
			::= { wingCfgProfDynRouteOspfTable 1 }

		
		WingCfgProfDynRouteOspfEntry ::=
			SEQUENCE { 
				wingCfgProfDynRouteOspfEnabled
					TruthValue,
				wingCfgProfDynRouteOspfRouterId
					OCTET STRING,
				wingCfgProfDynRouteOspfAutoCost
					Unsigned32,
				wingCfgProfDynRouteOspfPassiveAll
					TruthValue,
				wingCfgProfDynRouteOspfPassive
					DisplayString,
				wingCfgProfDynRouteOspfPassiveRemoved
					DisplayString,
				wingCfgProfDynRouteOspfVrrpStateCheck
					TruthValue,
				wingCfgProfDynRouteOspfDefaultRoutePriority
					Unsigned32,
				wingCfgProfDynRouteOspfNumRoutes
					Unsigned32,
				wingCfgProfDynRouteOspfRetryCount
					Unsigned32,
				wingCfgProfDynRouteOspfRetryTimeout
					Unsigned32,
				wingCfgProfDynRouteOspfResetTime
					Unsigned32
			 }

		-- 1.3.6.1.4.1.1916.2.131.50.1.3.16.20.1.1.1
		wingCfgProfDynRouteOspfEnabled OBJECT-TYPE
			SYNTAX TruthValue
			MAX-ACCESS read-write
			STATUS current
			DESCRIPTION
				"Dynamic routing protocol OSPF
				
				XPath: /wing-config/profile[name=key1]/dynamic_router_ospf/ospf"
			DEFVAL { false }
			::= { wingCfgProfDynRouteOspfEntry 1 }

		
		-- 1.3.6.1.4.1.1916.2.131.50.1.3.16.20.1.1.2
		wingCfgProfDynRouteOspfRouterId OBJECT-TYPE
			SYNTAX OCTET STRING
			MAX-ACCESS read-write
			STATUS current
			DESCRIPTION
				"Router-ID for this device. If Router-ID is not configured, system generates one and it can be viewed in statistics
				
				XPath: /wing-config/profile[name=key1]/dynamic_router_ospf/router_id"
			::= { wingCfgProfDynRouteOspfEntry 2 }

		
		-- 1.3.6.1.4.1.1916.2.131.50.1.3.16.20.1.1.3
		wingCfgProfDynRouteOspfAutoCost OBJECT-TYPE
			SYNTAX Unsigned32 (1..4294967)
			MAX-ACCESS read-write
			STATUS current
			DESCRIPTION
				"Specifies reference bandwidth to be used in Mbps to calculate OSPF interface cost if OSPF area is STUB or NSSA
				
				XPath: /wing-config/profile[name=key1]/dynamic_router_ospf/auto_cost"
			::= { wingCfgProfDynRouteOspfEntry 3 }

		
		-- 1.3.6.1.4.1.1916.2.131.50.1.3.16.20.1.1.4
		wingCfgProfDynRouteOspfPassiveAll OBJECT-TYPE
			SYNTAX TruthValue
			MAX-ACCESS read-write
			STATUS current
			DESCRIPTION
				"Configures all L3 interfaces as OSPF passive interface
				
				XPath: /wing-config/profile[name=key1]/dynamic_router_ospf/passive_all"
			DEFVAL { false }
			::= { wingCfgProfDynRouteOspfEntry 4 }

		
		-- 1.3.6.1.4.1.1916.2.131.50.1.3.16.20.1.1.5
		wingCfgProfDynRouteOspfPassive OBJECT-TYPE
			SYNTAX DisplayString
			MAX-ACCESS read-write
			STATUS current
			DESCRIPTION
				"Configures specified interface(s) as OSPF passive interface(s).
				
				XPath: /wing-config/profile[name=key1]/dynamic_router_ospf/passive"
			::= { wingCfgProfDynRouteOspfEntry 5 }

		
		-- 1.3.6.1.4.1.1916.2.131.50.1.3.16.20.1.1.6
		wingCfgProfDynRouteOspfPassiveRemoved OBJECT-TYPE
			SYNTAX DisplayString
			MAX-ACCESS read-write
			STATUS current
			DESCRIPTION
				"Configures specified interface(s) as OSPF NON-passive interface(s).
				
				XPath: /wing-config/profile[name=key1]/dynamic_router_ospf/passive_removed"
			REFERENCE
				"Configures specified interface(s) as OSPF NON-passive interface(s)."
			::= { wingCfgProfDynRouteOspfEntry 6 }

		
		-- 1.3.6.1.4.1.1916.2.131.50.1.3.16.20.1.1.7
		wingCfgProfDynRouteOspfVrrpStateCheck OBJECT-TYPE
			SYNTAX TruthValue
			MAX-ACCESS read-write
			STATUS current
			DESCRIPTION
				"Publish interface via OSPF only if the interface VRRP state is not BACKUP.
				
				XPath: /wing-config/profile[name=key1]/dynamic_router_ospf/vrrp_state_check"
			::= { wingCfgProfDynRouteOspfEntry 7 }

		
		-- 1.3.6.1.4.1.1916.2.131.50.1.3.16.20.1.1.8
		wingCfgProfDynRouteOspfDefaultRoutePriority OBJECT-TYPE
			SYNTAX Unsigned32 (1..8000)
			MAX-ACCESS read-write
			STATUS current
			DESCRIPTION
				"Priority for the default route learnt via OSPF.
				
				XPath: /wing-config/profile[name=key1]/dynamic_router_ospf/ospf_default_route_priority"
			DEFVAL { 7000 }
			::= { wingCfgProfDynRouteOspfEntry 8 }

		
		-- 1.3.6.1.4.1.1916.2.131.50.1.3.16.20.1.1.9
		wingCfgProfDynRouteOspfNumRoutes OBJECT-TYPE
			SYNTAX Unsigned32 (1..4294967295)
			MAX-ACCESS read-write
			STATUS current
			DESCRIPTION
				"Maximum number of OSPF routes allowed.
				
				XPath: /wing-config/profile[name=key1]/dynamic_router_ospf/route_limit/num_routes"
			::= { wingCfgProfDynRouteOspfEntry 9 }

		
		-- 1.3.6.1.4.1.1916.2.131.50.1.3.16.20.1.1.10
		wingCfgProfDynRouteOspfRetryCount OBJECT-TYPE
			SYNTAX Unsigned32 (1..32)
			MAX-ACCESS read-write
			STATUS current
			DESCRIPTION
				"Maximum number for which OSPF process will be reset before permanently shutting down OSPF.
				
				XPath: /wing-config/profile[name=key1]/dynamic_router_ospf/route_limit/retry_count"
			DEFVAL { 5 }
			::= { wingCfgProfDynRouteOspfEntry 10 }

		
		-- 1.3.6.1.4.1.1916.2.131.50.1.3.16.20.1.1.11
		wingCfgProfDynRouteOspfRetryTimeout OBJECT-TYPE
			SYNTAX Unsigned32 (1..3600)
			MAX-ACCESS read-write
			STATUS current
			DESCRIPTION
				"Time in seconds during which the OSPF process remains shut before attempting next retry.
				
				XPath: /wing-config/profile[name=key1]/dynamic_router_ospf/route_limit/retry_timeout"
			DEFVAL { 60 }
			::= { wingCfgProfDynRouteOspfEntry 11 }

		
		-- 1.3.6.1.4.1.1916.2.131.50.1.3.16.20.1.1.12
		wingCfgProfDynRouteOspfResetTime OBJECT-TYPE
			SYNTAX Unsigned32 (1..86400)
			MAX-ACCESS read-write
			STATUS current
			DESCRIPTION
				"Time in seconds after which retry-count is reset to zero.
				
				XPath: /wing-config/profile[name=key1]/dynamic_router_ospf/route_limit/reset_time"
			DEFVAL { 360 }
			::= { wingCfgProfDynRouteOspfEntry 12 }

		
		-- 1.3.6.1.4.1.1916.2.131.50.1.3.16.20.2
		wingCfgProfDynRouteOspfNetworkTable OBJECT-TYPE
			SYNTAX SEQUENCE OF WingCfgProfDynRouteOspfNetworkEntry
			MAX-ACCESS not-accessible
			STATUS current
			DESCRIPTION
				"Route Ospf Network Table
				
				/wing-config/profile/dynamic_router_cfg/ospf_network"
			::= { wingCfgProfDynRoute 2 }

		
		-- 1.3.6.1.4.1.1916.2.131.50.1.3.16.20.2.1
		wingCfgProfDynRouteOspfNetworkEntry OBJECT-TYPE
			SYNTAX WingCfgProfDynRouteOspfNetworkEntry
			MAX-ACCESS not-accessible
			STATUS current
			DESCRIPTION
				"An entry in the table."
			INDEX { wingCfgProfName, wingCfgProfDynRouteOspfNetwork }
			::= { wingCfgProfDynRouteOspfNetworkTable 1 }

		
		WingCfgProfDynRouteOspfNetworkEntry ::=
			SEQUENCE { 
				wingCfgProfDynRouteOspfNetwork
					WingIdentifier,
				wingCfgProfDynRouteOspfNetworkAreaId
					DisplayString
			 }

		-- 1.3.6.1.4.1.1916.2.131.50.1.3.16.20.2.1.1
		wingCfgProfDynRouteOspfNetwork OBJECT-TYPE
			SYNTAX WingIdentifier
			MAX-ACCESS read-only
			STATUS current
			DESCRIPTION
				"Networks that need to participate in OSPF
				
				XPath: /wing-config/profile[name=key1]/dynamic_router_ospf/ospf_network[network=key2]/network"
			::= { wingCfgProfDynRouteOspfNetworkEntry 1 }

		
		-- 1.3.6.1.4.1.1916.2.131.50.1.3.16.20.2.1.3
		wingCfgProfDynRouteOspfNetworkAreaId OBJECT-TYPE
			SYNTAX DisplayString
			MAX-ACCESS read-write
			STATUS current
			DESCRIPTION
				"OSPF area to which this network belongs; area is a 32 bit number, which can be represented as IPv4 address
				
				XPath: /wing-config/profile[name=key1]/dynamic_router_ospf/ospf_network[network=key2]/area_id"
			::= { wingCfgProfDynRouteOspfNetworkEntry 3 }

		
		-- 1.3.6.1.4.1.1916.2.131.50.1.3.16.20.3
		wingCfgProfDynRouteOspfAreaTable OBJECT-TYPE
			SYNTAX SEQUENCE OF WingCfgProfDynRouteOspfAreaEntry
			MAX-ACCESS not-accessible
			STATUS current
			DESCRIPTION
				"RouteOspfAreaTable
				
				/wing-config/profile/dynamic_router_cfg/ospf_area"
			::= { wingCfgProfDynRoute 3 }

		
		-- 1.3.6.1.4.1.1916.2.131.50.1.3.16.20.3.1
		wingCfgProfDynRouteOspfAreaEntry OBJECT-TYPE
			SYNTAX WingCfgProfDynRouteOspfAreaEntry
			MAX-ACCESS not-accessible
			STATUS current
			DESCRIPTION
				"An entry in the table."
			INDEX { wingCfgProfName, wingCfgProfDynRouteOspfAreaId }
			::= { wingCfgProfDynRouteOspfAreaTable 1 }

		
		WingCfgProfDynRouteOspfAreaEntry ::=
			SEQUENCE { 
				wingCfgProfDynRouteOspfAreaId
					WingIdentifier,
				wingCfgProfDynRouteOspfAreaAuthentication
					DisplayString,
				wingCfgProfDynRouteOspfAreaRange
					DisplayString,
				wingCfgProfDynRouteOspfAreaType
					DisplayString,
				wingCfgProfDynRouteOspfAreaDefaultCost
					Unsigned32,
				wingCfgProfDynRouteOspfAreaTranslateType
					DisplayString
			 }

		-- 1.3.6.1.4.1.1916.2.131.50.1.3.16.20.3.1.1
		wingCfgProfDynRouteOspfAreaId OBJECT-TYPE
			SYNTAX WingIdentifier
			MAX-ACCESS read-only
			STATUS current
			DESCRIPTION
				"OSPF area related parameters
                                 area id can be represented as IPv4 address or a 32 bit number between (0..4294967294).
				
				XPath: /wing-config/profile[name=key1]/dynamic_router_ospf/ospf_area[ospf_area_id=key2]/ospf_area_id"
			::= { wingCfgProfDynRouteOspfAreaEntry 1 }

		
		-- 1.3.6.1.4.1.1916.2.131.50.1.3.16.20.3.1.3
		wingCfgProfDynRouteOspfAreaAuthentication OBJECT-TYPE
			SYNTAX DisplayString
			MAX-ACCESS read-write
			STATUS current
			DESCRIPTION
				"OSPF authentication type
				
				Values:
				simple-password,
				message-digest,
				none
				
				XPath: /wing-config/profile[name=key1]/dynamic_router_ospf/ospf_area[ospf_area_id=key2]/authentication"
			DEFVAL { "none" }
			::= { wingCfgProfDynRouteOspfAreaEntry 3 }

		
		-- 1.3.6.1.4.1.1916.2.131.50.1.3.16.20.3.1.4
		wingCfgProfDynRouteOspfAreaRange OBJECT-TYPE
			SYNTAX DisplayString
			MAX-ACCESS read-only
			STATUS current
			DESCRIPTION
				"Specifies the routes matching address/mask for summarization
				
				XPath: /wing-config/profile[name=key1]/dynamic_router_ospf/ospf_area[ospf_area_id=key2]/range"
			::= { wingCfgProfDynRouteOspfAreaEntry 4 }

		
		-- 1.3.6.1.4.1.1916.2.131.50.1.3.16.20.3.1.5
		wingCfgProfDynRouteOspfAreaType OBJECT-TYPE
			SYNTAX DisplayString
			MAX-ACCESS read-write
			STATUS current
			DESCRIPTION
				"Type of this OSPF area
				
				Values:
				stub,
				totally-stub,
				nssa,
				totally-nssa,
				non-stub
				
				XPath: /wing-config/profile[name=key1]/dynamic_router_ospf/ospf_area[ospf_area_id=key2]/area_type/type"
			DEFVAL { "non-stub" }
			::= { wingCfgProfDynRouteOspfAreaEntry 5 }

		
		-- 1.3.6.1.4.1.1916.2.131.50.1.3.16.20.3.1.6
		wingCfgProfDynRouteOspfAreaDefaultCost OBJECT-TYPE
			SYNTAX Unsigned32 (1..16777215)
			MAX-ACCESS read-write
			STATUS current
			DESCRIPTION
				"Default summary cost that will be advertised if this are is stub
				
				XPath: /wing-config/profile[name=key1]/dynamic_router_ospf/ospf_area[ospf_area_id=key2]/area_type/default_cost"
			::= { wingCfgProfDynRouteOspfAreaEntry 6 }

		
		-- 1.3.6.1.4.1.1916.2.131.50.1.3.16.20.3.1.7
		wingCfgProfDynRouteOspfAreaTranslateType OBJECT-TYPE
			SYNTAX DisplayString
			MAX-ACCESS read-write
			STATUS current
			DESCRIPTION
				"Configures if/how LSA Type 7 message shall be translated
				
				Values:
				translate-always,
				translate-candidate,
				translate-never
				
				XPath: /wing-config/profile[name=key1]/dynamic_router_ospf/ospf_area[ospf_area_id=key2]/area_type/translate_type"
			::= { wingCfgProfDynRouteOspfAreaEntry 7 }

		
		-- 1.3.6.1.4.1.1916.2.131.50.1.3.16.20.4
		wingCfgProfDynRouteDefaultInfoTable OBJECT-TYPE
			SYNTAX SEQUENCE OF WingCfgProfDynRouteDefaultInfoEntry
			MAX-ACCESS not-accessible
			STATUS current
			DESCRIPTION
				"Description."
			::= { wingCfgProfDynRoute 4 }
-- Dyn Route Default Info.
-- 
-- XPath: /wing-config/device[mac=key1]/dynamic_router_ospf/default_information
		
		-- 1.3.6.1.4.1.1916.2.131.50.1.3.16.20.4.1
		wingCfgProfDynRouteDefaultInfoEntry OBJECT-TYPE
			SYNTAX WingCfgProfDynRouteDefaultInfoEntry
			MAX-ACCESS not-accessible
			STATUS current
			DESCRIPTION
				"An entry in the table."
			INDEX { wingCfgProfName }
			::= { wingCfgProfDynRouteDefaultInfoTable 1 }

		
		WingCfgProfDynRouteDefaultInfoEntry ::=
			SEQUENCE { 
				wingCfgProfDynRouteDefaultInfoOriginate
					TruthValue,
				wingCfgProfDynRouteDefaultInfoAlways
					TruthValue,
				wingCfgProfDynRouteDefaultInfoRtMetric
					Unsigned32,
				wingCfgProfDynRouteDefaultInfoRtMetricType
					DisplayString
			 }

		-- 1.3.6.1.4.1.1916.2.131.50.1.3.16.20.4.1.1
		wingCfgProfDynRouteDefaultInfoOriginate OBJECT-TYPE
			SYNTAX TruthValue
			MAX-ACCESS read-write
			STATUS current
			DESCRIPTION
				"Specifies whether default route should be distributed or not.
				
				XPath: /wing-config/profile[name=key1]/dynamic_router_ospf/default_information/originate"
			::= { wingCfgProfDynRouteDefaultInfoEntry 1 }

		
		-- 1.3.6.1.4.1.1916.2.131.50.1.3.16.20.4.1.2
		wingCfgProfDynRouteDefaultInfoAlways OBJECT-TYPE
			SYNTAX TruthValue
			MAX-ACCESS read-write
			STATUS current
			DESCRIPTION
				"Originate a default route even if one is not present in routing table.
				
				XPath: /wing-config/profile[name=key1]/dynamic_router_ospf/default_information/always"
			::= { wingCfgProfDynRouteDefaultInfoEntry 2 }

		
		-- 1.3.6.1.4.1.1916.2.131.50.1.3.16.20.4.1.3
		wingCfgProfDynRouteDefaultInfoRtMetric OBJECT-TYPE
			SYNTAX Unsigned32 (1..16777214)
			MAX-ACCESS read-write
			STATUS current
			DESCRIPTION
				"Metric for default route.
				
				XPath: /wing-config/profile[name=key1]/dynamic_router_ospf/default_information/default_rt_metric"
			::= { wingCfgProfDynRouteDefaultInfoEntry 3 }

		
		-- 1.3.6.1.4.1.1916.2.131.50.1.3.16.20.4.1.4
		wingCfgProfDynRouteDefaultInfoRtMetricType OBJECT-TYPE
			SYNTAX DisplayString
			MAX-ACCESS read-write
			STATUS current
			DESCRIPTION
				"OSPF exterior metric type for default route.
				
				XPath: /wing-config/profile[name=key1]/dynamic_router_ospf/default_information/default_rt_metric_type"
			::= { wingCfgProfDynRouteDefaultInfoEntry 4 }

		
		-- 1.3.6.1.4.1.1916.2.131.50.1.3.16.20.5
		wingCfgProfDynRouteRedistributeTable OBJECT-TYPE
			SYNTAX SEQUENCE OF WingCfgProfDynRouteRedistributeEntry
			MAX-ACCESS not-accessible
			STATUS current
			DESCRIPTION
				"
				
				/wing-config/profile/dynamic_router_cfg/redistribute"
			::= { wingCfgProfDynRoute 5 }

		
		-- 1.3.6.1.4.1.1916.2.131.50.1.3.16.20.5.1
		wingCfgProfDynRouteRedistributeEntry OBJECT-TYPE
			SYNTAX WingCfgProfDynRouteRedistributeEntry
			MAX-ACCESS not-accessible
			STATUS current
			DESCRIPTION
				"An entry in the table."
			INDEX { wingCfgProfName, wingCfgProfDynRouteRedistributeRouteType }
			::= { wingCfgProfDynRouteRedistributeTable 1 }

		
		WingCfgProfDynRouteRedistributeEntry ::=
			SEQUENCE { 
				wingCfgProfDynRouteRedistributeRouteType
					WingIdentifier,
				wingCfgProfDynRouteRedistributeMetric
					Unsigned32,
				wingCfgProfDynRouteRedistributeMetricType
					DisplayString
			 }

		-- 1.3.6.1.4.1.1916.2.131.50.1.3.16.20.5.1.1
		wingCfgProfDynRouteRedistributeRouteType OBJECT-TYPE
			SYNTAX WingIdentifier
			MAX-ACCESS read-only
			STATUS current
			DESCRIPTION
				"Type of redistributed type
				
				Values:
				connected,
				kernel,
				static
				
				XPath: /wing-config/profile[name=key1]/dynamic_router_ospf/redistribute[route_type=key2]/route_type"
			::= { wingCfgProfDynRouteRedistributeEntry 1 }

		
		-- 1.3.6.1.4.1.1916.2.131.50.1.3.16.20.5.1.3
		wingCfgProfDynRouteRedistributeMetric OBJECT-TYPE
			SYNTAX Unsigned32 (1..16777214)
			MAX-ACCESS read-write
			STATUS current
			DESCRIPTION
				"Metric for redistributed routes
				
				XPath: /wing-config/profile[name=key1]/dynamic_router_ospf/redistribute[route_type=key2]/metric"
			::= { wingCfgProfDynRouteRedistributeEntry 3 }

		
		-- 1.3.6.1.4.1.1916.2.131.50.1.3.16.20.5.1.4
		wingCfgProfDynRouteRedistributeMetricType OBJECT-TYPE
			SYNTAX DisplayString
			MAX-ACCESS read-write
			STATUS current
			DESCRIPTION
				"OSPF exterior metric type for redistributed routes
				
				Values:
				1,
				2
				
				XPath: /wing-config/profile[name=key1]/dynamic_router_ospf/redistribute[route_type=key2]/metric_type"
			::= { wingCfgProfDynRouteRedistributeEntry 4 }

		
		-- 1.3.6.1.4.1.1916.2.131.50.1.3.16.21
		wingCfgProfVrrp OBJECT IDENTIFIER ::= { wingCfgProf 21 }

		
		-- 1.3.6.1.4.1.1916.2.131.50.1.3.16.21.1
		wingCfgProfVrrpTable OBJECT-TYPE
			SYNTAX SEQUENCE OF WingCfgProfVrrpEntry
			MAX-ACCESS not-accessible
			STATUS current
			DESCRIPTION
				"
				
				/wing-config/profile"
			::= { wingCfgProfVrrp 1 }

		
		-- 1.3.6.1.4.1.1916.2.131.50.1.3.16.21.1.1
		wingCfgProfVrrpEntry OBJECT-TYPE
			SYNTAX WingCfgProfVrrpEntry
			MAX-ACCESS not-accessible
			STATUS current
			DESCRIPTION
				"An entry in the table."
			INDEX { wingCfgProfName }
			::= { wingCfgProfVrrpTable 1 }

		
		WingCfgProfVrrpEntry ::=
			SEQUENCE { 
				wingCfgProfVrrpVersion
					DisplayString
			 }

		-- 1.3.6.1.4.1.1916.2.131.50.1.3.16.21.1.1.1
		wingCfgProfVrrpVersion OBJECT-TYPE
			SYNTAX DisplayString
			MAX-ACCESS read-write
			STATUS current
			DESCRIPTION
				"VRRP version supported by the device
				
				Values:
				3
				
				XPath: /wing-config/profile[name=key1]/vrrp_version"
			DEFVAL { "2" }
			::= { wingCfgProfVrrpEntry 1 }

		
		-- 1.3.6.1.4.1.1916.2.131.50.1.3.16.21.2
		wingCfgProfVrrpGroupTable OBJECT-TYPE
			SYNTAX SEQUENCE OF WingCfgProfVrrpGroupEntry
			MAX-ACCESS not-accessible
			STATUS current
			DESCRIPTION
				"
				
				/wing-config/profile/vrrp_groups"
			::= { wingCfgProfVrrp 2 }

		
		-- 1.3.6.1.4.1.1916.2.131.50.1.3.16.21.2.1
		wingCfgProfVrrpGroupEntry OBJECT-TYPE
			SYNTAX WingCfgProfVrrpGroupEntry
			MAX-ACCESS not-accessible
			STATUS current
			DESCRIPTION
				"An entry in the table."
			INDEX { wingCfgProfName, wingCfgProfVrrpGroupVirtualRouterId }
			::= { wingCfgProfVrrpGroupTable 1 }

		
		WingCfgProfVrrpGroupEntry ::=
			SEQUENCE { 
				wingCfgProfVrrpGroupVirtualRouterId
					Unsigned32,
				wingCfgProfVrrpGroupDescription
					DisplayString,
				wingCfgProfVrrpGroupPriority
					Unsigned32,
				wingCfgProfVrrpGroupAdvertisementUnit
					DisplayString,
				wingCfgProfVrrpGroupAdvertisementIntervalV2
					Unsigned32,
				wingCfgProfVrrpGroupAdvertisementIntervalV2Msec
					Unsigned32,
				wingCfgProfVrrpGroupAdvertisementIntervalV3
					Unsigned32,
				wingCfgProfVrrpGroupPreempt
					TruthValue,
				wingCfgProfVrrpGroupPreemptDelay
					Unsigned32,
				wingCfgProfVrrpGroupCrmAction
					DisplayString,
				wingCfgProfVrrpGroupDeltaPriority
					Unsigned32,
				wingCfgProfVrrpGroupInterface
					DisplayString,
				wingCfgProfVrrpGroupSyncGroup
					TruthValue
			 }

		-- 1.3.6.1.4.1.1916.2.131.50.1.3.16.21.2.1.1
		wingCfgProfVrrpGroupVirtualRouterId OBJECT-TYPE
			SYNTAX Unsigned32 (1..255)
			MAX-ACCESS read-only
			STATUS current
			DESCRIPTION
				"Identifies the virtual router and used for associating VRRP packet with this field
				
				XPath: /wing-config/profile[name=key1]/vrrp_groups[virtual_router_id=key2]/virtual_router_id"
			::= { wingCfgProfVrrpGroupEntry 1 }

		
		-- 1.3.6.1.4.1.1916.2.131.50.1.3.16.21.2.1.3
		wingCfgProfVrrpGroupDescription OBJECT-TYPE
			SYNTAX DisplayString (SIZE (1..64))
			MAX-ACCESS read-write
			STATUS current
			DESCRIPTION
				"Assigns a text description to the VRRP group
				
				XPath: /wing-config/profile[name=key1]/vrrp_groups[virtual_router_id=key2]/description"
			::= { wingCfgProfVrrpGroupEntry 3 }

		
		-- 1.3.6.1.4.1.1916.2.131.50.1.3.16.21.2.1.4
		wingCfgProfVrrpGroupPriority OBJECT-TYPE
			SYNTAX Unsigned32 (1..254)
			MAX-ACCESS read-write
			STATUS current
			DESCRIPTION
				"the priority to be used for the virtual router master election process.  Higher values imply higher priority.
				
				XPath: /wing-config/profile[name=key1]/vrrp_groups[virtual_router_id=key2]/priority"
			DEFVAL { 100 }
			::= { wingCfgProfVrrpGroupEntry 4 }

		
		-- 1.3.6.1.4.1.1916.2.131.50.1.3.16.21.2.1.5
		wingCfgProfVrrpGroupAdvertisementUnit OBJECT-TYPE
			SYNTAX DisplayString
			MAX-ACCESS read-write
			STATUS current
			DESCRIPTION
				"unit of the advertisment interval
				
				Values:
				seconds,
				milliseconds,
				centiseconds
				
				XPath: /wing-config/profile[name=key1]/vrrp_groups[virtual_router_id=key2]/advertisement_interval/advertisement_unit"
			DEFVAL { "seconds" }
			::= { wingCfgProfVrrpGroupEntry 5 }

		
		-- 1.3.6.1.4.1.1916.2.131.50.1.3.16.21.2.1.6
		wingCfgProfVrrpGroupAdvertisementIntervalV2 OBJECT-TYPE
			SYNTAX Unsigned32 (1..255)
			UNITS "seconds"
			MAX-ACCESS read-write
			STATUS current
			DESCRIPTION
				"Time interval between VRRP advertisments
				
				XPath: /wing-config/profile[name=key1]/vrrp_groups[virtual_router_id=key2]/advertisement_interval/advertisement_interval_v2"
			DEFVAL { 1 }
			::= { wingCfgProfVrrpGroupEntry 6 }

		
		-- 1.3.6.1.4.1.1916.2.131.50.1.3.16.21.2.1.7
		wingCfgProfVrrpGroupAdvertisementIntervalV2Msec OBJECT-TYPE
			SYNTAX Unsigned32 (50..999)
			UNITS "milliseconds"
			MAX-ACCESS read-write
			STATUS current
			DESCRIPTION
				"Time interval between VRRP advertisments
				
				XPath: /wing-config/profile[name=key1]/vrrp_groups[virtual_router_id=key2]/advertisement_interval/advertisement_interval_v2_msec"
			::= { wingCfgProfVrrpGroupEntry 7 }

		
		-- 1.3.6.1.4.1.1916.2.131.50.1.3.16.21.2.1.8
		wingCfgProfVrrpGroupAdvertisementIntervalV3 OBJECT-TYPE
			SYNTAX Unsigned32 (1..4095)
			UNITS "centiseconds"
			MAX-ACCESS read-write
			STATUS current
			DESCRIPTION
				"Time interval between VRRP advertisments
				
				XPath: /wing-config/profile[name=key1]/vrrp_groups[virtual_router_id=key2]/advertisement_interval/advertisement_interval_v3"
			DEFVAL { 100 }
			::= { wingCfgProfVrrpGroupEntry 8 }

		
		-- 1.3.6.1.4.1.1916.2.131.50.1.3.16.21.2.1.9
		wingCfgProfVrrpGroupPreempt OBJECT-TYPE
			SYNTAX TruthValue
			MAX-ACCESS read-write
			STATUS current
			DESCRIPTION
				"Controls whether a higher priority backup router will preempt a lower priority master.
				
				XPath: /wing-config/profile[name=key1]/vrrp_groups[virtual_router_id=key2]/preemption/preempt"
			DEFVAL { true }
			::= { wingCfgProfVrrpGroupEntry 9 }

		
		-- 1.3.6.1.4.1.1916.2.131.50.1.3.16.21.2.1.10
		wingCfgProfVrrpGroupPreemptDelay OBJECT-TYPE
			SYNTAX Unsigned32 (1..65535)
			UNITS "seconds"
			MAX-ACCESS read-write
			STATUS current
			DESCRIPTION
				"Delay interval for pre-emption
				
				XPath: /wing-config/profile[name=key1]/vrrp_groups[virtual_router_id=key2]/preemption/preempt_delay"
			::= { wingCfgProfVrrpGroupEntry 10 }

		
		-- 1.3.6.1.4.1.1916.2.131.50.1.3.16.21.2.1.11
		wingCfgProfVrrpGroupCrmAction OBJECT-TYPE
			SYNTAX DisplayString
			MAX-ACCESS read-write
			STATUS current
			DESCRIPTION
				"Backup virtual router may raise its priority in case the critical resources connected via the master router fail so that
				
				Values:
				increment-priority,
				decrement-priority,
				none
				
				XPath: /wing-config/profile[name=key1]/vrrp_groups[virtual_router_id=key2]/crm_action"
			DEFVAL { "none" }
			::= { wingCfgProfVrrpGroupEntry 11 }

		
		-- 1.3.6.1.4.1.1916.2.131.50.1.3.16.21.2.1.12
		wingCfgProfVrrpGroupDeltaPriority OBJECT-TYPE
			SYNTAX Unsigned32 (1..253)
			MAX-ACCESS read-write
			STATUS current
			DESCRIPTION
				"The configured priority will be decremented by this value when the monitored interface state is down. In case of critical resource monitoring, the configured priority will be incremented by this value
				
				XPath: /wing-config/profile[name=key1]/vrrp_groups[virtual_router_id=key2]/delta_priority"
			::= { wingCfgProfVrrpGroupEntry 12 }

		
		-- 1.3.6.1.4.1.1916.2.131.50.1.3.16.21.2.1.13
		wingCfgProfVrrpGroupInterface OBJECT-TYPE
			SYNTAX DisplayString
			MAX-ACCESS read-write
			STATUS current
			DESCRIPTION
				"The SVI (VLAN only) interface on which VRRP will be running. This also enable/disable VRRP operations
				
				XPath: /wing-config/profile[name=key1]/vrrp_groups[virtual_router_id=key2]/interface"
			::= { wingCfgProfVrrpGroupEntry 13 }

		
		-- 1.3.6.1.4.1.1916.2.131.50.1.3.16.21.2.1.14
		wingCfgProfVrrpGroupSyncGroup OBJECT-TYPE
			SYNTAX TruthValue
			MAX-ACCESS read-write
			STATUS current
			DESCRIPTION
				"Make this group part of vrrp sync group. This triggers VRRP failover only when advertisement is not received from all the masters of the virtual routers that is part of this vrrp sync group
				
				XPath: /wing-config/profile[name=key1]/vrrp_groups[virtual_router_id=key2]/sync_group"
			DEFVAL { false }
			::= { wingCfgProfVrrpGroupEntry 14 }

		
		-- 1.3.6.1.4.1.1916.2.131.50.1.3.16.22
		wingCfgProfIgs OBJECT IDENTIFIER ::= { wingCfgProf 22 }

		
		-- 1.3.6.1.4.1.1916.2.131.50.1.3.16.22.1
		wingCfgProfIgsTable OBJECT-TYPE
			SYNTAX SEQUENCE OF WingCfgProfIgsEntry
			MAX-ACCESS not-accessible
			STATUS current
			DESCRIPTION
				"
				
				/wing-config/profile"
			::= { wingCfgProfIgs 1 }

		
		-- 1.3.6.1.4.1.1916.2.131.50.1.3.16.22.1.1
		wingCfgProfIgsEntry OBJECT-TYPE
			SYNTAX WingCfgProfIgsEntry
			MAX-ACCESS not-accessible
			STATUS current
			DESCRIPTION
				"An entry in the table."
			INDEX { wingCfgProfName }
			::= { wingCfgProfIgsTable 1 }

		
		WingCfgProfIgsEntry ::=
			SEQUENCE { 
				wingCfgProfIgsIpIgmpSnooping
					TruthValue,
				wingCfgProfIgsIpIgmpSnoopingForwardUnknownMulticast
					TruthValue,
				wingCfgProfIgsIpIgmpSnoopingQuerier
					TruthValue,
				wingCfgProfIgsIpIgmpSnoopingQuerierAddress
					DisplayString,
				wingCfgProfIgsIpIgmpSnoopingQuerierMaxResponseTime
					Unsigned32,
				wingCfgProfIgsIpIgmpSnoopingQuerierOtherQuerierTimerExpiry
					Unsigned32,
				wingCfgProfIgsIpIgmpSnoopingQuerierVersion
					Unsigned32,
				wingCfgProfIgsIpIgmpSnoopingQuerierQueryInterval
					Unsigned32,
				wingCfgProfIgsIpIgmpSnoopingQuerierRobustnessVariable
					Unsigned32
			 }

		-- 1.3.6.1.4.1.1916.2.131.50.1.3.16.22.1.1.1
		wingCfgProfIgsIpIgmpSnooping OBJECT-TYPE
			SYNTAX TruthValue
			MAX-ACCESS read-write
			STATUS current
			DESCRIPTION
				"Enable/Disable igmp snooping; if set to disable, then per vlan bridge configuration is ignored
				
				XPath: /wing-config/profile[name=key1]/ip_igmp_snooping"
			DEFVAL { true }
			::= { wingCfgProfIgsEntry 1 }

		
		-- 1.3.6.1.4.1.1916.2.131.50.1.3.16.22.1.1.2
		wingCfgProfIgsIpIgmpSnoopingForwardUnknownMulticast OBJECT-TYPE
			SYNTAX TruthValue
			MAX-ACCESS read-write
			STATUS current
			DESCRIPTION
				"Enable/Disable unknown multicast fowarding
				
				XPath: /wing-config/profile[name=key1]/ip_igmp_snooping_forward_unknown_multicast"
			DEFVAL { false }
			::= { wingCfgProfIgsEntry 2 }

		
		-- 1.3.6.1.4.1.1916.2.131.50.1.3.16.22.1.1.3
		wingCfgProfIgsIpIgmpSnoopingQuerier OBJECT-TYPE
			SYNTAX TruthValue
			MAX-ACCESS read-write
			STATUS current
			DESCRIPTION
				"Enable/Disable on board IGMP querier on the device
				
				XPath: /wing-config/profile[name=key1]/ip_igmp_snooping_querier"
			DEFVAL { false }
			::= { wingCfgProfIgsEntry 3 }

		
		-- 1.3.6.1.4.1.1916.2.131.50.1.3.16.22.1.1.4
		wingCfgProfIgsIpIgmpSnoopingQuerierAddress OBJECT-TYPE
			SYNTAX DisplayString
			MAX-ACCESS read-write
			STATUS current
			DESCRIPTION
				"IP Address used by IGMP querier
				
				XPath: /wing-config/profile[name=key1]/ip_igmp_snooping_querier_address"
			DEFVAL { "0.0.0.0" }
			::= { wingCfgProfIgsEntry 4 }

		
		-- 1.3.6.1.4.1.1916.2.131.50.1.3.16.22.1.1.5
		wingCfgProfIgsIpIgmpSnoopingQuerierMaxResponseTime OBJECT-TYPE
			SYNTAX Unsigned32 (1..25)
			UNITS "seconds"
			MAX-ACCESS read-write
			STATUS current
			DESCRIPTION
				"Maximum query response time
				
				XPath: /wing-config/profile[name=key1]/ip_igmp_snooping_querier_max_response_time"
			DEFVAL { 10 }
			::= { wingCfgProfIgsEntry 5 }

		
		-- 1.3.6.1.4.1.1916.2.131.50.1.3.16.22.1.1.6
		wingCfgProfIgsIpIgmpSnoopingQuerierOtherQuerierTimerExpiry OBJECT-TYPE
			SYNTAX Unsigned32 (60..300)
			UNITS "seconds"
			MAX-ACCESS read-write
			STATUS current
			DESCRIPTION
				"other querier time out value for the IGMP Querier
				
				XPath: /wing-config/profile[name=key1]/ip_igmp_snooping_querier_other_querier_timer_expiry"
			DEFVAL { 60 }
			::= { wingCfgProfIgsEntry 6 }

		
		-- 1.3.6.1.4.1.1916.2.131.50.1.3.16.22.1.1.7
		wingCfgProfIgsIpIgmpSnoopingQuerierVersion OBJECT-TYPE
			SYNTAX Unsigned32 (1..3)
			MAX-ACCESS read-write
			STATUS current
			DESCRIPTION
				"IGMP version for the querier
				
				XPath: /wing-config/profile[name=key1]/ip_igmp_snooping_querier_version"
			DEFVAL { 3 }
			::= { wingCfgProfIgsEntry 7 }

		
		-- 1.3.6.1.4.1.1916.2.131.50.1.3.16.22.1.1.8
		wingCfgProfIgsIpIgmpSnoopingQuerierQueryInterval OBJECT-TYPE
			SYNTAX Unsigned32 (1..18000)
			UNITS "seconds"
			MAX-ACCESS read-write
			STATUS current
			DESCRIPTION
				"
				
				XPath: /wing-config/profile[name=key1]/ip_igmp_snooping_querier_query_interval"
			DEFVAL { 60 }
			::= { wingCfgProfIgsEntry 8 }

		
		-- 1.3.6.1.4.1.1916.2.131.50.1.3.16.22.1.1.9
		wingCfgProfIgsIpIgmpSnoopingQuerierRobustnessVariable OBJECT-TYPE
			SYNTAX Unsigned32 (1..7)
			MAX-ACCESS read-write
			STATUS current
			DESCRIPTION
				"
				
				XPath: /wing-config/profile[name=key1]/ip_igmp_snooping_querier_robustness_variable"
			DEFVAL { 2 }
			::= { wingCfgProfIgsEntry 9 }

		
-- /wing-config/profile/critical_resources
		-- 1.3.6.1.4.1.1916.2.131.50.1.3.16.23
		wingCfgProfCriticalRes OBJECT IDENTIFIER ::= { wingCfgProf 23 }

		
		-- 1.3.6.1.4.1.1916.2.131.50.1.3.16.23.1
		wingCfgProfCriticalResMonitorTable OBJECT-TYPE
			SYNTAX SEQUENCE OF WingCfgProfCriticalResMonitorEntry
			MAX-ACCESS not-accessible
			STATUS current
			DESCRIPTION
				"
				
				/wing-config/profile"
			::= { wingCfgProfCriticalRes 1 }

		
		-- 1.3.6.1.4.1.1916.2.131.50.1.3.16.23.1.1
		wingCfgProfCriticalResMonitorEntry OBJECT-TYPE
			SYNTAX WingCfgProfCriticalResMonitorEntry
			MAX-ACCESS not-accessible
			STATUS current
			DESCRIPTION
				"An entry in the table."
			INDEX { wingCfgProfName }
			::= { wingCfgProfCriticalResMonitorTable 1 }

		
		WingCfgProfCriticalResMonitorEntry ::=
			SEQUENCE { 
				wingCfgProfCriticalResMonitorInt
					Unsigned32
			 }

		-- 1.3.6.1.4.1.1916.2.131.50.1.3.16.23.1.1.1
		wingCfgProfCriticalResMonitorInt OBJECT-TYPE
			SYNTAX Unsigned32 (5..86400)
			UNITS "seconds"
			MAX-ACCESS read-write
			STATUS current
			DESCRIPTION
				"Monitoring frequency
				
				XPath: /wing-config/profile[name=key1]/crm_monitor_interval"
			DEFVAL { 30 }
			::= { wingCfgProfCriticalResMonitorEntry 1 }

		
		-- 1.3.6.1.4.1.1916.2.131.50.1.3.16.23.2
		wingCfgProfCriticalResPolicyTable OBJECT-TYPE
			SYNTAX SEQUENCE OF WingCfgProfCriticalResPolicyEntry
			MAX-ACCESS not-accessible
			STATUS current
			DESCRIPTION
				"
				
				/wing-config/profile/critical_resources"
			::= { wingCfgProfCriticalRes 2 }

		
		-- 1.3.6.1.4.1.1916.2.131.50.1.3.16.23.2.1
		wingCfgProfCriticalResPolicyEntry OBJECT-TYPE
			SYNTAX WingCfgProfCriticalResPolicyEntry
			MAX-ACCESS not-accessible
			STATUS current
			DESCRIPTION
				"An entry in the table."
			INDEX { wingCfgProfName, wingCfgProfCriticalResPolicyVia }
			::= { wingCfgProfCriticalResPolicyTable 1 }

		
		WingCfgProfCriticalResPolicyEntry ::=
			SEQUENCE { 
				wingCfgProfCriticalResPolicyVia
					WingIdentifier,
				wingCfgProfCriticalResPolicyAnyAll
					DisplayString
			 }

		-- 1.3.6.1.4.1.1916.2.131.50.1.3.16.23.2.1.1
		wingCfgProfCriticalResPolicyVia OBJECT-TYPE
			SYNTAX WingIdentifier
			MAX-ACCESS read-only
			STATUS current
			DESCRIPTION
				"
				
				XPath: /wing-config/profile[name=key1]/critical_resources[via=key2]/via"
			::= { wingCfgProfCriticalResPolicyEntry 1 }

		
		-- 1.3.6.1.4.1.1916.2.131.50.1.3.16.23.2.1.3
		wingCfgProfCriticalResPolicyAnyAll OBJECT-TYPE
			SYNTAX DisplayString
			MAX-ACCESS read-write
			STATUS current
			DESCRIPTION
				"
				
				Values:
				any,
				all
				
				XPath: /wing-config/profile[name=key1]/critical_resources[via=key2]/any_all"
			DEFVAL { "any" }
			::= { wingCfgProfCriticalResPolicyEntry 3 }

		
		-- 1.3.6.1.4.1.1916.2.131.50.1.3.16.23.3
		wingCfgProfCriticalResourcesTable OBJECT-TYPE
			SYNTAX SEQUENCE OF WingCfgProfCriticalResourcesEntry
			MAX-ACCESS not-accessible
			STATUS current
			DESCRIPTION
				"
				
				/wing-config/profile/critical_resources/resources"
			::= { wingCfgProfCriticalRes 3 }

		
		-- 1.3.6.1.4.1.1916.2.131.50.1.3.16.23.3.1
		wingCfgProfCriticalResourcesEntry OBJECT-TYPE
			SYNTAX WingCfgProfCriticalResourcesEntry
			MAX-ACCESS not-accessible
			STATUS current
			DESCRIPTION
				"An entry in the table."
			INDEX { wingCfgProfName, wingCfgProfCriticalResPolicyVia, wingCfgProfCriticalResourcesAddr }
			::= { wingCfgProfCriticalResourcesTable 1 }

		
		WingCfgProfCriticalResourcesEntry ::=
			SEQUENCE { 
				wingCfgProfCriticalResourcesAddr
					WingIdentifier,
				wingCfgProfCriticalResourcesMonitorType
					DisplayString,
				wingCfgProfCriticalResourcesVlan
					Unsigned32,
				wingCfgProfCriticalResourcesPort
					DisplayString
			 }

		-- 1.3.6.1.4.1.1916.2.131.50.1.3.16.23.3.1.1
		wingCfgProfCriticalResourcesAddr OBJECT-TYPE
			SYNTAX WingIdentifier
			MAX-ACCESS read-only
			STATUS current
			DESCRIPTION
				"
				
				XPath: /wing-config/profile[name=key1]/critical_resources[via=key2]/resources[address=key3]/address"
			::= { wingCfgProfCriticalResourcesEntry 1 }

		
		-- 1.3.6.1.4.1.1916.2.131.50.1.3.16.23.3.1.3
		wingCfgProfCriticalResourcesMonitorType OBJECT-TYPE
			SYNTAX DisplayString
			MAX-ACCESS read-write
			STATUS current
			DESCRIPTION
				"
				
				Values:
				arp-only,
				arp-and-ping
				
				XPath: /wing-config/profile[name=key1]/critical_resources[via=key2]/resources[address=key3]/monitor_type"
			DEFVAL { "arp-and-ping" }
			::= { wingCfgProfCriticalResourcesEntry 3 }

		
		-- 1.3.6.1.4.1.1916.2.131.50.1.3.16.23.3.1.4
		wingCfgProfCriticalResourcesVlan OBJECT-TYPE
			SYNTAX Unsigned32 (1..4094)
			MAX-ACCESS read-write
			STATUS current
			DESCRIPTION
				"
				
				XPath: /wing-config/profile[name=key1]/critical_resources[via=key2]/resources[address=key3]/vlan"
			::= { wingCfgProfCriticalResourcesEntry 4 }

		
		-- 1.3.6.1.4.1.1916.2.131.50.1.3.16.23.3.1.5
		wingCfgProfCriticalResourcesPort OBJECT-TYPE
			SYNTAX DisplayString
			MAX-ACCESS read-write
			STATUS current
			DESCRIPTION
				"
				
				Values:
				ge1, ge2, ge3, ge4, ge5, ge6, ge7, ge8, xge1, xge2, fe1, fe2, fe3, fe4, me1, up1
				
				XPath: /wing-config/profile[name=key1]/critical_resources[via=key2]/resources[address=key3]/port"
			::= { wingCfgProfCriticalResourcesEntry 5 }

		
-- /wing-config/profile/l2tpv3
		-- 1.3.6.1.4.1.1916.2.131.50.1.3.16.24
		wingCfgProfl2tpv3 OBJECT IDENTIFIER ::= { wingCfgProf 24 }

		
-- /wing-config/profile/l2tpv3
		-- 1.3.6.1.4.1.1916.2.131.50.1.3.16.24.1
		wingCfgProfl2tpv3Table OBJECT-TYPE
			SYNTAX SEQUENCE OF WingCfgProfl2tpv3Entry
			MAX-ACCESS not-accessible
			STATUS current
			DESCRIPTION
				"/wing-config/profile/l2tpv3"
			::= { wingCfgProfl2tpv3 1 }

		
		-- 1.3.6.1.4.1.1916.2.131.50.1.3.16.24.1.1
		wingCfgProfl2tpv3Entry OBJECT-TYPE
			SYNTAX WingCfgProfl2tpv3Entry
			MAX-ACCESS not-accessible
			STATUS current
			DESCRIPTION
				"An entry in the table."
			INDEX { wingCfgProfName }
			::= { wingCfgProfl2tpv3Table 1 }

		
		WingCfgProfl2tpv3Entry ::=
			SEQUENCE { 
				wingCfgProfl2tpv3lUdpListenPort
					Unsigned32,
				wingCfgProfl2tpv3RouterId
					DisplayString,
				wingCfgProfl2tpv3HostName
					DisplayString,
				wingCfgProfl2tpv3InterTunnelBridging
					TruthValue
			 }

		-- 1.3.6.1.4.1.1916.2.131.50.1.3.16.24.1.1.1
		wingCfgProfl2tpv3lUdpListenPort OBJECT-TYPE
			SYNTAX Unsigned32
			MAX-ACCESS read-write
			STATUS current
			DESCRIPTION
				"The UDP port on which incoming requests are listened.
				
				XPath: /wing-config/profile[name=key1]/l2tpv3_udp_listen_port"
			::= { wingCfgProfl2tpv3Entry 1 }

		
		-- 1.3.6.1.4.1.1916.2.131.50.1.3.16.24.1.1.2
		wingCfgProfl2tpv3RouterId OBJECT-TYPE
			SYNTAX DisplayString
			MAX-ACCESS read-write
			STATUS current
			DESCRIPTION
				"Router Id used in AVP message for the tunnel.
				
				XPath: /wing-config/profile[name=key1]/l2tpv3_router_id"
			::= { wingCfgProfl2tpv3Entry 2 }

		
		-- 1.3.6.1.4.1.1916.2.131.50.1.3.16.24.1.1.3
		wingCfgProfl2tpv3HostName OBJECT-TYPE
			SYNTAX DisplayString
			MAX-ACCESS read-write
			STATUS current
			DESCRIPTION
				"Host name sent in AVP message for the tunnel.
				
				XPath: /wing-config/profile[name=key1]/l2tpv3_host_name"
			::= { wingCfgProfl2tpv3Entry 3 }

		
		-- 1.3.6.1.4.1.1916.2.131.50.1.3.16.24.1.1.4
		wingCfgProfl2tpv3InterTunnelBridging OBJECT-TYPE
			SYNTAX TruthValue
			MAX-ACCESS read-write
			STATUS current
			DESCRIPTION
				"Enable/Disable Bridge packets between tunnels.
				
				XPath: /wing-config/profile[name=key1]/l2tpv3_inter_tunnel_bridging"
			::= { wingCfgProfl2tpv3Entry 4 }

		
-- /wing-config/profile/l2tpv3_tunnel
		-- 1.3.6.1.4.1.1916.2.131.50.1.3.16.24.2
		wingCfgProfl2tpv3TunnelTable OBJECT-TYPE
			SYNTAX SEQUENCE OF WingCfgProfl2tpv3TunnelEntry
			MAX-ACCESS not-accessible
			STATUS current
			DESCRIPTION
				"/wing-config/profile/l2tpv3_tunnel"
			::= { wingCfgProfl2tpv3 2 }

		
		-- 1.3.6.1.4.1.1916.2.131.50.1.3.16.24.2.1
		wingCfgProfl2tpv3TunnelEntry OBJECT-TYPE
			SYNTAX WingCfgProfl2tpv3TunnelEntry
			MAX-ACCESS not-accessible
			STATUS current
			DESCRIPTION
				"An entry in the table."
			INDEX { wingCfgProfName, wingCfgProfl2tpv3TunnelName }
			::= { wingCfgProfl2tpv3TunnelTable 1 }

		
		WingCfgProfl2tpv3TunnelEntry ::=
			SEQUENCE { 
				wingCfgProfl2tpv3TunnelName
					WingIdentifier,
				wingCfgProfl2tpv3TunnelLocalIpAddrss
					DisplayString,
				wingCfgProfl2tpv3TunnelMtu
					Unsigned32,
				wingCfgProfl2tpv3TunnelUseTunnelPolicy
					DisplayString,
				wingCfgProfl2tpv3TunnelHostname
					DisplayString,
				wingCfgProfl2tpv3TunnelRouterId
					DisplayString
			 }

		-- 1.3.6.1.4.1.1916.2.131.50.1.3.16.24.2.1.1
		wingCfgProfl2tpv3TunnelName OBJECT-TYPE
			SYNTAX WingIdentifier
			MAX-ACCESS read-only
			STATUS current
			DESCRIPTION
				"tunnel name.
				
				XPath: /wing-config/profile[name=key1]/l2tpv3_tunnel[name=key2]/name"
			::= { wingCfgProfl2tpv3TunnelEntry 1 }

		
		-- 1.3.6.1.4.1.1916.2.131.50.1.3.16.24.2.1.3
		wingCfgProfl2tpv3TunnelLocalIpAddrss OBJECT-TYPE
			SYNTAX DisplayString
			MAX-ACCESS read-write
			STATUS current
			DESCRIPTION
				"Use this IP as local tunnel endpoint address, instead of the interface IP.
				
				XPath: /wing-config/profile[name=key1]/l2tpv3_tunnel[name=key2]/local_ip_address"
			::= { wingCfgProfl2tpv3TunnelEntry 3 }

		
		-- 1.3.6.1.4.1.1916.2.131.50.1.3.16.24.2.1.4
		wingCfgProfl2tpv3TunnelMtu OBJECT-TYPE
			SYNTAX Unsigned32
			MAX-ACCESS read-write
			STATUS current
			DESCRIPTION
				"MTU for the tunnel.
				
				XPath: /wing-config/profile[name=key1]/l2tpv3_tunnel[name=key2]/mtu"
			::= { wingCfgProfl2tpv3TunnelEntry 4 }

		
		-- 1.3.6.1.4.1.1916.2.131.50.1.3.16.24.2.1.5
		wingCfgProfl2tpv3TunnelUseTunnelPolicy OBJECT-TYPE
			SYNTAX DisplayString
			MAX-ACCESS read-write
			STATUS current
			DESCRIPTION
				"Policy used for the tunnel.
				
				XPath: /wing-config/profile[name=key1]/l2tpv3_tunnel[name=key2]/use_tunnel_policy"
			::= { wingCfgProfl2tpv3TunnelEntry 5 }

		
		-- 1.3.6.1.4.1.1916.2.131.50.1.3.16.24.2.1.6
		wingCfgProfl2tpv3TunnelHostname OBJECT-TYPE
			SYNTAX DisplayString
			MAX-ACCESS read-write
			STATUS current
			DESCRIPTION
				"Tunnel specific hostname.
				
				XPath: /wing-config/profile[name=key1]/l2tpv3_tunnel[name=key2]/tunnel_hostname"
			::= { wingCfgProfl2tpv3TunnelEntry 6 }

		
		-- 1.3.6.1.4.1.1916.2.131.50.1.3.16.24.2.1.7
		wingCfgProfl2tpv3TunnelRouterId OBJECT-TYPE
			SYNTAX DisplayString
			MAX-ACCESS read-write
			STATUS current
			DESCRIPTION
				"Local router-id
				
				XPath: /wing-config/profile[name=key1]/l2tpv3_tunnel[name=key2]/tunnel_router_id"
			::= { wingCfgProfl2tpv3TunnelEntry 7 }

		
-- /wing-config/profile/l2tpv3_tunnel/peer
		-- 1.3.6.1.4.1.1916.2.131.50.1.3.16.24.3
		wingCfgProfl2tpv3TunnelPeerTable OBJECT-TYPE
			SYNTAX SEQUENCE OF WingCfgProfl2tpv3TunnelPeerEntry
			MAX-ACCESS not-accessible
			STATUS current
			DESCRIPTION
				"/wing-config/profile/l2tpv3_tunnel/peer"
			::= { wingCfgProfl2tpv3 3 }

		
		-- 1.3.6.1.4.1.1916.2.131.50.1.3.16.24.3.1
		wingCfgProfl2tpv3TunnelPeerEntry OBJECT-TYPE
			SYNTAX WingCfgProfl2tpv3TunnelPeerEntry
			MAX-ACCESS not-accessible
			STATUS current
			DESCRIPTION
				"An entry in the table."
			INDEX { wingCfgProfName, wingCfgProfl2tpv3TunnelName, wingCfgProfl2tpv3TunnelPeerId }
			::= { wingCfgProfl2tpv3TunnelPeerTable 1 }

		
		WingCfgProfl2tpv3TunnelPeerEntry ::=
			SEQUENCE { 
				wingCfgProfl2tpv3TunnelPeerId
					Unsigned32,
				wingCfgProfl2tpv3TunnelPeerIp
					DisplayString,
				wingCfgProfl2tpv3TunnelPeerHostName
					DisplayString,
				wingCfgProfl2tpv3TunnelPeerRouterId
					DisplayString,
				wingCfgProfl2tpv3TunnelPeerEncapsulation
					DisplayString,
				wingCfgProfl2tpv3TunnelPeerUDPPort
					Unsigned32
			 }

		-- 1.3.6.1.4.1.1916.2.131.50.1.3.16.24.3.1.1
		wingCfgProfl2tpv3TunnelPeerId OBJECT-TYPE
			SYNTAX Unsigned32 (1..2)
			MAX-ACCESS read-only
			STATUS current
			DESCRIPTION
				"Primary peer to establish the tunnel and secondary peer for failover.
				
				XPath: /wing-config/profile[name=key1]/l2tpv3_tunnel[name=key2]/peer[peer_id=key3]/peer_id"
			::= { wingCfgProfl2tpv3TunnelPeerEntry 1 }

		
		-- 1.3.6.1.4.1.1916.2.131.50.1.3.16.24.3.1.3
		wingCfgProfl2tpv3TunnelPeerIp OBJECT-TYPE
			SYNTAX DisplayString
			MAX-ACCESS read-write
			STATUS current
			DESCRIPTION
				"Peer IP value.
				
				XPath: /wing-config/profile[name=key1]/l2tpv3_tunnel[name=key2]/peer[peer_id=key3]/ip"
			::= { wingCfgProfl2tpv3TunnelPeerEntry 3 }

		
		-- 1.3.6.1.4.1.1916.2.131.50.1.3.16.24.3.1.4
		wingCfgProfl2tpv3TunnelPeerHostName OBJECT-TYPE
			SYNTAX DisplayString
			MAX-ACCESS read-write
			STATUS current
			DESCRIPTION
				"Peer hostname.
				
				XPath: /wing-config/profile[name=key1]/l2tpv3_tunnel[name=key2]/peer[peer_id=key3]/hostname"
			::= { wingCfgProfl2tpv3TunnelPeerEntry 4 }

		
		-- 1.3.6.1.4.1.1916.2.131.50.1.3.16.24.3.1.5
		wingCfgProfl2tpv3TunnelPeerRouterId OBJECT-TYPE
			SYNTAX DisplayString
			MAX-ACCESS read-write
			STATUS current
			DESCRIPTION
				"Peer router-id.
				
				XPath: /wing-config/profile[name=key1]/l2tpv3_tunnel[name=key2]/peer[peer_id=key3]/router_id"
			::= { wingCfgProfl2tpv3TunnelPeerEntry 5 }

		
		-- 1.3.6.1.4.1.1916.2.131.50.1.3.16.24.3.1.6
		wingCfgProfl2tpv3TunnelPeerEncapsulation OBJECT-TYPE
			SYNTAX DisplayString
			MAX-ACCESS read-write
			STATUS current
			DESCRIPTION
				"Peer encapsulation protocol.
				
				XPath: /wing-config/profile[name=key1]/l2tpv3_tunnel[name=key2]/peer[peer_id=key3]/encapsulation"
			::= { wingCfgProfl2tpv3TunnelPeerEntry 6 }

		
		-- 1.3.6.1.4.1.1916.2.131.50.1.3.16.24.3.1.7
		wingCfgProfl2tpv3TunnelPeerUDPPort OBJECT-TYPE
			SYNTAX Unsigned32
			MAX-ACCESS read-write
			STATUS current
			DESCRIPTION
				"Peer UDP encapsualtion port.
				
				XPath: /wing-config/profile[name=key1]/l2tpv3_tunnel[name=key2]/peer[peer_id=key3]/udpport"
			::= { wingCfgProfl2tpv3TunnelPeerEntry 7 }

		
-- /wing-config/profile/l2tpv3_tunnel/session
		-- 1.3.6.1.4.1.1916.2.131.50.1.3.16.24.4
		wingCfgProfl2tpv3TunnelSessionTable OBJECT-TYPE
			SYNTAX SEQUENCE OF WingCfgProfl2tpv3TunnelSessionEntry
			MAX-ACCESS not-accessible
			STATUS current
			DESCRIPTION
				"/wing-config/profile/l2tpv3_tunnel/session"
			::= { wingCfgProfl2tpv3 4 }

		
		-- 1.3.6.1.4.1.1916.2.131.50.1.3.16.24.4.1
		wingCfgProfl2tpv3TunnelSessionEntry OBJECT-TYPE
			SYNTAX WingCfgProfl2tpv3TunnelSessionEntry
			MAX-ACCESS not-accessible
			STATUS current
			DESCRIPTION
				"An entry in the table."
			INDEX { wingCfgProfName, wingCfgProfl2tpv3TunnelName, wingCfgProfl2tpv3TunnelSessionName }
			::= { wingCfgProfl2tpv3TunnelSessionTable 1 }

		
		WingCfgProfl2tpv3TunnelSessionEntry ::=
			SEQUENCE { 
				wingCfgProfl2tpv3TunnelSessionName
					WingIdentifier,
				wingCfgProfl2tpv3TunnelSessionPseudoWireId
					Unsigned32,
				wingCfgProfl2tpv3TunnelSessionTrafficSourceType
					DisplayString,
				wingCfgProfl2tpv3TunnelSessionTrafficSourceValue
					Unsigned32,
				wingCfgProfl2tpv3TunnelSessionNativeVlan
					DisplayString
			 }

		-- 1.3.6.1.4.1.1916.2.131.50.1.3.16.24.4.1.1
		wingCfgProfl2tpv3TunnelSessionName OBJECT-TYPE
			SYNTAX WingIdentifier
			MAX-ACCESS read-only
			STATUS current
			DESCRIPTION
				"Name of the Session.
				
				XPath: /wing-config/profile[name=key1]/l2tpv3_tunnel[name=key2]/session[name=key3]/name"
			::= { wingCfgProfl2tpv3TunnelSessionEntry 1 }

		
		-- 1.3.6.1.4.1.1916.2.131.50.1.3.16.24.4.1.3
		wingCfgProfl2tpv3TunnelSessionPseudoWireId OBJECT-TYPE
			SYNTAX Unsigned32
			MAX-ACCESS read-write
			STATUS current
			DESCRIPTION
				"Pseudowire Id for the Session.
				
				XPath: /wing-config/profile[name=key1]/l2tpv3_tunnel[name=key2]/session[name=key3]/pseudowire_id"
			::= { wingCfgProfl2tpv3TunnelSessionEntry 3 }

		
		-- 1.3.6.1.4.1.1916.2.131.50.1.3.16.24.4.1.4
		wingCfgProfl2tpv3TunnelSessionTrafficSourceType OBJECT-TYPE
			SYNTAX DisplayString
			MAX-ACCESS read-write
			STATUS current
			DESCRIPTION
				"Tunneled traffic type.
				
				XPath: /wing-config/profile[name=key1]/l2tpv3_tunnel[name=key2]/session[name=key3]/traffic_source_type"
			::= { wingCfgProfl2tpv3TunnelSessionEntry 4 }

		
		-- 1.3.6.1.4.1.1916.2.131.50.1.3.16.24.4.1.5
		wingCfgProfl2tpv3TunnelSessionTrafficSourceValue OBJECT-TYPE
			SYNTAX Unsigned32
			MAX-ACCESS read-only
			STATUS current
			DESCRIPTION
				"The range of VLAN that is tunneled.
				
				XPath: /wing-config/profile[name=key1]/l2tpv3_tunnel[name=key2]/session[name=key3]/traffic_source_value"
			::= { wingCfgProfl2tpv3TunnelSessionEntry 5 }

		
		-- 1.3.6.1.4.1.1916.2.131.50.1.3.16.24.4.1.6
		wingCfgProfl2tpv3TunnelSessionNativeVlan OBJECT-TYPE
			SYNTAX DisplayString
			MAX-ACCESS read-write
			STATUS current
			DESCRIPTION
				"Vlan id which will not be tagged.
				
				XPath: /wing-config/profile[name=key1]/l2tpv3_tunnel[name=key2]/session[name=key3]/native_vlan"
			::= { wingCfgProfl2tpv3TunnelSessionEntry 6 }

		
-- /wing-config/profile/l2tpv3_manual_session
		-- 1.3.6.1.4.1.1916.2.131.50.1.3.16.24.5
		wingCfgProfl2tpv3ManualSessionTable OBJECT-TYPE
			SYNTAX SEQUENCE OF WingCfgProfl2tpv3ManualSessionEntry
			MAX-ACCESS not-accessible
			STATUS current
			DESCRIPTION
				"/wing-config/profile/l2tpv3_manual_session"
			::= { wingCfgProfl2tpv3 5 }

		
		-- 1.3.6.1.4.1.1916.2.131.50.1.3.16.24.5.1
		wingCfgProfl2tpv3ManualSessionEntry OBJECT-TYPE
			SYNTAX WingCfgProfl2tpv3ManualSessionEntry
			MAX-ACCESS not-accessible
			STATUS current
			DESCRIPTION
				"An entry in the table."
			INDEX { wingCfgProfName, wingCfgProfl2tpv3ManualSessionName }
			::= { wingCfgProfl2tpv3ManualSessionTable 1 }

		
		WingCfgProfl2tpv3ManualSessionEntry ::=
			SEQUENCE { 
				wingCfgProfl2tpv3ManualSessionName
					WingIdentifier,
				wingCfgProfl2tpv3ManualSessionLocalIpAddr
					DisplayString,
				wingCfgProfl2tpv3ManualSessionPeerIp
					DisplayString,
				wingCfgProfl2tpv3ManualSessionPeerEncapsulation
					DisplayString,
				wingCfgProfl2tpv3ManualSessionPeerUDPPort
					Unsigned32,
				wingCfgProfl2tpv3ManualSessionMtu
					Unsigned32,
				wingCfgProfl2tpv3ManualSessionTrafficSource
					DisplayString,
				wingCfgProfl2tpv3ManualSessionTrafficSourceValue
					Unsigned32,
				wingCfgProfl2tpv3ManualSessionNativeVlan
					DisplayString,
				wingCfgProfl2tpv3ManualSessionLocalSessionId
					Unsigned32,
				wingCfgProfl2tpv3ManualSessionRemoteSessionId
					Unsigned32
			 }

		-- 1.3.6.1.4.1.1916.2.131.50.1.3.16.24.5.1.1
		wingCfgProfl2tpv3ManualSessionName OBJECT-TYPE
			SYNTAX WingIdentifier
			MAX-ACCESS read-only
			STATUS current
			DESCRIPTION
				"Name of the session.
				
				XPath: /wing-config/profile[name=key1]/l2tpv3_manual_session[name=key2]/name"
			::= { wingCfgProfl2tpv3ManualSessionEntry 1 }

		
		-- 1.3.6.1.4.1.1916.2.131.50.1.3.16.24.5.1.3
		wingCfgProfl2tpv3ManualSessionLocalIpAddr OBJECT-TYPE
			SYNTAX DisplayString
			MAX-ACCESS read-write
			STATUS current
			DESCRIPTION
				"Use this IP as local tunnel endpoint address, instead of the interface IP.
				
				XPath: /wing-config/profile[name=key1]/l2tpv3_manual_session[name=key2]/local_ip_address"
			::= { wingCfgProfl2tpv3ManualSessionEntry 3 }

		
		-- 1.3.6.1.4.1.1916.2.131.50.1.3.16.24.5.1.4
		wingCfgProfl2tpv3ManualSessionPeerIp OBJECT-TYPE
			SYNTAX DisplayString
			MAX-ACCESS read-write
			STATUS current
			DESCRIPTION
				"Peer IP value.
				
				XPath: /wing-config/profile[name=key1]/l2tpv3_manual_session[name=key2]/peer/ip"
			::= { wingCfgProfl2tpv3ManualSessionEntry 4 }

		
		-- 1.3.6.1.4.1.1916.2.131.50.1.3.16.24.5.1.5
		wingCfgProfl2tpv3ManualSessionPeerEncapsulation OBJECT-TYPE
			SYNTAX DisplayString
			MAX-ACCESS read-write
			STATUS current
			DESCRIPTION
				"Peer encapsulation protocol.
				
				XPath: /wing-config/profile[name=key1]/l2tpv3_manual_session[name=key2]/peer/encapsulation"
			::= { wingCfgProfl2tpv3ManualSessionEntry 5 }

		
		-- 1.3.6.1.4.1.1916.2.131.50.1.3.16.24.5.1.6
		wingCfgProfl2tpv3ManualSessionPeerUDPPort OBJECT-TYPE
			SYNTAX Unsigned32
			MAX-ACCESS read-write
			STATUS current
			DESCRIPTION
				"Peer UDP encapsualtion port.
				
				XPath: /wing-config/profile[name=key1]/l2tpv3_manual_session[name=key2]/peer/udpport"
			::= { wingCfgProfl2tpv3ManualSessionEntry 6 }

		
		-- 1.3.6.1.4.1.1916.2.131.50.1.3.16.24.5.1.7
		wingCfgProfl2tpv3ManualSessionMtu OBJECT-TYPE
			SYNTAX Unsigned32
			MAX-ACCESS read-write
			STATUS current
			DESCRIPTION
				"MTU for the tunnel.
				
				XPath: /wing-config/profile[name=key1]/l2tpv3_manual_session[name=key2]/mtu"
			::= { wingCfgProfl2tpv3ManualSessionEntry 7 }

		
		-- 1.3.6.1.4.1.1916.2.131.50.1.3.16.24.5.1.8
		wingCfgProfl2tpv3ManualSessionTrafficSource OBJECT-TYPE
			SYNTAX DisplayString
			MAX-ACCESS read-write
			STATUS current
			DESCRIPTION
				"Tunneled traffic type.
				
				XPath: /wing-config/profile[name=key1]/l2tpv3_manual_session[name=key2]/traffic_source/traffic_source_type"
			::= { wingCfgProfl2tpv3ManualSessionEntry 8 }

		
		-- 1.3.6.1.4.1.1916.2.131.50.1.3.16.24.5.1.9
		wingCfgProfl2tpv3ManualSessionTrafficSourceValue OBJECT-TYPE
			SYNTAX Unsigned32
			MAX-ACCESS read-only
			STATUS current
			DESCRIPTION
				"The range of VLAN that is tunneled.
				
				XPath: /wing-config/profile[name=key1]/l2tpv3_manual_session[name=key2]/traffic_source/traffic_source_value"
			::= { wingCfgProfl2tpv3ManualSessionEntry 9 }

		
		-- 1.3.6.1.4.1.1916.2.131.50.1.3.16.24.5.1.10
		wingCfgProfl2tpv3ManualSessionNativeVlan OBJECT-TYPE
			SYNTAX DisplayString
			MAX-ACCESS read-write
			STATUS current
			DESCRIPTION
				"Vlan id which will not be tagged.
				
				XPath: /wing-config/profile[name=key1]/l2tpv3_manual_session[name=key2]/traffic_source/native_vlan"
			::= { wingCfgProfl2tpv3ManualSessionEntry 10 }

		
		-- 1.3.6.1.4.1.1916.2.131.50.1.3.16.24.5.1.11
		wingCfgProfl2tpv3ManualSessionLocalSessionId OBJECT-TYPE
			SYNTAX Unsigned32
			MAX-ACCESS read-write
			STATUS current
			DESCRIPTION
				"Local Session Id. Max limit is platform specific.
				
				XPath: /wing-config/profile[name=key1]/l2tpv3_manual_session[name=key2]/local_session_id"
			::= { wingCfgProfl2tpv3ManualSessionEntry 11 }

		
		-- 1.3.6.1.4.1.1916.2.131.50.1.3.16.24.5.1.12
		wingCfgProfl2tpv3ManualSessionRemoteSessionId OBJECT-TYPE
			SYNTAX Unsigned32
			MAX-ACCESS read-write
			STATUS current
			DESCRIPTION
				"Remote Session Id.
				
				XPath: /wing-config/profile[name=key1]/l2tpv3_manual_session[name=key2]/remote_session_id"
			::= { wingCfgProfl2tpv3ManualSessionEntry 12 }

		
-- /wing-config/profile/l2tpv3_manual_session/cookie
		-- 1.3.6.1.4.1.1916.2.131.50.1.3.16.24.6
		wingCfgProfl2tpv3ManualSessionCookieTable OBJECT-TYPE
			SYNTAX SEQUENCE OF WingCfgProfl2tpv3ManualSessionCookieEntry
			MAX-ACCESS not-accessible
			STATUS current
			DESCRIPTION
				"/wing-config/profile/l2tpv3_manual_session/cookie"
			::= { wingCfgProfl2tpv3 6 }

		
		-- 1.3.6.1.4.1.1916.2.131.50.1.3.16.24.6.1
		wingCfgProfl2tpv3ManualSessionCookieEntry OBJECT-TYPE
			SYNTAX WingCfgProfl2tpv3ManualSessionCookieEntry
			MAX-ACCESS not-accessible
			STATUS current
			DESCRIPTION
				"An entry in the table."
			INDEX { wingCfgProfName, wingCfgProfl2tpv3ManualSessionName, wingCfgProfl2tpv3ManualSessionCookieEndpoint }
			::= { wingCfgProfl2tpv3ManualSessionCookieTable 1 }

		
		WingCfgProfl2tpv3ManualSessionCookieEntry ::=
			SEQUENCE { 
				wingCfgProfl2tpv3ManualSessionCookieEndpoint
					WingIdentifier,
				wingCfgProfl2tpv3ManualSessionCookieSize
					DisplayString,
				wingCfgProfl2tpv3ManualSessionCookieVal1
					DisplayString,
				wingCfgProfl2tpv3ManualSessionCookieVal2
					DisplayString
			 }

		-- 1.3.6.1.4.1.1916.2.131.50.1.3.16.24.6.1.1
		wingCfgProfl2tpv3ManualSessionCookieEndpoint OBJECT-TYPE
			SYNTAX WingIdentifier
			MAX-ACCESS read-only
			STATUS current
			DESCRIPTION
				"Local or Remote endpoint.
				
				XPath: /wing-config/profile[name=key1]/l2tpv3_manual_session[name=key2]/cookie[endpoint=key3]/endpoint"
			::= { wingCfgProfl2tpv3ManualSessionCookieEntry 1 }

		
		-- 1.3.6.1.4.1.1916.2.131.50.1.3.16.24.6.1.3
		wingCfgProfl2tpv3ManualSessionCookieSize OBJECT-TYPE
			SYNTAX DisplayString
			MAX-ACCESS read-write
			STATUS current
			DESCRIPTION
				"Cookie Size  0 or 4 or 8.
				
				XPath: /wing-config/profile[name=key1]/l2tpv3_manual_session[name=key2]/cookie[endpoint=key3]/cookie_size"
			::= { wingCfgProfl2tpv3ManualSessionCookieEntry 3 }

		
		-- 1.3.6.1.4.1.1916.2.131.50.1.3.16.24.6.1.4
		wingCfgProfl2tpv3ManualSessionCookieVal1 OBJECT-TYPE
			SYNTAX DisplayString
			MAX-ACCESS read-write
			STATUS current
			DESCRIPTION
				"cookie value firstword.
				
				XPath: /wing-config/profile[name=key1]/l2tpv3_manual_session[name=key2]/cookie[endpoint=key3]/cookie_val_1"
			::= { wingCfgProfl2tpv3ManualSessionCookieEntry 4 }

		
		-- 1.3.6.1.4.1.1916.2.131.50.1.3.16.24.6.1.5
		wingCfgProfl2tpv3ManualSessionCookieVal2 OBJECT-TYPE
			SYNTAX DisplayString
			MAX-ACCESS read-write
			STATUS current
			DESCRIPTION
				"cookie value secondword.
				
				XPath: /wing-config/profile[name=key1]/l2tpv3_manual_session[name=key2]/cookie[endpoint=key3]/cookie_val_2"
			::= { wingCfgProfl2tpv3ManualSessionCookieEntry 5 }

		
		-- 1.3.6.1.4.1.1916.2.131.50.1.3.16.25
		wingCfgProfMcx OBJECT IDENTIFIER ::= { wingCfgProf 25 }

		
		-- 1.3.6.1.4.1.1916.2.131.50.1.3.16.25.1
		wingCfgProfMeshpointDevTable OBJECT-TYPE
			SYNTAX SEQUENCE OF WingCfgProfMeshpointDevEntry
			MAX-ACCESS not-accessible
			STATUS current
			DESCRIPTION
				"
				
				/wing-config/profile/meshpoint_device"
			::= { wingCfgProfMcx 1 }

		
		-- 1.3.6.1.4.1.1916.2.131.50.1.3.16.25.1.1
		wingCfgProfMeshpointDevEntry OBJECT-TYPE
			SYNTAX WingCfgProfMeshpointDevEntry
			MAX-ACCESS not-accessible
			STATUS current
			DESCRIPTION
				"An entry in the table."
			INDEX { wingCfgProfName, wingCfgProfMeshpointDevName }
			::= { wingCfgProfMeshpointDevTable 1 }

		
		WingCfgProfMeshpointDevEntry ::=
			SEQUENCE { 
				wingCfgProfMeshpointDevName
					WingIdentifier,
				wingCfgProfMeshpointDevIsRootDev
					DisplayString,
				wingCfgProfMeshpointDevPreferredRoot
					DisplayString,
				wingCfgProfMeshpointDevPreferredNeighbor
					MacAddress,
				wingCfgProfMeshpointDevPreferredIf
					DisplayString,
				wingCfgProfMeshpointDevPathMethod
					DisplayString
			 }

		-- 1.3.6.1.4.1.1916.2.131.50.1.3.16.25.1.1.1
		wingCfgProfMeshpointDevName OBJECT-TYPE
			SYNTAX WingIdentifier
			MAX-ACCESS read-only
			STATUS current
			DESCRIPTION
				"
				
				XPath: /wing-config/profile[name=key1]/meshpoint_device[name=key2]/name"
			::= { wingCfgProfMeshpointDevEntry 1 }

		
		-- 1.3.6.1.4.1.1916.2.131.50.1.3.16.25.1.1.3
		wingCfgProfMeshpointDevIsRootDev OBJECT-TYPE
			SYNTAX DisplayString
			MAX-ACCESS read-write
			STATUS current
			DESCRIPTION
				"Overrides whether the meshpoint is a root or not
				
				Values:
				none,
				true,
				false
				
				XPath: /wing-config/profile[name=key1]/meshpoint_device[name=key2]/is_root_dev"
			DEFVAL { "none" }
			::= { wingCfgProfMeshpointDevEntry 3 }

		
		-- 1.3.6.1.4.1.1916.2.131.50.1.3.16.25.1.1.4
		wingCfgProfMeshpointDevPreferredRoot OBJECT-TYPE
			SYNTAX DisplayString
			MAX-ACCESS read-write
			STATUS current
			DESCRIPTION
				"Preferred root MAC address
				
				XPath: /wing-config/profile[name=key1]/meshpoint_device[name=key2]/preferred_root"
			::= { wingCfgProfMeshpointDevEntry 4 }

		
		-- 1.3.6.1.4.1.1916.2.131.50.1.3.16.25.1.1.5
		wingCfgProfMeshpointDevPreferredNeighbor OBJECT-TYPE
			SYNTAX MacAddress
			MAX-ACCESS read-write
			STATUS current
			DESCRIPTION
				"Preferred neighbor MAC address
				
				XPath: /wing-config/profile[name=key1]/meshpoint_device[name=key2]/preferred_neighbor"
			::= { wingCfgProfMeshpointDevEntry 5 }

		
		-- 1.3.6.1.4.1.1916.2.131.50.1.3.16.25.1.1.6
		wingCfgProfMeshpointDevPreferredIf OBJECT-TYPE
			SYNTAX DisplayString
			MAX-ACCESS read-write
			STATUS current
			DESCRIPTION
				"Preferred interface
				
				Values:
				none,
				2.4GHz,
				5GHz
				
				XPath: /wing-config/profile[name=key1]/meshpoint_device[name=key2]/preferred_interface"
			DEFVAL { "none" }
			::= { wingCfgProfMeshpointDevEntry 6 }

		-- 1.3.6.1.4.1.1916.2.131.50.1.3.16.25.1.1.7
		wingCfgProfMeshpointDevPathMethod OBJECT-TYPE
			SYNTAX DisplayString
			MAX-ACCESS read-write
			STATUS current
			DESCRIPTION
				"Path selection method for determining the root path
				
				Values:
				none,
				uniform,
				mobile-snr-leaf
				
				XPath: /wing-config/profile[name=key1]/meshpoint_device[name=key2]/path_method"
			DEFVAL { "none" }
			::= { wingCfgProfMeshpointDevEntry 7 }

		
		
-- /wing-config/rf_domain
		-- 1.3.6.1.4.1.1916.2.131.50.1.3.17
		wingCfgRfd OBJECT IDENTIFIER ::= { wingConfig 17 }

		
		-- 1.3.6.1.4.1.1916.2.131.50.1.3.17.1
		wingCfgRfdTable OBJECT-TYPE
			SYNTAX SEQUENCE OF WingCfgRfdEntry
			MAX-ACCESS not-accessible
			STATUS current
			DESCRIPTION
				"
				
				/wing-config/rf_domain"
			::= { wingCfgRfd 1 }

		
		-- 1.3.6.1.4.1.1916.2.131.50.1.3.17.1.1
		wingCfgRfdEntry OBJECT-TYPE
			SYNTAX WingCfgRfdEntry
			MAX-ACCESS not-accessible
			STATUS current
			DESCRIPTION
				"An entry in the table."
			INDEX { wingCfgRfdName }
			::= { wingCfgRfdTable 1 }

		
		WingCfgRfdEntry ::=
			SEQUENCE { 
				wingCfgRfdName
					WingIdentifier,
				wingCfgRfdLocation
					DisplayString,
				wingCfgRfdContact
					DisplayString,
				wingCfgRfdTimezone
					DisplayString,
				wingCfgRfdCountryCode
					DisplayString,
				wingCfgRfdSmartRfPolicy
					WingIdentifier,
				wingCfgRfdWipsPolicyName
					WingIdentifier,
				wingCfgRfdNocUpdateInterval
					Unsigned32,
				wingCfgRfdControlVlan
					Unsigned32,
				wingCfgRfdSmartscanChanlistDynamic
					TruthValue,
				wingCfgRfdStatsUpdateInterval
					Unsigned32
			 }

		-- 1.3.6.1.4.1.1916.2.131.50.1.3.17.1.1.1
		wingCfgRfdName OBJECT-TYPE
			SYNTAX WingIdentifier
			MAX-ACCESS read-only
			STATUS current
			DESCRIPTION
				"
				
				XPath: /wing-config/rf_domain[name=key1]/name"
			::= { wingCfgRfdEntry 1 }

		
		-- 1.3.6.1.4.1.1916.2.131.50.1.3.17.1.1.3
		wingCfgRfdLocation OBJECT-TYPE
			SYNTAX DisplayString (SIZE (64))
			MAX-ACCESS read-write
			STATUS current
			DESCRIPTION
				"
				
				XPath: /wing-config/rf_domain[name=key1]/location"
			::= { wingCfgRfdEntry 3 }

		
		-- 1.3.6.1.4.1.1916.2.131.50.1.3.17.1.1.4
		wingCfgRfdContact OBJECT-TYPE
			SYNTAX DisplayString (SIZE (64))
			MAX-ACCESS read-write
			STATUS current
			DESCRIPTION
				"
				
				XPath: /wing-config/rf_domain[name=key1]/contact"
			::= { wingCfgRfdEntry 4 }

		
		-- 1.3.6.1.4.1.1916.2.131.50.1.3.17.1.1.5
		wingCfgRfdTimezone OBJECT-TYPE
			SYNTAX DisplayString
			MAX-ACCESS read-write
			STATUS current
			DESCRIPTION
				"
				
				Values:
				Pacific/Tongatapu
				Pacific/Fiji
				Pacific/Auckland
				Asia/Magadan
				Asia/Vladivostok
				Australia/Hobart
				Pacific/Guam
				Australia/Sydney
				Australia/Brisbane
				Australia/Adelaide
				Asia/Yakutsk
				Asia/Seoul
				Asia/Tokyo
				Australia/Perth
				Asia/Kuala_Lumpur
				Asia/Irkutsk
				Asia/Hong_Kong
				Asia/Singapore
				Asia/Chongqing
				Asia/Shanghai
				Asia/Taipei
				Asia/Krasnoyarsk
				Asia/Bangkok
				Asia/Rangoon
				Asia/Colombo
				Asia/Dhaka
				Asia/Almaty
				Asia/Katmandu
				Asia/Calcutta
				Asia/Karachi
				Asia/Yekaterinburg
				Asia/Kabul
				Asia/Baku
				Asia/Dubai
				Asia/Tehran
				Africa/Nairobi
				Europe/Moscow
				Asia/Kuwait
				Asia/Baghdad
				Asia/Jerusalem
				Europe/Istanbul
				Europe/Helsinki
				Africa/Harare
				Africa/Cairo
				Africa/Johannesburg
				Europe/Bucharest
				Europe/Athens
				EET
				Africa/Lagos
				Europe/Warsaw
				Europe/Prague
				Europe/Belgrade
				Europe/Stockholm
				Europe/Zurich
				Europe/Copenhagen
				Europe/Berlin
				Europe/Rome
				Europe/Brussels
				Europe/Paris
				Europe/Madrid
				Europe/Amsterdam
				CET
				Africa/Casablanca
				Europe/Lisbon
				Europe/London
				Europe/Dublin
				Atlantic/Reykjavik
				Atlantic/Azores
				Atlantic/Cape_Verde
				Atlantic/South_Georgia
				America/Sao_Paulo
				America/Buenos_Aires
				America/Thule
				America/St_Johns
				America/Montreal
				America/Caracas
				America/Santiago
				America/Bogota
				EST5EDT
				America/New_York
				America/Indianapolis
				America/Costa_Rica
				CST6CDT
				America/Chicago
				America/Mexico_City
				America/Winnipeg
				America/Phoenix
				America/Tegucigalpa
				MST7MDT
				America/Denver
				PST8PDT
				America/Los_Angeles
				America/Anchorage
				Pacific/Honolulu
				Pacific/Apia
				Etc/GMT+12
				Etc/GMT+11
				Etc/GMT+10
				Etc/GMT+9
				Etc/GMT+8
				Etc/GMT+7
				Etc/GMT+6
				Etc/GMT+5
				Etc/GMT+4
				Etc/GMT+3
				Etc/GMT+2
				Etc/GMT+1
				Etc/UTC
				Etc/GMT-1
				Etc/GMT-2
				Etc/GMT-3
				Etc/GMT-4
				Etc/GMT-5
				Etc/GMT-6
				Etc/GMT-7
				Etc/GMT-8
				Etc/GMT-9
				Etc/GMT-10
				Etc/GMT-11
				Etc/GMT-12
				Etc/GMT-13
				Etc/GMT-14
				
				XPath: /wing-config/rf_domain[name=key1]/timezone"
			::= { wingCfgRfdEntry 5 }

		
		-- 1.3.6.1.4.1.1916.2.131.50.1.3.17.1.1.6
		wingCfgRfdCountryCode OBJECT-TYPE
			SYNTAX DisplayString
			MAX-ACCESS read-write
			STATUS current
			DESCRIPTION
				"
				
				Values:
				not-set
				ae
				ai
				an
				ar
				at
				au
				ba
				bb
				be
				bg
				bh
				bm
				bo
				br
				bs
				bw
				by
				ca
				ch
				cl
				cn
				co
				cr
				cx
				cy
				cz
				de
				dk
				do
				dz
				ec
				ee
				eg
				es
				fi
				fk
				fr
				gb
				gf
				gp
				gr
				gt
				gu
				gy
				hk
				hn
				hr
				ht
				hu
				id
				ie
				il
				in
				is
				it
				jm
				jo
				jp
				ke
				kr
				kw
				ky
				kz
				lb
				li
				lk
				lt
				lu
				lv
				ma
				md
				mk
				mq
				mt
				mx
				my
				mp
				me
				nf
				ng
				ni
				nl
				no
				nu
				nz
				na
				om
				pa
				pe
				ph
				pk
				pl
				pr
				pt
				py
				qa
				ro
				rs
				ru
				sa
				se
				sg
				si
				sk
				sv
				th
				tr
				tn
				tt
				tw
				ua
				us
				uy
				ve
				vg
				vi
				vn
				za
				
				XPath: /wing-config/rf_domain[name=key1]/country_code"
			::= { wingCfgRfdEntry 6 }

		
		-- 1.3.6.1.4.1.1916.2.131.50.1.3.17.1.1.7
		wingCfgRfdSmartRfPolicy OBJECT-TYPE
			SYNTAX WingIdentifier
			MAX-ACCESS read-write
			STATUS current
			DESCRIPTION
				"
				
				XPath: /wing-config/rf_domain[name=key1]/smart_rf_policy"
			::= { wingCfgRfdEntry 7 }

		
		-- 1.3.6.1.4.1.1916.2.131.50.1.3.17.1.1.8
		wingCfgRfdWipsPolicyName OBJECT-TYPE
			SYNTAX WingIdentifier
			MAX-ACCESS read-write
			STATUS current
			DESCRIPTION
				"
				
				XPath: /wing-config/rf_domain[name=key1]/wips_policy_name"
			::= { wingCfgRfdEntry 8 }

		
		-- 1.3.6.1.4.1.1916.2.131.50.1.3.17.1.1.9
		wingCfgRfdNocUpdateInterval OBJECT-TYPE
			SYNTAX Unsigned32 (0 | 5..3600)
			UNITS "seconds"
			MAX-ACCESS read-write
			STATUS current
			DESCRIPTION
				"Statistics update interval from RF-domain manager to its
				adopting controller.  The special value of 0 is allowed
				to indicate auto mode, in which the interval is automatically
				adjusted by the controller based upon the load information.
				
				XPath: /wing-config/rf_domain[name=key1]/noc_update_interval"
			DEFVAL { 0 }
			::= { wingCfgRfdEntry 9 }

		
		-- 1.3.6.1.4.1.1916.2.131.50.1.3.17.1.1.10
		wingCfgRfdControlVlan OBJECT-TYPE
			SYNTAX Unsigned32 (1..4094)
			MAX-ACCESS read-write
			STATUS current
			DESCRIPTION
				"VLAN for control traffic on this RF Domain
				
				XPath: /wing-config/rf_domain[name=key1]/control_vlan"
			::= { wingCfgRfdEntry 10 }

		
		-- 1.3.6.1.4.1.1916.2.131.50.1.3.17.1.1.11
		wingCfgRfdSmartscanChanlistDynamic OBJECT-TYPE
			SYNTAX TruthValue
			MAX-ACCESS read-write
			STATUS current
			DESCRIPTION
				"Configure dynamic channel listing mode for smart-scan
				
				XPath: /wing-config/rf_domain[name=key1]/smartscan_chanlist_dynamic"
			DEFVAL { false }
			::= { wingCfgRfdEntry 11 }

		
		-- 1.3.6.1.4.1.1916.2.131.50.1.3.17.1.1.12
		wingCfgRfdStatsUpdateInterval OBJECT-TYPE
			SYNTAX Unsigned32 (0 | 5..300)
			UNITS "seconds"
			MAX-ACCESS read-write
			STATUS current
			DESCRIPTION
				"Statistics update interval for this RF Domain.  The special value of 0 is allowed to indicate auto mode, in which the interval is automatically adjusted by the RF Domain Manager based upon the load information.
				
				XPath: /wing-config/rf_domain[name=key1]/stats_update_interval"
			DEFVAL { 0 }
			::= { wingCfgRfdEntry 12 }

		
		-- 1.3.6.1.4.1.1916.2.131.50.1.3.17.2
		wingCfgRfdSensorSvrTable OBJECT-TYPE
			SYNTAX SEQUENCE OF WingCfgRfdSensorSvrEntry
			MAX-ACCESS not-accessible
			STATUS current
			DESCRIPTION
				"
				
				/wing-config/rf_domain/sensor_server"
			::= { wingCfgRfd 2 }

		
		-- 1.3.6.1.4.1.1916.2.131.50.1.3.17.2.1
		wingCfgRfdSensorSvrEntry OBJECT-TYPE
			SYNTAX WingCfgRfdSensorSvrEntry
			MAX-ACCESS not-accessible
			STATUS current
			DESCRIPTION
				"An entry in the table."
			INDEX { wingCfgRfdName, wingCfgRfdSensorSvrIdx }
			::= { wingCfgRfdSensorSvrTable 1 }

		
		WingCfgRfdSensorSvrEntry ::=
			SEQUENCE { 
				wingCfgRfdSensorSvrIdx
					Unsigned32,
				wingCfgRfdSensorSvrIp
					DisplayString,
				wingCfgRfdSensorSvrPort
					Unsigned32
			 }

		-- 1.3.6.1.4.1.1916.2.131.50.1.3.17.2.1.1
		wingCfgRfdSensorSvrIdx OBJECT-TYPE
			SYNTAX Unsigned32 (1..3)
			MAX-ACCESS read-only
			STATUS current
			DESCRIPTION
				"The index into the list of servers.
				
				XPath: /wing-config/rf_domain[name=key1]/sensor_server[server_idx=key2]/server_idx"
			::= { wingCfgRfdSensorSvrEntry 1 }

		
		-- 1.3.6.1.4.1.1916.2.131.50.1.3.17.2.1.3
		wingCfgRfdSensorSvrIp OBJECT-TYPE
			SYNTAX DisplayString
			MAX-ACCESS read-write
			STATUS current
			DESCRIPTION
				"The IP address of the sensor server.
				
				XPath: /wing-config/rf_domain[name=key1]/sensor_server[server_idx=key2]/ip"
			::= { wingCfgRfdSensorSvrEntry 3 }

		
		-- 1.3.6.1.4.1.1916.2.131.50.1.3.17.2.1.4
		wingCfgRfdSensorSvrPort OBJECT-TYPE
			SYNTAX Unsigned32 (1..65535)
			MAX-ACCESS read-write
			STATUS current
			DESCRIPTION
				"The port number of the sensor server.
				
				XPath: /wing-config/rf_domain[name=key1]/sensor_server[server_idx=key2]/port"
			DEFVAL { 443 }
			::= { wingCfgRfdSensorSvrEntry 4 }

		
-- /wing-config/rf_domain
		-- 1.3.6.1.4.1.1916.2.131.50.1.3.17.3
		wingCfgRfdWlan OBJECT IDENTIFIER ::= { wingCfgRfd 3 }

		
		-- 1.3.6.1.4.1.1916.2.131.50.1.3.17.3.1
		wingCfgRfdWlanSsidOverrideTable OBJECT-TYPE
			SYNTAX SEQUENCE OF WingCfgRfdWlanSsidOverrideEntry
			MAX-ACCESS not-accessible
			STATUS current
			DESCRIPTION
				"Override wlan ssid at the rf_domain level
				
				/wing-config/rf_domain/wlan_override_ssid"
			::= { wingCfgRfdWlan 1 }

		
		-- 1.3.6.1.4.1.1916.2.131.50.1.3.17.3.1.1
		wingCfgRfdWlanSsidOverrideEntry OBJECT-TYPE
			SYNTAX WingCfgRfdWlanSsidOverrideEntry
			MAX-ACCESS not-accessible
			STATUS current
			DESCRIPTION
				"An entry in the table."
			INDEX { wingCfgRfdName, wingCfgRfdWlanSsidOverrideWlan }
			::= { wingCfgRfdWlanSsidOverrideTable 1 }

		
		WingCfgRfdWlanSsidOverrideEntry ::=
			SEQUENCE { 
				wingCfgRfdWlanSsidOverrideWlan
					WingIdentifier,
				wingCfgRfdWlanSsidOverrideSsid
					DisplayString
			 }

		-- 1.3.6.1.4.1.1916.2.131.50.1.3.17.3.1.1.1
		wingCfgRfdWlanSsidOverrideWlan OBJECT-TYPE
			SYNTAX WingIdentifier
			MAX-ACCESS read-only
			STATUS current
			DESCRIPTION
				"
				
				XPath: /wing-config/rf_domain[name=key1]/wlan_override_ssid[wlan=key2]/wlan"
			::= { wingCfgRfdWlanSsidOverrideEntry 1 }

		
		-- 1.3.6.1.4.1.1916.2.131.50.1.3.17.3.1.1.3
		wingCfgRfdWlanSsidOverrideSsid OBJECT-TYPE
			SYNTAX DisplayString (SIZE (1..32))
			MAX-ACCESS read-write
			STATUS current
			DESCRIPTION
				"The Service Set Identifier for this WLAN.
				
				XPath: /wing-config/rf_domain[name=key1]/wlan_override_ssid[wlan=key2]/ssid"
			::= { wingCfgRfdWlanSsidOverrideEntry 3 }

		
		-- 1.3.6.1.4.1.1916.2.131.50.1.3.17.3.2
		wingCfgRfdWlanVlanOverrideTable OBJECT-TYPE
			SYNTAX SEQUENCE OF WingCfgRfdWlanVlanOverrideEntry
			MAX-ACCESS not-accessible
			STATUS current
			DESCRIPTION
				"Override WLAN VLANs at the RF Domain level.
				
				/wing-config/rf_domain/wlan_override_vlan"
			::= { wingCfgRfdWlan 2 }

		
		-- 1.3.6.1.4.1.1916.2.131.50.1.3.17.3.2.1
		wingCfgRfdWlanVlanOverrideEntry OBJECT-TYPE
			SYNTAX WingCfgRfdWlanVlanOverrideEntry
			MAX-ACCESS not-accessible
			STATUS current
			DESCRIPTION
				"An entry in the table."
			INDEX { wingCfgRfdName, wingCfgRfdWlanVlanOverrideWlan }
			::= { wingCfgRfdWlanVlanOverrideTable 1 }

		
		WingCfgRfdWlanVlanOverrideEntry ::=
			SEQUENCE { 
				wingCfgRfdWlanVlanOverrideWlan
					WingIdentifier
			 }

		-- 1.3.6.1.4.1.1916.2.131.50.1.3.17.3.2.1.1
		wingCfgRfdWlanVlanOverrideWlan OBJECT-TYPE
			SYNTAX WingIdentifier
			MAX-ACCESS read-only
			STATUS current
			DESCRIPTION
				"
				
				XPath: /wing-config/rf_domain[name=key1]/wlan_override_vlan[wlan=key2]/wlan"
			::= { wingCfgRfdWlanVlanOverrideEntry 1 }

		
		-- 1.3.6.1.4.1.1916.2.131.50.1.3.17.3.3
		wingCfgRfdWlanVlanOverrideInstTable OBJECT-TYPE
			SYNTAX SEQUENCE OF WingCfgRfdWlanVlanOverrideInstEntry
			MAX-ACCESS not-accessible
			STATUS current
			DESCRIPTION
				"
				
				/wing-config/rf_domain/wlan_override_vlan/vlans"
			::= { wingCfgRfdWlan 3 }

		
		-- 1.3.6.1.4.1.1916.2.131.50.1.3.17.3.3.1
		wingCfgRfdWlanVlanOverrideInstEntry OBJECT-TYPE
			SYNTAX WingCfgRfdWlanVlanOverrideInstEntry
			MAX-ACCESS not-accessible
			STATUS current
			DESCRIPTION
				"An entry in the table."
			INDEX { wingCfgRfdName, wingCfgRfdWlanVlanOverrideWlan, wingCfgRfdWlanVlanOverrideInstVlan }
			::= { wingCfgRfdWlanVlanOverrideInstTable 1 }

		
		WingCfgRfdWlanVlanOverrideInstEntry ::=
			SEQUENCE { 
				wingCfgRfdWlanVlanOverrideInstVlan
					Unsigned32,
				wingCfgRfdWlanVlanOverrideInstLimit
					Unsigned32
			 }

		-- 1.3.6.1.4.1.1916.2.131.50.1.3.17.3.3.1.1
		wingCfgRfdWlanVlanOverrideInstVlan OBJECT-TYPE
			SYNTAX Unsigned32 (1..4094)
			MAX-ACCESS read-only
			STATUS current
			DESCRIPTION
				"The VLAN identifier.
				
				XPath: /wing-config/rf_domain[name=key1]/wlan_override_vlan[wlan=key2]/vlans[vlan=key3]/vlan"
			::= { wingCfgRfdWlanVlanOverrideInstEntry 1 }

		
		-- 1.3.6.1.4.1.1916.2.131.50.1.3.17.3.3.1.3
		wingCfgRfdWlanVlanOverrideInstLimit OBJECT-TYPE
			SYNTAX Unsigned32 (0..8192)
			MAX-ACCESS read-write
			STATUS current
			DESCRIPTION
				"The number of users allowed (0 implies unlimited).
				
				XPath: /wing-config/rf_domain[name=key1]/wlan_override_vlan[wlan=key2]/vlans[vlan=key3]/limit"
			DEFVAL { 0 }
			::= { wingCfgRfdWlanVlanOverrideInstEntry 3 }

		
		-- 1.3.6.1.4.1.1916.2.131.50.1.3.17.4
		wingCfgRfdStatsWindowTable OBJECT-TYPE
			SYNTAX SEQUENCE OF WingCfgRfdStatsWindowEntry
			MAX-ACCESS not-accessible
			STATUS current
			DESCRIPTION
				"
				
				/wing-config/rf_domain/stats_window"
			::= { wingCfgRfd 4 }

		
		-- 1.3.6.1.4.1.1916.2.131.50.1.3.17.4.1
		wingCfgRfdStatsWindowEntry OBJECT-TYPE
			SYNTAX WingCfgRfdStatsWindowEntry
			MAX-ACCESS not-accessible
			STATUS current
			DESCRIPTION
				"An entry in the table."
			INDEX { wingCfgRfdName, wingCfgRfdStatsWindowIdx }
			::= { wingCfgRfdStatsWindowTable 1 }

		
		WingCfgRfdStatsWindowEntry ::=
			SEQUENCE { 
				wingCfgRfdStatsWindowIdx
					Unsigned32,
				wingCfgRfdStatsWindowSampleInterval
					Unsigned32,
				wingCfgRfdStatsWindowWindowSize
					Unsigned32
			 }

		-- 1.3.6.1.4.1.1916.2.131.50.1.3.17.4.1.1
		wingCfgRfdStatsWindowIdx OBJECT-TYPE
			SYNTAX Unsigned32 (1..2)
			MAX-ACCESS read-only
			STATUS current
			DESCRIPTION
				"The index into the list of stats-windows
				
				XPath: /wing-config/rf_domain[name=key1]/stats_window[window_idx=key2]/window_idx"
			::= { wingCfgRfdStatsWindowEntry 1 }

		
		-- 1.3.6.1.4.1.1916.2.131.50.1.3.17.4.1.3
		wingCfgRfdStatsWindowSampleInterval OBJECT-TYPE
			SYNTAX Unsigned32 (5..86640)
			MAX-ACCESS read-write
			STATUS current
			DESCRIPTION
				"sample interval in seconds for the window
				
				XPath: /wing-config/rf_domain[name=key1]/stats_window[window_idx=key2]/sample_interval"
			DEFVAL { 5 }
			::= { wingCfgRfdStatsWindowEntry 3 }

		
		-- 1.3.6.1.4.1.1916.2.131.50.1.3.17.4.1.4
		wingCfgRfdStatsWindowWindowSize OBJECT-TYPE
			SYNTAX Unsigned32 (3..100)
			MAX-ACCESS read-write
			STATUS current
			DESCRIPTION
				"number of samples in the window
				
				XPath: /wing-config/rf_domain[name=key1]/stats_window[window_idx=key2]/window_size"
			DEFVAL { 3 }
			::= { wingCfgRfdStatsWindowEntry 4 }

		
-- /wing-config/device
		-- 1.3.6.1.4.1.1916.2.131.50.1.3.18
		wingCfgDev OBJECT IDENTIFIER ::= { wingConfig 18 }

		
		-- 1.3.6.1.4.1.1916.2.131.50.1.3.18.1
		wingCfgDevTable OBJECT-TYPE
			SYNTAX SEQUENCE OF WingCfgDevEntry
			MAX-ACCESS not-accessible
			STATUS current
			DESCRIPTION
				"
				
				/wing-config/device"
			::= { wingCfgDev 1 }

		
		-- 1.3.6.1.4.1.1916.2.131.50.1.3.18.1.1
		wingCfgDevEntry OBJECT-TYPE
			SYNTAX WingCfgDevEntry
			MAX-ACCESS not-accessible
			STATUS current
			DESCRIPTION
				"An entry in the table."
			INDEX { wingCfgDevMac }
			::= { wingCfgDevTable 1 }

		
		WingCfgDevEntry ::=
			SEQUENCE { 
				wingCfgDevMac
					MacAddress,
				wingCfgDevHostname
					DisplayString,
				wingCfgDevBuilding
					DisplayString,
				wingCfgDevFloor
					DisplayString,
				wingCfgDevNumRadios
					Unsigned32,
				wingCfgDevProfileName
					WingIdentifier,
				wingCfgDevRfDomainName
					WingIdentifier,
				wingCfgDevHttpsTrustpoint
					DisplayString,
				wingCfgDevRadiusCaTrustpoint
					DisplayString,
				wingCfgDevRadiusServerTrustpoint
					DisplayString,
				wingCfgDevSshRsaKey
					WingIdentifier,
				wingCfgDevHasOverrides
					TruthValue,
				wingCfgDevTunnelController
					DisplayString,
				wingCfgDevPreferredTunnelController
					DisplayString,
				wingCfgDevDot1xSysAuthCtrl
					TruthValue,
				wingCfgDevDot1xGuestVlanCtrl
					TruthValue,
				wingCfgDevDot1xAaaPolicy
					WingIdentifier
			 }

		-- 1.3.6.1.4.1.1916.2.131.50.1.3.18.1.1.1
		wingCfgDevMac OBJECT-TYPE
			SYNTAX MacAddress
			MAX-ACCESS read-only
			STATUS current
			DESCRIPTION
				"
				
				XPath: /wing-config/device[mac=key1]/mac"
			::= { wingCfgDevEntry 1 }

		
		-- 1.3.6.1.4.1.1916.2.131.50.1.3.18.1.1.3
		wingCfgDevHostname OBJECT-TYPE
			SYNTAX DisplayString (SIZE (64))
			MAX-ACCESS read-write
			STATUS current
			DESCRIPTION
				"
				
				XPath: /wing-config/device[mac=key1]/hostname"
			::= { wingCfgDevEntry 3 }

		
		-- 1.3.6.1.4.1.1916.2.131.50.1.3.18.1.1.4
		wingCfgDevBuilding OBJECT-TYPE
			SYNTAX DisplayString (SIZE (64))
			MAX-ACCESS read-write
			STATUS current
			DESCRIPTION
				"
				
				XPath: /wing-config/device[mac=key1]/building"
			::= { wingCfgDevEntry 4 }

		
		-- 1.3.6.1.4.1.1916.2.131.50.1.3.18.1.1.5
		wingCfgDevFloor OBJECT-TYPE
			SYNTAX DisplayString (SIZE (32))
			MAX-ACCESS read-write
			STATUS current
			DESCRIPTION
				"
				
				XPath: /wing-config/device[mac=key1]/floor"
			::= { wingCfgDevEntry 5 }

		
		-- 1.3.6.1.4.1.1916.2.131.50.1.3.18.1.1.6
		wingCfgDevNumRadios OBJECT-TYPE
			SYNTAX Unsigned32 (0..3)
			MAX-ACCESS read-write
			STATUS current
			DESCRIPTION
				"
				
				XPath: /wing-config/device[mac=key1]/num_radios"
			::= { wingCfgDevEntry 6 }

		
		-- 1.3.6.1.4.1.1916.2.131.50.1.3.18.1.1.7
		wingCfgDevProfileName OBJECT-TYPE
			SYNTAX WingIdentifier
			MAX-ACCESS read-write
			STATUS current
			DESCRIPTION
				"
				
				XPath: /wing-config/device[mac=key1]/profile_name"
			::= { wingCfgDevEntry 7 }

		
		-- 1.3.6.1.4.1.1916.2.131.50.1.3.18.1.1.8
		wingCfgDevRfDomainName OBJECT-TYPE
			SYNTAX WingIdentifier
			MAX-ACCESS read-write
			STATUS current
			DESCRIPTION
				"
				
				XPath: /wing-config/device[mac=key1]/rf_domain_name"
			::= { wingCfgDevEntry 8 }

		
		-- 1.3.6.1.4.1.1916.2.131.50.1.3.18.1.1.9
		wingCfgDevHttpsTrustpoint OBJECT-TYPE
			SYNTAX DisplayString (SIZE (1..32))
			MAX-ACCESS read-write
			STATUS current
			DESCRIPTION
				"
				
				XPath: /wing-config/device[mac=key1]/https-trustpoint"
			DEFVAL { "default-trustpoint" }
			::= { wingCfgDevEntry 9 }

		
		-- 1.3.6.1.4.1.1916.2.131.50.1.3.18.1.1.10
		wingCfgDevRadiusCaTrustpoint OBJECT-TYPE
			SYNTAX DisplayString (SIZE (1..32))
			MAX-ACCESS read-write
			STATUS current
			DESCRIPTION
				"
				
				XPath: /wing-config/device[mac=key1]/radius-ca-trustpoint"
			::= { wingCfgDevEntry 10 }

		
		-- 1.3.6.1.4.1.1916.2.131.50.1.3.18.1.1.11
		wingCfgDevRadiusServerTrustpoint OBJECT-TYPE
			SYNTAX DisplayString (SIZE (1..32))
			MAX-ACCESS read-write
			STATUS current
			DESCRIPTION
				"
				
				XPath: /wing-config/device[mac=key1]/radius-server-trustpoint"
			DEFVAL { "default-trustpoint" }
			::= { wingCfgDevEntry 11 }

		
		-- 1.3.6.1.4.1.1916.2.131.50.1.3.18.1.1.12
		wingCfgDevSshRsaKey OBJECT-TYPE
			SYNTAX WingIdentifier
			MAX-ACCESS read-write
			STATUS current
			DESCRIPTION
				"
				
				XPath: /wing-config/device[mac=key1]/ssh-rsa-key"
			DEFVAL { "default_rsa_key" }
			::= { wingCfgDevEntry 12 }

		
		-- 1.3.6.1.4.1.1916.2.131.50.1.3.18.1.1.13
		wingCfgDevHasOverrides OBJECT-TYPE
			SYNTAX TruthValue
			MAX-ACCESS read-only
			STATUS current
			DESCRIPTION
				"read only value to indicate whether the device has at least one override
				
				XPath: /wing-config/device[mac=key1]/has_overrides"
			DEFVAL { false }
			::= { wingCfgDevEntry 13 }

		
		-- 1.3.6.1.4.1.1916.2.131.50.1.3.18.1.1.14
		wingCfgDevTunnelController OBJECT-TYPE
			SYNTAX DisplayString
			MAX-ACCESS read-write
			STATUS current
			DESCRIPTION
				"Name of this tunneled-wlan-controller
				
				XPath: /wing-config/device[mac=key1]/tunnel_controller"
			::= { wingCfgDevEntry 14 }

		
		-- 1.3.6.1.4.1.1916.2.131.50.1.3.18.1.1.15
		wingCfgDevPreferredTunnelController OBJECT-TYPE
			SYNTAX DisplayString
			MAX-ACCESS read-write
			STATUS current
			DESCRIPTION
				"Controller this AP will prefer to tunnel tunnelled-wlan a.k.a extended-vlan traffic to
				
				XPath: /wing-config/device[mac=key1]/preferred_tunnel_controller"
			::= { wingCfgDevEntry 15 }

		
		-- 1.3.6.1.4.1.1916.2.131.50.1.3.18.1.1.16
		wingCfgDevDot1xSysAuthCtrl OBJECT-TYPE
			SYNTAX TruthValue
			MAX-ACCESS read-write
			STATUS current
			DESCRIPTION
				"Globally enable 802.1x authentication
				
				XPath: /wing-config/device[mac=key1]/dot1x_sys_auth_ctrl"
			DEFVAL { false }
			::= { wingCfgDevEntry 16 }

		
		-- 1.3.6.1.4.1.1916.2.131.50.1.3.18.1.1.17
		wingCfgDevDot1xGuestVlanCtrl OBJECT-TYPE
			SYNTAX TruthValue
			MAX-ACCESS read-write
			STATUS current
			DESCRIPTION
				"Globally enable 802.1x guest vlans
				
				XPath: /wing-config/device[mac=key1]/dot1x_guest_vlan_ctrl"
			DEFVAL { false }
			::= { wingCfgDevEntry 17 }

		
		-- 1.3.6.1.4.1.1916.2.131.50.1.3.18.1.1.18
		wingCfgDevDot1xAaaPolicy OBJECT-TYPE
			SYNTAX WingIdentifier
			MAX-ACCESS read-write
			STATUS current
			DESCRIPTION
				"AAA Authentication policy for 802.1x Authentication
				
				XPath: /wing-config/device[mac=key1]/dot1x_aaa_policy"
			::= { wingCfgDevEntry 18 }

		
--  /wing-config/device/interface
		-- 1.3.6.1.4.1.1916.2.131.50.1.3.18.3
		wingCfgDevIf OBJECT IDENTIFIER ::= { wingCfgDev 3 }

		
		-- 1.3.6.1.4.1.1916.2.131.50.1.3.18.3.1
		wingCfgDevIfTable OBJECT-TYPE
			SYNTAX SEQUENCE OF WingCfgDevIfEntry
			MAX-ACCESS not-accessible
			STATUS current
			DESCRIPTION
				"
				
				/wing-config/device/interface"
			::= { wingCfgDevIf 1 }

		
		-- 1.3.6.1.4.1.1916.2.131.50.1.3.18.3.1.1
		wingCfgDevIfEntry OBJECT-TYPE
			SYNTAX WingCfgDevIfEntry
			MAX-ACCESS not-accessible
			STATUS current
			DESCRIPTION
				"An entry in the table."
			INDEX { wingCfgDevMac, wingCfgDevIfName }
			::= { wingCfgDevIfTable 1 }

		
		WingCfgDevIfEntry ::=
			SEQUENCE { 
				wingCfgDevIfName
					WingIdentifier,
				wingCfgDevIfDescription
					DisplayString,
				wingCfgDevIfType
					DisplayString,
				wingCfgDevIfShutdown
					TruthValue,
				wingCfgDevIfIpInAcl
					WingIdentifier,
				wingCfgDevIfMacInAcl
					WingIdentifier
			 }

		-- 1.3.6.1.4.1.1916.2.131.50.1.3.18.3.1.1.1
		wingCfgDevIfName OBJECT-TYPE
			SYNTAX WingIdentifier
			MAX-ACCESS read-only
			STATUS current
			DESCRIPTION
				"
				
				XPath: /wing-config/device[mac=key1]/interface[name=key2]/name"
			::= { wingCfgDevIfEntry 1 }

		
		-- 1.3.6.1.4.1.1916.2.131.50.1.3.18.3.1.1.3
		wingCfgDevIfDescription OBJECT-TYPE
			SYNTAX DisplayString
			MAX-ACCESS read-write
			STATUS current
			DESCRIPTION
				"
				
				XPath: /wing-config/device[mac=key1]/interface[name=key2]/description"
			::= { wingCfgDevIfEntry 3 }

		
		-- 1.3.6.1.4.1.1916.2.131.50.1.3.18.3.1.1.4
		wingCfgDevIfType OBJECT-TYPE
			SYNTAX DisplayString
			MAX-ACCESS read-write
			STATUS current
			DESCRIPTION
				"Hardware type of the network interface
				
				Values:
				ethernet
				vlan
				radio
				port_channel
				
				XPath: /wing-config/device[mac=key1]/interface[name=key2]/type"
			::= { wingCfgDevIfEntry 4 }

		
		-- 1.3.6.1.4.1.1916.2.131.50.1.3.18.3.1.1.5
		wingCfgDevIfShutdown OBJECT-TYPE
			SYNTAX TruthValue
			MAX-ACCESS read-write
			STATUS current
			DESCRIPTION
				"
				
				XPath: /wing-config/device[mac=key1]/interface[name=key2]/shutdown"
			DEFVAL { false }
			::= { wingCfgDevIfEntry 5 }

		
		-- 1.3.6.1.4.1.1916.2.131.50.1.3.18.3.1.1.6
		wingCfgDevIfIpInAcl OBJECT-TYPE
			SYNTAX WingIdentifier
			MAX-ACCESS read-write
			STATUS current
			DESCRIPTION
				"
				
				XPath: /wing-config/device[mac=key1]/interface[name=key2]/ip_in_acl"
			::= { wingCfgDevIfEntry 6 }

		
		-- 1.3.6.1.4.1.1916.2.131.50.1.3.18.3.1.1.7
		wingCfgDevIfMacInAcl OBJECT-TYPE
			SYNTAX WingIdentifier
			MAX-ACCESS read-write
			STATUS current
			DESCRIPTION
				"
				
				XPath: /wing-config/device[mac=key1]/interface[name=key2]/mac_in_acl"
			::= { wingCfgDevIfEntry 7 }

		
		-- 1.3.6.1.4.1.1916.2.131.50.1.3.18.3.2
		wingCfgDevIfEthTable OBJECT-TYPE
			SYNTAX SEQUENCE OF WingCfgDevIfEthEntry
			MAX-ACCESS not-accessible
			STATUS current
			DESCRIPTION
				"
				
				/wing-config/device/interface"
			::= { wingCfgDevIf 2 }

		
		-- 1.3.6.1.4.1.1916.2.131.50.1.3.18.3.2.1
		wingCfgDevIfEthEntry OBJECT-TYPE
			SYNTAX WingCfgDevIfEthEntry
			MAX-ACCESS not-accessible
			STATUS current
			DESCRIPTION
				"An entry in the table."
			INDEX { wingCfgDevMac, wingCfgDevIfName }
			::= { wingCfgDevIfEthTable 1 }

		
		WingCfgDevIfEthEntry ::=
			SEQUENCE { 
				wingCfgDevIfEthSpeed
					DisplayString,
				wingCfgDevIfEthDuplex
					DisplayString,
				wingCfgDevIfEthSwitchportMode
					DisplayString,
				wingCfgDevIfEthSwitchportNativeVlan
					Unsigned32,
				wingCfgDevIfEthSwitchportNativeVlanTagged
					TruthValue,
				wingCfgDevIfEthArpTrust
					TruthValue,
				wingCfgDevIfEthDhcpTrust
					TruthValue,
				wingCfgDevIfEthArpHeaderMismatchValidation
					TruthValue,
				wingCfgDevIfEthQosTrustDscp
					TruthValue,
				wingCfgDevIfEthQosTrust802dot1p
					TruthValue,
				wingCfgDevIfEthStaticChannelGroup
					Unsigned32,
				wingCfgDevIfEthPoeSupported
					TruthValue,
				wingCfgDevIfEthPoePower
					TruthValue,
				wingCfgDevIfEthPoeLimit
					Unsigned32,
				wingCfgDevIfEthPoePriority
					DisplayString,
				wingCfgDevIfEthDot1xSupported
					TruthValue,
				wingCfgDevIfEthDot1xEnable
					TruthValue,
				wingCfgDevIfEthDot1xUsername
					DisplayString,
				wingCfgDevIfEthDot1xPassword
					DisplayString,
				wingCfgDevIfEthCdpReceive
					TruthValue,
				wingCfgDevIfEthCdpTransmit
					TruthValue,
				wingCfgDevIfEthLldpReceive
					TruthValue,
				wingCfgDevIfEthLldpTransmit
					TruthValue,
				wingCfgDevIfEthPortChannelLoadBalance
					DisplayString
			 }

		-- 1.3.6.1.4.1.1916.2.131.50.1.3.18.3.2.1.1
		wingCfgDevIfEthSpeed OBJECT-TYPE
			SYNTAX DisplayString
			MAX-ACCESS read-write
			STATUS current
			DESCRIPTION
				"
				Values:
				10
				100
				1000
				auto
				
				XPath: /wing-config/device[mac=key1]/interface[name=key2]/speed"
			DEFVAL { "auto" }
			::= { wingCfgDevIfEthEntry 1 }

		
		-- 1.3.6.1.4.1.1916.2.131.50.1.3.18.3.2.1.2
		wingCfgDevIfEthDuplex OBJECT-TYPE
			SYNTAX DisplayString
			MAX-ACCESS read-write
			STATUS current
			DESCRIPTION
				"
				Values:
				half
				full
				auto
				
				XPath: /wing-config/device[mac=key1]/interface[name=key2]/duplex"
			DEFVAL { "auto" }
			::= { wingCfgDevIfEthEntry 2 }

		
		-- 1.3.6.1.4.1.1916.2.131.50.1.3.18.3.2.1.3
		wingCfgDevIfEthSwitchportMode OBJECT-TYPE
			SYNTAX DisplayString
			MAX-ACCESS read-write
			STATUS current
			DESCRIPTION
				"Mode of the Layer 2 interface.
				
				Values:
				access
				trunk
				
				XPath: /wing-config/device[mac=key1]/interface[name=key2]/switchport/mode"
			DEFVAL { "access" }
			::= { wingCfgDevIfEthEntry 3 }

		
		-- 1.3.6.1.4.1.1916.2.131.50.1.3.18.3.2.1.4
		wingCfgDevIfEthSwitchportNativeVlan OBJECT-TYPE
			SYNTAX Unsigned32 (1..4094)
			MAX-ACCESS read-write
			STATUS current
			DESCRIPTION
				"Native VLAN for classifying untagged traffic.
				
				XPath: /wing-config/device[mac=key1]/interface[name=key2]/switchport/native_vlan"
			DEFVAL { 1 }
			::= { wingCfgDevIfEthEntry 4 }

		
		-- 1.3.6.1.4.1.1916.2.131.50.1.3.18.3.2.1.5
		wingCfgDevIfEthSwitchportNativeVlanTagged OBJECT-TYPE
			SYNTAX TruthValue
			MAX-ACCESS read-write
			STATUS current
			DESCRIPTION
				"Tag the native VLAN.
				
				XPath: /wing-config/device[mac=key1]/interface[name=key2]/switchport/native_vlan_tagged"
			DEFVAL { false }
			::= { wingCfgDevIfEthEntry 5 }

		
		-- 1.3.6.1.4.1.1916.2.131.50.1.3.18.3.2.1.6
		wingCfgDevIfEthArpTrust OBJECT-TYPE
			SYNTAX TruthValue
			MAX-ACCESS read-write
			STATUS current
			DESCRIPTION
				"Trust ARP request on this port.
				
				XPath: /wing-config/device[mac=key1]/interface[name=key2]/arp_trust"
			DEFVAL { false }
			::= { wingCfgDevIfEthEntry 6 }

		
		-- 1.3.6.1.4.1.1916.2.131.50.1.3.18.3.2.1.7
		wingCfgDevIfEthDhcpTrust OBJECT-TYPE
			SYNTAX TruthValue
			MAX-ACCESS read-write
			STATUS current
			DESCRIPTION
				"Trust DHCP responses on this port
				
				XPath: /wing-config/device[mac=key1]/interface[name=key2]/dhcp_trust"
			DEFVAL { true }
			::= { wingCfgDevIfEthEntry 7 }

		
		-- 1.3.6.1.4.1.1916.2.131.50.1.3.18.3.2.1.8
		wingCfgDevIfEthArpHeaderMismatchValidation OBJECT-TYPE
			SYNTAX TruthValue
			MAX-ACCESS read-write
			STATUS current
			DESCRIPTION
				"Check mismatch for source MAC in ARP header and ethernet header.
				
				XPath: /wing-config/device[mac=key1]/interface[name=key2]/arp_header_mismatch_validation"
			DEFVAL { false }
			::= { wingCfgDevIfEthEntry 8 }

		
		-- 1.3.6.1.4.1.1916.2.131.50.1.3.18.3.2.1.9
		wingCfgDevIfEthQosTrustDscp OBJECT-TYPE
			SYNTAX TruthValue
			MAX-ACCESS read-write
			STATUS current
			DESCRIPTION
				"Trust IP DSCP values on this port.
				
				XPath: /wing-config/device[mac=key1]/interface[name=key2]/qos_trust_dscp"
			DEFVAL { true }
			::= { wingCfgDevIfEthEntry 9 }

		
		-- 1.3.6.1.4.1.1916.2.131.50.1.3.18.3.2.1.10
		wingCfgDevIfEthQosTrust802dot1p OBJECT-TYPE
			SYNTAX TruthValue
			MAX-ACCESS read-write
			STATUS current
			DESCRIPTION
				"Trust 802.1p COS values on this port.
				
				XPath: /wing-config/device[mac=key1]/interface[name=key2]/qos_trust_802dot1p"
			DEFVAL { true }
			::= { wingCfgDevIfEthEntry 10 }

		
		-- 1.3.6.1.4.1.1916.2.131.50.1.3.18.3.2.1.11
		wingCfgDevIfEthStaticChannelGroup OBJECT-TYPE
			SYNTAX Unsigned32 (1..5)
			MAX-ACCESS read-write
			STATUS current
			DESCRIPTION
				"Channel group to which the port belongs.
				
				XPath: /wing-config/device[mac=key1]/interface[name=key2]/static_channel_group"
			::= { wingCfgDevIfEthEntry 11 }

		
		-- 1.3.6.1.4.1.1916.2.131.50.1.3.18.3.2.1.12
		wingCfgDevIfEthPoeSupported OBJECT-TYPE
			SYNTAX TruthValue
			MAX-ACCESS read-write
			STATUS current
			DESCRIPTION
				"POE supported on this port when true.
				
				XPath: /wing-config/device[mac=key1]/interface[name=key2]/poe_supported"
			DEFVAL { false }
			::= { wingCfgDevIfEthEntry 12 }

		
		-- 1.3.6.1.4.1.1916.2.131.50.1.3.18.3.2.1.13
		wingCfgDevIfEthPoePower OBJECT-TYPE
			SYNTAX TruthValue
			MAX-ACCESS read-write
			STATUS current
			DESCRIPTION
				"Enable/Disable POE Power.
				
				XPath: /wing-config/device[mac=key1]/interface[name=key2]/poe_power"
			DEFVAL { true }
			::= { wingCfgDevIfEthEntry 13 }

		
		-- 1.3.6.1.4.1.1916.2.131.50.1.3.18.3.2.1.14
		wingCfgDevIfEthPoeLimit OBJECT-TYPE
			SYNTAX Unsigned32 (0..40)
			UNITS "watts"
			MAX-ACCESS read-write
			STATUS current
			DESCRIPTION
				"
				
				XPath: /wing-config/device[mac=key1]/interface[name=key2]/poe_limit"
			DEFVAL { 0 }
			::= { wingCfgDevIfEthEntry 14 }

		
		-- 1.3.6.1.4.1.1916.2.131.50.1.3.18.3.2.1.15
		wingCfgDevIfEthPoePriority OBJECT-TYPE
			SYNTAX DisplayString
			MAX-ACCESS read-write
			STATUS current
			DESCRIPTION
				"
				Values:
				critical
				high
				low
				
				XPath: /wing-config/device[mac=key1]/interface[name=key2]/poe_priority"
			DEFVAL { "low" }
			::= { wingCfgDevIfEthEntry 15 }

		
		-- 1.3.6.1.4.1.1916.2.131.50.1.3.18.3.2.1.16
		wingCfgDevIfEthDot1xSupported OBJECT-TYPE
			SYNTAX TruthValue
			MAX-ACCESS read-write
			STATUS current
			DESCRIPTION
				"Dot1x supported on port when enabled.
				
				XPath: /wing-config/device[mac=key1]/interface[name=key2]/dot1x_supported"
			DEFVAL { false }
			::= { wingCfgDevIfEthEntry 16 }

		
		-- 1.3.6.1.4.1.1916.2.131.50.1.3.18.3.2.1.17
		wingCfgDevIfEthDot1xEnable OBJECT-TYPE
			SYNTAX TruthValue
			MAX-ACCESS read-write
			STATUS current
			DESCRIPTION
				"
				
				XPath: /wing-config/device[mac=key1]/interface[name=key2]/dot1x/enable"
			DEFVAL { false }
			::= { wingCfgDevIfEthEntry 17 }

		
		-- 1.3.6.1.4.1.1916.2.131.50.1.3.18.3.2.1.18
		wingCfgDevIfEthDot1xUsername OBJECT-TYPE
			SYNTAX DisplayString (SIZE (1..32))
			MAX-ACCESS read-write
			STATUS current
			DESCRIPTION
				"
				
				XPath: /wing-config/device[mac=key1]/interface[name=key2]/dot1x/username"
			::= { wingCfgDevIfEthEntry 18 }

		
		-- 1.3.6.1.4.1.1916.2.131.50.1.3.18.3.2.1.19
		wingCfgDevIfEthDot1xPassword OBJECT-TYPE
			SYNTAX DisplayString
			MAX-ACCESS read-write
			STATUS current
			DESCRIPTION
				"
				
				XPath: /wing-config/device[mac=key1]/interface[name=key2]/dot1x/password"
			::= { wingCfgDevIfEthEntry 19 }

		
		-- 1.3.6.1.4.1.1916.2.131.50.1.3.18.3.2.1.20
		wingCfgDevIfEthCdpReceive OBJECT-TYPE
			SYNTAX TruthValue
			MAX-ACCESS read-write
			STATUS current
			DESCRIPTION
				"Snoop CDP on port
				
				XPath: /wing-config/device[mac=key1]/interface[name=key2]/cdp_receive"
			DEFVAL { true }
			::= { wingCfgDevIfEthEntry 20 }

		
		-- 1.3.6.1.4.1.1916.2.131.50.1.3.18.3.2.1.21
		wingCfgDevIfEthCdpTransmit OBJECT-TYPE
			SYNTAX TruthValue
			MAX-ACCESS read-write
			STATUS current
			DESCRIPTION
				"Transmit CDP packets on port
				
				XPath: /wing-config/device[mac=key1]/interface[name=key2]/cdp_transmit"
			DEFVAL { false }
			::= { wingCfgDevIfEthEntry 21 }

		
		-- 1.3.6.1.4.1.1916.2.131.50.1.3.18.3.2.1.22
		wingCfgDevIfEthLldpReceive OBJECT-TYPE
			SYNTAX TruthValue
			MAX-ACCESS read-write
			STATUS current
			DESCRIPTION
				"Snoop LLDP on port
				
				XPath: /wing-config/device[mac=key1]/interface[name=key2]/lldp_receive"
			DEFVAL { true }
			::= { wingCfgDevIfEthEntry 22 }

		
		-- 1.3.6.1.4.1.1916.2.131.50.1.3.18.3.2.1.23
		wingCfgDevIfEthLldpTransmit OBJECT-TYPE
			SYNTAX TruthValue
			MAX-ACCESS read-write
			STATUS current
			DESCRIPTION
				"Transmit LLDP PDUs on port
				
				XPath: /wing-config/device[mac=key1]/interface[name=key2]/lldp_transmit"
			DEFVAL { false }
			::= { wingCfgDevIfEthEntry 23 }

		
		-- 1.3.6.1.4.1.1916.2.131.50.1.3.18.3.2.1.24
		wingCfgDevIfEthPortChannelLoadBalance OBJECT-TYPE
			SYNTAX DisplayString
			MAX-ACCESS read-write
			STATUS current
			DESCRIPTION
				"
				Values:
				src-dst-ip
				src-dst-mac
				
				XPath: /wing-config/device[mac=key1]/interface[name=key2]/poe_priority"
			DEFVAL { "src-dst-ip" }
			::= { wingCfgDevIfEthEntry 24 }

		
		-- 1.3.6.1.4.1.1916.2.131.50.1.3.18.3.3
		wingCfgDevIfVlanTable OBJECT-TYPE
			SYNTAX SEQUENCE OF WingCfgDevIfVlanEntry
			MAX-ACCESS not-accessible
			STATUS current
			DESCRIPTION
				"
				
				/wing-config/device/interface"
			::= { wingCfgDevIf 3 }

		
		-- 1.3.6.1.4.1.1916.2.131.50.1.3.18.3.3.1
		wingCfgDevIfVlanEntry OBJECT-TYPE
			SYNTAX WingCfgDevIfVlanEntry
			MAX-ACCESS not-accessible
			STATUS current
			DESCRIPTION
				"An entry in the table."
			INDEX { wingCfgDevMac, wingCfgDevIfName }
			::= { wingCfgDevIfVlanTable 1 }

		
		WingCfgDevIfVlanEntry ::=
			SEQUENCE { 
				wingCfgDevIfVlanVlan
					Unsigned32,
				wingCfgDevIfVlanDhcpcOptAll
					TruthValue,
				wingCfgDevIfVlanNatDirection
					DisplayString,
				wingCfgDevIfVlanCryptoMap
					WingIdentifier,
				wingCfgDevIfVlanDhcpRelayIncoming
					TruthValue
			 }

		-- 1.3.6.1.4.1.1916.2.131.50.1.3.18.3.3.1.1
		wingCfgDevIfVlanVlan OBJECT-TYPE
			SYNTAX Unsigned32 (1..4094)
			MAX-ACCESS read-write
			STATUS current
			DESCRIPTION
				"
				
				XPath: /wing-config/device[mac=key1]/interface[name=key2]/vlan"
			::= { wingCfgDevIfVlanEntry 1 }

		
		-- 1.3.6.1.4.1.1916.2.131.50.1.3.18.3.3.1.2
		wingCfgDevIfVlanDhcpcOptAll OBJECT-TYPE
			SYNTAX TruthValue
			MAX-ACCESS read-write
			STATUS current
			DESCRIPTION
				"Learn default gateway, name servers, domain name on this
				interface.
				
				XPath: /wing-config/device[mac=key1]/interface[name=key2]/dhcpc_opt_all"
			DEFVAL { false }
			::= { wingCfgDevIfVlanEntry 2 }

		
		-- 1.3.6.1.4.1.1916.2.131.50.1.3.18.3.3.1.3
		wingCfgDevIfVlanNatDirection OBJECT-TYPE
			SYNTAX DisplayString
			MAX-ACCESS read-write
			STATUS current
			DESCRIPTION
				"
				
				Values:
				inside
				outside
				none
				
				XPath: /wing-config/device[mac=key1]/interface[name=key2]/nat_direction"
			DEFVAL { "none" }
			::= { wingCfgDevIfVlanEntry 3 }

		
		-- 1.3.6.1.4.1.1916.2.131.50.1.3.18.3.3.1.4
		wingCfgDevIfVlanCryptoMap OBJECT-TYPE
			SYNTAX WingIdentifier
			MAX-ACCESS read-write
			STATUS current
			DESCRIPTION
				"Attach an already configured crypto map to this interface.
				
				XPath: /wing-config/device[mac=key1]/interface[name=key2]/crypto_map"
			::= { wingCfgDevIfVlanEntry 4 }

		
		-- 1.3.6.1.4.1.1916.2.131.50.1.3.18.3.3.1.5
		wingCfgDevIfVlanDhcpRelayIncoming OBJECT-TYPE
			SYNTAX TruthValue
			MAX-ACCESS read-write
			STATUS current
			DESCRIPTION
				"Allow on-board DHCP server to respond to relayed DHCP packets on this interface
				
				XPath: /wing-config/device[mac=key1]/interface[name=key2]/dhcp_relay_incoming"
			DEFVAL { false }
			::= { wingCfgDevIfVlanEntry 5 }

		
		-- 1.3.6.1.4.1.1916.2.131.50.1.3.18.3.5
		wingCfgDevIfRadioTable OBJECT-TYPE
			SYNTAX SEQUENCE OF WingCfgDevIfRadioEntry
			MAX-ACCESS not-accessible
			STATUS current
			DESCRIPTION
				"
				
				/wing-config/device/interface"
			::= { wingCfgDevIf 5 }

		
		-- 1.3.6.1.4.1.1916.2.131.50.1.3.18.3.5.1
		wingCfgDevIfRadioEntry OBJECT-TYPE
			SYNTAX WingCfgDevIfRadioEntry
			MAX-ACCESS not-accessible
			STATUS current
			DESCRIPTION
				"An entry in the table."
			INDEX { wingCfgDevMac, wingCfgDevIfName }
			::= { wingCfgDevIfRadioTable 1 }

		
		WingCfgDevIfRadioEntry ::=
			SEQUENCE { 
				wingCfgDevIfRadioRfMode
					DisplayString,
				wingCfgDevIfRadioChannel
					DisplayString,
				wingCfgDevIfRadioPower
					Unsigned32,
				wingCfgDevIfRadioPlacement
					DisplayString,
				wingCfgDevIfRadioBeaconInterval
					DisplayString,
				wingCfgDevIfRadioRtsThreshold
					Unsigned32,
				wingCfgDevIfRadioOffChannelScan
					TruthValue,
				wingCfgDevIfRadioPreambleShort
					TruthValue,
				wingCfgDevIfRadioGuardInterval
					DisplayString,
				wingCfgDevIfRadioAmpduMode
					DisplayString,
				wingCfgDevIfRadioAmsduMode
					DisplayString,
				wingCfgDevIfRadioRifsMode
					DisplayString,
				wingCfgDevIfRadioAmpduMaxAggrSizeRx
					DisplayString,
				wingCfgDevIfRadioAmpduMaxAggrSizeTx
					Unsigned32,
				wingCfgDevIfRadioAmpduMinSpacing
					DisplayString,
				wingCfgDevIfRadioAntennaMode
					DisplayString,
				wingCfgDevIfRadioNonUnicastForwarding
					DisplayString,
				wingCfgDevIfRadioDynamicChainSelection
					TruthValue,
				wingCfgDevIfRadioLockRfMode
					TruthValue,
				wingCfgDevIfRadioSnifferRedirHost
					DisplayString,
				wingCfgDevIfRadioSnifferRedirChannel
					DisplayString,
				wingCfgDevIfRadioMesh
					DisplayString,
				wingCfgDevIfRadioMeshLinks
					Unsigned32,
				wingCfgDevIfRadioProbeResponseRetry
					TruthValue,
				wingCfgDevIfRadioProbeResponseRate
					DisplayString,
				wingCfgDevIfRadioMaxClients
					Unsigned32,
				wingCfgDevIfRadioRadioTapMode
					DisplayString,
				wingCfgDevIfRadioWirelessClientPower
					Unsigned32,
				wingCfgDevIfRadioLoadBalLfCount
					Unsigned32,
				wingCfgDevIfRadioLoadBalLfThroughput
					Unsigned32,
				wingCfgDevIfRadioLoadBalWmCount
					Unsigned32,
				wingCfgDevIfRadioLoadBalWmTput
					Unsigned32,
				wingCfgDevIfRadioAssocAcl
					WingIdentifier,
				wingCfgDevIfRadioQosPolicy
					WingIdentifier,
                                wingCfgDevIfRadioAntennaDowntilt
                                        TruthValue,
                                wingCfgDevIfRadioExtendedRange
                                        Unsigned32
			 }

		-- 1.3.6.1.4.1.1916.2.131.50.1.3.18.3.5.1.1
		wingCfgDevIfRadioRfMode OBJECT-TYPE
			SYNTAX DisplayString
			MAX-ACCESS read-write
			STATUS current
			DESCRIPTION
				"
				
				Values:
				2.4GHz-wlan
				5GHz-wlan
				sensor
				
				Notes:
				On a WM3400 the radio-mode of radio1 can only be 2.4|sensor.
				radio2 can only be 5|sensor(so the 2.4-wlan and 5-wlan modes
				cant be interchanged) 
				
				On an AP4700 radio3 can only be sensor. It can never be
				2.4-wlan/5-wlan 
				
				XPath: /wing-config/device[mac=key1]/interface[name=key2]/rf_mode"
			::= { wingCfgDevIfRadioEntry 1 }

		
		-- 1.3.6.1.4.1.1916.2.131.50.1.3.18.3.5.1.2
		wingCfgDevIfRadioChannel OBJECT-TYPE
			SYNTAX DisplayString
			MAX-ACCESS read-write
			STATUS current
			DESCRIPTION
				"Channel of operation for this radio.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, 46, and smart
				
				
				When 'rf_mode' is set to '2.4GHz-wlan', valid channels are
				'1' through '14' and 'smart'.
				
				When 'rf_mode' is set to '5GHz-wlan', '1' through '14'
				are not allowed. Rest of the channels (including 'smart' are
				allowed)
				
				When 'rf_mode' is set to 'sensor', 'channel' setting
				is ignored.
				
				XPath: /wing-config/device[mac=key1]/interface[name=key2]/channel"
			DEFVAL { "smart" }
			::= { wingCfgDevIfRadioEntry 2 }

		
		-- 1.3.6.1.4.1.1916.2.131.50.1.3.18.3.5.1.3
		wingCfgDevIfRadioPower OBJECT-TYPE
			SYNTAX Unsigned32 (0..27)
			UNITS "dBm"
			MAX-ACCESS read-write
			STATUS current
			DESCRIPTION
				"Transmit power of the radio.  A setting of 0 indicates
				Smart RF is managing the power.
				
				XPath: /wing-config/device[mac=key1]/interface[name=key2]/power"
			DEFVAL { 20 }
			::= { wingCfgDevIfRadioEntry 3 }

		
		-- 1.3.6.1.4.1.1916.2.131.50.1.3.18.3.5.1.4
		wingCfgDevIfRadioPlacement OBJECT-TYPE
			SYNTAX DisplayString
			MAX-ACCESS read-write
			STATUS current
			DESCRIPTION
				"Location where this radio is operating.
				
				Values:
				indoor
				outdoor
				
				XPath: /wing-config/device[mac=key1]/interface[name=key2]/placement"
			DEFVAL { "indoor" }
			::= { wingCfgDevIfRadioEntry 4 }

		
		-- 1.3.6.1.4.1.1916.2.131.50.1.3.18.3.5.1.5
		wingCfgDevIfRadioBeaconInterval OBJECT-TYPE
			SYNTAX DisplayString
			UNITS "milliseconds"
			MAX-ACCESS read-write
			STATUS current
			DESCRIPTION
				"Interval between radio beacons.
				
				Values:
				50
				100
				200
				
				XPath: /wing-config/device[mac=key1]/interface[name=key2]/beacon_interval"
			DEFVAL { "100" }
			::= { wingCfgDevIfRadioEntry 5 }

		
		-- 1.3.6.1.4.1.1916.2.131.50.1.3.18.3.5.1.6
		wingCfgDevIfRadioRtsThreshold OBJECT-TYPE
			SYNTAX Unsigned32 (1..2347)
			UNITS "bytes"
			MAX-ACCESS read-write
			STATUS current
			DESCRIPTION
				"Ready to Send threshold on this radio.
				
				XPath: /wing-config/device[mac=key1]/interface[name=key2]/rts_threshold"
			DEFVAL { 2347 }
			::= { wingCfgDevIfRadioEntry 6 }

		
		-- 1.3.6.1.4.1.1916.2.131.50.1.3.18.3.5.1.7
		wingCfgDevIfRadioOffChannelScan OBJECT-TYPE
			SYNTAX TruthValue
			MAX-ACCESS read-write
			STATUS current
			DESCRIPTION
				"Enable off-channel scanning on this radio.
				
				XPath: /wing-config/device[mac=key1]/interface[name=key2]/off_channel_scan"
			DEFVAL { false }
			::= { wingCfgDevIfRadioEntry 7 }

		
		-- 1.3.6.1.4.1.1916.2.131.50.1.3.18.3.5.1.8
		wingCfgDevIfRadioPreambleShort OBJECT-TYPE
			SYNTAX TruthValue
			MAX-ACCESS read-write
			STATUS current
			DESCRIPTION
				"Configure use of short preamble.
				
				XPath: /wing-config/device[mac=key1]/interface[name=key2]/preamble_short"
			DEFVAL { false }
			::= { wingCfgDevIfRadioEntry 8 }

		
		-- 1.3.6.1.4.1.1916.2.131.50.1.3.18.3.5.1.9
		wingCfgDevIfRadioGuardInterval OBJECT-TYPE
			SYNTAX DisplayString
			MAX-ACCESS read-write
			STATUS current
			DESCRIPTION
				"802.11n guard interval.
				
				Values:
				any
				long
				
				XPath: /wing-config/device[mac=key1]/interface[name=key2]/guard_interval"
			DEFVAL { "any" }
			::= { wingCfgDevIfRadioEntry 9 }

		
		-- 1.3.6.1.4.1.1916.2.131.50.1.3.18.3.5.1.10
		wingCfgDevIfRadioAmpduMode OBJECT-TYPE
			SYNTAX DisplayString
			MAX-ACCESS read-write
			STATUS current
			DESCRIPTION
				"Mode in which A-MPDU will be supported.
				
				Values:
				tx-only
				rx-only
				tx-rx
				none
				
				XPath: /wing-config/device[mac=key1]/interface[name=key2]/ampdu_mode"
			DEFVAL { "tx-rx" }
			::= { wingCfgDevIfRadioEntry 10 }

		
		-- 1.3.6.1.4.1.1916.2.131.50.1.3.18.3.5.1.11
		wingCfgDevIfRadioAmsduMode OBJECT-TYPE
			SYNTAX DisplayString
			MAX-ACCESS read-write
			STATUS current
			DESCRIPTION
				"Mode in which A-MSDU will be supported.
				
				Values:
				rx-only
				tx-rx
				
				XPath: /wing-config/device[mac=key1]/interface[name=key2]/amsdu_mode"
			DEFVAL { "rx-only" }
			::= { wingCfgDevIfRadioEntry 11 }

		
		-- 1.3.6.1.4.1.1916.2.131.50.1.3.18.3.5.1.12
		wingCfgDevIfRadioRifsMode OBJECT-TYPE
			SYNTAX DisplayString
			MAX-ACCESS read-write
			STATUS current
			DESCRIPTION
				"Modes in which RIFS will be supported.
				
				Values:
				tx-only
				rx-only
				tx-rx
				none
				
				XPath: /wing-config/device[mac=key1]/interface[name=key2]/rifs_mode"
			DEFVAL { "tx-rx" }
			::= { wingCfgDevIfRadioEntry 12 }

		
		-- 1.3.6.1.4.1.1916.2.131.50.1.3.18.3.5.1.13
		wingCfgDevIfRadioAmpduMaxAggrSizeRx OBJECT-TYPE
			SYNTAX DisplayString
			UNITS "bytes"
			MAX-ACCESS read-write
			STATUS current
			DESCRIPTION
				"Advertised maximum limit on A-MPDU aggregated received frames.
				
				Values:
				8191
				16383
				32767
				65535
				
				XPath: /wing-config/device[mac=key1]/interface[name=key2]/ampdu_max_aggr_size_rx"
			DEFVAL { "65535" }
			::= { wingCfgDevIfRadioEntry 13 }

		
		-- 1.3.6.1.4.1.1916.2.131.50.1.3.18.3.5.1.14
		wingCfgDevIfRadioAmpduMaxAggrSizeTx OBJECT-TYPE
			SYNTAX Unsigned32 (0..65535)
			UNITS "bytes"
			MAX-ACCESS read-write
			STATUS current
			DESCRIPTION
				"Limit on A-MPDU aggregated transmitted frames.
				
				XPath: /wing-config/device[mac=key1]/interface[name=key2]/ampdu_max_aggr_size_tx"
			DEFVAL { 65535 }
			::= { wingCfgDevIfRadioEntry 14 }

		
		-- 1.3.6.1.4.1.1916.2.131.50.1.3.18.3.5.1.15
		wingCfgDevIfRadioAmpduMinSpacing OBJECT-TYPE
			SYNTAX DisplayString
			UNITS "microseconds"
			MAX-ACCESS read-write
			STATUS current
			DESCRIPTION
				"Minimum gap between A-MPDU frames (in microseconds).
				
				Values:
				0
				1
				2
				4
				8
				16
				
				XPath: /wing-config/device[mac=key1]/interface[name=key2]/ampdu_min_spacing"
			DEFVAL { "4" }
			::= { wingCfgDevIfRadioEntry 15 }

		
		-- 1.3.6.1.4.1.1916.2.131.50.1.3.18.3.5.1.16
		wingCfgDevIfRadioAntennaMode OBJECT-TYPE
			SYNTAX DisplayString
			MAX-ACCESS read-write
			STATUS current
			DESCRIPTION
				"Number of transmit and receive antennas on the radio. 1x1 implies only the A antenna; 1x3 implies A for Tx and all three for Rx; default depends on the AP type, the type of power (802.3af etc), etc.
				
				Values:
				1x1
				1xALL
				2x2
				default
				
				XPath: /wing-config/device[mac=key1]/interface[name=key2]/antenna_mode"
			DEFVAL { "default" }
			::= { wingCfgDevIfRadioEntry 16 }

		
		-- 1.3.6.1.4.1.1916.2.131.50.1.3.18.3.5.1.17
		wingCfgDevIfRadioNonUnicastForwarding OBJECT-TYPE
			SYNTAX DisplayString
			MAX-ACCESS read-write
			STATUS current
			DESCRIPTION
				"Whether broadcast and multicast packets should always follow
				DTIM, or do so only if some wireless clients are in
				power-save mode.
				
				Values:
				follow-dtim
				power-save-aware
				
				XPath: /wing-config/device[mac=key1]/interface[name=key2]/non_unicast_forwarding"
			DEFVAL { "follow-dtim" }
			::= { wingCfgDevIfRadioEntry 17 }

		
		-- 1.3.6.1.4.1.1916.2.131.50.1.3.18.3.5.1.18
		wingCfgDevIfRadioDynamicChainSelection OBJECT-TYPE
			SYNTAX TruthValue
			MAX-ACCESS read-write
			STATUS current
			DESCRIPTION
				"Whether the radio should dynamically change the number of
				transmit chains used (use a single chain/antenna for frames
				at non-11n data-rates).
				
				XPath: /wing-config/device[mac=key1]/interface[name=key2]/dynamic_chain_selection"
			DEFVAL { false }
			::= { wingCfgDevIfRadioEntry 18 }

		
		-- 1.3.6.1.4.1.1916.2.131.50.1.3.18.3.5.1.19
		wingCfgDevIfRadioLockRfMode OBJECT-TYPE
			SYNTAX TruthValue
			MAX-ACCESS read-write
			STATUS current
			DESCRIPTION
				"Lock Smart RF mode of operation for this radio.
				
				XPath: /wing-config/device[mac=key1]/interface[name=key2]/lock_rf_mode"
			DEFVAL { false }
			::= { wingCfgDevIfRadioEntry 19 }

		
		-- 1.3.6.1.4.1.1916.2.131.50.1.3.18.3.5.1.20
		wingCfgDevIfRadioSnifferRedirHost OBJECT-TYPE
			SYNTAX DisplayString
			MAX-ACCESS read-write
			STATUS current
			DESCRIPTION
				"Address of host to which captured packets are redirected.
				
				XPath: /wing-config/device[mac=key1]/interface[name=key2]/sniffer_redirect/host"
			::= { wingCfgDevIfRadioEntry 20 }

		
		-- 1.3.6.1.4.1.1916.2.131.50.1.3.18.3.5.1.21
		wingCfgDevIfRadioSnifferRedirChannel OBJECT-TYPE
			SYNTAX DisplayString
			MAX-ACCESS read-write
			STATUS current
			DESCRIPTION
				"Channel on which to capture packets.
				
				Values:
				1, 1+, 2, 2+, 3, 3+, 4, 4+, 5, 5+, 5-, 6, 6+, 6-, 7, 7+, 7-,
				8, 8+, 8-, 9, 9+, 9-, 10, 10-, 11, 11-, 12, 12-, 13, 13-, 14,
				36, 36+, 40, 40-, 44, 44+, 48, 48-, 52, 52+, 56, 56-, 60, 60+,
				64, 64-, 100, 100+, 104, 104-, 108, 108+, 112, 112-, 116,
				116+, 120, 120-, 124, 124+, 128, 128-, 132, 132+, 136, 136-,
				140, 149, 149+, 153, 153-, 157, 157+, 161, 161-, 165, 34, 38,
				42, and 46
				
				XPath: /wing-config/device[mac=key1]/interface[name=key2]/sniffer_redirect/channel"
			DEFVAL { "1" }
			::= { wingCfgDevIfRadioEntry 21 }

		
		-- 1.3.6.1.4.1.1916.2.131.50.1.3.18.3.5.1.22
		wingCfgDevIfRadioMesh OBJECT-TYPE
			SYNTAX DisplayString
			MAX-ACCESS read-write
			STATUS current
			DESCRIPTION
				"Client operation scans for Mesh Portals, or nodes that have
				connectivity to Portals, and connects through them. 
				Portal operation begins beaconing immediately and accepting
				connections from other Mesh nodes.  Generally the Portal node
				is connected to the wired network.
				
				Values:
				disabled
				portal
				client
				
				XPath: /wing-config/device[mac=key1]/interface[name=key2]/mesh"
			DEFVAL { "disabled" }
			::= { wingCfgDevIfRadioEntry 22 }

		
		-- 1.3.6.1.4.1.1916.2.131.50.1.3.18.3.5.1.23
		wingCfgDevIfRadioMeshLinks OBJECT-TYPE
			SYNTAX Unsigned32 (1..6)
			MAX-ACCESS read-write
			STATUS current
			DESCRIPTION
				"Maximum number of Mesh links that this radio will attempt to
				create.
				
				XPath: /wing-config/device[mac=key1]/interface[name=key2]/mesh_links"
			DEFVAL { 3 }
			::= { wingCfgDevIfRadioEntry 23 }

		
		-- 1.3.6.1.4.1.1916.2.131.50.1.3.18.3.5.1.24
		wingCfgDevIfRadioProbeResponseRetry OBJECT-TYPE
			SYNTAX TruthValue
			MAX-ACCESS read-write
			STATUS current
			DESCRIPTION
				"Whether Probe-Responses are retried on the air if they are
				not acknowledged by the wireless client
				
				XPath: /wing-config/device[mac=key1]/interface[name=key2]/probe_response_retry"
			DEFVAL { true }
			::= { wingCfgDevIfRadioEntry 24 }

		
		-- 1.3.6.1.4.1.1916.2.131.50.1.3.18.3.5.1.25
		wingCfgDevIfRadioProbeResponseRate OBJECT-TYPE
			SYNTAX DisplayString
			MAX-ACCESS read-write
			STATUS current
			DESCRIPTION
				"The data transmission rate used for sending Probe Responses
				
				Values:
				follow-probe-request
				highest-basic
				lowest-basic
				
				XPath: /wing-config/device[mac=key1]/interface[name=key2]/probe_response_rate"
			DEFVAL { "follow-probe-request" }
			::= { wingCfgDevIfRadioEntry 25 }

		
		-- 1.3.6.1.4.1.1916.2.131.50.1.3.18.3.5.1.26
		wingCfgDevIfRadioMaxClients OBJECT-TYPE
			SYNTAX Unsigned32 (0..256)
			MAX-ACCESS read-write
			STATUS current
			DESCRIPTION
				"The maximum number of clients allowed to associate
				with this radio
				
				XPath: /wing-config/device[mac=key1]/interface[name=key2]/max_clients"
			DEFVAL { 256 }
			::= { wingCfgDevIfRadioEntry 26 }

		
		-- 1.3.6.1.4.1.1916.2.131.50.1.3.18.3.5.1.27
		wingCfgDevIfRadioRadioTapMode OBJECT-TYPE
			SYNTAX DisplayString
			MAX-ACCESS read-write
			STATUS current
			DESCRIPTION
				"Radio tap mode of operation
				
				Values:
				off
				inline
				promiscuous
				
				Note:
				Radio tap can be enabled only on wlan radio and in 5.1,
				only when another radio on AP is sensor.
				
				XPath: /wing-config/device[mac=key1]/interface[name=key2]/radio_tap_mode"
			DEFVAL { "off" }
			::= { wingCfgDevIfRadioEntry 27 }

		
		-- 1.3.6.1.4.1.1916.2.131.50.1.3.18.3.5.1.28
		wingCfgDevIfRadioWirelessClientPower OBJECT-TYPE
			SYNTAX Unsigned32 (0..20)
			UNITS "dBm"
			MAX-ACCESS read-write
			STATUS current
			DESCRIPTION
				"Transmit power indicated to wireless clients for transmission.
				
				XPath: /wing-config/device[mac=key1]/interface[name=key2]/wireless_client_power"
			::= { wingCfgDevIfRadioEntry 28 }

		
		-- 1.3.6.1.4.1.1916.2.131.50.1.3.18.3.5.1.29
		wingCfgDevIfRadioLoadBalLfCount OBJECT-TYPE
			SYNTAX Unsigned32 (0..10)
			MAX-ACCESS read-write
			STATUS current
			DESCRIPTION
				"Consider the number of Wireless Clients in determining
				the load on an AP.  High numbers indicate a higher weight
				assigned to the criteria. 0 implies that count is
				not considered.
				
				XPath: /wing-config/device[mac=key1]/interface[name=key2]/load_balance_lf_count"
			DEFVAL { 10 }
			::= { wingCfgDevIfRadioEntry 29 }

		
		-- 1.3.6.1.4.1.1916.2.131.50.1.3.18.3.5.1.30
		wingCfgDevIfRadioLoadBalLfThroughput OBJECT-TYPE
			SYNTAX Unsigned32 (0..10)
			MAX-ACCESS read-write
			STATUS current
			DESCRIPTION
				"Consider the throughput of traffic in determining the load
				on an AP.  High numbers indicate a higher weight assigned
				to the criteria.  0 implies that throughput is not considered.
				
				XPath: /wing-config/device[mac=key1]/interface[name=key2]/load_balance_lf_throughput"
			DEFVAL { 0 }
			::= { wingCfgDevIfRadioEntry 30 }

		
		-- 1.3.6.1.4.1.1916.2.131.50.1.3.18.3.5.1.31
		wingCfgDevIfRadioLoadBalWmCount OBJECT-TYPE
			SYNTAX Unsigned32 (1..255)
			MAX-ACCESS read-write
			STATUS current
			DESCRIPTION
				"The number of clients that can associate with a radio before
				load-balancing would be triggered
				
				XPath: /wing-config/device[mac=key1]/interface[name=key2]/load_balance_wm_count"
			DEFVAL { 10 }
			::= { wingCfgDevIfRadioEntry 31 }

		
		-- 1.3.6.1.4.1.1916.2.131.50.1.3.18.3.5.1.32
		wingCfgDevIfRadioLoadBalWmTput OBJECT-TYPE
			SYNTAX Unsigned32 (1..1000)
			MAX-ACCESS read-write
			STATUS current
			DESCRIPTION
				"When the average throughput of a radio exceeds this threshold
				(in Mbps) load balancing would be triggered
				
				XPath: /wing-config/device[mac=key1]/interface[name=key2]/load_balance_wm_tput_mbps"
			DEFVAL { 10 }
			::= { wingCfgDevIfRadioEntry 32 }

		
		-- 1.3.6.1.4.1.1916.2.131.50.1.3.18.3.5.1.33
		wingCfgDevIfRadioAssocAcl OBJECT-TYPE
			SYNTAX WingIdentifier
			MAX-ACCESS read-write
			STATUS current
			DESCRIPTION
				"
				
				XPath: /wing-config/device[mac=key1]/interface[name=key2]/assoc_acl"
			::= { wingCfgDevIfRadioEntry 33 }

		
		-- 1.3.6.1.4.1.1916.2.131.50.1.3.18.3.5.1.34
		wingCfgDevIfRadioQosPolicy OBJECT-TYPE
			SYNTAX WingIdentifier
			MAX-ACCESS read-write
			STATUS current
			DESCRIPTION
				"
				
				XPath: /wing-config/device[mac=key1]/interface[name=key2]/qos_policy"
			::= { wingCfgDevIfRadioEntry 34 }

                -- 1.3.6.1.4.1.1916.2.131.50.1.3.18.3.5.1.35
                wingCfgDevIfRadioAntennaDowntilt OBJECT-TYPE
                        SYNTAX TruthValue
                        MAX-ACCESS read-write
                        STATUS current
                        DESCRIPTION
                                "Whether the radio should enable ADEPT antenna modes.
 
                                XPath: /wing-config/device[mac=key1]/interface[name=key2]/antenna_downtilt"
                        DEFVAL { false }
                        ::= { wingCfgDevIfRadioEntry 35 }
 
 
                -- 1.3.6.1.4.1.1916.2.131.50.1.3.18.3.5.1.36
                wingCfgDevIfRadioExtendedRange OBJECT-TYPE
                        SYNTAX Unsigned32
                        MAX-ACCESS read-write
                        STATUS current
                        DESCRIPTION
                                "Configure extended rate selection.

				Default Value
                                for 2.4 Ghz : 7 Kilometer
                                    5 GHz   : 2 Kilometer
                                XPath: /wing-config/device[mac=key1]/interface[name=key2]/extended_range"
                        DEFVAL { "kilometer" }
                        ::= { wingCfgDevIfRadioEntry 36 }

		-- 1.3.6.1.4.1.1916.2.131.50.1.3.18.3.6
		wingCfgDevIfRadioBssmapTable OBJECT-TYPE
			SYNTAX SEQUENCE OF WingCfgDevIfRadioBssmapEntry
			MAX-ACCESS not-accessible
			STATUS current
			DESCRIPTION
				"
				
				/wing-config/device/interface/wlanbssmap"
			::= { wingCfgDevIf 6 }

		
		-- 1.3.6.1.4.1.1916.2.131.50.1.3.18.3.6.1
		wingCfgDevIfRadioBssmapEntry OBJECT-TYPE
			SYNTAX WingCfgDevIfRadioBssmapEntry
			MAX-ACCESS not-accessible
			STATUS current
			DESCRIPTION
				"An entry in the table."
			INDEX { wingCfgDevMac, wingCfgDevIfName, wingCfgDevIfRadioBssmapWlan }
			::= { wingCfgDevIfRadioBssmapTable 1 }

		
		WingCfgDevIfRadioBssmapEntry ::=
			SEQUENCE { 
				wingCfgDevIfRadioBssmapWlan
					WingIdentifier,
				wingCfgDevIfRadioBssmapBss
					Unsigned32,
				wingCfgDevIfRadioBssmapPrimary
					TruthValue
			 }

		-- 1.3.6.1.4.1.1916.2.131.50.1.3.18.3.6.1.1
		wingCfgDevIfRadioBssmapWlan OBJECT-TYPE
			SYNTAX WingIdentifier
			MAX-ACCESS read-only
			STATUS current
			DESCRIPTION
				"
				
				XPath: /wing-config/device[mac=key1]/interface[name=key2]/wlanbssmap[wlan=key3]/wlan"
			::= { wingCfgDevIfRadioBssmapEntry 1 }

		
		-- 1.3.6.1.4.1.1916.2.131.50.1.3.18.3.6.1.3
		wingCfgDevIfRadioBssmapBss OBJECT-TYPE
			SYNTAX Unsigned32 (1..8)
			MAX-ACCESS read-write
			STATUS current
			DESCRIPTION
				"
				
				XPath: /wing-config/device[mac=key1]/interface[name=key2]/wlanbssmap[wlan=key3]/bss"
			::= { wingCfgDevIfRadioBssmapEntry 3 }

		
		-- 1.3.6.1.4.1.1916.2.131.50.1.3.18.3.6.1.4
		wingCfgDevIfRadioBssmapPrimary OBJECT-TYPE
			SYNTAX TruthValue
			MAX-ACCESS read-write
			STATUS current
			DESCRIPTION
				"
				
				XPath: /wing-config/device[mac=key1]/interface[name=key2]/wlanbssmap[wlan=key3]/primary"
			::= { wingCfgDevIfRadioBssmapEntry 4 }

		
		-- 1.3.6.1.4.1.1916.2.131.50.1.3.18.3.8
		wingCfgDevIfSpanTreeTable OBJECT-TYPE
			SYNTAX SEQUENCE OF WingCfgDevIfSpanTreeEntry
			MAX-ACCESS not-accessible
			STATUS current
			DESCRIPTION
				"Interface Spanning Tree configuration
				
				/wing-config/device/interface/spanningtree"
			::= { wingCfgDevIf 8 }

		
		-- 1.3.6.1.4.1.1916.2.131.50.1.3.18.3.8.1
		wingCfgDevIfSpanTreeEntry OBJECT-TYPE
			SYNTAX WingCfgDevIfSpanTreeEntry
			MAX-ACCESS not-accessible
			STATUS current
			DESCRIPTION
				"An entry in the table."
			INDEX { wingCfgDevMac, wingCfgDevIfName }
			::= { wingCfgDevIfSpanTreeTable 1 }

		
		WingCfgDevIfSpanTreeEntry ::=
			SEQUENCE { 
				wingCfgDevIfSpanTreeLinkType
					DisplayString,
				wingCfgDevIfSpanTreePortfast
					TruthValue,
				wingCfgDevIfSpanTreeEdgeport
					TruthValue,
				wingCfgDevIfSpanTreeBpduguard
					DisplayString,
				wingCfgDevIfSpanTreeBpdufilter
					DisplayString,
				wingCfgDevIfSpanTreePortCiscoInterop
					DisplayString,
				wingCfgDevIfSpanTreeForceVersion
					Unsigned32,
				wingCfgDevIfSpanTreeGuard
					DisplayString
			 }

		-- 1.3.6.1.4.1.1916.2.131.50.1.3.18.3.8.1.1
		wingCfgDevIfSpanTreeLinkType OBJECT-TYPE
			SYNTAX DisplayString
			MAX-ACCESS read-write
			STATUS current
			DESCRIPTION
				"Point-to-point enables rapid transition.  Shared disables
				rapid transition.
				
				Values:
				point-to-point
				shared
				
				XPath: /wing-config/device[mac=key1]/interface[name=key2]/spanningtree/link_type"
			DEFVAL { "point-to-point" }
			::= { wingCfgDevIfSpanTreeEntry 1 }

		
		-- 1.3.6.1.4.1.1916.2.131.50.1.3.18.3.8.1.2
		wingCfgDevIfSpanTreePortfast OBJECT-TYPE
			SYNTAX TruthValue
			MAX-ACCESS read-write
			STATUS current
			DESCRIPTION
				"Enable fast transitions.
				
				XPath: /wing-config/device[mac=key1]/interface[name=key2]/spanningtree/portfast"
			DEFVAL { false }
			::= { wingCfgDevIfSpanTreeEntry 2 }

		
		-- 1.3.6.1.4.1.1916.2.131.50.1.3.18.3.8.1.3
		wingCfgDevIfSpanTreeEdgeport OBJECT-TYPE
			SYNTAX TruthValue
			MAX-ACCESS read-write
			STATUS current
			DESCRIPTION
				"Enable the port as an edge port.
				
				XPath: /wing-config/device[mac=key1]/interface[name=key2]/spanningtree/edgeport"
			DEFVAL { false }
			::= { wingCfgDevIfSpanTreeEntry 3 }

		
		-- 1.3.6.1.4.1.1916.2.131.50.1.3.18.3.8.1.4
		wingCfgDevIfSpanTreeBpduguard OBJECT-TYPE
			SYNTAX DisplayString
			MAX-ACCESS read-write
			STATUS current
			DESCRIPTION
				"Guard the port against reception of BPDUs.
				
				Values:
				none
				enable
				disable
				
				XPath: /wing-config/device[mac=key1]/interface[name=key2]/spanningtree/bpduguard"
			DEFVAL { "none" }
			::= { wingCfgDevIfSpanTreeEntry 4 }

		
		-- 1.3.6.1.4.1.1916.2.131.50.1.3.18.3.8.1.5
		wingCfgDevIfSpanTreeBpdufilter OBJECT-TYPE
			SYNTAX DisplayString
			MAX-ACCESS read-write
			STATUS current
			DESCRIPTION
				"Set the PortFast BPDU filter for the port.  Enabling the BPDU
				filter ensures that PortFast enabled ports do not transmit or
				receive BPDUs.
				
				Values:
				none
				enable
				disable
				
				XPath: /wing-config/device[mac=key1]/interface[name=key2]/spanningtree/bpdufilter"
			DEFVAL { "none" }
			::= { wingCfgDevIfSpanTreeEntry 5 }

		
		-- 1.3.6.1.4.1.1916.2.131.50.1.3.18.3.8.1.6
		wingCfgDevIfSpanTreePortCiscoInterop OBJECT-TYPE
			SYNTAX DisplayString
			MAX-ACCESS read-write
			STATUS current
			DESCRIPTION
				"Enable interoperability with Cisco's version of MSTP,
				which is incompatible with standard MSTP.
				
				Values:
				enable
				disable
				
				XPath: /wing-config/device[mac=key1]/interface[name=key2]/spanningtree/port_cisco_interop"
			DEFVAL { "disable" }
			::= { wingCfgDevIfSpanTreeEntry 6 }

		
		-- 1.3.6.1.4.1.1916.2.131.50.1.3.18.3.8.1.7
		wingCfgDevIfSpanTreeForceVersion OBJECT-TYPE
			SYNTAX Unsigned32 (0..3)
			MAX-ACCESS read-write
			STATUS current
			DESCRIPTION
				"Version identifier where 0=STP, 1=Not Supported, 2=RSTP,
				3=MSTP.
				
				XPath: /wing-config/device[mac=key1]/interface[name=key2]/spanningtree/force_version"
			DEFVAL { 3 }
			::= { wingCfgDevIfSpanTreeEntry 7 }

		
		-- 1.3.6.1.4.1.1916.2.131.50.1.3.18.3.8.1.8
		wingCfgDevIfSpanTreeGuard OBJECT-TYPE
			SYNTAX DisplayString
			MAX-ACCESS read-write
			STATUS current
			DESCRIPTION
				"Setting 'root' disables reception of superior BPDUs.
				
				Values:
				none
				root
				
				XPath: /wing-config/device[mac=key1]/interface[name=key2]/spanningtree/guard"
			DEFVAL { "none" }
			::= { wingCfgDevIfSpanTreeEntry 8 }

		
		-- 1.3.6.1.4.1.1916.2.131.50.1.3.18.3.11
		wingCfgDevIfVlanOspfTable OBJECT-TYPE
			SYNTAX SEQUENCE OF WingCfgDevIfVlanOspfEntry
			MAX-ACCESS not-accessible
			STATUS current
			DESCRIPTION
				"
				
				/wing-config/device/interface"
			::= { wingCfgDevIf 11 }

		
		-- 1.3.6.1.4.1.1916.2.131.50.1.3.18.3.11.1
		wingCfgDevIfVlanOspfEntry OBJECT-TYPE
			SYNTAX WingCfgDevIfVlanOspfEntry
			MAX-ACCESS not-accessible
			STATUS current
			DESCRIPTION
				"An entry in the table."
			INDEX { wingCfgDevMac, wingCfgDevIfName }
			::= { wingCfgDevIfVlanOspfTable 1 }

		
		WingCfgDevIfVlanOspfEntry ::=
			SEQUENCE { 
				wingCfgDevIfVlanOspfOspfAuthentication
					DisplayString,
				wingCfgDevIfVlanOspfOspfAuthKey
					DisplayString,
				wingCfgDevIfVlanOspfOspfPriority
					Unsigned32,
				wingCfgDevIfVlanOspfOspfCost
					Unsigned32,
				wingCfgDevIfVlanOspfOspfBandWidth
					Unsigned32
			 }

		-- 1.3.6.1.4.1.1916.2.131.50.1.3.18.3.11.1.1
		wingCfgDevIfVlanOspfOspfAuthentication OBJECT-TYPE
			SYNTAX DisplayString
			MAX-ACCESS read-write
			STATUS current
			DESCRIPTION
				"OSPF authentication type
				
				Values:
				simple-password,
				message-digest,
				none
				
				XPath: /wing-config/device[mac=key1]/interface[name=key2]/ospf_authentication"
			DEFVAL { "none" }
			::= { wingCfgDevIfVlanOspfEntry 1 }

		
		-- 1.3.6.1.4.1.1916.2.131.50.1.3.18.3.11.1.2
		wingCfgDevIfVlanOspfOspfAuthKey OBJECT-TYPE
			SYNTAX DisplayString (SIZE (1..8))
			MAX-ACCESS read-write
			STATUS current
			DESCRIPTION
				"Simple auth key for OSPF.
				 Max 8 characters are accepted for the key.

				XPath: /wing-config/device[mac=key1]/interface[name=key2]/ospf_auth_key"
			::= { wingCfgDevIfVlanOspfEntry 2 }

		
		-- 1.3.6.1.4.1.1916.2.131.50.1.3.18.3.11.1.3
		wingCfgDevIfVlanOspfOspfPriority OBJECT-TYPE
			SYNTAX Unsigned32 (0..255)
			MAX-ACCESS read-write
			STATUS current
			DESCRIPTION
				"OSPF priority used in DR election
				
				XPath: /wing-config/device[mac=key1]/interface[name=key2]/ospf_priority"
			DEFVAL { 0 }
			::= { wingCfgDevIfVlanOspfEntry 3 }

		
		-- 1.3.6.1.4.1.1916.2.131.50.1.3.18.3.11.1.4
		wingCfgDevIfVlanOspfOspfCost OBJECT-TYPE
			SYNTAX Unsigned32 (1..65535)
			MAX-ACCESS read-write
			STATUS current
			DESCRIPTION
				"Cost of this OSPF interface
				
				XPath: /wing-config/device[mac=key1]/interface[name=key2]/ospf_cost"
			DEFVAL { 10 }
			::= { wingCfgDevIfVlanOspfEntry 4 }

		
		-- 1.3.6.1.4.1.1916.2.131.50.1.3.18.3.11.1.5
		wingCfgDevIfVlanOspfOspfBandWidth OBJECT-TYPE
			SYNTAX Unsigned32 (1..10000000)
			MAX-ACCESS read-write
			STATUS current
			DESCRIPTION
				"Bandwidth of the interface in Kbps.
				
				XPath: /wing-config/device[mac=key1]/interface[name=key2]/bandwidth"
			::= { wingCfgDevIfVlanOspfEntry 5 }

		
		-- 1.3.6.1.4.1.1916.2.131.50.1.3.18.3.12
		wingCfgDevIfVlanOspfMsgDigestTable OBJECT-TYPE
			SYNTAX SEQUENCE OF WingCfgDevIfVlanOspfMsgDigestEntry
			MAX-ACCESS not-accessible
			STATUS current
			DESCRIPTION
				"
				
				/wing-config/device/interface/ospf_message_digest_key"
			::= { wingCfgDevIf 12 }

		
		-- 1.3.6.1.4.1.1916.2.131.50.1.3.18.3.12.1
		wingCfgDevIfVlanOspfMsgDigestEntry OBJECT-TYPE
			SYNTAX WingCfgDevIfVlanOspfMsgDigestEntry
			MAX-ACCESS not-accessible
			STATUS current
			DESCRIPTION
				"An entry in the table."
			INDEX { wingCfgDevMac, wingCfgDevIfName, wingCfgDevIfVlanOspfMsgDigestKeyId }
			::= { wingCfgDevIfVlanOspfMsgDigestTable 1 }

		
		WingCfgDevIfVlanOspfMsgDigestEntry ::=
			SEQUENCE { 
				wingCfgDevIfVlanOspfMsgDigestKeyId
					Unsigned32,
				wingCfgDevIfVlanOspfMsgDigestMessageDigest
					DisplayString
			 }

		-- 1.3.6.1.4.1.1916.2.131.50.1.3.18.3.12.1.1
		wingCfgDevIfVlanOspfMsgDigestKeyId OBJECT-TYPE
			SYNTAX Unsigned32 (1..255)
			MAX-ACCESS read-only
			STATUS current
			DESCRIPTION
				"OSPF message digest auth key ID.
				
				XPath: /wing-config/device[mac=key1]/interface[name=key2]/ospf_message_digest_key[key_id=key3]/key_id"
			::= { wingCfgDevIfVlanOspfMsgDigestEntry 1 }

		
		-- 1.3.6.1.4.1.1916.2.131.50.1.3.18.3.12.1.3
		wingCfgDevIfVlanOspfMsgDigestMessageDigest OBJECT-TYPE
			SYNTAX DisplayString
			MAX-ACCESS read-write
			STATUS current
			DESCRIPTION
				"OSPF message digest key.
				
				XPath: /wing-config/device[mac=key1]/interface[name=key2]/ospf_message_digest_key[key_id=key3]/message_digest"
			::= { wingCfgDevIfVlanOspfMsgDigestEntry 3 }

		
		-- 1.3.6.1.4.1.1916.2.131.50.1.3.18.3.13
		wingCfgDevIfPppoeTable OBJECT-TYPE
			SYNTAX SEQUENCE OF WingCfgDevIfPppoeEntry
			MAX-ACCESS not-accessible
			STATUS current
			DESCRIPTION
				"
				
				/wing-config/device/interface"
			::= { wingCfgDevIf 13 }

		
		-- 1.3.6.1.4.1.1916.2.131.50.1.3.18.3.13.1
		wingCfgDevIfPppoeEntry OBJECT-TYPE
			SYNTAX WingCfgDevIfPppoeEntry
			MAX-ACCESS not-accessible
			STATUS current
			DESCRIPTION
				"An entry in the table."
			INDEX { wingCfgDevMac, wingCfgDevIfName }
			::= { wingCfgDevIfPppoeTable 1 }

		
		WingCfgDevIfPppoeEntry ::=
			SEQUENCE { 
				wingCfgDevIfPppoeAuthType
					DisplayString,
				wingCfgDevIfPppoeIdleTime
					Unsigned32,
				wingCfgDevIfPppoeKeepalive
					TruthValue,
				wingCfgDevIfPppoeUsername
					DisplayString,
				wingCfgDevIfPppoePassword
					DisplayString,
				wingCfgDevIfPppoeService
					DisplayString,
				wingCfgDevIfPppoeLocalnetVlan
					Unsigned32,
				wingCfgDevIfPppoeMtu
					Unsigned32,
				wingCfgDevIfPppoeDefaultRoutePriority
					Unsigned32,
				wingCfgDevIfPppoeIp
					DisplayString
			 }

		-- 1.3.6.1.4.1.1916.2.131.50.1.3.18.3.13.1.1
		wingCfgDevIfPppoeAuthType OBJECT-TYPE
			SYNTAX DisplayString
			MAX-ACCESS read-write
			STATUS current
			DESCRIPTION
				"PPPoE Client authentication type.
				
				Values:
				none,
				chap,
				mschap,
				mschap-v2,
				pap
				
				XPath: /wing-config/device[mac=key1]/interface[name=key2]/auth-type"
			DEFVAL { "pap" }
			::= { wingCfgDevIfPppoeEntry 1 }

		
		-- 1.3.6.1.4.1.1916.2.131.50.1.3.18.3.13.1.2
		wingCfgDevIfPppoeIdleTime OBJECT-TYPE
			SYNTAX Unsigned32 (1..65535)
			UNITS "seconds"
			MAX-ACCESS read-write
			STATUS current
			DESCRIPTION
				"PPPoE client Idle Timeout.
				
				XPath: /wing-config/device[mac=key1]/interface[name=key2]/idle-time"
			DEFVAL { 600 }
			::= { wingCfgDevIfPppoeEntry 2 }

		
		-- 1.3.6.1.4.1.1916.2.131.50.1.3.18.3.13.1.3
		wingCfgDevIfPppoeKeepalive OBJECT-TYPE
			SYNTAX TruthValue
			MAX-ACCESS read-write
			STATUS current
			DESCRIPTION
				"PPPoE client keep-alive mode.
				
				XPath: /wing-config/device[mac=key1]/interface[name=key2]/keepalive"
			DEFVAL { false }
			::= { wingCfgDevIfPppoeEntry 3 }

		
		-- 1.3.6.1.4.1.1916.2.131.50.1.3.18.3.13.1.4
		wingCfgDevIfPppoeUsername OBJECT-TYPE
			SYNTAX DisplayString (SIZE (0..64))
			MAX-ACCESS read-write
			STATUS current
			DESCRIPTION
				"PPPoE client username.
				
				XPath: /wing-config/device[mac=key1]/interface[name=key2]/username"
			DEFVAL { "" }
			::= { wingCfgDevIfPppoeEntry 4 }

		
		-- 1.3.6.1.4.1.1916.2.131.50.1.3.18.3.13.1.5
		wingCfgDevIfPppoePassword OBJECT-TYPE
			SYNTAX DisplayString (SIZE (0..64))
			MAX-ACCESS read-write
			STATUS current
			DESCRIPTION
				"PPPoE client password.
				
				XPath: /wing-config/device[mac=key1]/interface[name=key2]/password"
			DEFVAL { "" }
			::= { wingCfgDevIfPppoeEntry 5 }

		
		-- 1.3.6.1.4.1.1916.2.131.50.1.3.18.3.13.1.6
		wingCfgDevIfPppoeService OBJECT-TYPE
			SYNTAX DisplayString (SIZE (0..128))
			MAX-ACCESS read-write
			STATUS current
			DESCRIPTION
				"PPPoE client service-name.
				
				XPath: /wing-config/device[mac=key1]/interface[name=key2]/service"
			DEFVAL { "" }
			::= { wingCfgDevIfPppoeEntry 6 }

		
		-- 1.3.6.1.4.1.1916.2.131.50.1.3.18.3.13.1.7
		wingCfgDevIfPppoeLocalnetVlan OBJECT-TYPE
			SYNTAX Unsigned32 (1..4094)
			MAX-ACCESS read-write
			STATUS current
			DESCRIPTION
				"PPPoE client local network(vlan) connected to DSL modem.
				
				XPath: /wing-config/device[mac=key1]/interface[name=key2]/localnet_vlan"
			DEFVAL { 1 }
			::= { wingCfgDevIfPppoeEntry 7 }

		
		-- 1.3.6.1.4.1.1916.2.131.50.1.3.18.3.13.1.8
		wingCfgDevIfPppoeMtu OBJECT-TYPE
			SYNTAX Unsigned32 (500..1492)
			MAX-ACCESS read-write
			STATUS current
			DESCRIPTION
				"PPPoE client Maximum Transmission Unit(MTU).
				
				XPath: /wing-config/device[mac=key1]/interface[name=key2]/mtu"
			DEFVAL { 1492 }
			::= { wingCfgDevIfPppoeEntry 8 }

		
		-- 1.3.6.1.4.1.1916.2.131.50.1.3.18.3.13.1.9
		wingCfgDevIfPppoeDefaultRoutePriority OBJECT-TYPE
			SYNTAX Unsigned32 (1..8000)
			MAX-ACCESS read-write
			STATUS current
			DESCRIPTION
				"Priority for the default route learnt via PPPoE
				
				XPath: /wing-config/device[mac=key1]/interface[name=key2]/pppoe_default_route_priority"
			DEFVAL { 2000 }
			::= { wingCfgDevIfPppoeEntry 9 }

		
		-- 1.3.6.1.4.1.1916.2.131.50.1.3.18.3.13.1.10
		wingCfgDevIfPppoeIp OBJECT-TYPE
			SYNTAX DisplayString
			MAX-ACCESS read-write
			STATUS current
			DESCRIPTION
				"PPPoE client IP address.
				
				XPath: /wing-config/device[mac=key1]/interface[name=key2]/ip"
			DEFVAL { "0.0.0.0" }
			::= { wingCfgDevIfPppoeEntry 10 }

		
		-- 1.3.6.1.4.1.1916.2.131.50.1.3.18.3.14
		wingCfgDevIfT1E1Table OBJECT-TYPE
			SYNTAX SEQUENCE OF WingCfgDevIfT1E1Entry
			MAX-ACCESS not-accessible
			STATUS current
			DESCRIPTION
				"T1 or E1 interface (switched interface) configuration.
				
				/wing-config/device/interface"
			::= { wingCfgDevIf 14 }

		
		-- 1.3.6.1.4.1.1916.2.131.50.1.3.18.3.14.1
		wingCfgDevIfT1E1Entry OBJECT-TYPE
			SYNTAX WingCfgDevIfT1E1Entry
			MAX-ACCESS not-accessible
			STATUS current
			DESCRIPTION
				"An entry in the table."
			INDEX { wingCfgDevMac, wingCfgDevIfName }
			::= { wingCfgDevIfT1E1Table 1 }

		
		WingCfgDevIfT1E1Entry ::=
			SEQUENCE { 
				wingCfgDevIfT1E1Media
					DisplayString,
				wingCfgDevIfT1E1ClockMode
					DisplayString,
				wingCfgDevIfT1E1HighImpedance
					DisplayString,
				wingCfgDevIfT1E1LineBuildOut
					DisplayString,
				wingCfgDevIfT1E1LineEncoding
					DisplayString,
				wingCfgDevIfT1E1RxSensitivityLevel
					DisplayString
			 }

		-- 1.3.6.1.4.1.1916.2.131.50.1.3.18.3.14.1.1
		wingCfgDevIfT1E1Media OBJECT-TYPE
			SYNTAX DisplayString
			MAX-ACCESS read-write
			STATUS current
			DESCRIPTION
				"The media type for the physical interface
				
				Values:
				t1
				e1
				
				XPath: /wing-config/device[mac=key1]/interface[name=key2]/media"
			DEFVAL { "t1" }
			::= { wingCfgDevIfT1E1Entry 1 }

		
		-- 1.3.6.1.4.1.1916.2.131.50.1.3.18.3.14.1.2
		wingCfgDevIfT1E1ClockMode OBJECT-TYPE
			SYNTAX DisplayString
			MAX-ACCESS read-write
			STATUS current
			DESCRIPTION
				"The mode for the clock
				
				Values:
				normal
				master
				
				XPath: /wing-config/device[mac=key1]/interface[name=key2]/clock_mode"
			DEFVAL { "normal" }
			::= { wingCfgDevIfT1E1Entry 2 }

		
		-- 1.3.6.1.4.1.1916.2.131.50.1.3.18.3.14.1.3
		wingCfgDevIfT1E1HighImpedance OBJECT-TYPE
			SYNTAX DisplayString
			MAX-ACCESS read-write
			STATUS current
			DESCRIPTION
				"High impedance mode
				
				Values:
				disable
				enable
				
				XPath: /wing-config/device[mac=key1]/interface[name=key2]/high_impedance"
			DEFVAL { "disable" }
			::= { wingCfgDevIfT1E1Entry 3 }

		
		-- 1.3.6.1.4.1.1916.2.131.50.1.3.18.3.14.1.4
		wingCfgDevIfT1E1LineBuildOut OBJECT-TYPE
			SYNTAX DisplayString
			MAX-ACCESS read-write
			STATUS current
			DESCRIPTION
				"Line build out in decibels (dB) or feet (ft)
				
				Values:
				0-110ft
				0dB
				110-220ft
				15dB
				22.5dB
				220-330ft
				330-440ft
				440-550ft
				550-660ft
				7.5dB
				
				XPath: /wing-config/device[mac=key1]/interface[name=key2]/line_build_out"
			DEFVAL { "0dB" }
			::= { wingCfgDevIfT1E1Entry 4 }

		
		-- 1.3.6.1.4.1.1916.2.131.50.1.3.18.3.14.1.5
		wingCfgDevIfT1E1LineEncoding OBJECT-TYPE
			SYNTAX DisplayString
			MAX-ACCESS read-write
			STATUS current
			DESCRIPTION
				"Line encoding type
				
				Values:
				ami
				b8zs
				
				XPath: /wing-config/device[mac=key1]/interface[name=key2]/line_encoding"
			DEFVAL { "b8zs" }
			::= { wingCfgDevIfT1E1Entry 5 }

		
		-- 1.3.6.1.4.1.1916.2.131.50.1.3.18.3.14.1.6
		wingCfgDevIfT1E1RxSensitivityLevel OBJECT-TYPE
			SYNTAX DisplayString
			MAX-ACCESS read-write
			STATUS current
			DESCRIPTION
				"Receive sensitivity level in decibels
				
				Values:
				12dB
				18dB
				30dB
				36dB
				
				XPath: /wing-config/device[mac=key1]/interface[name=key2]/rx_sensitivity_level"
			DEFVAL { "36dB" }
			::= { wingCfgDevIfT1E1Entry 6 }

		
		-- 1.3.6.1.4.1.1916.2.131.50.1.3.18.3.15
		wingCfgDevIfSerialTable OBJECT-TYPE
			SYNTAX SEQUENCE OF WingCfgDevIfSerialEntry
			MAX-ACCESS not-accessible
			STATUS current
			DESCRIPTION
				"Serial interface (virtual interface) configuration.
				
				/wing-config/device/interface"
			::= { wingCfgDevIf 15 }

		
		-- 1.3.6.1.4.1.1916.2.131.50.1.3.18.3.15.1
		wingCfgDevIfSerialEntry OBJECT-TYPE
			SYNTAX WingCfgDevIfSerialEntry
			MAX-ACCESS not-accessible
			STATUS current
			DESCRIPTION
				"An entry in the table."
			INDEX { wingCfgDevMac, wingCfgDevIfName }
			::= { wingCfgDevIfSerialTable 1 }

		
		WingCfgDevIfSerialEntry ::=
			SEQUENCE { 
				wingCfgDevIfSerialAuthentication
					DisplayString,
				wingCfgDevIfSerialEncapsulation
					DisplayString,
				wingCfgDevIfSerialLocalIpAddress
					DisplayString,
				wingCfgDevIfSerialUsername
					DisplayString,
				wingCfgDevIfSerialPassword
					DisplayString,
				wingCfgDevIfSerialRemoteIpSubnet
					DisplayString
			 }

		-- 1.3.6.1.4.1.1916.2.131.50.1.3.18.3.15.1.1
		wingCfgDevIfSerialAuthentication OBJECT-TYPE
			SYNTAX DisplayString
			MAX-ACCESS read-write
			STATUS current
			DESCRIPTION
				"Type of authentication
				
				Values:
				none
				pap
				chap
				
				XPath: /wing-config/device[mac=key1]/interface[name=key2]/authentication"
			DEFVAL { "none" }
			::= { wingCfgDevIfSerialEntry 1 }

		
		-- 1.3.6.1.4.1.1916.2.131.50.1.3.18.3.15.1.2
		wingCfgDevIfSerialEncapsulation OBJECT-TYPE
			SYNTAX DisplayString
			MAX-ACCESS read-write
			STATUS current
			DESCRIPTION
				"The type of traffic that this group handles
				
				Values:
				chdlc
				hdlc
				ppp
				
				XPath: /wing-config/device[mac=key1]/interface[name=key2]/encapsulation"
			DEFVAL { "ppp" }
			::= { wingCfgDevIfSerialEntry 2 }

		
		-- 1.3.6.1.4.1.1916.2.131.50.1.3.18.3.15.1.3
		wingCfgDevIfSerialLocalIpAddress OBJECT-TYPE
			SYNTAX DisplayString
			MAX-ACCESS read-write
			STATUS current
			DESCRIPTION
				"IP address assigned to the local system
				
				XPath: /wing-config/device[mac=key1]/interface[name=key2]/local_ip_address"
			DEFVAL { "" }
			::= { wingCfgDevIfSerialEntry 3 }

		
		-- 1.3.6.1.4.1.1916.2.131.50.1.3.18.3.15.1.4
		wingCfgDevIfSerialUsername OBJECT-TYPE
			SYNTAX DisplayString (SIZE (0..32))
			MAX-ACCESS read-write
			STATUS current
			DESCRIPTION
				"Username provided by the service provider
				
				XPath: /wing-config/device[mac=key1]/interface[name=key2]/username"
			DEFVAL { "" }
			::= { wingCfgDevIfSerialEntry 4 }

		
		-- 1.3.6.1.4.1.1916.2.131.50.1.3.18.3.15.1.5
		wingCfgDevIfSerialPassword OBJECT-TYPE
			SYNTAX DisplayString (SIZE (0..32))
			MAX-ACCESS read-write
			STATUS current
			DESCRIPTION
				"Password provided by the service provider
				
				XPath: /wing-config/device[mac=key1]/interface[name=key2]/password"
			DEFVAL { "" }
			::= { wingCfgDevIfSerialEntry 5 }

		
		-- 1.3.6.1.4.1.1916.2.131.50.1.3.18.3.15.1.6
		wingCfgDevIfSerialRemoteIpSubnet OBJECT-TYPE
			SYNTAX DisplayString
			MAX-ACCESS read-write
			STATUS current
			DESCRIPTION
				"IP subnet assigned to the remote system along with subnet
				in CIDR notation - A.B.C.D/M
				
				XPath: /wing-config/device[mac=key1]/interface[name=key2]/remote_ip_subnet"
			DEFVAL { "" }
			::= { wingCfgDevIfSerialEntry 6 }

		
		-- 1.3.6.1.4.1.1916.2.131.50.1.3.18.3.16
		wingCfgDevIfDot1xAuthTable OBJECT-TYPE
			SYNTAX SEQUENCE OF WingCfgDevIfDot1xAuthEntry
			MAX-ACCESS not-accessible
			STATUS current
			DESCRIPTION
				"
				
				/wing-config/device/interface"
			::= { wingCfgDevIf 16 }

		
		-- 1.3.6.1.4.1.1916.2.131.50.1.3.18.3.16.1
		wingCfgDevIfDot1xAuthEntry OBJECT-TYPE
			SYNTAX WingCfgDevIfDot1xAuthEntry
			MAX-ACCESS not-accessible
			STATUS current
			DESCRIPTION
				"An entry in the table."
			INDEX { wingCfgDevMac, wingCfgDevIfName }
			::= { wingCfgDevIfDot1xAuthTable 1 }

		
		WingCfgDevIfDot1xAuthEntry ::=
			SEQUENCE { 
				wingCfgDevIfDot1xAuthHostMode
					DisplayString,
				wingCfgDevIfDot1xAuthGuestVlan
					Unsigned32,
				wingCfgDevIfDot1xAuthPortControl
					DisplayString,
				wingCfgDevIfDot1xAuthReauthenticate
					TruthValue,
				wingCfgDevIfDot1xAuthMaxReauthCount
					Unsigned32,
				wingCfgDevIfDot1xAuthMaxReq
					Unsigned32,
				wingCfgDevIfDot1xAuthQuietPeriod
					Unsigned32,
				wingCfgDevIfDot1xAuthReauthPeriod
					Unsigned32
			 }

		-- 1.3.6.1.4.1.1916.2.131.50.1.3.18.3.16.1.1
		wingCfgDevIfDot1xAuthHostMode OBJECT-TYPE
			SYNTAX DisplayString
			MAX-ACCESS read-write
			STATUS current
			DESCRIPTION
				"Single or multi-host mode.
				
				Values:
				single-host,
				multi-host
				
				XPath: /wing-config/device[mac=key1]/interface[name=key2]/host_mode"
			DEFVAL { "single-host" }
			::= { wingCfgDevIfDot1xAuthEntry 1 }

		
		-- 1.3.6.1.4.1.1916.2.131.50.1.3.18.3.16.1.2
		wingCfgDevIfDot1xAuthGuestVlan OBJECT-TYPE
			SYNTAX Unsigned32 (1..4094)
			MAX-ACCESS read-write
			STATUS current
			DESCRIPTION
				"Vlan onto which traffic is bridged if port is unauthorized and guest vlan is globally enabled
				
				XPath: /wing-config/device[mac=key1]/interface[name=key2]/guest_vlan"
			::= { wingCfgDevIfDot1xAuthEntry 2 }

		
		-- 1.3.6.1.4.1.1916.2.131.50.1.3.18.3.16.1.3
		wingCfgDevIfDot1xAuthPortControl OBJECT-TYPE
			SYNTAX DisplayString
			MAX-ACCESS read-write
			STATUS current
			DESCRIPTION
				"Set 802.1x port state
				
				Values:
				auto,
				force-authorized,
				force-unauthorized
				
				XPath: /wing-config/device[mac=key1]/interface[name=key2]/port_control"
			DEFVAL { "force-authorized" }
			::= { wingCfgDevIfDot1xAuthEntry 3 }

		
		-- 1.3.6.1.4.1.1916.2.131.50.1.3.18.3.16.1.4
		wingCfgDevIfDot1xAuthReauthenticate OBJECT-TYPE
			SYNTAX TruthValue
			MAX-ACCESS read-write
			STATUS current
			DESCRIPTION
				"Enable 802.1x re-authentication
				
				XPath: /wing-config/device[mac=key1]/interface[name=key2]/reauthenticate"
			DEFVAL { false }
			::= { wingCfgDevIfDot1xAuthEntry 4 }

		
		-- 1.3.6.1.4.1.1916.2.131.50.1.3.18.3.16.1.5
		wingCfgDevIfDot1xAuthMaxReauthCount OBJECT-TYPE
			SYNTAX Unsigned32 (1..10)
			MAX-ACCESS read-write
			STATUS current
			DESCRIPTION
				"Number of reauthentication attempts before a port is moved to unauthorized
				
				XPath: /wing-config/device[mac=key1]/interface[name=key2]/max_reauth_count"
			DEFVAL { 2 }
			::= { wingCfgDevIfDot1xAuthEntry 5 }

		
		-- 1.3.6.1.4.1.1916.2.131.50.1.3.18.3.16.1.6
		wingCfgDevIfDot1xAuthMaxReq OBJECT-TYPE
			SYNTAX Unsigned32 (1..10)
			MAX-ACCESS read-write
			STATUS current
			DESCRIPTION
				"Number of times 802.1x will retry authentication with the Radius Server before giving up and returning failed to the supplicant.
				
				XPath: /wing-config/device[mac=key1]/interface[name=key2]/max_req"
			DEFVAL { 2 }
			::= { wingCfgDevIfDot1xAuthEntry 6 }

		
		-- 1.3.6.1.4.1.1916.2.131.50.1.3.18.3.16.1.7
		wingCfgDevIfDot1xAuthQuietPeriod OBJECT-TYPE
			SYNTAX Unsigned32 (1..65535)
			MAX-ACCESS read-write
			STATUS current
			DESCRIPTION
				"Time in seconds 802.1x will wait after authentication fails
				
				XPath: /wing-config/device[mac=key1]/interface[name=key2]/quiet_period"
			DEFVAL { 60 }
			::= { wingCfgDevIfDot1xAuthEntry 7 }

		
		-- 1.3.6.1.4.1.1916.2.131.50.1.3.18.3.16.1.8
		wingCfgDevIfDot1xAuthReauthPeriod OBJECT-TYPE
			SYNTAX Unsigned32 (1..65535)
			MAX-ACCESS read-write
			STATUS current
			DESCRIPTION
				"Time in seconds until port is reauthenicated
				
				XPath: /wing-config/device[mac=key1]/interface[name=key2]/reauth_period"
			DEFVAL { 60 }
			::= { wingCfgDevIfDot1xAuthEntry 8 }

		
		-- 1.3.6.1.4.1.1916.2.131.50.1.3.18.3.17
		wingCfgDevIfMeshpointBssmapTable OBJECT-TYPE
			SYNTAX SEQUENCE OF WingCfgDevIfMeshpointBssmapEntry
			MAX-ACCESS not-accessible
			STATUS current
			DESCRIPTION
				"
				
				/wing-config/device/interface/meshpoint"
			::= { wingCfgDevIf 17 }

		
		-- 1.3.6.1.4.1.1916.2.131.50.1.3.18.3.17.1
		wingCfgDevIfMeshpointBssmapEntry OBJECT-TYPE
			SYNTAX WingCfgDevIfMeshpointBssmapEntry
			MAX-ACCESS not-accessible
			STATUS current
			DESCRIPTION
				"An entry in the table."
			INDEX { wingCfgDevMac, wingCfgDevIfName, wingCfgDevIfMeshpointBssmapMeshpoint }
			::= { wingCfgDevIfMeshpointBssmapTable 1 }

		
		WingCfgDevIfMeshpointBssmapEntry ::=
			SEQUENCE { 
				wingCfgDevIfMeshpointBssmapMeshpoint
					WingIdentifier,
				wingCfgDevIfMeshpointBssmapBss
					Unsigned32
			 }

		-- 1.3.6.1.4.1.1916.2.131.50.1.3.18.3.17.1.1
		wingCfgDevIfMeshpointBssmapMeshpoint OBJECT-TYPE
			SYNTAX WingIdentifier
			MAX-ACCESS read-write
			STATUS current
			DESCRIPTION
				"
				
				XPath: /wing-config/device[mac=key1]/interface[name=key2]/meshpoint[meshpoint=key3]/meshpoint"
			::= { wingCfgDevIfMeshpointBssmapEntry 1 }

		
		-- 1.3.6.1.4.1.1916.2.131.50.1.3.18.3.17.1.3
		wingCfgDevIfMeshpointBssmapBss OBJECT-TYPE
			SYNTAX Unsigned32 (1..8)
			MAX-ACCESS read-write
			STATUS current
			DESCRIPTION
				"
				
				XPath: /wing-config/device[mac=key1]/interface[name=key2]/meshpoint[meshpoint=key3]/bss"
			::= { wingCfgDevIfMeshpointBssmapEntry 3 }

		
-- /wing-config/device/bridge_vlan
		-- 1.3.6.1.4.1.1916.2.131.50.1.3.18.8
		wingCfgDevBridgeVlan OBJECT IDENTIFIER ::= { wingCfgDev 8 }

		
		-- 1.3.6.1.4.1.1916.2.131.50.1.3.18.8.1
		wingCfgDevBridgeVlanTable OBJECT-TYPE
			SYNTAX SEQUENCE OF WingCfgDevBridgeVlanEntry
			MAX-ACCESS not-accessible
			STATUS current
			DESCRIPTION
				"
				
				/wing-config/profile/bridge_vlan"
			::= { wingCfgDevBridgeVlan 1 }

		
		-- 1.3.6.1.4.1.1916.2.131.50.1.3.18.8.1.1
		wingCfgDevBridgeVlanEntry OBJECT-TYPE
			SYNTAX WingCfgDevBridgeVlanEntry
			MAX-ACCESS not-accessible
			STATUS current
			DESCRIPTION
				"An entry in the table."
			INDEX { wingCfgDevMac, wingCfgDevBridgeVlanId }
			::= { wingCfgDevBridgeVlanTable 1 }

		
		WingCfgDevBridgeVlanEntry ::=
			SEQUENCE { 
				wingCfgDevBridgeVlanId
					Unsigned32,
				wingCfgDevBridgeVlanDescription
					DisplayString,
				wingCfgDevBridgeVlanEdgeVlan
					TruthValue,
				wingCfgDevBridgeVlanBridgingMode
					DisplayString,
				wingCfgDevBridgeVlanIpArpTrust
					TruthValue,
				wingCfgDevBridgeVlanIpDhcpTrust
					TruthValue,
				wingCfgDevBridgeVlanTunnelMacOutAcl
					WingIdentifier,
				wingCfgDevBridgeVlanTunnelIpOutAcl
					WingIdentifier
			 }

		-- 1.3.6.1.4.1.1916.2.131.50.1.3.18.8.1.1.1
		wingCfgDevBridgeVlanId OBJECT-TYPE
			SYNTAX Unsigned32 (1..4095)
			MAX-ACCESS read-only
			STATUS current
			DESCRIPTION
				"
				
				XPath: /wing-config/device[mac=key1]/bridge_vlan[vlan=key2]/vlan"
			::= { wingCfgDevBridgeVlanEntry 1 }

		
		-- 1.3.6.1.4.1.1916.2.131.50.1.3.18.8.1.1.3
		wingCfgDevBridgeVlanDescription OBJECT-TYPE
			SYNTAX DisplayString (SIZE (64))
			MAX-ACCESS read-write
			STATUS current
			DESCRIPTION
				"
				
				XPath: /wing-config/device[mac=key1]/bridge_vlan[vlan=key2]/description"
			::= { wingCfgDevBridgeVlanEntry 3 }

		
		-- 1.3.6.1.4.1.1916.2.131.50.1.3.18.8.1.1.4
		wingCfgDevBridgeVlanEdgeVlan OBJECT-TYPE
			SYNTAX TruthValue
			MAX-ACCESS read-write
			STATUS current
			DESCRIPTION
				"
				
				XPath: /wing-config/device[mac=key1]/bridge_vlan[vlan=key2]/edge_vlan"
			DEFVAL { true }
			::= { wingCfgDevBridgeVlanEntry 4 }

		
		-- 1.3.6.1.4.1.1916.2.131.50.1.3.18.8.1.1.5
		wingCfgDevBridgeVlanBridgingMode OBJECT-TYPE
			SYNTAX DisplayString
			MAX-ACCESS read-write
			STATUS current
			DESCRIPTION
				"
				
				Values:
				auto,
				local,
				tunnel,
				isolated-tunnel
				
				XPath: /wing-config/device[mac=key1]/bridge_vlan[vlan=key2]/bridging_mode"
			DEFVAL { "auto" }
			::= { wingCfgDevBridgeVlanEntry 5 }

		
		-- 1.3.6.1.4.1.1916.2.131.50.1.3.18.8.1.1.6
		wingCfgDevBridgeVlanIpArpTrust OBJECT-TYPE
			SYNTAX TruthValue
			MAX-ACCESS read-write
			STATUS current
			DESCRIPTION
				"
				
				XPath: /wing-config/device[mac=key1]/bridge_vlan[vlan=key2]/ip_arp_trust"
			DEFVAL { false }
			::= { wingCfgDevBridgeVlanEntry 6 }

		
		-- 1.3.6.1.4.1.1916.2.131.50.1.3.18.8.1.1.7
		wingCfgDevBridgeVlanIpDhcpTrust OBJECT-TYPE
			SYNTAX TruthValue
			MAX-ACCESS read-write
			STATUS current
			DESCRIPTION
				"
				
				XPath: /wing-config/device[mac=key1]/bridge_vlan[vlan=key2]/ip_dhcp_trust"
			DEFVAL { false }
			::= { wingCfgDevBridgeVlanEntry 7 }

		
		-- 1.3.6.1.4.1.1916.2.131.50.1.3.18.8.1.1.8
		wingCfgDevBridgeVlanTunnelMacOutAcl OBJECT-TYPE
			SYNTAX WingIdentifier
			MAX-ACCESS read-write
			STATUS current
			DESCRIPTION
				"
				
				XPath: /wing-config/device[mac=key1]/bridge_vlan[vlan=key2]/tunnel_mac_out_acl"
			::= { wingCfgDevBridgeVlanEntry 8 }

		
		-- 1.3.6.1.4.1.1916.2.131.50.1.3.18.8.1.1.9
		wingCfgDevBridgeVlanTunnelIpOutAcl OBJECT-TYPE
			SYNTAX WingIdentifier
			MAX-ACCESS read-write
			STATUS current
			DESCRIPTION
				"
				
				XPath: /wing-config/device[mac=key1]/bridge_vlan[vlan=key2]/tunnel_ip_out_acl"
			::= { wingCfgDevBridgeVlanEntry 9 }

		
		-- 1.3.6.1.4.1.1916.2.131.50.1.3.18.8.2
		wingCfgDevBridgeVlanIgsTable OBJECT-TYPE
			SYNTAX SEQUENCE OF WingCfgDevBridgeVlanIgsEntry
			MAX-ACCESS not-accessible
			STATUS current
			DESCRIPTION
				"
				
				/wing-config/device/interface"
			::= { wingCfgDevBridgeVlan 2 }

		
		-- 1.3.6.1.4.1.1916.2.131.50.1.3.18.8.2.1
		wingCfgDevBridgeVlanIgsEntry OBJECT-TYPE
			SYNTAX WingCfgDevBridgeVlanIgsEntry
			MAX-ACCESS not-accessible
			STATUS current
			DESCRIPTION
				"An entry in the table."
			INDEX { wingCfgDevMac, wingCfgDevBridgeVlanId }
			::= { wingCfgDevBridgeVlanIgsTable 1 }

		
		WingCfgDevBridgeVlanIgsEntry ::=
			SEQUENCE { 
				wingCfgDevBridgeVlanIgsIpIgs
					TruthValue,
				wingCfgDevBridgeVlanIgsIpIgsQuerier
					TruthValue,
				wingCfgDevBridgeVlanIgsIpIgsQuerierMaxResponseTime
					Unsigned32,
				wingCfgDevBridgeVlanIgsIpIgsQuerierVersion
					Unsigned32,
				wingCfgDevBridgeVlanIgsIpIgsQuerierAddress
					DisplayString,
				wingCfgDevBridgeVlanIgsIpIgsOtherQuerierTimerExpiry
					Unsigned32,
				wingCfgDevBridgeVlanIgsIpIgsForwardUnknownMcast
					TruthValue,
				wingCfgDevBridgeVlanIgsIpIgsMrouterLearnPimDvmrp
					DisplayString
			 }

		-- 1.3.6.1.4.1.1916.2.131.50.1.3.18.8.2.1.1
		wingCfgDevBridgeVlanIgsIpIgs OBJECT-TYPE
			SYNTAX TruthValue
			MAX-ACCESS read-write
			STATUS current
			DESCRIPTION
				"
				
				XPath: /wing-config/device[mac=key1]/bridge_vlan[vlan=key2]/ip_igs"
			DEFVAL { true }
			::= { wingCfgDevBridgeVlanIgsEntry 1 }

		
		-- 1.3.6.1.4.1.1916.2.131.50.1.3.18.8.2.1.2
		wingCfgDevBridgeVlanIgsIpIgsQuerier OBJECT-TYPE
			SYNTAX TruthValue
			MAX-ACCESS read-write
			STATUS current
			DESCRIPTION
				"
				
				XPath: /wing-config/device[mac=key1]/bridge_vlan[vlan=key2]/ip_igs_querier"
			DEFVAL { false }
			::= { wingCfgDevBridgeVlanIgsEntry 2 }

		
		-- 1.3.6.1.4.1.1916.2.131.50.1.3.18.8.2.1.3
		wingCfgDevBridgeVlanIgsIpIgsQuerierMaxResponseTime OBJECT-TYPE
			SYNTAX Unsigned32 (1..25)
			UNITS "seconds"
			MAX-ACCESS read-write
			STATUS current
			DESCRIPTION
				"
				
				XPath: /wing-config/device[mac=key1]/bridge_vlan[vlan=key2]/ip_igs_querier_max_response_time"
			::= { wingCfgDevBridgeVlanIgsEntry 3 }

		
		-- 1.3.6.1.4.1.1916.2.131.50.1.3.18.8.2.1.4
		wingCfgDevBridgeVlanIgsIpIgsQuerierVersion OBJECT-TYPE
			SYNTAX Unsigned32 (1..3)
			MAX-ACCESS read-write
			STATUS current
			DESCRIPTION
				"
				
				XPath: /wing-config/device[mac=key1]/bridge_vlan[vlan=key2]/ip_igs_querier_version"
			::= { wingCfgDevBridgeVlanIgsEntry 4 }

		
		-- 1.3.6.1.4.1.1916.2.131.50.1.3.18.8.2.1.5
		wingCfgDevBridgeVlanIgsIpIgsQuerierAddress OBJECT-TYPE
			SYNTAX DisplayString
			MAX-ACCESS read-write
			STATUS current
			DESCRIPTION
				"
				
				XPath: /wing-config/device[mac=key1]/bridge_vlan[vlan=key2]/ip_igs_querier_address"
			::= { wingCfgDevBridgeVlanIgsEntry 5 }

		
		-- 1.3.6.1.4.1.1916.2.131.50.1.3.18.8.2.1.6
		wingCfgDevBridgeVlanIgsIpIgsOtherQuerierTimerExpiry OBJECT-TYPE
			SYNTAX Unsigned32 (60..300)
			UNITS "seconds"
			MAX-ACCESS read-write
			STATUS current
			DESCRIPTION
				"
				
				XPath: /wing-config/device[mac=key1]/bridge_vlan[vlan=key2]/ip_igs_other_querier_timer_expiry"
			::= { wingCfgDevBridgeVlanIgsEntry 6 }

		
		-- 1.3.6.1.4.1.1916.2.131.50.1.3.18.8.2.1.7
		wingCfgDevBridgeVlanIgsIpIgsForwardUnknownMcast OBJECT-TYPE
			SYNTAX TruthValue
			MAX-ACCESS read-write
			STATUS current
			DESCRIPTION
				"
				
				XPath: /wing-config/device[mac=key1]/bridge_vlan[vlan=key2]/ip_igs_forward_unknown_mcast"
			DEFVAL { false }
			::= { wingCfgDevBridgeVlanIgsEntry 7 }

		
		-- 1.3.6.1.4.1.1916.2.131.50.1.3.18.8.2.1.8
		wingCfgDevBridgeVlanIgsIpIgsMrouterLearnPimDvmrp OBJECT-TYPE
			SYNTAX DisplayString
			MAX-ACCESS read-write
			STATUS current
			DESCRIPTION
				"
				
				XPath: /wing-config/device[mac=key1]/bridge_vlan[vlan=key2]/ip_igs_mrouter_learn_pim_dvmrp"
			DEFVAL { "pim-dvmrp" }
			::= { wingCfgDevBridgeVlanIgsEntry 8 }

		
-- /wing-config/device/mint_link_cfg
		-- 1.3.6.1.4.1.1916.2.131.50.1.3.18.10
		wingCfgDevMint OBJECT IDENTIFIER ::= { wingCfgDev 10 }

		
		-- 1.3.6.1.4.1.1916.2.131.50.1.3.18.10.1
		wingCfgDevMintTable OBJECT-TYPE
			SYNTAX SEQUENCE OF WingCfgDevMintEntry
			MAX-ACCESS not-accessible
			STATUS current
			DESCRIPTION
				"
				
				/wing-config/device/mint_link_cfg"
			::= { wingCfgDevMint 1 }

		
		-- 1.3.6.1.4.1.1916.2.131.50.1.3.18.10.1.1
		wingCfgDevMintEntry OBJECT-TYPE
			SYNTAX WingCfgDevMintEntry
			MAX-ACCESS not-accessible
			STATUS current
			DESCRIPTION
				"An entry in the table."
			INDEX { wingCfgDevMac }
			::= { wingCfgDevMintTable 1 }

		
		WingCfgDevMintEntry ::=
			SEQUENCE { 
				wingCfgDevMintLevel1AreaId
					DisplayString,
				wingCfgDevMintSpfLatency
					DisplayString,
				wingCfgDevMintDisPriorityAdjustment
					Integer32,
				wingCfgDevMintMlcpVlan
					TruthValue,
				wingCfgDevMintMlcpIp
					TruthValue,
				wingCfgDevMintTunnelControllerLoadBalancingLevel1
					TruthValue
			 }

		-- 1.3.6.1.4.1.1916.2.131.50.1.3.18.10.1.1.1
		wingCfgDevMintLevel1AreaId OBJECT-TYPE
			SYNTAX DisplayString
			MAX-ACCESS read-write
			STATUS current
			DESCRIPTION
				"
				
				XPath: /wing-config/device[mac=key1]/mint_link_cfg/mint_level1_area_id"
			::= { wingCfgDevMintEntry 1 }

		
		-- 1.3.6.1.4.1.1916.2.131.50.1.3.18.10.1.1.2
		wingCfgDevMintSpfLatency OBJECT-TYPE
			SYNTAX DisplayString
			UNITS "seconds"
			MAX-ACCESS read-write
			STATUS current
			DESCRIPTION
				"
				
				XPath: /wing-config/device[mac=key1]/mint_link_cfg/mint_spf_latency"
			::= { wingCfgDevMintEntry 2 }

		
		-- 1.3.6.1.4.1.1916.2.131.50.1.3.18.10.1.1.3
		wingCfgDevMintDisPriorityAdjustment OBJECT-TYPE
			SYNTAX Integer32 (-255..255)
			MAX-ACCESS read-write
			STATUS current
			DESCRIPTION
				"value added to base level DIS priority to influence the DIS election. +1 increases DISiness.
				
				XPath: /wing-config/device[mac=key1]/mint_link_cfg/mint_dis_priority_adjustment"
			DEFVAL { 0 }
			::= { wingCfgDevMintEntry 3 }

		
		-- 1.3.6.1.4.1.1916.2.131.50.1.3.18.10.1.1.4
		wingCfgDevMintMlcpVlan OBJECT-TYPE
			SYNTAX TruthValue
			MAX-ACCESS read-write
			STATUS current
			DESCRIPTION
				"MLCP for automated MiNT VLAN link creation
				
				XPath: /wing-config/device[mac=key1]/mint_link_cfg/mint_mlcp_vlan"
			DEFVAL { true }
			::= { wingCfgDevMintEntry 4 }

		
		-- 1.3.6.1.4.1.1916.2.131.50.1.3.18.10.1.1.5
		wingCfgDevMintMlcpIp OBJECT-TYPE
			SYNTAX TruthValue
			MAX-ACCESS read-write
			STATUS current
			DESCRIPTION
				"MLCP for automated MiNT UDP/IP link creation
				
				XPath: /wing-config/device[mac=key1]/mint_link_cfg/mint_mlcp_ip"
			DEFVAL { true }
			::= { wingCfgDevMintEntry 5 }

		
		-- 1.3.6.1.4.1.1916.2.131.50.1.3.18.10.1.1.6
		wingCfgDevMintTunnelControllerLoadBalancingLevel1 OBJECT-TYPE
			SYNTAX TruthValue
			MAX-ACCESS read-write
			STATUS current
			DESCRIPTION
				"MLCP for automated MiNT UDP/IP link creation
				
				XPath: /wing-config/device[mac=key1]/mint_link_cfg/mint_tunnel_controller_load_balancing_level1"
			::= { wingCfgDevMintEntry 6 }

		
--  /wing-config/device/dot11_cfg
		-- 1.3.6.1.4.1.1916.2.131.50.1.3.18.11
		wingCfgDevDot11 OBJECT IDENTIFIER ::= { wingCfgDev 11 }

		
		-- 1.3.6.1.4.1.1916.2.131.50.1.3.18.11.1
		wingCfgDevDot11Table OBJECT-TYPE
			SYNTAX SEQUENCE OF WingCfgDevDot11Entry
			MAX-ACCESS not-accessible
			STATUS current
			DESCRIPTION
				"802.11 global parameters for this device.
				
				/wing-config/device/dot11_cfg"
			::= { wingCfgDevDot11 1 }

		
		-- 1.3.6.1.4.1.1916.2.131.50.1.3.18.11.1.1
		wingCfgDevDot11Entry OBJECT-TYPE
			SYNTAX WingCfgDevDot11Entry
			MAX-ACCESS not-accessible
			STATUS current
			DESCRIPTION
				"An entry in the table."
			INDEX { wingCfgDevMac }
			::= { wingCfgDevDot11Table 1 }

		
		WingCfgDevDot11Entry ::=
			SEQUENCE { 
				wingCfgDevDot11WepSharedKeyAuth
					TruthValue,
				wingCfgDevDot11LegacyAutoUpdateAp650
					TruthValue,
				wingCfgDevDot11LegacyAutoUpdateImgAp7131
					DisplayString,
				wingCfgDevDot11LegacyAutoDowngrade
					TruthValue,
				wingCfgDevDot11NasIdentifier
					DisplayString,
				wingCfgDevDot11NasPortId
					DisplayString
			 }

		-- 1.3.6.1.4.1.1916.2.131.50.1.3.18.11.1.1.1
		wingCfgDevDot11WepSharedKeyAuth OBJECT-TYPE
			SYNTAX TruthValue
			MAX-ACCESS read-write
			STATUS current
			DESCRIPTION
				"Whether 802.11 shared key authentication is supported
				with WEP. Note: this method has known security vulnerabilities
				and its use is not recommended unless there are devices
				on the network that are only capable of
				shared-key authentication.
				
				XPath: /wing-config/device[mac=key1]/dot11_cfg/wep_shared_key_auth"
			DEFVAL { false }
			::= { wingCfgDevDot11Entry 1 }

		
		-- 1.3.6.1.4.1.1916.2.131.50.1.3.18.11.1.1.2
		wingCfgDevDot11LegacyAutoUpdateAp650 OBJECT-TYPE
			SYNTAX TruthValue
			MAX-ACCESS read-write
			STATUS current
			DESCRIPTION
				"Whether legacy devices found on the network will automatically
				be updated to supported firmware.
				
				XPath: /wing-config/device[mac=key1]/dot11_cfg/legacy_auto_update_ap650"
			DEFVAL { true }
			::= { wingCfgDevDot11Entry 2 }

		
		-- 1.3.6.1.4.1.1916.2.131.50.1.3.18.11.1.1.3
		wingCfgDevDot11LegacyAutoUpdateImgAp7131 OBJECT-TYPE
			SYNTAX DisplayString (SIZE (0..253))
			MAX-ACCESS read-write
			STATUS current
			DESCRIPTION
				"Path to the AP4700 legacy auto update image.
				
				XPath: /wing-config/device[mac=key1]/dot11_cfg/legacy_auto_update_img_ap7131"
			DEFVAL { "" }
			::= { wingCfgDevDot11Entry 3 }

		
		-- 1.3.6.1.4.1.1916.2.131.50.1.3.18.11.1.1.4
		wingCfgDevDot11LegacyAutoDowngrade OBJECT-TYPE
			SYNTAX TruthValue
			MAX-ACCESS read-write
			STATUS current
			DESCRIPTION
				"Whether the AP4600 will connect to a legacy device and
				downgrade to be compatible with legacy devices.
				
				XPath: /wing-config/device[mac=key1]/dot11_cfg/legacy_auto_downgrade"
			DEFVAL { true }
			::= { wingCfgDevDot11Entry 4 }

		
		-- 1.3.6.1.4.1.1916.2.131.50.1.3.18.11.1.1.5
		wingCfgDevDot11NasIdentifier OBJECT-TYPE
			SYNTAX DisplayString (SIZE (0..253))
			MAX-ACCESS read-write
			STATUS current
			DESCRIPTION
				"The RADIUS NAS-Identifier attribute which typically identifies
				the Access Point or Wireless Controller where the RADIUS
				message originates.
				
				XPath: /wing-config/device[mac=key1]/dot11_cfg/nas_identifier"
			DEFVAL { "" }
			::= { wingCfgDevDot11Entry 5 }

		
		-- 1.3.6.1.4.1.1916.2.131.50.1.3.18.11.1.1.6
		wingCfgDevDot11NasPortId OBJECT-TYPE
			SYNTAX DisplayString (SIZE (0..253))
			MAX-ACCESS read-write
			STATUS current
			DESCRIPTION
				"The RADIUS NAS-Port-Id attribute which typically identifies
				the port of the device where the RADIUS messages originates.
				
				XPath: /wing-config/device[mac=key1]/dot11_cfg/nas_port_id"
			DEFVAL { "" }
			::= { wingCfgDevDot11Entry 6 }

		
-- /wing-config/device
		-- 1.3.6.1.4.1.1916.2.131.50.1.3.18.16
		wingCfgDevNat OBJECT IDENTIFIER ::= { wingCfgDev 16 }

		
		-- 1.3.6.1.4.1.1916.2.131.50.1.3.18.16.1
		wingCfgDevNatPoolTable OBJECT-TYPE
			SYNTAX SEQUENCE OF WingCfgDevNatPoolEntry
			MAX-ACCESS not-accessible
			STATUS current
			DESCRIPTION
				"
				
				/wing-config/device/nat_pool"
			::= { wingCfgDevNat 1 }

		
		-- 1.3.6.1.4.1.1916.2.131.50.1.3.18.16.1.1
		wingCfgDevNatPoolEntry OBJECT-TYPE
			SYNTAX WingCfgDevNatPoolEntry
			MAX-ACCESS not-accessible
			STATUS current
			DESCRIPTION
				"An entry in the table."
			INDEX { wingCfgDevMac, wingCfgDevNatPoolName }
			::= { wingCfgDevNatPoolTable 1 }

		
		WingCfgDevNatPoolEntry ::=
			SEQUENCE { 
				wingCfgDevNatPoolName
					WingIdentifier
			 }

		-- 1.3.6.1.4.1.1916.2.131.50.1.3.18.16.1.1.1
		wingCfgDevNatPoolName OBJECT-TYPE
			SYNTAX WingIdentifier
			MAX-ACCESS read-only
			STATUS current
			DESCRIPTION
				"Name of the NAT pool.
				
				XPath: /wing-config/device[mac=key1]/nat_pool[name=key2]/name"
			::= { wingCfgDevNatPoolEntry 1 }

		
		-- 1.3.6.1.4.1.1916.2.131.50.1.3.18.16.2
		wingCfgDevNatPoolAddrTable OBJECT-TYPE
			SYNTAX SEQUENCE OF WingCfgDevNatPoolAddrEntry
			MAX-ACCESS not-accessible
			STATUS current
			DESCRIPTION
				"
				
				/wing-config/device/nat_pool/address_range"
			::= { wingCfgDevNat 2 }

		
		-- 1.3.6.1.4.1.1916.2.131.50.1.3.18.16.2.1
		wingCfgDevNatPoolAddrEntry OBJECT-TYPE
			SYNTAX WingCfgDevNatPoolAddrEntry
			MAX-ACCESS not-accessible
			STATUS current
			DESCRIPTION
				"An entry in the table."
			INDEX { wingCfgDevMac, wingCfgDevNatPoolName, wingCfgDevNatPoolAddrStartIp }
			::= { wingCfgDevNatPoolAddrTable 1 }

		
		WingCfgDevNatPoolAddrEntry ::=
			SEQUENCE { 
				wingCfgDevNatPoolAddrStartIp
					WingIdentifier,
				wingCfgDevNatPoolAddrEndIp
					DisplayString
			 }

		-- 1.3.6.1.4.1.1916.2.131.50.1.3.18.16.2.1.1
		wingCfgDevNatPoolAddrStartIp OBJECT-TYPE
			SYNTAX WingIdentifier
			MAX-ACCESS read-only
			STATUS current
			DESCRIPTION
				"
				
				XPath: /wing-config/device[mac=key1]/nat_pool[name=key2]/address_rage[start_ip=key3]/start_ip"
			::= { wingCfgDevNatPoolAddrEntry 1 }

		
		-- 1.3.6.1.4.1.1916.2.131.50.1.3.18.16.2.1.3
		wingCfgDevNatPoolAddrEndIp OBJECT-TYPE
			SYNTAX DisplayString
			MAX-ACCESS read-write
			STATUS current
			DESCRIPTION
				"
				
				XPath: /wing-config/device[mac=key1]/nat_pool[name=key2]/address_rage[start_ip=key3]/end_ip"
			::= { wingCfgDevNatPoolAddrEntry 3 }

		
		-- 1.3.6.1.4.1.1916.2.131.50.1.3.18.16.7
		wingCfgDevNatBridgeSrcDynamicTable OBJECT-TYPE
			SYNTAX SEQUENCE OF WingCfgDevNatBridgeSrcDynamicEntry
			MAX-ACCESS not-accessible
			STATUS current
			DESCRIPTION
				"
				/wing-config/device/bridge_source_dynamic_nat"
			::= { wingCfgDevNat 7 }

		
		-- 1.3.6.1.4.1.1916.2.131.50.1.3.18.16.7.1
		wingCfgDevNatBridgeSrcDynamicEntry OBJECT-TYPE
			SYNTAX WingCfgDevNatBridgeSrcDynamicEntry
			MAX-ACCESS not-accessible
			STATUS current
			DESCRIPTION
				"An entry in the table."
			INDEX { wingCfgDevMac, wingCfgDevNatBridgeSrcDynamicAcl }
			::= { wingCfgDevNatBridgeSrcDynamicTable 1 }

		
		WingCfgDevNatBridgeSrcDynamicEntry ::=
			SEQUENCE { 
				wingCfgDevNatBridgeSrcDynamicAcl
					WingIdentifier
			 }

		-- 1.3.6.1.4.1.1916.2.131.50.1.3.18.16.7.1.1
		wingCfgDevNatBridgeSrcDynamicAcl OBJECT-TYPE
			SYNTAX WingIdentifier
			MAX-ACCESS read-only
			STATUS current
			DESCRIPTION
				"ACL 
				
				XPath: /wing-config/device[mac=key1]/bridge_source_dynamic_nat[acl=key2]/acl"
			::= { wingCfgDevNatBridgeSrcDynamicEntry 1 }

		
		-- 1.3.6.1.4.1.1916.2.131.50.1.3.18.16.8
		wingCfgDevNatBridgeSrcDynamicIfTable OBJECT-TYPE
			SYNTAX SEQUENCE OF WingCfgDevNatBridgeSrcDynamicIfEntry
			MAX-ACCESS not-accessible
			STATUS current
			DESCRIPTION
				"
				
				/wing-config/device/bridge_source_dynamic_nat/interface_cfg"
			::= { wingCfgDevNat 8 }

		
		-- 1.3.6.1.4.1.1916.2.131.50.1.3.18.16.8.1
		wingCfgDevNatBridgeSrcDynamicIfEntry OBJECT-TYPE
			SYNTAX WingCfgDevNatBridgeSrcDynamicIfEntry
			MAX-ACCESS not-accessible
			STATUS current
			DESCRIPTION
				"An entry in the table."
			INDEX { wingCfgDevMac, wingCfgDevNatBridgeSrcDynamicAcl, wingCfgDevNatBridgeSrcDynamicIfName }
			::= { wingCfgDevNatBridgeSrcDynamicIfTable 1 }

		
		WingCfgDevNatBridgeSrcDynamicIfEntry ::=
			SEQUENCE { 
				wingCfgDevNatBridgeSrcDynamicIfName
					WingIdentifier,
				wingCfgDevNatBridgeSrcDynamicIfOverloadType
					DisplayString,
				wingCfgDevNatBridgeSrcDynamicIfOverloadIp
					DisplayString,
				wingCfgDevNatBridgeSrcDynamicIfNatPool
					DisplayString
			 }

		-- 1.3.6.1.4.1.1916.2.131.50.1.3.18.16.8.1.1
		wingCfgDevNatBridgeSrcDynamicIfName OBJECT-TYPE
			SYNTAX WingIdentifier
			MAX-ACCESS read-only
			STATUS current
			DESCRIPTION
				"The outgoing layer 3 interface for NAT.
				
				XPath: /wing-config/device[mac=key1]/bridge_source_dynamic_nat[acl=key2]/interface_cfg[interface=key3]/interface"
			::= { wingCfgDevNatBridgeSrcDynamicIfEntry 1 }

		
		-- 1.3.6.1.4.1.1916.2.131.50.1.3.18.16.8.1.3
		wingCfgDevNatBridgeSrcDynamicIfOverloadType OBJECT-TYPE
			SYNTAX DisplayString
			MAX-ACCESS read-write
			STATUS current
			DESCRIPTION
				"Overload Type.
				
				XPath: /wing-config/device[mac=key1]/bridge_source_dynamic_nat[acl=key2]/interface_cfg[interface=key3]/overload_type"
			::= { wingCfgDevNatBridgeSrcDynamicIfEntry 3 }

		
		-- 1.3.6.1.4.1.1916.2.131.50.1.3.18.16.8.1.4
		wingCfgDevNatBridgeSrcDynamicIfOverloadIp OBJECT-TYPE
			SYNTAX DisplayString
			MAX-ACCESS read-write
			STATUS current
			DESCRIPTION
				"Overload IP.
				
				XPath: /wing-config/device[mac=key1]/bridge_source_dynamic_nat[acl=key2]/interface_cfg[interface=key3]/overload_ip"
			::= { wingCfgDevNatBridgeSrcDynamicIfEntry 4 }

		
		-- 1.3.6.1.4.1.1916.2.131.50.1.3.18.16.8.1.5
		wingCfgDevNatBridgeSrcDynamicIfNatPool OBJECT-TYPE
			SYNTAX DisplayString
			MAX-ACCESS read-write
			STATUS current
			DESCRIPTION
				"Nat Pool.
				
				XPath: /wing-config/device[mac=key1]/bridge_source_dynamic_nat[acl=key2]/interface_cfg[interface=key3]/nat_pool"
			::= { wingCfgDevNatBridgeSrcDynamicIfEntry 5 }

		
-- /wing-config/device
		-- 1.3.6.1.4.1.1916.2.131.50.1.3.18.19
		wingCfgDevVpn OBJECT IDENTIFIER ::= { wingCfgDev 19 }

		
		-- 1.3.6.1.4.1.1916.2.131.50.1.3.18.19.1
		wingCfgDevVpnTable OBJECT-TYPE
			SYNTAX SEQUENCE OF WingCfgDevVpnEntry
			MAX-ACCESS not-accessible
			STATUS current
			DESCRIPTION
				"
				
				/wing-config/profile"
			::= { wingCfgDevVpn 1 }

		
		-- 1.3.6.1.4.1.1916.2.131.50.1.3.18.19.1.1
		wingCfgDevVpnEntry OBJECT-TYPE
			SYNTAX WingCfgDevVpnEntry
			MAX-ACCESS not-accessible
			STATUS current
			DESCRIPTION
				"An entry in the table."
			INDEX { wingCfgDevMac }
			::= { wingCfgDevVpnTable 1 }

		
		WingCfgDevVpnEntry ::=
			SEQUENCE { 
				wingCfgDevVpnLifetimeSeconds
					Unsigned32,
				wingCfgDevVpnLifetimeKb
					Unsigned32,
				wingCfgDevVpnIkev1GlobalDpdKeepalive
					Unsigned32,
				wingCfgDevVpnIkev1GlobalDpdRetries
					Unsigned32,
				wingCfgDevVpnIkev1GlobalNatKeepalive
					Unsigned32,
				wingCfgDevVpnIkev2GlobalDpdKeepalive
					Unsigned32,
				wingCfgDevVpnIkev2GlobalDpdRetries
					Unsigned32,
				wingCfgDevVpnIkev2GlobalNatKeepalive
					Unsigned32,
				wingCfgDevVpnCookieChallengeThreshold
					Unsigned32,
				wingCfgDevVpnMaxInNegotiationSa
					Unsigned32,
				wingCfgDevVpnDfBit
					DisplayString
			 }

		-- 1.3.6.1.4.1.1916.2.131.50.1.3.18.19.1.1.1
		wingCfgDevVpnLifetimeSeconds OBJECT-TYPE
			SYNTAX Unsigned32 (120..2147483646)
			UNITS "seconds"
			MAX-ACCESS read-write
			STATUS current
			DESCRIPTION
				"Time-based IPsec security association lifetime.
				
				XPath: /wing-config/device[mac=key1]/lifetime_seconds"
			DEFVAL { 3600 }
			::= { wingCfgDevVpnEntry 1 }

		
		-- 1.3.6.1.4.1.1916.2.131.50.1.3.18.19.1.1.2
		wingCfgDevVpnLifetimeKb OBJECT-TYPE
			SYNTAX Unsigned32 (500..2147483646)
			UNITS "kilobytes"
			MAX-ACCESS read-write
			STATUS current
			DESCRIPTION
				"Data-based IPsec security association lifetime.
				
				XPath: /wing-config/device[mac=key1]/lifetime_kb"
			DEFVAL { 4608000 }
			::= { wingCfgDevVpnEntry 2 }

		
		-- 1.3.6.1.4.1.1916.2.131.50.1.3.18.19.1.1.3
		wingCfgDevVpnIkev1GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /wing-config/device[mac=key1]/ikev1_dpd_keepalive"
			DEFVAL { 30 }
			::= { wingCfgDevVpnEntry 3 }

		
		-- 1.3.6.1.4.1.1916.2.131.50.1.3.18.19.1.1.4
		wingCfgDevVpnIkev1GlobalDpdRetries OBJECT-TYPE
			SYNTAX Unsigned32 (1..100)
			MAX-ACCESS read-write
			STATUS current
			DESCRIPTION
				"Global setting for number of keepalive messages to send before declaring a peer dead.
				
				XPath: /wing-config/device[mac=key1]/ikev1_dpd_retries"
			DEFVAL { 5 }
			::= { wingCfgDevVpnEntry 4 }

		
		-- 1.3.6.1.4.1.1916.2.131.50.1.3.18.19.1.1.5
		wingCfgDevVpnIkev1GlobalNatKeepalive OBJECT-TYPE
			SYNTAX Unsigned32 (10..3600)
			UNITS "seconds"
			MAX-ACCESS read-write
			STATUS current
			DESCRIPTION
				"Global setting for frequency of NAT keepalive messages.
				
				XPath: /wing-config/device[mac=key1]/ikev1_nat_keepalive"
			DEFVAL { 20 }
			::= { wingCfgDevVpnEntry 5 }

		
		-- 1.3.6.1.4.1.1916.2.131.50.1.3.18.19.1.1.6
		wingCfgDevVpnIkev2GlobalDpdKeepalive OBJECT-TYPE
			SYNTAX Unsigned32 (10..3600)
			UNITS "seconds"
			MAX-ACCESS read-write
			STATUS current
			DESCRIPTION
				"Global setting for frequency of IKE keepalive messages for Dead Peer Detection.
				
				XPath: /wing-config/device[mac=key1]/ikev2_dpd_keepalive"
			DEFVAL { 30 }
			::= { wingCfgDevVpnEntry 6 }

		
		-- 1.3.6.1.4.1.1916.2.131.50.1.3.18.19.1.1.7
		wingCfgDevVpnIkev2GlobalDpdRetries OBJECT-TYPE
			SYNTAX Unsigned32 (1..100)
			MAX-ACCESS read-write
			STATUS current
			DESCRIPTION
				"Global setting for number of keepalive messages to send before declaring a peer dead.
				
				XPath: /wing-config/device[mac=key1]/ikev2_dpd_retries"
			DEFVAL { 5 }
			::= { wingCfgDevVpnEntry 7 }

		
		-- 1.3.6.1.4.1.1916.2.131.50.1.3.18.19.1.1.8
		wingCfgDevVpnIkev2GlobalNatKeepalive OBJECT-TYPE
			SYNTAX Unsigned32 (10..3600)
			UNITS "seconds"
			MAX-ACCESS read-write
			STATUS current
			DESCRIPTION
				"Global setting for frequency of NAT keepalive messages.
				
				XPath: /wing-config/device[mac=key1]/ikev2_nat_keepalive"
			DEFVAL { 20 }
			::= { wingCfgDevVpnEntry 8 }

		
		-- 1.3.6.1.4.1.1916.2.131.50.1.3.18.19.1.1.9
		wingCfgDevVpnCookieChallengeThreshold OBJECT-TYPE
			SYNTAX Unsigned32 (1..100)
			MAX-ACCESS read-write
			STATUS current
			DESCRIPTION
				"Number of Half open IKE SA after which cookie challenge mechanism is enabled (IKEv2 only).
				
				XPath: /wing-config/device[mac=key1]/cookie_challenge_threshold"
			DEFVAL { 5 }
			::= { wingCfgDevVpnEntry 9 }

		
		-- 1.3.6.1.4.1.1916.2.131.50.1.3.18.19.1.1.10
		wingCfgDevVpnMaxInNegotiationSa OBJECT-TYPE
			SYNTAX Unsigned32 (1..100)
			MAX-ACCESS read-write
			STATUS current
			DESCRIPTION
				"Maximum allowed half open IKE SAs (IKEv2 only).
				
				XPath: /wing-config/device[mac=key1]/max_in_negotiation_sa"
			DEFVAL { 10 }
			::= { wingCfgDevVpnEntry 10 }

		
		-- 1.3.6.1.4.1.1916.2.131.50.1.3.18.19.1.1.11
		wingCfgDevVpnDfBit OBJECT-TYPE
			SYNTAX DisplayString
			MAX-ACCESS read-write
			STATUS current
			DESCRIPTION
				"Configure DF bit handling for esp encapsulating header
				
				Values:
				clear,
				set,
				copy
				
				XPath: /wing-config/device[mac=key1]/df_bit"
			DEFVAL { "copy" }
			::= { wingCfgDevVpnEntry 11 }

		
		-- 1.3.6.1.4.1.1916.2.131.50.1.3.18.19.2
		wingCfgDevVpnIkev1Table OBJECT-TYPE
			SYNTAX SEQUENCE OF WingCfgDevVpnIkev1Entry
			MAX-ACCESS not-accessible
			STATUS current
			DESCRIPTION
				"
				
				/wing-config/device/ikev1_policy"
			::= { wingCfgDevVpn 2 }

		
		-- 1.3.6.1.4.1.1916.2.131.50.1.3.18.19.2.1
		wingCfgDevVpnIkev1Entry OBJECT-TYPE
			SYNTAX WingCfgDevVpnIkev1Entry
			MAX-ACCESS not-accessible
			STATUS current
			DESCRIPTION
				"An entry in the table."
			INDEX { wingCfgDevMac, wingCfgDevVpnIkev1Name }
			::= { wingCfgDevVpnIkev1Table 1 }

		
		WingCfgDevVpnIkev1Entry ::=
			SEQUENCE { 
				wingCfgDevVpnIkev1Name
					WingIdentifier,
				wingCfgDevVpnIkev1Mode
					DisplayString,
				wingCfgDevVpnIkev1IsakmpLifetime
					Unsigned32,
				wingCfgDevVpnIkev1DpdKeepalive
					Unsigned32,
				wingCfgDevVpnIkev1DpdRetries
					Unsigned32
			 }

		-- 1.3.6.1.4.1.1916.2.131.50.1.3.18.19.2.1.1
		wingCfgDevVpnIkev1Name OBJECT-TYPE
			SYNTAX WingIdentifier
			MAX-ACCESS read-only
			STATUS current
			DESCRIPTION
				"
				
				XPath: /wing-config/device[mac=key1]/ikev1_policy[name=key2]/name"
			::= { wingCfgDevVpnIkev1Entry 1 }

		
		-- 1.3.6.1.4.1.1916.2.131.50.1.3.18.19.2.1.3
		wingCfgDevVpnIkev1Mode OBJECT-TYPE
			SYNTAX DisplayString
			MAX-ACCESS read-write
			STATUS current
			DESCRIPTION
				"IKE version 1 mode of operation (main/aggressive).
				
				Values:
				main,
				aggressive
				
				XPath: /wing-config/device[mac=key1]/ikev1_policy[name=key2]/mode"
			DEFVAL { "main" }
			::= { wingCfgDevVpnIkev1Entry 3 }

		
		-- 1.3.6.1.4.1.1916.2.131.50.1.3.18.19.2.1.4
		wingCfgDevVpnIkev1IsakmpLifetime OBJECT-TYPE
			SYNTAX Unsigned32 (600..2147483646)
			UNITS "seconds"
			MAX-ACCESS read-write
			STATUS current
			DESCRIPTION
				"Lifetime in seconds for IKE Security Association (ISAKMP SA).
				
				XPath: /wing-config/device[mac=key1]/ikev1_policy[name=key2]/isakmp_lifetime"
			DEFVAL { 86400 }
			::= { wingCfgDevVpnIkev1Entry 4 }

		
		-- 1.3.6.1.4.1.1916.2.131.50.1.3.18.19.2.1.5
		wingCfgDevVpnIkev1DpdKeepalive OBJECT-TYPE
			SYNTAX Unsigned32 (10..3600)
			UNITS "seconds"
			MAX-ACCESS read-write
			STATUS current
			DESCRIPTION
				"Frequency of IKE keepalive messages for Dead Peer Detection.
				
				XPath: /wing-config/device[mac=key1]/ikev1_policy[name=key2]/dpd_keepalive"
			DEFVAL { 30 }
			::= { wingCfgDevVpnIkev1Entry 5 }

		
		-- 1.3.6.1.4.1.1916.2.131.50.1.3.18.19.2.1.6
		wingCfgDevVpnIkev1DpdRetries OBJECT-TYPE
			SYNTAX Unsigned32 (1..100)
			MAX-ACCESS read-write
			STATUS current
			DESCRIPTION
				"Number of keepalive messages to send before declaring a peer dead.
				
				XPath: /wing-config/device[mac=key1]/ikev1_policy[name=key2]/dpd_retries"
			DEFVAL { 5 }
			::= { wingCfgDevVpnIkev1Entry 6 }

		
		-- 1.3.6.1.4.1.1916.2.131.50.1.3.18.19.3
		wingCfgDevVpnIkev1IsakmpTable OBJECT-TYPE
			SYNTAX SEQUENCE OF WingCfgDevVpnIkev1IsakmpEntry
			MAX-ACCESS not-accessible
			STATUS current
			DESCRIPTION
				"
				
				/wing-config/device/ikev1_policy/isakmp_proposal"
			::= { wingCfgDevVpn 3 }

		
		-- 1.3.6.1.4.1.1916.2.131.50.1.3.18.19.3.1
		wingCfgDevVpnIkev1IsakmpEntry OBJECT-TYPE
			SYNTAX WingCfgDevVpnIkev1IsakmpEntry
			MAX-ACCESS not-accessible
			STATUS current
			DESCRIPTION
				"An entry in the table."
			INDEX { wingCfgDevMac, wingCfgDevVpnIkev1Name, wingCfgDevVpnIkev1IsakmpName }
			::= { wingCfgDevVpnIkev1IsakmpTable 1 }

		
		WingCfgDevVpnIkev1IsakmpEntry ::=
			SEQUENCE { 
				wingCfgDevVpnIkev1IsakmpName
					WingIdentifier,
				wingCfgDevVpnIkev1IsakmpEncryption
					DisplayString,
				wingCfgDevVpnIkev1IsakmpGroup
					DisplayString,
				wingCfgDevVpnIkev1IsakmpHash
					DisplayString
			 }

		-- 1.3.6.1.4.1.1916.2.131.50.1.3.18.19.3.1.1
		wingCfgDevVpnIkev1IsakmpName OBJECT-TYPE
			SYNTAX WingIdentifier
			MAX-ACCESS read-only
			STATUS current
			DESCRIPTION
				"
				
				XPath: /wing-config/device[mac=key1]/ikev1_policy[name=key2]/isakmp_proposal[name=key3]/name"
			::= { wingCfgDevVpnIkev1IsakmpEntry 1 }

		
		-- 1.3.6.1.4.1.1916.2.131.50.1.3.18.19.3.1.3
		wingCfgDevVpnIkev1IsakmpEncryption OBJECT-TYPE
			SYNTAX DisplayString
			MAX-ACCESS read-write
			STATUS current
			DESCRIPTION
				"Encryption method protecting data transmitted between peers.
				
				Values:
				3des,
				aes,
				aes-192,
				aes-256
				
				XPath: /wing-config/device[mac=key1]/ikev1_policy[name=key2]/isakmp_proposal[name=key3]/encryption"
			DEFVAL { "aes-256" }
			::= { wingCfgDevVpnIkev1IsakmpEntry 3 }

		
		-- 1.3.6.1.4.1.1916.2.131.50.1.3.18.19.3.1.4
		wingCfgDevVpnIkev1IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /wing-config/device[mac=key1]/ikev1_policy[name=key2]/isakmp_proposal[name=key3]/group"
			DEFVAL { "2" }
			::= { wingCfgDevVpnIkev1IsakmpEntry 4 }

		
		-- 1.3.6.1.4.1.1916.2.131.50.1.3.18.19.3.1.5
		wingCfgDevVpnIkev1IsakmpHash OBJECT-TYPE
			SYNTAX DisplayString
			MAX-ACCESS read-write
			STATUS current
			DESCRIPTION
				"Hash algorithm used to ensure data integrity.
				
				Values:
				md5,
				sha
				
				XPath: /wing-config/device[mac=key1]/ikev1_policy[name=key2]/isakmp_proposal[name=key3]/hash"
			DEFVAL { "sha" }
			::= { wingCfgDevVpnIkev1IsakmpEntry 5 }

		
		-- 1.3.6.1.4.1.1916.2.131.50.1.3.18.19.4
		wingCfgDevVpnIkev2Table OBJECT-TYPE
			SYNTAX SEQUENCE OF WingCfgDevVpnIkev2Entry
			MAX-ACCESS not-accessible
			STATUS current
			DESCRIPTION
				"
				
				/wing-config/device/ikev2_policy"
			::= { wingCfgDevVpn 4 }

		
		-- 1.3.6.1.4.1.1916.2.131.50.1.3.18.19.4.1
		wingCfgDevVpnIkev2Entry OBJECT-TYPE
			SYNTAX WingCfgDevVpnIkev2Entry
			MAX-ACCESS not-accessible
			STATUS current
			DESCRIPTION
				"An entry in the table."
			INDEX { wingCfgDevMac, wingCfgDevVpnIkev2Name }
			::= { wingCfgDevVpnIkev2Table 1 }

		
		WingCfgDevVpnIkev2Entry ::=
			SEQUENCE { 
				wingCfgDevVpnIkev2Name
					WingIdentifier,
				wingCfgDevVpnIkev2IkeLifetime
					Unsigned32,
				wingCfgDevVpnIkev2DpdKeepalive
					Unsigned32
			 }

		-- 1.3.6.1.4.1.1916.2.131.50.1.3.18.19.4.1.1
		wingCfgDevVpnIkev2Name OBJECT-TYPE
			SYNTAX WingIdentifier
			MAX-ACCESS read-only
			STATUS current
			DESCRIPTION
				"
				
				XPath: /wing-config/device[mac=key1]/ikev2_policy[name=key2]/name"
			::= { wingCfgDevVpnIkev2Entry 1 }

		
		-- 1.3.6.1.4.1.1916.2.131.50.1.3.18.19.4.1.3
		wingCfgDevVpnIkev2IkeLifetime OBJECT-TYPE
			SYNTAX Unsigned32 (600..2147483646)
			UNITS "seconds"
			MAX-ACCESS read-write
			STATUS current
			DESCRIPTION
				"Lifetime in seconds for IKE Security Association (ISAKMP SA).
				
				XPath: /wing-config/device[mac=key1]/ikev2_policy[name=key2]/isakmp_lifetime"
			DEFVAL { 86400 }
			::= { wingCfgDevVpnIkev2Entry 3 }

		
		-- 1.3.6.1.4.1.1916.2.131.50.1.3.18.19.4.1.4
		wingCfgDevVpnIkev2DpdKeepalive OBJECT-TYPE
			SYNTAX Unsigned32 (10..3600)
			UNITS "seconds"
			MAX-ACCESS read-write
			STATUS current
			DESCRIPTION
				"Frequency of IKE keepalive messages for Dead Peer Detection.
				
				XPath: /wing-config/device[mac=key1]/ikev2_policy[name=key2]/dpd_keepalive"
			DEFVAL { 10 }
			::= { wingCfgDevVpnIkev2Entry 4 }

		
		-- 1.3.6.1.4.1.1916.2.131.50.1.3.18.19.5
		wingCfgDevVpnIkev2IsakmpTable OBJECT-TYPE
			SYNTAX SEQUENCE OF WingCfgDevVpnIkev2IsakmpEntry
			MAX-ACCESS not-accessible
			STATUS current
			DESCRIPTION
				"
				
				/wing-config/device/ikev2_policy/isakmp_proposal"
			::= { wingCfgDevVpn 5 }

		
		-- 1.3.6.1.4.1.1916.2.131.50.1.3.18.19.5.1
		wingCfgDevVpnIkev2IsakmpEntry OBJECT-TYPE
			SYNTAX WingCfgDevVpnIkev2IsakmpEntry
			MAX-ACCESS not-accessible
			STATUS current
			DESCRIPTION
				"An entry in the table."
			INDEX { wingCfgDevMac, wingCfgDevVpnIkev2Name, wingCfgDevVpnIkev2IsakmpName }
			::= { wingCfgDevVpnIkev2IsakmpTable 1 }

		
		WingCfgDevVpnIkev2IsakmpEntry ::=
			SEQUENCE { 
				wingCfgDevVpnIkev2IsakmpName
					WingIdentifier,
				wingCfgDevVpnIkev2IsakmpEncryption
					DisplayString,
				wingCfgDevVpnIkev2IsakmpGroup
					DisplayString,
				wingCfgDevVpnIkev2IsakmpHash
					DisplayString
			 }

		-- 1.3.6.1.4.1.1916.2.131.50.1.3.18.19.5.1.1
		wingCfgDevVpnIkev2IsakmpName OBJECT-TYPE
			SYNTAX WingIdentifier
			MAX-ACCESS read-only
			STATUS current
			DESCRIPTION
				"
				
				XPath: /wing-config/device[mac=key1]/ikev2_policy[name=key2]/isakmp_proposal[name=key3]/name"
			::= { wingCfgDevVpnIkev2IsakmpEntry 1 }

		
		-- 1.3.6.1.4.1.1916.2.131.50.1.3.18.19.5.1.3
		wingCfgDevVpnIkev2IsakmpEncryption OBJECT-TYPE
			SYNTAX DisplayString
			MAX-ACCESS read-write
			STATUS current
			DESCRIPTION
				"Encryption method protecting data transmitted between peers.
				
				Values:
				3des,
				aes,
				aes-192,
				aes-256
				
				XPath: /wing-config/device[mac=key1]/ikev2_policy[name=key2]/isakmp_proposal[name=key3]/encryption"
			DEFVAL { "aes-256" }
			::= { wingCfgDevVpnIkev2IsakmpEntry 3 }

		
		-- 1.3.6.1.4.1.1916.2.131.50.1.3.18.19.5.1.4
		wingCfgDevVpnIkev2IsakmpGroup OBJECT-TYPE
			SYNTAX DisplayString
			MAX-ACCESS read-write
			STATUS current
			DESCRIPTION
				"Diffie-Hellman group identifier. IPsec peers use the defined value to derive a shared secret without transmitting.
				
				Values:
				2,
				5,
				14
				
				XPath: /wing-config/device[mac=key1]/ikev2_policy[name=key2]/isakmp_proposal[name=key3]/group"
			DEFVAL { "2" }
			::= { wingCfgDevVpnIkev2IsakmpEntry 4 }

		
		-- 1.3.6.1.4.1.1916.2.131.50.1.3.18.19.5.1.5
		wingCfgDevVpnIkev2IsakmpHash OBJECT-TYPE
			SYNTAX DisplayString
			MAX-ACCESS read-write
			STATUS current
			DESCRIPTION
				"Hash algorithm used to ensure data integrity.
				
				Values:
				md5,
				sha
				
				XPath: /wing-config/device[mac=key1]/ikev2_policy[name=key2]/isakmp_proposal[name=key3]/hash"
			DEFVAL { "sha" }
			::= { wingCfgDevVpnIkev2IsakmpEntry 5 }

		
		-- 1.3.6.1.4.1.1916.2.131.50.1.3.18.19.6
		wingCfgDevVpnIkev1PeerTable OBJECT-TYPE
			SYNTAX SEQUENCE OF WingCfgDevVpnIkev1PeerEntry
			MAX-ACCESS not-accessible
			STATUS current
			DESCRIPTION
				"
				
				/wing-config/device/ikev1_peer"
			::= { wingCfgDevVpn 6 }

		
		-- 1.3.6.1.4.1.1916.2.131.50.1.3.18.19.6.1
		wingCfgDevVpnIkev1PeerEntry OBJECT-TYPE
			SYNTAX WingCfgDevVpnIkev1PeerEntry
			MAX-ACCESS not-accessible
			STATUS current
			DESCRIPTION
				"An entry in the table."
			INDEX { wingCfgDevMac, wingCfgDevVpnIkev1PeerName }
			::= { wingCfgDevVpnIkev1PeerTable 1 }

		
		WingCfgDevVpnIkev1PeerEntry ::=
			SEQUENCE { 
				wingCfgDevVpnIkev1PeerName
					WingIdentifier,
				wingCfgDevVpnIkev1PeerIpType
					DisplayString,
				wingCfgDevVpnIkev1PeerIpValue
					DisplayString,
				wingCfgDevVpnIkev1PeerAuthType
					DisplayString,
				wingCfgDevVpnIkev1PeerAuthKey
					DisplayString,
				wingCfgDevVpnIkev1PeerLocalidType
					DisplayString,
				wingCfgDevVpnIkev1PeerLocalidValue
					DisplayString,
				wingCfgDevVpnIkev1PeerRemoteidType
					DisplayString,
				wingCfgDevVpnIkev1PeerRemoteidValue
					DisplayString,
				wingCfgDevVpnIkev1PeerIkev1Policy
					WingIdentifier
			 }

		-- 1.3.6.1.4.1.1916.2.131.50.1.3.18.19.6.1.1
		wingCfgDevVpnIkev1PeerName OBJECT-TYPE
			SYNTAX WingIdentifier
			MAX-ACCESS read-only
			STATUS current
			DESCRIPTION
				"
				
				XPath: /wing-config/device[mac=key1]/ikev1_peer[name=key2]/name"
			::= { wingCfgDevVpnIkev1PeerEntry 1 }

		
		-- 1.3.6.1.4.1.1916.2.131.50.1.3.18.19.6.1.3
		wingCfgDevVpnIkev1PeerIpType OBJECT-TYPE
			SYNTAX DisplayString
			MAX-ACCESS read-write
			STATUS current
			DESCRIPTION
				"IP address/fqdn of the IPSEC VPN peer for tunnel setup
				
				Values:
				address,
				fqdn
				
				XPath: /wing-config/device[mac=key1]/ikev1_peer[name=key2]/ip/type"
			DEFVAL { "address" }
			::= { wingCfgDevVpnIkev1PeerEntry 3 }

		
		-- 1.3.6.1.4.1.1916.2.131.50.1.3.18.19.6.1.4
		wingCfgDevVpnIkev1PeerIpValue OBJECT-TYPE
			SYNTAX DisplayString (SIZE (1..64))
			MAX-ACCESS read-write
			STATUS current
			DESCRIPTION
				"Peer IP can be specified as either IP or FQDN.
				
				XPath: /wing-config/device[mac=key1]/ikev1_peer[name=key2]/ip/value"
			::= { wingCfgDevVpnIkev1PeerEntry 4 }

		
		-- 1.3.6.1.4.1.1916.2.131.50.1.3.18.19.6.1.5
		wingCfgDevVpnIkev1PeerAuthType OBJECT-TYPE
			SYNTAX DisplayString
			MAX-ACCESS read-write
			STATUS current
			DESCRIPTION
				"
				
				Values:
				psk,
				rsa
				
				XPath: /wing-config/device[mac=key1]/ikev1_peer[name=key2]/authentication/type"
			DEFVAL { "rsa" }
			::= { wingCfgDevVpnIkev1PeerEntry 5 }

		
		-- 1.3.6.1.4.1.1916.2.131.50.1.3.18.19.6.1.6
		wingCfgDevVpnIkev1PeerAuthKey OBJECT-TYPE
			SYNTAX DisplayString (SIZE (8..21))
			MAX-ACCESS read-write
			STATUS current
			DESCRIPTION
				"The shared secret used for peer authentication.
				
				XPath: /wing-config/device[mac=key1]/ikev1_peer[name=key2]/authentication/key"
			::= { wingCfgDevVpnIkev1PeerEntry 6 }

		
		-- 1.3.6.1.4.1.1916.2.131.50.1.3.18.19.6.1.7
		wingCfgDevVpnIkev1PeerLocalidType OBJECT-TYPE
			SYNTAX DisplayString
			MAX-ACCESS read-write
			STATUS current
			DESCRIPTION
				"Local identity to use in IKE exchange with this peer.
				
				Values:
				address,
				dn,
				fqdn,
				email,
				string
				
				XPath: /wing-config/device[mac=key1]/ikev1_peer[name=key2]/localid/localid_type"
			DEFVAL { "'string'" }
			::= { wingCfgDevVpnIkev1PeerEntry 7 }

		
		-- 1.3.6.1.4.1.1916.2.131.50.1.3.18.19.6.1.8
		wingCfgDevVpnIkev1PeerLocalidValue OBJECT-TYPE
			SYNTAX DisplayString (SIZE (1..128))
			MAX-ACCESS read-write
			STATUS current
			DESCRIPTION
				"
				
				XPath: /wing-config/device[mac=key1]/ikev1_peer[name=key2]/localid/localid_value"
			::= { wingCfgDevVpnIkev1PeerEntry 8 }

		
		-- 1.3.6.1.4.1.1916.2.131.50.1.3.18.19.6.1.9
		wingCfgDevVpnIkev1PeerRemoteidType OBJECT-TYPE
			SYNTAX DisplayString
			MAX-ACCESS read-write
			STATUS current
			DESCRIPTION
				"Peer identity of this peer.
				
				Values:
				address,
				dn,
				fqdn,
				email,
				string
				
				XPath: /wing-config/device[mac=key1]/ikev1_peer[name=key2]/remoteid/remoteid_type"
			DEFVAL { "'string'" }
			::= { wingCfgDevVpnIkev1PeerEntry 9 }

		
		-- 1.3.6.1.4.1.1916.2.131.50.1.3.18.19.6.1.10
		wingCfgDevVpnIkev1PeerRemoteidValue OBJECT-TYPE
			SYNTAX DisplayString (SIZE (1..128))
			MAX-ACCESS read-write
			STATUS current
			DESCRIPTION
				"
				
				XPath: /wing-config/device[mac=key1]/ikev1_peer[name=key2]/remoteid/remoteid_value"
			::= { wingCfgDevVpnIkev1PeerEntry 10 }

		
		-- 1.3.6.1.4.1.1916.2.131.50.1.3.18.19.6.1.11
		wingCfgDevVpnIkev1PeerIkev1Policy OBJECT-TYPE
			SYNTAX WingIdentifier
			MAX-ACCESS read-write
			STATUS current
			DESCRIPTION
				"
				
				XPath: /wing-config/device[mac=key1]/ikev1_peer[name=key2]/ikev1_policy"
			::= { wingCfgDevVpnIkev1PeerEntry 11 }

		
		-- 1.3.6.1.4.1.1916.2.131.50.1.3.18.19.7
		wingCfgDevVpnIkev2PeerTable OBJECT-TYPE
			SYNTAX SEQUENCE OF WingCfgDevVpnIkev2PeerEntry
			MAX-ACCESS not-accessible
			STATUS current
			DESCRIPTION
				"
				
				/wing-config/device/ikev2_peer"
			::= { wingCfgDevVpn 7 }

		
		-- 1.3.6.1.4.1.1916.2.131.50.1.3.18.19.7.1
		wingCfgDevVpnIkev2PeerEntry OBJECT-TYPE
			SYNTAX WingCfgDevVpnIkev2PeerEntry
			MAX-ACCESS not-accessible
			STATUS current
			DESCRIPTION
				"An entry in the table."
			INDEX { wingCfgDevMac, wingCfgDevVpnIkev2PeerName }
			::= { wingCfgDevVpnIkev2PeerTable 1 }

		
		WingCfgDevVpnIkev2PeerEntry ::=
			SEQUENCE { 
				wingCfgDevVpnIkev2PeerName
					WingIdentifier,
				wingCfgDevVpnIkev2PeerIpType
					DisplayString,
				wingCfgDevVpnIkev2PeerIpValue
					DisplayString,
				wingCfgDevVpnIkev2PeerLocalAuthType
					DisplayString,
				wingCfgDevVpnIkev2PeerLocalAuthKey
					DisplayString,
				wingCfgDevVpnIkev2PeerRemoteAuthType
					DisplayString,
				wingCfgDevVpnIkev2PeerRemoteAuthKey
					DisplayString,
				wingCfgDevVpnIkev2PeerLocalidType
					DisplayString,
				wingCfgDevVpnIkev2PeerLocalidValue
					DisplayString,
				wingCfgDevVpnIkev2PeerRemoteidType
					DisplayString,
				wingCfgDevVpnIkev2PeerRemoteidValue
					DisplayString,
				wingCfgDevVpnIkev2PeerIkev2Policy
					WingIdentifier
			 }

		-- 1.3.6.1.4.1.1916.2.131.50.1.3.18.19.7.1.1
		wingCfgDevVpnIkev2PeerName OBJECT-TYPE
			SYNTAX WingIdentifier
			MAX-ACCESS read-only
			STATUS current
			DESCRIPTION
				"
				
				XPath: /wing-config/device[mac=key1]/ikev2_peer[name=key2]/name"
			::= { wingCfgDevVpnIkev2PeerEntry 1 }

		
		-- 1.3.6.1.4.1.1916.2.131.50.1.3.18.19.7.1.3
		wingCfgDevVpnIkev2PeerIpType OBJECT-TYPE
			SYNTAX DisplayString
			MAX-ACCESS read-write
			STATUS current
			DESCRIPTION
				"IP address/hostname of the IPSEC VPN peer for tunnel setup
				
				Values:
				address,
				fqdn
				
				XPath: /wing-config/device[mac=key1]/ikev2_peer[name=key2]/ip/type"
			DEFVAL { "address" }
			::= { wingCfgDevVpnIkev2PeerEntry 3 }

		
		-- 1.3.6.1.4.1.1916.2.131.50.1.3.18.19.7.1.4
		wingCfgDevVpnIkev2PeerIpValue OBJECT-TYPE
			SYNTAX DisplayString (SIZE (1..64))
			MAX-ACCESS read-write
			STATUS current
			DESCRIPTION
				"Peer IP can be specified as either IP or FQDN.
				
				XPath: /wing-config/device[mac=key1]/ikev2_peer[name=key2]/ip/value"
			::= { wingCfgDevVpnIkev2PeerEntry 4 }

		
		-- 1.3.6.1.4.1.1916.2.131.50.1.3.18.19.7.1.5
		wingCfgDevVpnIkev2PeerLocalAuthType OBJECT-TYPE
			SYNTAX DisplayString
			MAX-ACCESS read-write
			STATUS current
			DESCRIPTION
				"
				
				Values:
				psk,
				rsa
				
				XPath: /wing-config/device[mac=key1]/ikev2_peer[name=key2]/local_authentication/type"
			DEFVAL { "rsa" }
			::= { wingCfgDevVpnIkev2PeerEntry 5 }

		
		-- 1.3.6.1.4.1.1916.2.131.50.1.3.18.19.7.1.6
		wingCfgDevVpnIkev2PeerLocalAuthKey OBJECT-TYPE
			SYNTAX DisplayString (SIZE (8..21))
			MAX-ACCESS read-write
			STATUS current
			DESCRIPTION
				"The shared secret used for local peer authentication.
				
				XPath: /wing-config/device[mac=key1]/ikev2_peer[name=key2]/local_authentication/key"
			::= { wingCfgDevVpnIkev2PeerEntry 6 }

		
		-- 1.3.6.1.4.1.1916.2.131.50.1.3.18.19.7.1.7
		wingCfgDevVpnIkev2PeerRemoteAuthType OBJECT-TYPE
			SYNTAX DisplayString
			MAX-ACCESS read-write
			STATUS current
			DESCRIPTION
				"
				
				Values:
				psk,
				rsa
				
				XPath: /wing-config/device[mac=key1]/ikev2_peer[name=key2]/remote_authentication/type"
			DEFVAL { "rsa" }
			::= { wingCfgDevVpnIkev2PeerEntry 7 }

		
		-- 1.3.6.1.4.1.1916.2.131.50.1.3.18.19.7.1.8
		wingCfgDevVpnIkev2PeerRemoteAuthKey OBJECT-TYPE
			SYNTAX DisplayString (SIZE (8..21))
			MAX-ACCESS read-write
			STATUS current
			DESCRIPTION
				"The shared secret used for remote peer authentication.
				
				XPath: /wing-config/device[mac=key1]/ikev2_peer[name=key2]/remote_authentication/key"
			::= { wingCfgDevVpnIkev2PeerEntry 8 }

		
		-- 1.3.6.1.4.1.1916.2.131.50.1.3.18.19.7.1.9
		wingCfgDevVpnIkev2PeerLocalidType OBJECT-TYPE
			SYNTAX DisplayString
			MAX-ACCESS read-write
			STATUS current
			DESCRIPTION
				"Local identity to use in IKE exchange with this peer.
				
				Values:
				address,
				dn,
				fqdn,
				email,
				string
				
				XPath: /wing-config/device[mac=key1]/ikev2_peer[name=key2]/localid/localid_type"
			DEFVAL { "'string'" }
			::= { wingCfgDevVpnIkev2PeerEntry 9 }

		
		-- 1.3.6.1.4.1.1916.2.131.50.1.3.18.19.7.1.10
		wingCfgDevVpnIkev2PeerLocalidValue OBJECT-TYPE
			SYNTAX DisplayString (SIZE (1..128))
			MAX-ACCESS read-write
			STATUS current
			DESCRIPTION
				"
				
				XPath: /wing-config/device[mac=key1]/ikev2_peer[name=key2]/localid/localid_value"
			::= { wingCfgDevVpnIkev2PeerEntry 10 }

		
		-- 1.3.6.1.4.1.1916.2.131.50.1.3.18.19.7.1.11
		wingCfgDevVpnIkev2PeerRemoteidType OBJECT-TYPE
			SYNTAX DisplayString
			MAX-ACCESS read-write
			STATUS current
			DESCRIPTION
				"Peer identity of this peer.
				
				Values:
				address,
				dn,
				fqdn,
				email,
				string
				
				XPath: /wing-config/device[mac=key1]/ikev2_peer[name=key2]/remoteid/remoteid_type"
			DEFVAL { "'string'" }
			::= { wingCfgDevVpnIkev2PeerEntry 11 }

		
		-- 1.3.6.1.4.1.1916.2.131.50.1.3.18.19.7.1.12
		wingCfgDevVpnIkev2PeerRemoteidValue OBJECT-TYPE
			SYNTAX DisplayString (SIZE (1..128))
			MAX-ACCESS read-write
			STATUS current
			DESCRIPTION
				"
				
				XPath: /wing-config/device[mac=key1]/ikev2_peer[name=key2]/remoteid/remoteid_value"
			::= { wingCfgDevVpnIkev2PeerEntry 12 }

		
		-- 1.3.6.1.4.1.1916.2.131.50.1.3.18.19.7.1.13
		wingCfgDevVpnIkev2PeerIkev2Policy OBJECT-TYPE
			SYNTAX WingIdentifier
			MAX-ACCESS read-write
			STATUS current
			DESCRIPTION
				"IKEv2 Policy to use with this peer.
				
				XPath: /wing-config/device[mac=key1]/ikev2_peer[name=key2]/ikev2_policy"
			::= { wingCfgDevVpnIkev2PeerEntry 13 }

		
		-- 1.3.6.1.4.1.1916.2.131.50.1.3.18.19.8
		wingCfgDevVpnTransformTable OBJECT-TYPE
			SYNTAX SEQUENCE OF WingCfgDevVpnTransformEntry
			MAX-ACCESS not-accessible
			STATUS current
			DESCRIPTION
				"
				
				/wing-config/device/ipsec_transform_set"
			::= { wingCfgDevVpn 8 }

		
		-- 1.3.6.1.4.1.1916.2.131.50.1.3.18.19.8.1
		wingCfgDevVpnTransformEntry OBJECT-TYPE
			SYNTAX WingCfgDevVpnTransformEntry
			MAX-ACCESS not-accessible
			STATUS current
			DESCRIPTION
				"An entry in the table."
			INDEX { wingCfgDevMac, wingCfgDevVpnTransformName }
			::= { wingCfgDevVpnTransformTable 1 }

		
		WingCfgDevVpnTransformEntry ::=
			SEQUENCE { 
				wingCfgDevVpnTransformName
					WingIdentifier,
				wingCfgDevVpnTransformCipherAlgo
					DisplayString,
				wingCfgDevVpnTransformAuthAlgo
					DisplayString,
				wingCfgDevVpnTransformMode
					DisplayString
			 }

		-- 1.3.6.1.4.1.1916.2.131.50.1.3.18.19.8.1.1
		wingCfgDevVpnTransformName OBJECT-TYPE
			SYNTAX WingIdentifier
			MAX-ACCESS read-only
			STATUS current
			DESCRIPTION
				"
				
				XPath: /wing-config/device[mac=key1]/ipsec_transform_set[name=key2]/name"
			::= { wingCfgDevVpnTransformEntry 1 }

		
		-- 1.3.6.1.4.1.1916.2.131.50.1.3.18.19.8.1.3
		wingCfgDevVpnTransformCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /wing-config/device[mac=key1]/ipsec_transform_set[name=key2]/cipher_algo"
			DEFVAL { "aes-256" }
			::= { wingCfgDevVpnTransformEntry 3 }

		
		-- 1.3.6.1.4.1.1916.2.131.50.1.3.18.19.8.1.4
		wingCfgDevVpnTransformAuthAlgo OBJECT-TYPE
			SYNTAX DisplayString
			MAX-ACCESS read-write
			STATUS current
			DESCRIPTION
				"Authentication scheme used to validate identity.
				
				Values:
				md5-hmac,
				sha-hmac
				
				XPath: /wing-config/device[mac=key1]/ipsec_transform_set[name=key2]/auth_algo"
			DEFVAL { "sha-hmac" }
			::= { wingCfgDevVpnTransformEntry 4 }

		
		-- 1.3.6.1.4.1.1916.2.131.50.1.3.18.19.8.1.5
		wingCfgDevVpnTransformMode OBJECT-TYPE
			SYNTAX DisplayString
			MAX-ACCESS read-write
			STATUS current
			DESCRIPTION
				"IPsec tunnel type - tunnel mode is used for site-to-site vpn and transport mode is used to remote-vpn.
				
				Values:
				tunnel,
				transport
				
				XPath: /wing-config/device[mac=key1]/ipsec_transform_set[name=key2]/mode"
			DEFVAL { "tunnel" }
			::= { wingCfgDevVpnTransformEntry 5 }

		
		-- 1.3.6.1.4.1.1916.2.131.50.1.3.18.19.9
		wingCfgDevVpnCryptoTable OBJECT-TYPE
			SYNTAX SEQUENCE OF WingCfgDevVpnCryptoEntry
			MAX-ACCESS not-accessible
			STATUS current
			DESCRIPTION
				"
				
				/wing-config/device/crypto_map"
			::= { wingCfgDevVpn 9 }

		
		-- 1.3.6.1.4.1.1916.2.131.50.1.3.18.19.9.1
		wingCfgDevVpnCryptoEntry OBJECT-TYPE
			SYNTAX WingCfgDevVpnCryptoEntry
			MAX-ACCESS not-accessible
			STATUS current
			DESCRIPTION
				"An entry in the table."
			INDEX { wingCfgDevMac, wingCfgDevVpnCryptoName }
			::= { wingCfgDevVpnCryptoTable 1 }

		
		WingCfgDevVpnCryptoEntry ::=
			SEQUENCE { 
				wingCfgDevVpnCryptoName
					WingIdentifier
			 }

		-- 1.3.6.1.4.1.1916.2.131.50.1.3.18.19.9.1.1
		wingCfgDevVpnCryptoName OBJECT-TYPE
			SYNTAX WingIdentifier
			MAX-ACCESS read-only
			STATUS current
			DESCRIPTION
				"
				
				XPath: /wing-config/device[mac=key1]/crypto_map[name=key2]/name"
			::= { wingCfgDevVpnCryptoEntry 1 }

		
		-- 1.3.6.1.4.1.1916.2.131.50.1.3.18.19.10
		wingCfgDevVpnCryptoInstTable OBJECT-TYPE
			SYNTAX SEQUENCE OF WingCfgDevVpnCryptoInstEntry
			MAX-ACCESS not-accessible
			STATUS current
			DESCRIPTION
				"
				
				/wing-config/device/crypto_map/crypto_map_entry"
			::= { wingCfgDevVpn 10 }

		
		-- 1.3.6.1.4.1.1916.2.131.50.1.3.18.19.10.1
		wingCfgDevVpnCryptoInstEntry OBJECT-TYPE
			SYNTAX WingCfgDevVpnCryptoInstEntry
			MAX-ACCESS not-accessible
			STATUS current
			DESCRIPTION
				"An entry in the table."
			INDEX { wingCfgDevMac, wingCfgDevVpnCryptoName, wingCfgDevVpnCryptoInstSequence }
			::= { wingCfgDevVpnCryptoInstTable 1 }

		
		WingCfgDevVpnCryptoInstEntry ::=
			SEQUENCE { 
				wingCfgDevVpnCryptoInstSequence
					Unsigned32,
				wingCfgDevVpnCryptoInstType
					DisplayString,
				wingCfgDevVpnCryptoInstIpAcl
					WingIdentifier,
				wingCfgDevVpnCryptoInstTransformSet
					WingIdentifier,
				wingCfgDevVpnCryptoInstLocalip
					DisplayString,
				wingCfgDevVpnCryptoInstPfs
					DisplayString,
				wingCfgDevVpnCryptoInstLifetimeSeconds
					Unsigned32,
				wingCfgDevVpnCryptoInstLifetimeKb
					Unsigned32,
				wingCfgDevVpnCryptoInstRemoteType
					DisplayString,
				wingCfgDevVpnCryptoInstModeconfig
					DisplayString,
				wingCfgDevVpnCryptoInstPeer
					DisplayString,
				wingCfgDevVpnCryptoInstProtocol
					DisplayString,
				wingCfgDevVpnCryptoInstMode
					DisplayString
			 }

		-- 1.3.6.1.4.1.1916.2.131.50.1.3.18.19.10.1.1
		wingCfgDevVpnCryptoInstSequence OBJECT-TYPE
			SYNTAX Unsigned32 (1..1000)
			MAX-ACCESS read-only
			STATUS current
			DESCRIPTION
				"
				
				XPath: /wing-config/device[mac=key1]/crypto_map[name=key2]/crypto_map_entry[sequence=key3]/sequence"
			::= { wingCfgDevVpnCryptoInstEntry 1 }

		
		-- 1.3.6.1.4.1.1916.2.131.50.1.3.18.19.10.1.3
		wingCfgDevVpnCryptoInstType OBJECT-TYPE
			SYNTAX DisplayString
			MAX-ACCESS read-write
			STATUS current
			DESCRIPTION
				"
				
				Values:
				site-to-site-auto,
				remote-vpn,
				site-to-site-manual
				
				XPath: /wing-config/device[mac=key1]/crypto_map[name=key2]/crypto_map_entry[sequence=key3]/type"
			DEFVAL { "site-to-site-auto" }
			::= { wingCfgDevVpnCryptoInstEntry 3 }

		
		-- 1.3.6.1.4.1.1916.2.131.50.1.3.18.19.10.1.4
		wingCfgDevVpnCryptoInstIpAcl OBJECT-TYPE
			SYNTAX WingIdentifier
			MAX-ACCESS read-write
			STATUS current
			DESCRIPTION
				"Access list for traffic that should be protected by IPsec.
				
				XPath: /wing-config/device[mac=key1]/crypto_map[name=key2]/crypto_map_entry[sequence=key3]/ip_acl"
			::= { wingCfgDevVpnCryptoInstEntry 4 }

		
		-- 1.3.6.1.4.1.1916.2.131.50.1.3.18.19.10.1.5
		wingCfgDevVpnCryptoInstTransformSet OBJECT-TYPE
			SYNTAX WingIdentifier
			MAX-ACCESS read-write
			STATUS current
			DESCRIPTION
				"NOTE: This column is valid only if wingCfgDevVpnCryptoInstType sets to site-to-site-auto or remote-vpn
				
				IPsec transform (encryption and hash algorithms) to use.
				
				XPath: /wing-config/device[mac=key1]/crypto_map[name=key2]/crypto_map_entry[sequence=key3]/ipsec_transform_set"
			::= { wingCfgDevVpnCryptoInstEntry 5 }

		
		-- 1.3.6.1.4.1.1916.2.131.50.1.3.18.19.10.1.6
		wingCfgDevVpnCryptoInstLocalip OBJECT-TYPE
			SYNTAX DisplayString
			MAX-ACCESS read-write
			STATUS current
			DESCRIPTION
				"Use this IP as local tunnel endpoint address, instead of the interface IP (Advanced Configuration).
				
				XPath: /wing-config/device[mac=key1]/crypto_map[name=key2]/crypto_map_entry[sequence=key3]/localip"
			::= { wingCfgDevVpnCryptoInstEntry 6 }

		
		-- 1.3.6.1.4.1.1916.2.131.50.1.3.18.19.10.1.7
		wingCfgDevVpnCryptoInstPfs OBJECT-TYPE
			SYNTAX DisplayString
			MAX-ACCESS read-write
			STATUS current
			DESCRIPTION
				"NOTE: This column is valid only if wingCfgDevVpnCryptoInstType sets to site-to-site-auto or remote-vpn
				
				Perfect Forward Secrecy.
				
				Values:
				none,
				2,
				5,
				14
				
				XPath: /wing-config/device[mac=key1]/crypto_map[name=key2]/crypto_map_entry[sequence=key3]/pfs"
			DEFVAL { "none" }
			::= { wingCfgDevVpnCryptoInstEntry 7 }

		
		-- 1.3.6.1.4.1.1916.2.131.50.1.3.18.19.10.1.8
		wingCfgDevVpnCryptoInstLifetimeSeconds OBJECT-TYPE
			SYNTAX Unsigned32 (120..2147483646)
			UNITS "seconds"
			MAX-ACCESS read-write
			STATUS current
			DESCRIPTION
				"Time-based IPsec security association lifetime.
				
				XPath: /wing-config/device[mac=key1]/crypto_map[name=key2]/crypto_map_entry[sequence=key3]/lifetime_seconds"
			::= { wingCfgDevVpnCryptoInstEntry 8 }

		
		-- 1.3.6.1.4.1.1916.2.131.50.1.3.18.19.10.1.9
		wingCfgDevVpnCryptoInstLifetimeKb OBJECT-TYPE
			SYNTAX Unsigned32 (500..2147483646)
			UNITS "kilobytes"
			MAX-ACCESS read-write
			STATUS current
			DESCRIPTION
				"Volume-based IPsec security association lifetime.
				
				XPath: /wing-config/device[mac=key1]/crypto_map[name=key2]/crypto_map_entry[sequence=key3]/lifetime_kb"
			::= { wingCfgDevVpnCryptoInstEntry 9 }

		
		-- 1.3.6.1.4.1.1916.2.131.50.1.3.18.19.10.1.10
		wingCfgDevVpnCryptoInstRemoteType OBJECT-TYPE
			SYNTAX DisplayString
			MAX-ACCESS read-write
			STATUS current
			DESCRIPTION
				"NOTE: This column is valid only if wingCfgDevVpnCryptoInstType sets to remote-vpn
				
				Remote VPN client type.
				
				Values:
				none,
				xauth
				
				XPath: /wing-config/device[mac=key1]/crypto_map[name=key2]/crypto_map_entry[sequence=key3]/remote_type"
			DEFVAL { "xauth" }
			::= { wingCfgDevVpnCryptoInstEntry 10 }

		
		-- 1.3.6.1.4.1.1916.2.131.50.1.3.18.19.10.1.11
		wingCfgDevVpnCryptoInstModeconfig OBJECT-TYPE
			SYNTAX DisplayString
			MAX-ACCESS read-write
			STATUS current
			DESCRIPTION
				"NOTE: This column is valid only if wingCfgDevVpnCryptoInstType sets to remote-vpn
				
				Choose the modeconfig method to use.
				
				Values:
				push,
				pull
				
				XPath: /wing-config/device[mac=key1]/crypto_map[name=key2]/crypto_map_entry[sequence=key3]/modeconfig"
			DEFVAL { "push" }
			::= { wingCfgDevVpnCryptoInstEntry 11 }

		
		-- 1.3.6.1.4.1.1916.2.131.50.1.3.18.19.10.1.12
		wingCfgDevVpnCryptoInstPeer OBJECT-TYPE
			SYNTAX DisplayString
			MAX-ACCESS read-write
			STATUS current
			DESCRIPTION
				"NOTE: This column is valid only if wingCfgDevVpnCryptoInstType sets to site-to-site-manual
				
				Allowed Encryption/Decryption peer.
				
				XPath: /wing-config/device[mac=key1]/crypto_map[name=key2]/crypto_map_entry[sequence=key3]/peer"
			::= { wingCfgDevVpnCryptoInstEntry 12 }

		
		-- 1.3.6.1.4.1.1916.2.131.50.1.3.18.19.10.1.13
		wingCfgDevVpnCryptoInstProtocol OBJECT-TYPE
			SYNTAX DisplayString
			MAX-ACCESS read-write
			STATUS current
			DESCRIPTION
				"NOTE: This column is valid only if wingCfgDevVpnCryptoInstType sets to site-to-site-manual
				
				Procotol to be used to the IPsec tunnel. It can be ESP or AH.
				
				Values:
				ESP,
				AH
				
				XPath: /wing-config/device[mac=key1]/crypto_map[name=key2]/crypto_map_entry[sequence=key3]/protocol"
			DEFVAL { "ESP" }
			::= { wingCfgDevVpnCryptoInstEntry 13 }

		
		-- 1.3.6.1.4.1.1916.2.131.50.1.3.18.19.10.1.14
		wingCfgDevVpnCryptoInstMode OBJECT-TYPE
			SYNTAX DisplayString
			MAX-ACCESS read-write
			STATUS current
			DESCRIPTION
				"NOTE: This column is valid only if wingCfgDevVpnCryptoInstType sets to site-to-site-manual
				
				IPsec tunnel type - tunnel or transport mode.
				
				Values:
				tunnel,
				transport
				
				XPath: /wing-config/device[mac=key1]/crypto_map[name=key2]/crypto_map_entry[sequence=key3]/mode"
			DEFVAL { "tunnel" }
			::= { wingCfgDevVpnCryptoInstEntry 14 }

		
		-- 1.3.6.1.4.1.1916.2.131.50.1.3.18.19.11
		wingCfgDevVpnCryptoInstPeerListTable OBJECT-TYPE
			SYNTAX SEQUENCE OF WingCfgDevVpnCryptoInstPeerListEntry
			MAX-ACCESS not-accessible
			STATUS current
			DESCRIPTION
				"NOTE: Columns under this table are valid only if wingCfgDevVpnCryptoInstType sets to site-to-site-auto or remote-vpn
				
				/wing-config/device/crypto_map/crypto_map_entry"
			::= { wingCfgDevVpn 11 }

		
		-- 1.3.6.1.4.1.1916.2.131.50.1.3.18.19.11.1
		wingCfgDevVpnCryptoInstPeerListEntry OBJECT-TYPE
			SYNTAX WingCfgDevVpnCryptoInstPeerListEntry
			MAX-ACCESS not-accessible
			STATUS current
			DESCRIPTION
				"An entry in the table."
			INDEX { wingCfgDevMac, wingCfgDevVpnCryptoName, wingCfgDevVpnCryptoInstSequence, wingCfgDevVpnCryptoInstPeerListPriority }
			::= { wingCfgDevVpnCryptoInstPeerListTable 1 }

		
		WingCfgDevVpnCryptoInstPeerListEntry ::=
			SEQUENCE { 
				wingCfgDevVpnCryptoInstPeerListPriority
					Unsigned32,
				wingCfgDevVpnCryptoInstPeerListType
					DisplayString,
				wingCfgDevVpnCryptoInstPeerListIkev1Peer
					WingIdentifier,
				wingCfgDevVpnCryptoInstPeerListIkev2Peer
					WingIdentifier
			 }

		-- 1.3.6.1.4.1.1916.2.131.50.1.3.18.19.11.1.1
		wingCfgDevVpnCryptoInstPeerListPriority OBJECT-TYPE
			SYNTAX Unsigned32 (1..3)
			MAX-ACCESS read-only
			STATUS current
			DESCRIPTION
				"List of prioritized redundant peers.
				
				XPath: /wing-config/device[mac=key1]/crypto_map[name=key2]/crypto_map_entry[sequence=key3]/peer_list[priority=key4]/priority"
			::= { wingCfgDevVpnCryptoInstPeerListEntry 1 }

		
		-- 1.3.6.1.4.1.1916.2.131.50.1.3.18.19.11.1.3
		wingCfgDevVpnCryptoInstPeerListType OBJECT-TYPE
			SYNTAX DisplayString
			MAX-ACCESS read-write
			STATUS current
			DESCRIPTION
				"Peer IKE type.
				
				Values:
				ikev1,
				ikev2
				
				XPath: /wing-config/device[mac=key1]/crypto_map[name=key2]/crypto_map_entry[sequence=key3]/peer_list[priority=key4]/type"
			::= { wingCfgDevVpnCryptoInstPeerListEntry 3 }

		
		-- 1.3.6.1.4.1.1916.2.131.50.1.3.18.19.11.1.4
		wingCfgDevVpnCryptoInstPeerListIkev1Peer OBJECT-TYPE
			SYNTAX WingIdentifier
			MAX-ACCESS read-write
			STATUS current
			DESCRIPTION
				"Name of the IKEv1 Peer.
				
				XPath: /wing-config/device[mac=key1]/crypto_map[name=key2]/crypto_map_entry[sequence=key3]/peer_list[priority=key4]/ikev1_peer"
			::= { wingCfgDevVpnCryptoInstPeerListEntry 4 }

		
		-- 1.3.6.1.4.1.1916.2.131.50.1.3.18.19.11.1.5
		wingCfgDevVpnCryptoInstPeerListIkev2Peer OBJECT-TYPE
			SYNTAX WingIdentifier
			MAX-ACCESS read-write
			STATUS current
			DESCRIPTION
				"Name of the IKEv2 Peer.
				
				XPath: /wing-config/device[mac=key1]/crypto_map[name=key2]/crypto_map_entry[sequence=key3]/peer_list[priority=key4]/ikev2_peer"
			::= { wingCfgDevVpnCryptoInstPeerListEntry 5 }

		
		-- 1.3.6.1.4.1.1916.2.131.50.1.3.18.19.12
		wingCfgDevVpnCryptoInstAhSessionTable OBJECT-TYPE
			SYNTAX SEQUENCE OF WingCfgDevVpnCryptoInstAhSessionEntry
			MAX-ACCESS not-accessible
			STATUS current
			DESCRIPTION
				"NOTE: Columns under this table are valid only if wingCfgDevVpnCryptoInstType sets to site-to-site-manual
				
				/wing-config/device/crypto_map/crypto_map_entry/ah_session_keys"
			::= { wingCfgDevVpn 12 }

		
		-- 1.3.6.1.4.1.1916.2.131.50.1.3.18.19.12.1
		wingCfgDevVpnCryptoInstAhSessionEntry OBJECT-TYPE
			SYNTAX WingCfgDevVpnCryptoInstAhSessionEntry
			MAX-ACCESS not-accessible
			STATUS current
			DESCRIPTION
				"An entry in the table."
			INDEX { wingCfgDevMac, wingCfgDevVpnCryptoName, wingCfgDevVpnCryptoInstSequence, wingCfgDevVpnCryptoInstAhSessionDirection }
			::= { wingCfgDevVpnCryptoInstAhSessionTable 1 }

		
		WingCfgDevVpnCryptoInstAhSessionEntry ::=
			SEQUENCE { 
				wingCfgDevVpnCryptoInstAhSessionDirection
					WingIdentifier,
				wingCfgDevVpnCryptoInstAhSessionSpi
					Unsigned32,
				wingCfgDevVpnCryptoInstAhSessionAuthAlgo
					DisplayString,
				wingCfgDevVpnCryptoInstAhSessionKey
					OCTET STRING
			 }

		-- 1.3.6.1.4.1.1916.2.131.50.1.3.18.19.12.1.1
		wingCfgDevVpnCryptoInstAhSessionDirection OBJECT-TYPE
			SYNTAX WingIdentifier
			MAX-ACCESS read-only
			STATUS current
			DESCRIPTION
				"Direction of the security association.
				
				Values:
				inbound,
				outbound
				
				XPath: /wing-config/device[mac=key1]/crypto_map[name=key2]/crypto_map_entry[sequence=key3]/ah_session_keys[direction=key4]/direction"
			::= { wingCfgDevVpnCryptoInstAhSessionEntry 1 }

		
		-- 1.3.6.1.4.1.1916.2.131.50.1.3.18.19.12.1.3
		wingCfgDevVpnCryptoInstAhSessionSpi OBJECT-TYPE
			SYNTAX Unsigned32 (256..4294967295)
			MAX-ACCESS read-write
			STATUS current
			DESCRIPTION
				"Security Parameter Index for Security Association. This should be unique for all Security Associations.
				
				XPath: /wing-config/device[mac=key1]/crypto_map[name=key2]/crypto_map_entry[sequence=key3]/ah_session_keys[direction=key4]/spi"
			::= { wingCfgDevVpnCryptoInstAhSessionEntry 3 }

		
		-- 1.3.6.1.4.1.1916.2.131.50.1.3.18.19.12.1.4
		wingCfgDevVpnCryptoInstAhSessionAuthAlgo OBJECT-TYPE
			SYNTAX DisplayString
			MAX-ACCESS read-write
			STATUS current
			DESCRIPTION
				"Authentication scheme used to validate identity.
				
				Values:
				md5,
				sha
				
				XPath: /wing-config/device[mac=key1]/crypto_map[name=key2]/crypto_map_entry[sequence=key3]/ah_session_keys[direction=key4]/auth_algo"
			DEFVAL { "sha" }
			::= { wingCfgDevVpnCryptoInstAhSessionEntry 4 }

		
		-- 1.3.6.1.4.1.1916.2.131.50.1.3.18.19.12.1.5
		wingCfgDevVpnCryptoInstAhSessionKey OBJECT-TYPE
			SYNTAX OCTET STRING (SIZE (8..512))
			MAX-ACCESS read-write
			STATUS current
			DESCRIPTION
				"Security association key value. The following key lengths (in hex characters) are required.ESP-MD5: 32,ESP-SHA: 40.
				
				XPath: /wing-config/device[mac=key1]/crypto_map[name=key2]/crypto_map_entry[sequence=key3]/ah_session_keys[direction=key4]/key"
			::= { wingCfgDevVpnCryptoInstAhSessionEntry 5 }

		
		-- 1.3.6.1.4.1.1916.2.131.50.1.3.18.19.13
		wingCfgDevVpnCryptoInstEspSessionTable OBJECT-TYPE
			SYNTAX SEQUENCE OF WingCfgDevVpnCryptoInstEspSessionEntry
			MAX-ACCESS not-accessible
			STATUS current
			DESCRIPTION
				"NOTE: Columns under this table are valid only if wingCfgDevVpnCryptoInstType sets to site-to-site-manual
				
				/wing-config/device/crypto_map/crypto_map_entry/esp_session_keys"
			::= { wingCfgDevVpn 13 }

		
		-- 1.3.6.1.4.1.1916.2.131.50.1.3.18.19.13.1
		wingCfgDevVpnCryptoInstEspSessionEntry OBJECT-TYPE
			SYNTAX WingCfgDevVpnCryptoInstEspSessionEntry
			MAX-ACCESS not-accessible
			STATUS current
			DESCRIPTION
				"An entry in the table."
			INDEX { wingCfgDevMac, wingCfgDevVpnCryptoName, wingCfgDevVpnCryptoInstSequence, wingCfgDevVpnCryptoInstEspSessionDirection }
			::= { wingCfgDevVpnCryptoInstEspSessionTable 1 }

		
		WingCfgDevVpnCryptoInstEspSessionEntry ::=
			SEQUENCE { 
				wingCfgDevVpnCryptoInstEspSessionDirection
					WingIdentifier,
				wingCfgDevVpnCryptoInstEspSessionSpi
					Unsigned32,
				wingCfgDevVpnCryptoInstEspSessionCipherAlgo
					DisplayString,
				wingCfgDevVpnCryptoInstEspSessionCipherKey
					OCTET STRING,
				wingCfgDevVpnCryptoInstEspSessionAuthAlgo
					DisplayString,
				wingCfgDevVpnCryptoInstEspSessionAuthKey
					OCTET STRING
			 }

		-- 1.3.6.1.4.1.1916.2.131.50.1.3.18.19.13.1.1
		wingCfgDevVpnCryptoInstEspSessionDirection OBJECT-TYPE
			SYNTAX WingIdentifier
			MAX-ACCESS read-only
			STATUS current
			DESCRIPTION
				"
				
				Values:
				inbound,
				outbound
				
				XPath: /wing-config/device[mac=key1]/crypto_map[name=key2]/crypto_map_entry[sequence=key3]/esp_session_keys[direction=key4]/direction"
			::= { wingCfgDevVpnCryptoInstEspSessionEntry 1 }

		
		-- 1.3.6.1.4.1.1916.2.131.50.1.3.18.19.13.1.3
		wingCfgDevVpnCryptoInstEspSessionSpi OBJECT-TYPE
			SYNTAX Unsigned32 (256..4294967295)
			MAX-ACCESS read-write
			STATUS current
			DESCRIPTION
				"Security Parameter Index for Security Association. This should be unique for all Security Associations.
				
				XPath: /wing-config/device[mac=key1]/crypto_map[name=key2]/crypto_map_entry[sequence=key3]/esp_session_keys[direction=key4]/spi"
			::= { wingCfgDevVpnCryptoInstEspSessionEntry 3 }

		
		-- 1.3.6.1.4.1.1916.2.131.50.1.3.18.19.13.1.4
		wingCfgDevVpnCryptoInstEspSessionCipherAlgo OBJECT-TYPE
			SYNTAX DisplayString
			MAX-ACCESS read-write
			STATUS current
			DESCRIPTION
				"Encryption method protecting data transmission.
				
				Values:
				esp-null,
				des,
				3des,
				aes,
				aes-192,
				aes-256
				
				XPath: /wing-config/device[mac=key1]/crypto_map[name=key2]/crypto_map_entry[sequence=key3]/esp_session_keys[direction=key4]/cipher_algo"
			DEFVAL { "aes-256" }
			::= { wingCfgDevVpnCryptoInstEspSessionEntry 4 }

		
		-- 1.3.6.1.4.1.1916.2.131.50.1.3.18.19.13.1.5
		wingCfgDevVpnCryptoInstEspSessionCipherKey OBJECT-TYPE
			SYNTAX OCTET STRING (SIZE (8..512))
			MAX-ACCESS read-write
			STATUS current
			DESCRIPTION
				"Security association key value. The following key lengths (in hex characters) are required .ESP-NULL: 0, ESP-DES: 16, ESP-3DES: 48, ESP-AES: 32, ESP-AES-192: 48, ESP-AES-256: 64
				
				XPath: /wing-config/device[mac=key1]/crypto_map[name=key2]/crypto_map_entry[sequence=key3]/esp_session_keys[direction=key4]/cipher_key"
			::= { wingCfgDevVpnCryptoInstEspSessionEntry 5 }

		
		-- 1.3.6.1.4.1.1916.2.131.50.1.3.18.19.13.1.6
		wingCfgDevVpnCryptoInstEspSessionAuthAlgo OBJECT-TYPE
			SYNTAX DisplayString
			MAX-ACCESS read-write
			STATUS current
			DESCRIPTION
				"Authentication scheme used to validate identity.
				
				Values:
				md5,
				sha
				
				XPath: /wing-config/device[mac=key1]/crypto_map[name=key2]/crypto_map_entry[sequence=key3]/esp_session_keys[direction=key4]/auth_algo"
			DEFVAL { "sha" }
			::= { wingCfgDevVpnCryptoInstEspSessionEntry 6 }

		
		-- 1.3.6.1.4.1.1916.2.131.50.1.3.18.19.13.1.7
		wingCfgDevVpnCryptoInstEspSessionAuthKey OBJECT-TYPE
			SYNTAX OCTET STRING (SIZE (8..512))
			MAX-ACCESS read-write
			STATUS current
			DESCRIPTION
				"Security association key value. The following key lengths (in hex characters) are required.ESP-MD5: 32,ESP-SHA: 40.
				
				XPath: /wing-config/device[mac=key1]/crypto_map[name=key2]/crypto_map_entry[sequence=key3]/esp_session_keys[direction=key4]/auth_key"
			::= { wingCfgDevVpnCryptoInstEspSessionEntry 7 }

		
		-- 1.3.6.1.4.1.1916.2.131.50.1.3.18.19.14
		wingCfgDevVpnIkev1RemoteTable OBJECT-TYPE
			SYNTAX SEQUENCE OF WingCfgDevVpnIkev1RemoteEntry
			MAX-ACCESS not-accessible
			STATUS current
			DESCRIPTION
				"
				
				/wing-config/device/ikev1_remote_vpn"
			::= { wingCfgDevVpn 14 }

		
		-- 1.3.6.1.4.1.1916.2.131.50.1.3.18.19.14.1
		wingCfgDevVpnIkev1RemoteEntry OBJECT-TYPE
			SYNTAX WingCfgDevVpnIkev1RemoteEntry
			MAX-ACCESS not-accessible
			STATUS current
			DESCRIPTION
				"An entry in the table."
			INDEX { wingCfgDevMac }
			::= { wingCfgDevVpnIkev1RemoteTable 1 }

		
		WingCfgDevVpnIkev1RemoteEntry ::=
			SEQUENCE { 
				wingCfgDevVpnIkev1RemoteAuthMethod
					DisplayString,
				wingCfgDevVpnIkev1RemoteAaaPolicy
					WingIdentifier,
				wingCfgDevVpnIkev1RemoteIpLocalPool
					DisplayString
			 }

		-- 1.3.6.1.4.1.1916.2.131.50.1.3.18.19.14.1.1
		wingCfgDevVpnIkev1RemoteAuthMethod OBJECT-TYPE
			SYNTAX DisplayString
			MAX-ACCESS read-write
			STATUS current
			DESCRIPTION
				"The authentication method used for Remove VPN client. It can be one of RADIUS or LOCAL.
				
				Values:
				radius,
				local
				
				XPath: /wing-config/device[mac=key1]/ikev1_remote_vpn/auth_method"
			DEFVAL { "local" }
			::= { wingCfgDevVpnIkev1RemoteEntry 1 }

		
		-- 1.3.6.1.4.1.1916.2.131.50.1.3.18.19.14.1.2
		wingCfgDevVpnIkev1RemoteAaaPolicy OBJECT-TYPE
			SYNTAX WingIdentifier
			MAX-ACCESS read-write
			STATUS current
			DESCRIPTION
				"AAA Policy to use for remote VPN clients.
				
				XPath: /wing-config/device[mac=key1]/ikev1_remote_vpn/aaa_policy"
			::= { wingCfgDevVpnIkev1RemoteEntry 2 }

		
		-- 1.3.6.1.4.1.1916.2.131.50.1.3.18.19.14.1.3
		wingCfgDevVpnIkev1RemoteIpLocalPool OBJECT-TYPE
			SYNTAX DisplayString
			MAX-ACCESS read-write
			STATUS current
			DESCRIPTION
				"The virtual IP pool for assigning IP addresses to remote VPN clients.
				
				XPath: /wing-config/device[mac=key1]/ikev1_remote_vpn/ip_local_pool"
			::= { wingCfgDevVpnIkev1RemoteEntry 3 }

		
		-- 1.3.6.1.4.1.1916.2.131.50.1.3.18.19.15
		wingCfgDevVpnIkev1RemoteLocalUsersTable OBJECT-TYPE
			SYNTAX SEQUENCE OF WingCfgDevVpnIkev1RemoteLocalUsersEntry
			MAX-ACCESS not-accessible
			STATUS current
			DESCRIPTION
				"
				
				/wing-config/device/ikev1_remote_vpn/local_users"
			::= { wingCfgDevVpn 15 }

		
		-- 1.3.6.1.4.1.1916.2.131.50.1.3.18.19.15.1
		wingCfgDevVpnIkev1RemoteLocalUsersEntry OBJECT-TYPE
			SYNTAX WingCfgDevVpnIkev1RemoteLocalUsersEntry
			MAX-ACCESS not-accessible
			STATUS current
			DESCRIPTION
				"An entry in the table."
			INDEX { wingCfgDevMac, wingCfgDevVpnIkev1RemoteLocalUsersName }
			::= { wingCfgDevVpnIkev1RemoteLocalUsersTable 1 }

		
		WingCfgDevVpnIkev1RemoteLocalUsersEntry ::=
			SEQUENCE { 
				wingCfgDevVpnIkev1RemoteLocalUsersName
					WingIdentifier,
				wingCfgDevVpnIkev1RemoteLocalUsersPassword
					DisplayString
			 }

		-- 1.3.6.1.4.1.1916.2.131.50.1.3.18.19.15.1.1
		wingCfgDevVpnIkev1RemoteLocalUsersName OBJECT-TYPE
			SYNTAX WingIdentifier
			MAX-ACCESS read-only
			STATUS current
			DESCRIPTION
				"User name
				
				XPath: /wing-config/device[mac=key1]/ikev1_remote_vpn/local_users[name=key2]/name"
			::= { wingCfgDevVpnIkev1RemoteLocalUsersEntry 1 }
-- TODO: Key length may exceed 128 sub-identifiers
-- add leaf with Integer as key to append as the last digit of OID
		
		-- 1.3.6.1.4.1.1916.2.131.50.1.3.18.19.15.1.3
		wingCfgDevVpnIkev1RemoteLocalUsersPassword OBJECT-TYPE
			SYNTAX DisplayString (SIZE (8..21))
			MAX-ACCESS read-write
			STATUS current
			DESCRIPTION
				"The password to authenticate the user.
				
				XPath: /wing-config/device[mac=key1]/ikev1_remote_vpn/local_users[name=key2]/password"
			::= { wingCfgDevVpnIkev1RemoteLocalUsersEntry 3 }

		
		-- 1.3.6.1.4.1.1916.2.131.50.1.3.18.19.16
		wingCfgDevVpnIkev1RemoteWinsTable OBJECT-TYPE
			SYNTAX SEQUENCE OF WingCfgDevVpnIkev1RemoteWinsEntry
			MAX-ACCESS not-accessible
			STATUS current
			DESCRIPTION
				"
				
				/wing-config/device/ikev1_remote_vpn/wins"
			::= { wingCfgDevVpn 16 }

		
		-- 1.3.6.1.4.1.1916.2.131.50.1.3.18.19.16.1
		wingCfgDevVpnIkev1RemoteWinsEntry OBJECT-TYPE
			SYNTAX WingCfgDevVpnIkev1RemoteWinsEntry
			MAX-ACCESS not-accessible
			STATUS current
			DESCRIPTION
				"An entry in the table."
			INDEX { wingCfgDevMac, wingCfgDevVpnIkev1RemoteWinsServerType }
			::= { wingCfgDevVpnIkev1RemoteWinsTable 1 }

		
		WingCfgDevVpnIkev1RemoteWinsEntry ::=
			SEQUENCE { 
				wingCfgDevVpnIkev1RemoteWinsServerType
					WingIdentifier,
				wingCfgDevVpnIkev1RemoteWinsServerIp
					DisplayString
			 }

		-- 1.3.6.1.4.1.1916.2.131.50.1.3.18.19.16.1.1
		wingCfgDevVpnIkev1RemoteWinsServerType OBJECT-TYPE
			SYNTAX WingIdentifier
			MAX-ACCESS read-only
			STATUS current
			DESCRIPTION
				"Primary or Secondary WINS server.
				
				Values:
				primary,
				secondary
				
				XPath: /wing-config/device[mac=key1]/ikev1_remote_vpn/wins[server_type=key2]/server_type"
			::= { wingCfgDevVpnIkev1RemoteWinsEntry 1 }

		
		-- 1.3.6.1.4.1.1916.2.131.50.1.3.18.19.16.1.3
		wingCfgDevVpnIkev1RemoteWinsServerIp OBJECT-TYPE
			SYNTAX DisplayString
			MAX-ACCESS read-write
			STATUS current
			DESCRIPTION
				"
				
				XPath: /wing-config/device[mac=key1]/ikev1_remote_vpn/wins[server_type=key2]/server_ip"
			::= { wingCfgDevVpnIkev1RemoteWinsEntry 3 }

		
		-- 1.3.6.1.4.1.1916.2.131.50.1.3.18.19.17
		wingCfgDevVpnIkev1RemoteNameServerTable OBJECT-TYPE
			SYNTAX SEQUENCE OF WingCfgDevVpnIkev1RemoteNameServerEntry
			MAX-ACCESS not-accessible
			STATUS current
			DESCRIPTION
				"
				
				/wing-config/device/ikev1_remote_vpn/nameserver"
			::= { wingCfgDevVpn 17 }

		
		-- 1.3.6.1.4.1.1916.2.131.50.1.3.18.19.17.1
		wingCfgDevVpnIkev1RemoteNameServerEntry OBJECT-TYPE
			SYNTAX WingCfgDevVpnIkev1RemoteNameServerEntry
			MAX-ACCESS not-accessible
			STATUS current
			DESCRIPTION
				"An entry in the table."
			INDEX { wingCfgDevMac, wingCfgDevVpnIkev1RemoteNameServerType }
			::= { wingCfgDevVpnIkev1RemoteNameServerTable 1 }

		
		WingCfgDevVpnIkev1RemoteNameServerEntry ::=
			SEQUENCE { 
				wingCfgDevVpnIkev1RemoteNameServerType
					WingIdentifier,
				wingCfgDevVpnIkev1RemoteNameServerIp
					DisplayString
			 }

		-- 1.3.6.1.4.1.1916.2.131.50.1.3.18.19.17.1.1
		wingCfgDevVpnIkev1RemoteNameServerType OBJECT-TYPE
			SYNTAX WingIdentifier
			MAX-ACCESS read-only
			STATUS current
			DESCRIPTION
				"Primary or Secondary Name server.
				
				Values:
				primary,
				secondary
				
				XPath: /wing-config/device[mac=key1]/ikev1_remote_vpn/nameserver[server_type=key2]/server_type"
			::= { wingCfgDevVpnIkev1RemoteNameServerEntry 1 }

		
		-- 1.3.6.1.4.1.1916.2.131.50.1.3.18.19.17.1.4
		wingCfgDevVpnIkev1RemoteNameServerIp OBJECT-TYPE
			SYNTAX DisplayString
			MAX-ACCESS read-write
			STATUS current
			DESCRIPTION
				"
				
				XPath: /wing-config/device[mac=key1]/ikev1_remote_vpn/nameserver[server_type=key2]/server_ip"
			::= { wingCfgDevVpnIkev1RemoteNameServerEntry 4 }

		
		-- 1.3.6.1.4.1.1916.2.131.50.1.3.18.19.18
		wingCfgDevVpnIkev2RemoteTable OBJECT-TYPE
			SYNTAX SEQUENCE OF WingCfgDevVpnIkev2RemoteEntry
			MAX-ACCESS not-accessible
			STATUS current
			DESCRIPTION
				"
				
				/wing-config/device/ikev2_remote_vpn"
			::= { wingCfgDevVpn 18 }

		
		-- 1.3.6.1.4.1.1916.2.131.50.1.3.18.19.18.1
		wingCfgDevVpnIkev2RemoteEntry OBJECT-TYPE
			SYNTAX WingCfgDevVpnIkev2RemoteEntry
			MAX-ACCESS not-accessible
			STATUS current
			DESCRIPTION
				"An entry in the table."
			INDEX { wingCfgDevMac }
			::= { wingCfgDevVpnIkev2RemoteTable 1 }

		
		WingCfgDevVpnIkev2RemoteEntry ::=
			SEQUENCE { 
				wingCfgDevVpnIkev2RemoteAuthMethod
					DisplayString,
				wingCfgDevVpnIkev2RemoteAaaPolicy
					WingIdentifier,
				wingCfgDevVpnIkev2RemoteIpLocalPool
					DisplayString,
				wingCfgDevVpnIkev2RemoteDhcpServerType
					DisplayString,
				wingCfgDevVpnIkev2RemoteDhcpServer
					DisplayString,
				wingCfgDevVpnIkev2RemoteDhcpServerGiaddr
					DisplayString,
				wingCfgDevVpnIkev2RemoteNetmask
					DisplayString
			 }

		-- 1.3.6.1.4.1.1916.2.131.50.1.3.18.19.18.1.1
		wingCfgDevVpnIkev2RemoteAuthMethod OBJECT-TYPE
			SYNTAX DisplayString
			MAX-ACCESS read-write
			STATUS current
			DESCRIPTION
				"The authentication method used for Remove VPN client. It can be one of RADIUS or LOCAL.
				
				Values:
				radius,
				local
				
				XPath: /wing-config/device[mac=key1]/ikev2_remote_vpn/auth_method"
			DEFVAL { "local" }
			::= { wingCfgDevVpnIkev2RemoteEntry 1 }

		
		-- 1.3.6.1.4.1.1916.2.131.50.1.3.18.19.18.1.2
		wingCfgDevVpnIkev2RemoteAaaPolicy OBJECT-TYPE
			SYNTAX WingIdentifier
			MAX-ACCESS read-write
			STATUS current
			DESCRIPTION
				"AAA Policy to use for remote VPN clients.
				
				XPath: /wing-config/device[mac=key1]/ikev2_remote_vpn/aaa_policy"
			::= { wingCfgDevVpnIkev2RemoteEntry 2 }

		
		-- 1.3.6.1.4.1.1916.2.131.50.1.3.18.19.18.1.3
		wingCfgDevVpnIkev2RemoteIpLocalPool OBJECT-TYPE
			SYNTAX DisplayString
			MAX-ACCESS read-write
			STATUS current
			DESCRIPTION
				"The virtual IP pool for assigning IP addresses to remote VPN clients.
				
				XPath: /wing-config/device[mac=key1]/ikev2_remote_vpn/ip_local_pool"
			::= { wingCfgDevVpnIkev2RemoteEntry 3 }

		
		-- 1.3.6.1.4.1.1916.2.131.50.1.3.18.19.18.1.4
		wingCfgDevVpnIkev2RemoteDhcpServerType OBJECT-TYPE
			SYNTAX DisplayString
			MAX-ACCESS read-write
			STATUS current
			DESCRIPTION
				"Select DHCP server type as IP or Hostname.
				
				Values:
				address,
				hostname,
				none
				
				XPath: /wing-config/device[mac=key1]/ikev2_remote_vpn/dhcp_server/dhcp_server_type"
			DEFVAL { "'none'" }
			::= { wingCfgDevVpnIkev2RemoteEntry 4 }

		
		-- 1.3.6.1.4.1.1916.2.131.50.1.3.18.19.18.1.5
		wingCfgDevVpnIkev2RemoteDhcpServer OBJECT-TYPE
			SYNTAX DisplayString (SIZE (1..64))
			MAX-ACCESS read-write
			STATUS current
			DESCRIPTION
				"Specify DHCP server IP or Hostname.
				
				XPath: /wing-config/device[mac=key1]/ikev2_remote_vpn/dhcp_server/dhcp_server"
			::= { wingCfgDevVpnIkev2RemoteEntry 5 }

		
		-- 1.3.6.1.4.1.1916.2.131.50.1.3.18.19.18.1.6
		wingCfgDevVpnIkev2RemoteDhcpServerGiaddr OBJECT-TYPE
			SYNTAX DisplayString
			MAX-ACCESS read-write
			STATUS current
			DESCRIPTION
				"DHCP Relay Agent IP address
				
				XPath: /wing-config/device[mac=key1]/ikev2_remote_vpn/dhcp_server/giaddr"
			::= { wingCfgDevVpnIkev2RemoteEntry 6 }

		
		-- 1.3.6.1.4.1.1916.2.131.50.1.3.18.19.18.1.7
		wingCfgDevVpnIkev2RemoteNetmask OBJECT-TYPE
			SYNTAX DisplayString
			MAX-ACCESS read-write
			STATUS current
			DESCRIPTION
				"Netmask for remote VPN clients (IKEv2 only)
				
				XPath: /wing-config/device[mac=key1]/ikev2_remote_vpn/netmask"
			::= { wingCfgDevVpnIkev2RemoteEntry 7 }

		
		-- 1.3.6.1.4.1.1916.2.131.50.1.3.18.19.19
		wingCfgDevVpnIkev2RemoteLocalUsersTable OBJECT-TYPE
			SYNTAX SEQUENCE OF WingCfgDevVpnIkev2RemoteLocalUsersEntry
			MAX-ACCESS not-accessible
			STATUS current
			DESCRIPTION
				"
				
				/wing-config/device/ikev2_remote_vpn/local_users"
			::= { wingCfgDevVpn 19 }

		
		-- 1.3.6.1.4.1.1916.2.131.50.1.3.18.19.19.1
		wingCfgDevVpnIkev2RemoteLocalUsersEntry OBJECT-TYPE
			SYNTAX WingCfgDevVpnIkev2RemoteLocalUsersEntry
			MAX-ACCESS not-accessible
			STATUS current
			DESCRIPTION
				"An entry in the table."
			INDEX { wingCfgDevMac, wingCfgDevVpnIkev2RemoteLocalUsersName }
			::= { wingCfgDevVpnIkev2RemoteLocalUsersTable 1 }

		
		WingCfgDevVpnIkev2RemoteLocalUsersEntry ::=
			SEQUENCE { 
				wingCfgDevVpnIkev2RemoteLocalUsersName
					WingIdentifier,
				wingCfgDevVpnIkev2RemoteLocalUsersPassword
					DisplayString
			 }

		-- 1.3.6.1.4.1.1916.2.131.50.1.3.18.19.19.1.1
		wingCfgDevVpnIkev2RemoteLocalUsersName OBJECT-TYPE
			SYNTAX WingIdentifier
			MAX-ACCESS read-only
			STATUS current
			DESCRIPTION
				"User name
				
				XPath: /wing-config/device[mac=key1]/ikev2_remote_vpn/local_users[name=key2]/name"
			::= { wingCfgDevVpnIkev2RemoteLocalUsersEntry 1 }
-- TODO: Key length may exceed 128 sub-identifiers
-- add leaf with Integer as key to append as the last digit of OID
		
		-- 1.3.6.1.4.1.1916.2.131.50.1.3.18.19.19.1.3
		wingCfgDevVpnIkev2RemoteLocalUsersPassword OBJECT-TYPE
			SYNTAX DisplayString (SIZE (8..21))
			MAX-ACCESS read-write
			STATUS current
			DESCRIPTION
				"The password to authenticate the user.
				
				XPath: /wing-config/device[mac=key1]/ikev2_remote_vpn/local_users[name=key2]/password"
			::= { wingCfgDevVpnIkev2RemoteLocalUsersEntry 3 }

		
		-- 1.3.6.1.4.1.1916.2.131.50.1.3.18.19.20
		wingCfgDevVpnIkev2RemoteWinsTable OBJECT-TYPE
			SYNTAX SEQUENCE OF WingCfgDevVpnIkev2RemoteWinsEntry
			MAX-ACCESS not-accessible
			STATUS current
			DESCRIPTION
				"
				
				/wing-config/device/ikev2_remote_vpn/wins"
			::= { wingCfgDevVpn 20 }

		
		-- 1.3.6.1.4.1.1916.2.131.50.1.3.18.19.20.1
		wingCfgDevVpnIkev2RemoteWinsEntry OBJECT-TYPE
			SYNTAX WingCfgDevVpnIkev2RemoteWinsEntry
			MAX-ACCESS not-accessible
			STATUS current
			DESCRIPTION
				"An entry in the table."
			INDEX { wingCfgDevMac, wingCfgDevVpnIkev2RemoteWinsServerType }
			::= { wingCfgDevVpnIkev2RemoteWinsTable 1 }

		
		WingCfgDevVpnIkev2RemoteWinsEntry ::=
			SEQUENCE { 
				wingCfgDevVpnIkev2RemoteWinsServerType
					WingIdentifier,
				wingCfgDevVpnIkev2RemoteWinsServerIp
					DisplayString
			 }

		-- 1.3.6.1.4.1.1916.2.131.50.1.3.18.19.20.1.1
		wingCfgDevVpnIkev2RemoteWinsServerType OBJECT-TYPE
			SYNTAX WingIdentifier
			MAX-ACCESS read-only
			STATUS current
			DESCRIPTION
				"Primary or Secondary WINS server.
				
				Values:
				primary,
				secondary
				
				XPath: /wing-config/device[mac=key1]/ikev2_remote_vpn/wins[server_type=key2]/server_type"
			::= { wingCfgDevVpnIkev2RemoteWinsEntry 1 }

		
		-- 1.3.6.1.4.1.1916.2.131.50.1.3.18.19.20.1.3
		wingCfgDevVpnIkev2RemoteWinsServerIp OBJECT-TYPE
			SYNTAX DisplayString
			MAX-ACCESS read-write
			STATUS current
			DESCRIPTION
				"
				
				XPath: /wing-config/device[mac=key1]/ikev2_remote_vpn/wins[server_type=key2]/server_ip"
			::= { wingCfgDevVpnIkev2RemoteWinsEntry 3 }

		
		-- 1.3.6.1.4.1.1916.2.131.50.1.3.18.19.21
		wingCfgDevVpnIkev2RemoteNameServerTable OBJECT-TYPE
			SYNTAX SEQUENCE OF WingCfgDevVpnIkev2RemoteNameServerEntry
			MAX-ACCESS not-accessible
			STATUS current
			DESCRIPTION
				"
				
				/wing-config/device/ikev2_remote_vpn/nameserver"
			::= { wingCfgDevVpn 21 }

		
		-- 1.3.6.1.4.1.1916.2.131.50.1.3.18.19.21.1
		wingCfgDevVpnIkev2RemoteNameServerEntry OBJECT-TYPE
			SYNTAX WingCfgDevVpnIkev2RemoteNameServerEntry
			MAX-ACCESS not-accessible
			STATUS current
			DESCRIPTION
				"An entry in the table."
			INDEX { wingCfgDevMac, wingCfgDevVpnIkev2RemoteNameServerType }
			::= { wingCfgDevVpnIkev2RemoteNameServerTable 1 }

		
		WingCfgDevVpnIkev2RemoteNameServerEntry ::=
			SEQUENCE { 
				wingCfgDevVpnIkev2RemoteNameServerType
					WingIdentifier,
				wingCfgDevVpnIkev2RemoteNameServerIp
					DisplayString
			 }

		-- 1.3.6.1.4.1.1916.2.131.50.1.3.18.19.21.1.1
		wingCfgDevVpnIkev2RemoteNameServerType OBJECT-TYPE
			SYNTAX WingIdentifier
			MAX-ACCESS read-only
			STATUS current
			DESCRIPTION
				"Primary or Secondary Name server.
				
				Values:
				primary,
				secondary
				
				XPath: /wing-config/device[mac=key1]/ikev2_remote_vpn/nameserver[server_type=key2]/server_type"
			::= { wingCfgDevVpnIkev2RemoteNameServerEntry 1 }

		
		-- 1.3.6.1.4.1.1916.2.131.50.1.3.18.19.21.1.3
		wingCfgDevVpnIkev2RemoteNameServerIp OBJECT-TYPE
			SYNTAX DisplayString
			MAX-ACCESS read-write
			STATUS current
			DESCRIPTION
				"
				
				XPath: /wing-config/device[mac=key1]/ikev2_remote_vpn/nameserver[server_type=key2]/server_ip"
			::= { wingCfgDevVpnIkev2RemoteNameServerEntry 3 }

		
		-- 1.3.6.1.4.1.1916.2.131.50.1.3.18.19.22
		wingCfgDevVpnAutoIPSecSecureTable OBJECT-TYPE
			SYNTAX SEQUENCE OF WingCfgDevVpnAutoIPSecSecureEntry
			MAX-ACCESS not-accessible
			STATUS current
			DESCRIPTION
				"Description."
			::= { wingCfgDevVpn 22 }

		
		-- 1.3.6.1.4.1.1916.2.131.50.1.3.18.19.22.1
		wingCfgDevVpnAutoIPSecSecureEntry OBJECT-TYPE
			SYNTAX WingCfgDevVpnAutoIPSecSecureEntry
			MAX-ACCESS not-accessible
			STATUS current
			DESCRIPTION
				"Description."
			INDEX { wingCfgDevMac }
			::= { wingCfgDevVpnAutoIPSecSecureTable 1 }

		
		WingCfgDevVpnAutoIPSecSecureEntry ::=
			SEQUENCE { 
				wingCfgDevVpnAutoIPSecSecureGroupId
					OCTET STRING,
				wingCfgDevVpnAutoIPSecSecureGroupIdAuthType
					DisplayString,
				wingCfgDevVpnAutoIPSecSecureGroupIdAuthKey
					DisplayString,
				wingCfgDevVpnAutoIPSecSecureRemoteGWIkeVersion
					DisplayString
			 }

		-- 1.3.6.1.4.1.1916.2.131.50.1.3.18.19.22.1.1
		wingCfgDevVpnAutoIPSecSecureGroupId OBJECT-TYPE
			SYNTAX OCTET STRING (SIZE (1..128))
			MAX-ACCESS read-write
			STATUS current
			DESCRIPTION
				"Group identity to use in IKE exchange for auto ipsec secure peers.
				
				XPath: /wing-config/device[mac=key1]/auto_ipsec_secure/group_id_auth_type_key/groupid_id"
			::= { wingCfgDevVpnAutoIPSecSecureEntry 1 }

		
		-- 1.3.6.1.4.1.1916.2.131.50.1.3.18.19.22.1.2
		wingCfgDevVpnAutoIPSecSecureGroupIdAuthType OBJECT-TYPE
			SYNTAX DisplayString
			MAX-ACCESS read-write
			STATUS current
			DESCRIPTION
				"The authentication type for auto ipsec secure peer authentication.
				
				XPath: /wing-config/device[mac=key1]/auto_ipsec_secure/group_id_auth_type_key/groupid_auth_type"
			::= { wingCfgDevVpnAutoIPSecSecureEntry 2 }

		
		-- 1.3.6.1.4.1.1916.2.131.50.1.3.18.19.22.1.3
		wingCfgDevVpnAutoIPSecSecureGroupIdAuthKey OBJECT-TYPE
			SYNTAX DisplayString (SIZE (8..21))
			MAX-ACCESS read-write
			STATUS current
			DESCRIPTION
				"The shared secret used for auto ipsec secure peer authentication.
				
				XPath: /wing-config/device[mac=key1]/auto_ipsec_secure/group_id_auth_type_key/groupid_auth_key"
			::= { wingCfgDevVpnAutoIPSecSecureEntry 3 }

		
		-- 1.3.6.1.4.1.1916.2.131.50.1.3.18.19.22.1.4
		wingCfgDevVpnAutoIPSecSecureRemoteGWIkeVersion OBJECT-TYPE
			SYNTAX DisplayString
			MAX-ACCESS read-write
			STATUS current
			DESCRIPTION
				"The ike version for auto ipsec secure authentication with ipsec gateway other than controllers.
				
				XPath: /wing-config/device[mac=key1]/auto_ipsec_secure/remotegw_ike_version"
			::= { wingCfgDevVpnAutoIPSecSecureEntry 4 }

		
-- /wing-config/device/controller_host
		-- 1.3.6.1.4.1.1916.2.131.50.1.3.18.20
		wingCfgDevControllerHost OBJECT IDENTIFIER ::= { wingCfgDev 20 }

		
		-- 1.3.6.1.4.1.1916.2.131.50.1.3.18.20.1
		wingCfgDevControllerHostTable OBJECT-TYPE
			SYNTAX SEQUENCE OF WingCfgDevControllerHostEntry
			MAX-ACCESS not-accessible
			STATUS current
			DESCRIPTION
				"WLAN controller configuration
				
				/wing-config/device/controller_host"
			::= { wingCfgDevControllerHost 1 }

		
		-- 1.3.6.1.4.1.1916.2.131.50.1.3.18.20.1.1
		wingCfgDevControllerHostEntry OBJECT-TYPE
			SYNTAX WingCfgDevControllerHostEntry
			MAX-ACCESS not-accessible
			STATUS current
			DESCRIPTION
				"An entry in the table."
			INDEX { wingCfgDevMac, wingCfgDevControllerHostIndex }
			::= { wingCfgDevControllerHostTable 1 }

		
		WingCfgDevControllerHostEntry ::=
			SEQUENCE { 
				wingCfgDevControllerHostIndex
					WingIdentifier,
				wingCfgDevControllerHostRowStatus
					RowStatus,
				wingCfgDevControllerHostHost
					DisplayString,
				wingCfgDevControllerHostPool
					Unsigned32,
				wingCfgDevControllerHostLevel
					Unsigned32
			 }

		-- 1.3.6.1.4.1.1916.2.131.50.1.3.18.20.1.1.1
		wingCfgDevControllerHostIndex OBJECT-TYPE
			SYNTAX WingIdentifier
			MAX-ACCESS not-accessible
			STATUS current
			DESCRIPTION
				"Key of the table is a string in the following format:
				
				IP address or hostname of controller,Pool,Level"
			::= { wingCfgDevControllerHostEntry 1 }

		
		-- 1.3.6.1.4.1.1916.2.131.50.1.3.18.20.1.1.2
		wingCfgDevControllerHostRowStatus OBJECT-TYPE
			SYNTAX RowStatus
				{
				active(1),
				createAndGo(4),
				destroy(6)
				}
			MAX-ACCESS read-create
			STATUS current
			DESCRIPTION
				"The status of this conceptual row.
				
				XPath: /wing-config/device[mac=key1]/controller_host[controller_entry=key2]/row_status"
			::= { wingCfgDevControllerHostEntry 2 }

		
		-- 1.3.6.1.4.1.1916.2.131.50.1.3.18.20.1.1.3
		wingCfgDevControllerHostHost OBJECT-TYPE
			SYNTAX DisplayString
			MAX-ACCESS read-only
			STATUS current
			DESCRIPTION
				"IP address or hostname of controller.
				
				As this object is indirectly part of the key,
				to change its value the row must be deleted and created with
				the new key.
				
				XPath: /wing-config/device[mac=key1]/controller_host[controller_entry=key2]/host"
			::= { wingCfgDevControllerHostEntry 3 }

		
		-- 1.3.6.1.4.1.1916.2.131.50.1.3.18.20.1.1.4
		wingCfgDevControllerHostPool OBJECT-TYPE
			SYNTAX Unsigned32 (1..2)
			MAX-ACCESS read-only
			STATUS current
			DESCRIPTION
				"Pool this controller belongs to.
				
				As this object is indirectly part of the key,
				to change its value the row must be deleted and created with
				the new key.
				
				XPath: /wing-config/device[mac=key1]/controller_host[controller_entry=key2]/pool"
			DEFVAL { 1 }
			::= { wingCfgDevControllerHostEntry 4 }

		
		-- 1.3.6.1.4.1.1916.2.131.50.1.3.18.20.1.1.5
		wingCfgDevControllerHostLevel OBJECT-TYPE
			SYNTAX Unsigned32 (1..2)
			MAX-ACCESS read-only
			STATUS current
			DESCRIPTION
				"Routing level for controller link.
				
				As this object is indirectly part of the key,
				to change its value the row must be deleted and created with
				the new key.
				
				Values:
				1  Level 1 (local)
				2  Level 2 (inter-site)
				
				XPath: /wing-config/device[mac=key1]/controller_host[controller_entry=key2]/level"
			DEFVAL { 1 }
			::= { wingCfgDevControllerHostEntry 5 }

		
		-- 1.3.6.1.4.1.1916.2.131.50.1.3.18.23
		wingCfgDevWlan OBJECT IDENTIFIER ::= { wingCfgDev 23 }

		
		-- 1.3.6.1.4.1.1916.2.131.50.1.3.18.23.1
		wingCfgDevWlanSsidOverrideTable OBJECT-TYPE
			SYNTAX SEQUENCE OF WingCfgDevWlanSsidOverrideEntry
			MAX-ACCESS not-accessible
			STATUS current
			DESCRIPTION
				"Override wlan ssid at the rf_domain level
				
				/wing-config/device/wlan_override_ssid"
			::= { wingCfgDevWlan 1 }

		
		-- 1.3.6.1.4.1.1916.2.131.50.1.3.18.23.1.1
		wingCfgDevWlanSsidOverrideEntry OBJECT-TYPE
			SYNTAX WingCfgDevWlanSsidOverrideEntry
			MAX-ACCESS not-accessible
			STATUS current
			DESCRIPTION
				"An entry in the table."
			INDEX { wingCfgDevMac, wingCfgDevWlanSsidOverrideWlan }
			::= { wingCfgDevWlanSsidOverrideTable 1 }

		
		WingCfgDevWlanSsidOverrideEntry ::=
			SEQUENCE { 
				wingCfgDevWlanSsidOverrideWlan
					WingIdentifier,
				wingCfgDevWlanSsidOverrideSsid
					DisplayString
			 }

		-- 1.3.6.1.4.1.1916.2.131.50.1.3.18.23.1.1.1
		wingCfgDevWlanSsidOverrideWlan OBJECT-TYPE
			SYNTAX WingIdentifier
			MAX-ACCESS read-only
			STATUS current
			DESCRIPTION
				"
				
				XPath: /wing-config/device[mac=key1]/wlan_override_ssid[wlan=key2]/wlan"
			::= { wingCfgDevWlanSsidOverrideEntry 1 }

		
		-- 1.3.6.1.4.1.1916.2.131.50.1.3.18.23.1.1.3
		wingCfgDevWlanSsidOverrideSsid OBJECT-TYPE
			SYNTAX DisplayString (SIZE (1..32))
			MAX-ACCESS read-write
			STATUS current
			DESCRIPTION
				"The Service Set Identifier for this WLAN.
				
				XPath: /wing-config/device[mac=key1]/wlan_override_ssid[wlan=key2]/ssid"
			::= { wingCfgDevWlanSsidOverrideEntry 3 }

		
		-- 1.3.6.1.4.1.1916.2.131.50.1.3.18.23.2
		wingCfgDevWlanVlanOverrideTable OBJECT-TYPE
			SYNTAX SEQUENCE OF WingCfgDevWlanVlanOverrideEntry
			MAX-ACCESS not-accessible
			STATUS current
			DESCRIPTION
				"Override WLAN VLANs at the RF Domain level.
				
				/wing-config/device/wlan_override_vlan"
			::= { wingCfgDevWlan 2 }

		
		-- 1.3.6.1.4.1.1916.2.131.50.1.3.18.23.2.1
		wingCfgDevWlanVlanOverrideEntry OBJECT-TYPE
			SYNTAX WingCfgDevWlanVlanOverrideEntry
			MAX-ACCESS not-accessible
			STATUS current
			DESCRIPTION
				"An entry in the table."
			INDEX { wingCfgDevMac, wingCfgDevWlanVlanOverrideWlan }
			::= { wingCfgDevWlanVlanOverrideTable 1 }

		
		WingCfgDevWlanVlanOverrideEntry ::=
			SEQUENCE { 
				wingCfgDevWlanVlanOverrideWlan
					WingIdentifier
			 }

		-- 1.3.6.1.4.1.1916.2.131.50.1.3.18.23.2.1.1
		wingCfgDevWlanVlanOverrideWlan OBJECT-TYPE
			SYNTAX WingIdentifier
			MAX-ACCESS read-only
			STATUS current
			DESCRIPTION
				"
				
				XPath: /wing-config/device[mac=key1]/wlan_override_vlan[wlan=key2]/wlan"
			::= { wingCfgDevWlanVlanOverrideEntry 1 }

		
		-- 1.3.6.1.4.1.1916.2.131.50.1.3.18.23.3
		wingCfgDevWlanVlanOverrideInstTable OBJECT-TYPE
			SYNTAX SEQUENCE OF WingCfgDevWlanVlanOverrideInstEntry
			MAX-ACCESS not-accessible
			STATUS current
			DESCRIPTION
				"
				/wing-config/device/wlan_override_vlan/vlans"
			::= { wingCfgDevWlan 3 }

		
		-- 1.3.6.1.4.1.1916.2.131.50.1.3.18.23.3.1
		wingCfgDevWlanVlanOverrideInstEntry OBJECT-TYPE
			SYNTAX WingCfgDevWlanVlanOverrideInstEntry
			MAX-ACCESS not-accessible
			STATUS current
			DESCRIPTION
				"An entry in the table."
			INDEX { wingCfgDevMac, wingCfgDevWlanVlanOverrideWlan, wingCfgDevWlanVlanOverrideInstVlan }
			::= { wingCfgDevWlanVlanOverrideInstTable 1 }

		
		WingCfgDevWlanVlanOverrideInstEntry ::=
			SEQUENCE { 
				wingCfgDevWlanVlanOverrideInstVlan
					Unsigned32,
				wingCfgDevWlanVlanOverrideInstLimit
					Unsigned32
			 }

		-- 1.3.6.1.4.1.1916.2.131.50.1.3.18.23.3.1.1
		wingCfgDevWlanVlanOverrideInstVlan OBJECT-TYPE
			SYNTAX Unsigned32 (1..4094)
			MAX-ACCESS read-only
			STATUS current
			DESCRIPTION
				"The VLAN identifier.
				
				XPath: /wing-config/device[mac=key1]/wlan_override_vlan[wlan=key2]/vlans[vlan=key3]/vlan"
			::= { wingCfgDevWlanVlanOverrideInstEntry 1 }

		
		-- 1.3.6.1.4.1.1916.2.131.50.1.3.18.23.3.1.3
		wingCfgDevWlanVlanOverrideInstLimit OBJECT-TYPE
			SYNTAX Unsigned32 (0..8192)
			MAX-ACCESS read-write
			STATUS current
			DESCRIPTION
				"The number of users allowed (0 implies unlimited).
				
				XPath: /wing-config/device[mac=key1]/wlan_override_vlan[wlan=key2]/vlans[vlan=key3]/limit"
			DEFVAL { 0 }
			::= { wingCfgDevWlanVlanOverrideInstEntry 3 }

		
		-- 1.3.6.1.4.1.1916.2.131.50.1.3.18.24
		wingCfgDevStatsWindowTable OBJECT-TYPE
			SYNTAX SEQUENCE OF WingCfgDevStatsWindowEntry
			MAX-ACCESS not-accessible
			STATUS current
			DESCRIPTION
				"
				
				/wing-config/device/stats_window"
			::= { wingCfgDev 24 }

		
		-- 1.3.6.1.4.1.1916.2.131.50.1.3.18.24.1
		wingCfgDevStatsWindowEntry OBJECT-TYPE
			SYNTAX WingCfgDevStatsWindowEntry
			MAX-ACCESS not-accessible
			STATUS current
			DESCRIPTION
				"An entry in the table."
			INDEX { wingCfgDevMac, wingCfgDevStatsWindowIdx }
			::= { wingCfgDevStatsWindowTable 1 }

		
		WingCfgDevStatsWindowEntry ::=
			SEQUENCE { 
				wingCfgDevStatsWindowIdx
					Unsigned32,
				wingCfgDevStatsWindowSampleInterval
					Unsigned32,
				wingCfgDevStatsWindowWindowSize
					Unsigned32
			 }

		-- 1.3.6.1.4.1.1916.2.131.50.1.3.18.24.1.1
		wingCfgDevStatsWindowIdx OBJECT-TYPE
			SYNTAX Unsigned32 (1..2)
			MAX-ACCESS read-only
			STATUS current
			DESCRIPTION
				"The index into the list of stats-windows
				
				XPath: /wing-config/device[mac=key1]/stats_window[window_idx=key2]/window_idx"
			::= { wingCfgDevStatsWindowEntry 1 }

		
		-- 1.3.6.1.4.1.1916.2.131.50.1.3.18.24.1.3
		wingCfgDevStatsWindowSampleInterval OBJECT-TYPE
			SYNTAX Unsigned32 (5..86640)
			MAX-ACCESS read-write
			STATUS current
			DESCRIPTION
				"sample interval in seconds for the window
				
				XPath: /wing-config/device[mac=key1]/stats_window[window_idx=key2]/sample_interval"
			DEFVAL { 5 }
			::= { wingCfgDevStatsWindowEntry 3 }

		
		-- 1.3.6.1.4.1.1916.2.131.50.1.3.18.24.1.4
		wingCfgDevStatsWindowWindowSize OBJECT-TYPE
			SYNTAX Unsigned32 (3..100)
			MAX-ACCESS read-write
			STATUS current
			DESCRIPTION
				"number of samples in the window
				
				XPath: /wing-config/device[mac=key1]/stats_window[window_idx=key2]/window_size"
			DEFVAL { 3 }
			::= { wingCfgDevStatsWindowEntry 4 }

		
		-- 1.3.6.1.4.1.1916.2.131.50.1.3.18.26
		wingCfgDevVrrp OBJECT IDENTIFIER ::= { wingCfgDev 26 }

		
		-- 1.3.6.1.4.1.1916.2.131.50.1.3.18.26.1
		wingCfgDevVrrpTable OBJECT-TYPE
			SYNTAX SEQUENCE OF WingCfgDevVrrpEntry
			MAX-ACCESS not-accessible
			STATUS current
			DESCRIPTION
				"
				
				/wing-config/device"
			::= { wingCfgDevVrrp 1 }

		
		-- 1.3.6.1.4.1.1916.2.131.50.1.3.18.26.1.1
		wingCfgDevVrrpEntry OBJECT-TYPE
			SYNTAX WingCfgDevVrrpEntry
			MAX-ACCESS not-accessible
			STATUS current
			DESCRIPTION
				"An entry in the table."
			INDEX { wingCfgDevMac }
			::= { wingCfgDevVrrpTable 1 }

		
		WingCfgDevVrrpEntry ::=
			SEQUENCE { 
				wingCfgDevVrrpVersion
					DisplayString
			 }

		-- 1.3.6.1.4.1.1916.2.131.50.1.3.18.26.1.1.1
		wingCfgDevVrrpVersion OBJECT-TYPE
			SYNTAX DisplayString
			MAX-ACCESS read-write
			STATUS current
			DESCRIPTION
				"VRRP version supported by the device
				
				Values:
				3
				
				XPath: /wing-config/device[mac=key1]/vrrp_version"
			DEFVAL { "2" }
			::= { wingCfgDevVrrpEntry 1 }

		
		-- 1.3.6.1.4.1.1916.2.131.50.1.3.18.26.2
		wingCfgDevVrrpGroupTable OBJECT-TYPE
			SYNTAX SEQUENCE OF WingCfgDevVrrpGroupEntry
			MAX-ACCESS not-accessible
			STATUS current
			DESCRIPTION
				"
				
				/wing-config/device/vrrp_groups"
			::= { wingCfgDevVrrp 2 }

		
		-- 1.3.6.1.4.1.1916.2.131.50.1.3.18.26.2.1
		wingCfgDevVrrpGroupEntry OBJECT-TYPE
			SYNTAX WingCfgDevVrrpGroupEntry
			MAX-ACCESS not-accessible
			STATUS current
			DESCRIPTION
				"An entry in the table."
			INDEX { wingCfgDevMac, wingCfgDevVrrpGroupVirtualRouterId }
			::= { wingCfgDevVrrpGroupTable 1 }

		
		WingCfgDevVrrpGroupEntry ::=
			SEQUENCE { 
				wingCfgDevVrrpGroupVirtualRouterId
					Unsigned32,
				wingCfgDevVrrpGroupDescription
					DisplayString,
				wingCfgDevVrrpGroupPriority
					Unsigned32,
				wingCfgDevVrrpGroupAdvertisementUnit
					DisplayString,
				wingCfgDevVrrpGroupAdvertisementIntervalV2
					Unsigned32,
				wingCfgDevVrrpGroupAdvertisementIntervalV2Msec
					Unsigned32,
				wingCfgDevVrrpGroupAdvertisementIntervalV3
					Unsigned32,
				wingCfgDevVrrpGroupPreempt
					TruthValue,
				wingCfgDevVrrpGroupPreemptDelay
					Unsigned32,
				wingCfgDevVrrpGroupCrmAction
					DisplayString,
				wingCfgDevVrrpGroupDeltaPriority
					Unsigned32,
				wingCfgDevVrrpGroupInterface
					DisplayString,
				wingCfgDevVrrpGroupSyncGroup
					TruthValue
			 }

		-- 1.3.6.1.4.1.1916.2.131.50.1.3.18.26.2.1.1
		wingCfgDevVrrpGroupVirtualRouterId OBJECT-TYPE
			SYNTAX Unsigned32 (1..255)
			MAX-ACCESS read-only
			STATUS current
			DESCRIPTION
				"Identifies the virtual router and used for associating VRRP packet with this field
				
				XPath: /wing-config/device[mac=key1]/vrrp_groups[virtual_router_id=key2]/virtual_router_id"
			::= { wingCfgDevVrrpGroupEntry 1 }

		
		-- 1.3.6.1.4.1.1916.2.131.50.1.3.18.26.2.1.3
		wingCfgDevVrrpGroupDescription OBJECT-TYPE
			SYNTAX DisplayString (SIZE (1..64))
			MAX-ACCESS read-write
			STATUS current
			DESCRIPTION
				"Assigns a text description to the VRRP group
				
				XPath: /wing-config/device[mac=key1]/vrrp_groups[virtual_router_id=key2]/description"
			::= { wingCfgDevVrrpGroupEntry 3 }

		
		-- 1.3.6.1.4.1.1916.2.131.50.1.3.18.26.2.1.4
		wingCfgDevVrrpGroupPriority OBJECT-TYPE
			SYNTAX Unsigned32 (1..254)
			MAX-ACCESS read-write
			STATUS current
			DESCRIPTION
				"the priority to be used for the virtual router master election process.  Higher values imply higher priority.
				
				XPath: /wing-config/device[mac=key1]/vrrp_groups[virtual_router_id=key2]/priority"
			DEFVAL { 100 }
			::= { wingCfgDevVrrpGroupEntry 4 }

		
		-- 1.3.6.1.4.1.1916.2.131.50.1.3.18.26.2.1.5
		wingCfgDevVrrpGroupAdvertisementUnit OBJECT-TYPE
			SYNTAX DisplayString
			MAX-ACCESS read-write
			STATUS current
			DESCRIPTION
				"unit of the advertisment interval
				
				Values:
				seconds,
				milliseconds,
				centiseconds
				
				XPath: /wing-config/device[mac=key1]/vrrp_groups[virtual_router_id=key2]/advertisement_interval/advertisement_unit"
			DEFVAL { "seconds" }
			::= { wingCfgDevVrrpGroupEntry 5 }

		
		-- 1.3.6.1.4.1.1916.2.131.50.1.3.18.26.2.1.6
		wingCfgDevVrrpGroupAdvertisementIntervalV2 OBJECT-TYPE
			SYNTAX Unsigned32 (1..255)
			UNITS "seconds"
			MAX-ACCESS read-write
			STATUS current
			DESCRIPTION
				"Time interval between VRRP advertisments
				
				XPath: /wing-config/device[mac=key1]/vrrp_groups[virtual_router_id=key2]/advertisement_interval/advertisement_interval_v2"
			DEFVAL { 1 }
			::= { wingCfgDevVrrpGroupEntry 6 }

		
		-- 1.3.6.1.4.1.1916.2.131.50.1.3.18.26.2.1.7
		wingCfgDevVrrpGroupAdvertisementIntervalV2Msec OBJECT-TYPE
			SYNTAX Unsigned32 (50..999)
			UNITS "milliseconds"
			MAX-ACCESS read-write
			STATUS current
			DESCRIPTION
				"Time interval between VRRP advertisments
				
				XPath: /wing-config/device[mac=key1]/vrrp_groups[virtual_router_id=key2]/advertisement_interval/advertisement_interval_v2_msec"
			::= { wingCfgDevVrrpGroupEntry 7 }

		
		-- 1.3.6.1.4.1.1916.2.131.50.1.3.18.26.2.1.8
		wingCfgDevVrrpGroupAdvertisementIntervalV3 OBJECT-TYPE
			SYNTAX Unsigned32 (1..4095)
			UNITS "centiseconds"
			MAX-ACCESS read-write
			STATUS current
			DESCRIPTION
				"Time interval between VRRP advertisments
				
				XPath: /wing-config/device[mac=key1]/vrrp_groups[virtual_router_id=key2]/advertisement_interval/advertisement_interval_v3"
			DEFVAL { 100 }
			::= { wingCfgDevVrrpGroupEntry 8 }

		
		-- 1.3.6.1.4.1.1916.2.131.50.1.3.18.26.2.1.9
		wingCfgDevVrrpGroupPreempt OBJECT-TYPE
			SYNTAX TruthValue
			MAX-ACCESS read-write
			STATUS current
			DESCRIPTION
				"Controls whether a higher priority backup router will preempt a lower priority master.
				
				XPath: /wing-config/device[mac=key1]/vrrp_groups[virtual_router_id=key2]/preemption/preempt"
			DEFVAL { true }
			::= { wingCfgDevVrrpGroupEntry 9 }

		
		-- 1.3.6.1.4.1.1916.2.131.50.1.3.18.26.2.1.10
		wingCfgDevVrrpGroupPreemptDelay OBJECT-TYPE
			SYNTAX Unsigned32 (1..65535)
			UNITS "seconds"
			MAX-ACCESS read-write
			STATUS current
			DESCRIPTION
				"Delay interval for pre-emption
				
				XPath: /wing-config/device[mac=key1]/vrrp_groups[virtual_router_id=key2]/preemption/preempt_delay"
			::= { wingCfgDevVrrpGroupEntry 10 }

		
		-- 1.3.6.1.4.1.1916.2.131.50.1.3.18.26.2.1.11
		wingCfgDevVrrpGroupCrmAction OBJECT-TYPE
			SYNTAX DisplayString
			MAX-ACCESS read-write
			STATUS current
			DESCRIPTION
				"Backup virtual router may raise its priority in case the critical resources connected via the master router fail so that
				
				Values:
				increment-priority,
				decrement-priority,
				none
				
				XPath: /wing-config/device[mac=key1]/vrrp_groups[virtual_router_id=key2]/crm_action"
			DEFVAL { "none" }
			::= { wingCfgDevVrrpGroupEntry 11 }

		
		-- 1.3.6.1.4.1.1916.2.131.50.1.3.18.26.2.1.12
		wingCfgDevVrrpGroupDeltaPriority OBJECT-TYPE
			SYNTAX Unsigned32 (1..253)
			MAX-ACCESS read-write
			STATUS current
			DESCRIPTION
				"The configured priority will be decremented by this value when the monitored interface state is down. In case of critical resource monitoring, the configured priority will be incremented by this value
				
				XPath: /wing-config/device[mac=key1]/vrrp_groups[virtual_router_id=key2]/delta_priority"
			::= { wingCfgDevVrrpGroupEntry 12 }

		
		-- 1.3.6.1.4.1.1916.2.131.50.1.3.18.26.2.1.13
		wingCfgDevVrrpGroupInterface OBJECT-TYPE
			SYNTAX DisplayString
			MAX-ACCESS read-write
			STATUS current
			DESCRIPTION
				"The SVI (VLAN only) interface on which VRRP will be running. This also enable/disable VRRP operations
				
				XPath: /wing-config/device[mac=key1]/vrrp_groups[virtual_router_id=key2]/interface"
			::= { wingCfgDevVrrpGroupEntry 13 }

		
		-- 1.3.6.1.4.1.1916.2.131.50.1.3.18.26.2.1.14
		wingCfgDevVrrpGroupSyncGroup OBJECT-TYPE
			SYNTAX TruthValue
			MAX-ACCESS read-write
			STATUS current
			DESCRIPTION
				"Make this group part of vrrp sync group. This triggers VRRP failover only when advertisement is not received from all the masters of the virtual routers that is part of this vrrp sync group
				
				XPath: /wing-config/device[mac=key1]/vrrp_groups[virtual_router_id=key2]/sync_group"
			DEFVAL { false }
			::= { wingCfgDevVrrpGroupEntry 14 }

		
		-- 1.3.6.1.4.1.1916.2.131.50.1.3.18.27
		wingCfgDevIgs OBJECT IDENTIFIER ::= { wingCfgDev 27 }

		
		-- 1.3.6.1.4.1.1916.2.131.50.1.3.18.27.1
		wingCfgDevIgsTable OBJECT-TYPE
			SYNTAX SEQUENCE OF WingCfgDevIgsEntry
			MAX-ACCESS not-accessible
			STATUS current
			DESCRIPTION
				"
				
				/wing-config/device"
			::= { wingCfgDevIgs 1 }

		
		-- 1.3.6.1.4.1.1916.2.131.50.1.3.18.27.1.1
		wingCfgDevIgsEntry OBJECT-TYPE
			SYNTAX WingCfgDevIgsEntry
			MAX-ACCESS not-accessible
			STATUS current
			DESCRIPTION
				"An entry in the table."
			INDEX { wingCfgDevMac }
			::= { wingCfgDevIgsTable 1 }

		
		WingCfgDevIgsEntry ::=
			SEQUENCE { 
				wingCfgDevIgsIpIgmpSnooping
					TruthValue,
				wingCfgDevIgsIpIgmpSnoopingForwardUnknownMulticast
					TruthValue,
				wingCfgDevIgsIpIgmpSnoopingQuerier
					TruthValue,
				wingCfgDevIgsIpIgmpSnoopingQuerierAddress
					DisplayString,
				wingCfgDevIgsIpIgmpSnoopingQuerierMaxResponseTime
					Unsigned32,
				wingCfgDevIgsIpIgmpSnoopingQuerierOtherQuerierTimerExpiry
					Unsigned32,
				wingCfgDevIgsIpIgmpSnoopingQuerierVersion
					Unsigned32,
				wingCfgDevIgsIpIgmpSnoopingQuerierQueryInterval
					Unsigned32,
				wingCfgDevIgsIpIgmpSnoopingQuerierRobustnessVariable
					Unsigned32
			 }

		-- 1.3.6.1.4.1.1916.2.131.50.1.3.18.27.1.1.1
		wingCfgDevIgsIpIgmpSnooping OBJECT-TYPE
			SYNTAX TruthValue
			MAX-ACCESS read-write
			STATUS current
			DESCRIPTION
				"Enable/Disable igmp snooping; if set to disable, then per vlan bridge configuration is ignored
				
				XPath: /wing-config/device[mac=key1]/ip_igmp_snooping"
			DEFVAL { true }
			::= { wingCfgDevIgsEntry 1 }

		
		-- 1.3.6.1.4.1.1916.2.131.50.1.3.18.27.1.1.2
		wingCfgDevIgsIpIgmpSnoopingForwardUnknownMulticast OBJECT-TYPE
			SYNTAX TruthValue
			MAX-ACCESS read-write
			STATUS current
			DESCRIPTION
				"Enable/Disable unknown multicast fowarding
				
				XPath: /wing-config/device[mac=key1]/ip_igmp_snooping_forward_unknown_multicast"
			DEFVAL { false }
			::= { wingCfgDevIgsEntry 2 }

		
		-- 1.3.6.1.4.1.1916.2.131.50.1.3.18.27.1.1.3
		wingCfgDevIgsIpIgmpSnoopingQuerier OBJECT-TYPE
			SYNTAX TruthValue
			MAX-ACCESS read-write
			STATUS current
			DESCRIPTION
				"Enable/Disable on board IGMP querier on the device
				
				XPath: /wing-config/device[mac=key1]/ip_igmp_snooping_querier"
			DEFVAL { false }
			::= { wingCfgDevIgsEntry 3 }

		
		-- 1.3.6.1.4.1.1916.2.131.50.1.3.18.27.1.1.4
		wingCfgDevIgsIpIgmpSnoopingQuerierAddress OBJECT-TYPE
			SYNTAX DisplayString
			MAX-ACCESS read-write
			STATUS current
			DESCRIPTION
				"IP Address used by IGMP querier
				
				XPath: /wing-config/device[mac=key1]/ip_igmp_snooping_querier_address"
			DEFVAL { "0.0.0.0" }
			::= { wingCfgDevIgsEntry 4 }

		
		-- 1.3.6.1.4.1.1916.2.131.50.1.3.18.27.1.1.5
		wingCfgDevIgsIpIgmpSnoopingQuerierMaxResponseTime OBJECT-TYPE
			SYNTAX Unsigned32 (1..25)
			UNITS "seconds"
			MAX-ACCESS read-write
			STATUS current
			DESCRIPTION
				"Maximum query response time
				
				XPath: /wing-config/device[mac=key1]/ip_igmp_snooping_querier_max_response_time"
			DEFVAL { 10 }
			::= { wingCfgDevIgsEntry 5 }

		
		-- 1.3.6.1.4.1.1916.2.131.50.1.3.18.27.1.1.6
		wingCfgDevIgsIpIgmpSnoopingQuerierOtherQuerierTimerExpiry OBJECT-TYPE
			SYNTAX Unsigned32 (60..300)
			UNITS "seconds"
			MAX-ACCESS read-write
			STATUS current
			DESCRIPTION
				"other querier time out value for the IGMP Querier
				
				XPath: /wing-config/device[mac=key1]/ip_igmp_snooping_querier_other_querier_timer_expiry"
			DEFVAL { 60 }
			::= { wingCfgDevIgsEntry 6 }

		
		-- 1.3.6.1.4.1.1916.2.131.50.1.3.18.27.1.1.7
		wingCfgDevIgsIpIgmpSnoopingQuerierVersion OBJECT-TYPE
			SYNTAX Unsigned32 (1..3)
			MAX-ACCESS read-write
			STATUS current
			DESCRIPTION
				"IGMP version for the querier
				
				XPath: /wing-config/device[mac=key1]/ip_igmp_snooping_querier_version"
			DEFVAL { 3 }
			::= { wingCfgDevIgsEntry 7 }

		
		-- 1.3.6.1.4.1.1916.2.131.50.1.3.18.27.1.1.8
		wingCfgDevIgsIpIgmpSnoopingQuerierQueryInterval OBJECT-TYPE
			SYNTAX Unsigned32 (1..18000)
			UNITS "seconds"
			MAX-ACCESS read-write
			STATUS current
			DESCRIPTION
				"
				
				XPath: /wing-config/device[mac=key1]/ip_igmp_snooping_querier_query_interval"
			DEFVAL { 60 }
			::= { wingCfgDevIgsEntry 8 }

		
		-- 1.3.6.1.4.1.1916.2.131.50.1.3.18.27.1.1.9
		wingCfgDevIgsIpIgmpSnoopingQuerierRobustnessVariable OBJECT-TYPE
			SYNTAX Unsigned32 (1..7)
			MAX-ACCESS read-write
			STATUS current
			DESCRIPTION
				"
				
				XPath: /wing-config/device[mac=key1]/ip_igmp_snooping_querier_robustness_variable"
			DEFVAL { 2 }
			::= { wingCfgDevIgsEntry 9 }

		
		-- 1.3.6.1.4.1.1916.2.131.50.1.3.18.28
		wingCfgDevDynRoute OBJECT IDENTIFIER ::= { wingCfgDev 28 }

		
		-- 1.3.6.1.4.1.1916.2.131.50.1.3.18.28.1
		wingCfgDevDynRouteOspfTable OBJECT-TYPE
			SYNTAX SEQUENCE OF WingCfgDevDynRouteOspfEntry
			MAX-ACCESS not-accessible
			STATUS current
			DESCRIPTION
				"Route Ospf Table.
				
				/wing-config/device/dynamic_router_ospf"
			::= { wingCfgDevDynRoute 1 }

		
		-- 1.3.6.1.4.1.1916.2.131.50.1.3.18.28.1.1
		wingCfgDevDynRouteOspfEntry OBJECT-TYPE
			SYNTAX WingCfgDevDynRouteOspfEntry
			MAX-ACCESS not-accessible
			STATUS current
			DESCRIPTION
				"An entry in the table."
			INDEX { wingCfgDevMac }
			::= { wingCfgDevDynRouteOspfTable 1 }

		
		WingCfgDevDynRouteOspfEntry ::=
			SEQUENCE { 
				wingCfgDevDynRouteOspfEnabled
					TruthValue,
				wingCfgDevDynRouteOspfRouterId
					OCTET STRING,
				wingCfgDevDynRouteOspfAutoCost
					Unsigned32,
				wingCfgDevDynRouteOspfPassiveAll
					TruthValue,
				wingCfgDevDynRouteOspfPassive
					DisplayString,
				wingCfgDevDynRouteOspfPassiveRemoved
					DisplayString,
				wingCfgDevDynRouteOspfVrrpStateCheck
					TruthValue,
				wingCfgDevDynRouteOspfDefaultRoutePriority
					Unsigned32,
				wingCfgDevDynRouteOspfNumRoutes
					Unsigned32,
				wingCfgDevDynRouteOspfRetryCount
					Unsigned32,
				wingCfgDevDynRouteOspfRetryTimeout
					Unsigned32,
				wingCfgDevDynRouteOspfResetTime
					Unsigned32
			 }

		-- 1.3.6.1.4.1.1916.2.131.50.1.3.18.28.1.1.1
		wingCfgDevDynRouteOspfEnabled OBJECT-TYPE
			SYNTAX TruthValue
			MAX-ACCESS read-write
			STATUS current
			DESCRIPTION
				"Dynamic routing protocol OSPF
				
				XPath: /wing-config/device[mac=key1]/dynamic_router_ospf/ospf"
			DEFVAL { false }
			::= { wingCfgDevDynRouteOspfEntry 1 }

		
		-- 1.3.6.1.4.1.1916.2.131.50.1.3.18.28.1.1.2
		wingCfgDevDynRouteOspfRouterId OBJECT-TYPE
			SYNTAX OCTET STRING
			MAX-ACCESS read-write
			STATUS current
			DESCRIPTION
				"Router-ID for this device. If Router-ID is not configured, system generates one and it can be viewed in statistics
				
				XPath: /wing-config/device[mac=key1]/dynamic_router_ospf/router_id"
			::= { wingCfgDevDynRouteOspfEntry 2 }

		
		-- 1.3.6.1.4.1.1916.2.131.50.1.3.18.28.1.1.3
		wingCfgDevDynRouteOspfAutoCost OBJECT-TYPE
			SYNTAX Unsigned32 (1..4294967)
			MAX-ACCESS read-write
			STATUS current
			DESCRIPTION
				"Specifies reference bandwidth to be used in Mbps to calculate OSPF interface cost if OSPF area is STUB or NSSA
				
				XPath: /wing-config/device[mac=key1]/dynamic_router_ospf/auto_cost"
			::= { wingCfgDevDynRouteOspfEntry 3 }

		
		-- 1.3.6.1.4.1.1916.2.131.50.1.3.18.28.1.1.4
		wingCfgDevDynRouteOspfPassiveAll OBJECT-TYPE
			SYNTAX TruthValue
			MAX-ACCESS read-write
			STATUS current
			DESCRIPTION
				"Configures all L3 interfaces as OSPF passive interface
				
				XPath: /wing-config/device[mac=key1]/dynamic_router_ospf/passive_all"
			DEFVAL { false }
			::= { wingCfgDevDynRouteOspfEntry 4 }

		
		-- 1.3.6.1.4.1.1916.2.131.50.1.3.18.28.1.1.5
		wingCfgDevDynRouteOspfPassive OBJECT-TYPE
			SYNTAX DisplayString
			MAX-ACCESS read-write
			STATUS current
			DESCRIPTION
				"Configures specified interface(s) as OSPF passive interface(s).
				
				XPath: /wing-config/device[mac=key1]/dynamic_router_ospf/passive"
			::= { wingCfgDevDynRouteOspfEntry 5 }

		
		-- 1.3.6.1.4.1.1916.2.131.50.1.3.18.28.1.1.6
		wingCfgDevDynRouteOspfPassiveRemoved OBJECT-TYPE
			SYNTAX DisplayString
			MAX-ACCESS read-write
			STATUS current
			DESCRIPTION
				"Configures specified interface(s) as OSPF NON-passive interface(s).
				
				XPath: /wing-config/device[mac=key1]/dynamic_router_ospf/passive_removed"
			REFERENCE
				"Configures specified interface(s) as OSPF NON-passive interface(s)."
			::= { wingCfgDevDynRouteOspfEntry 6 }

		
		-- 1.3.6.1.4.1.1916.2.131.50.1.3.18.28.1.1.7
		wingCfgDevDynRouteOspfVrrpStateCheck OBJECT-TYPE
			SYNTAX TruthValue
			MAX-ACCESS read-write
			STATUS current
			DESCRIPTION
				"Publish interface via OSPF only if the interface VRRP state is not BACKUP.
				
				XPath: /wing-config/device[mac=key1]/dynamic_router_ospf/vrrp_state_check"
			::= { wingCfgDevDynRouteOspfEntry 7 }

		
		-- 1.3.6.1.4.1.1916.2.131.50.1.3.18.28.1.1.8
		wingCfgDevDynRouteOspfDefaultRoutePriority OBJECT-TYPE
			SYNTAX Unsigned32 (1..8000)
			MAX-ACCESS read-write
			STATUS current
			DESCRIPTION
				"Priority for the default route learnt via OSPF.
				
				XPath: /wing-config/device[mac=key1]/dynamic_router_ospf/ospf_default_route_priority"
			DEFVAL { 7000 }
			::= { wingCfgDevDynRouteOspfEntry 8 }

		
		-- 1.3.6.1.4.1.1916.2.131.50.1.3.18.28.1.1.9
		wingCfgDevDynRouteOspfNumRoutes OBJECT-TYPE
			SYNTAX Unsigned32 (1..4294967295)
			MAX-ACCESS read-write
			STATUS current
			DESCRIPTION
				"Maximum number of OSPF routes allowed.
				
				XPath: /wing-config/device[mac=key1]/dynamic_router_ospf/route_limit/num_routes"
			::= { wingCfgDevDynRouteOspfEntry 9 }

		
		-- 1.3.6.1.4.1.1916.2.131.50.1.3.18.28.1.1.10
		wingCfgDevDynRouteOspfRetryCount OBJECT-TYPE
			SYNTAX Unsigned32 (1..32)
			MAX-ACCESS read-write
			STATUS current
			DESCRIPTION
				"Maximum number for which OSPF process will be reset before permanently shutting down OSPF.
				
				XPath: /wing-config/device[mac=key1]/dynamic_router_ospf/route_limit/retry_count"
			DEFVAL { 5 }
			::= { wingCfgDevDynRouteOspfEntry 10 }

		
		-- 1.3.6.1.4.1.1916.2.131.50.1.3.18.28.1.1.11
		wingCfgDevDynRouteOspfRetryTimeout OBJECT-TYPE
			SYNTAX Unsigned32 (1..3600)
			MAX-ACCESS read-write
			STATUS current
			DESCRIPTION
				"Time in seconds during which the OSPF process remains shut before attempting next retry.
				
				XPath: /wing-config/device[mac=key1]/dynamic_router_ospf/route_limit/retry_timeout"
			DEFVAL { 60 }
			::= { wingCfgDevDynRouteOspfEntry 11 }

		
		-- 1.3.6.1.4.1.1916.2.131.50.1.3.18.28.1.1.12
		wingCfgDevDynRouteOspfResetTime OBJECT-TYPE
			SYNTAX Unsigned32 (1..86400)
			MAX-ACCESS read-write
			STATUS current
			DESCRIPTION
				"Time in seconds after which retry-count is reset to zero.
				
				XPath: /wing-config/device[mac=key1]/dynamic_router_ospf/route_limit/reset_time"
			DEFVAL { 360 }
			::= { wingCfgDevDynRouteOspfEntry 12 }

		
		-- 1.3.6.1.4.1.1916.2.131.50.1.3.18.28.2
		wingCfgDevDynRouteOspfNetworkTable OBJECT-TYPE
			SYNTAX SEQUENCE OF WingCfgDevDynRouteOspfNetworkEntry
			MAX-ACCESS not-accessible
			STATUS current
			DESCRIPTION
				"Route Ospf Network Table
				
				/wing-config/device/dynamic_router_cfg/ospf_network"
			::= { wingCfgDevDynRoute 2 }

		
		-- 1.3.6.1.4.1.1916.2.131.50.1.3.18.28.2.1
		wingCfgDevDynRouteOspfNetworkEntry OBJECT-TYPE
			SYNTAX WingCfgDevDynRouteOspfNetworkEntry
			MAX-ACCESS not-accessible
			STATUS current
			DESCRIPTION
				"An entry in the table."
			INDEX { wingCfgDevMac, wingCfgDevDynRouteOspfNetwork }
			::= { wingCfgDevDynRouteOspfNetworkTable 1 }

		
		WingCfgDevDynRouteOspfNetworkEntry ::=
			SEQUENCE { 
				wingCfgDevDynRouteOspfNetwork
					WingIdentifier,
				wingCfgDevDynRouteOspfNetworkAreaId
					DisplayString
			 }

		-- 1.3.6.1.4.1.1916.2.131.50.1.3.18.28.2.1.1
		wingCfgDevDynRouteOspfNetwork OBJECT-TYPE
			SYNTAX WingIdentifier
			MAX-ACCESS read-only
			STATUS current
			DESCRIPTION
				"Networks that need to participate in OSPF
				
				XPath: /wing-config/device[mac=key1]/dynamic_router_ospf/ospf_network[network=key2]/network"
			::= { wingCfgDevDynRouteOspfNetworkEntry 1 }

		
		-- 1.3.6.1.4.1.1916.2.131.50.1.3.18.28.2.1.3
		wingCfgDevDynRouteOspfNetworkAreaId OBJECT-TYPE
			SYNTAX DisplayString
			MAX-ACCESS read-write
			STATUS current
			DESCRIPTION
				"OSPF area to which this network belongs; area is a 32 bit number, which can be represented as IPv4 address
				
				XPath: /wing-config/device[mac=key1]/dynamic_router_ospf/ospf_network[network=key2]/area_id"
			::= { wingCfgDevDynRouteOspfNetworkEntry 3 }

		
		-- 1.3.6.1.4.1.1916.2.131.50.1.3.18.28.3
		wingCfgDevDynRouteOspfAreaTable OBJECT-TYPE
			SYNTAX SEQUENCE OF WingCfgDevDynRouteOspfAreaEntry
			MAX-ACCESS not-accessible
			STATUS current
			DESCRIPTION
				"RouteOspfAreaTable
				
				/wing-config/device/dynamic_router_cfg/ospf_area"
			::= { wingCfgDevDynRoute 3 }

		
		-- 1.3.6.1.4.1.1916.2.131.50.1.3.18.28.3.1
		wingCfgDevDynRouteOspfAreaEntry OBJECT-TYPE
			SYNTAX WingCfgDevDynRouteOspfAreaEntry
			MAX-ACCESS not-accessible
			STATUS current
			DESCRIPTION
				"An entry in the table."
			INDEX { wingCfgDevMac, wingCfgDevDynRouteOspfAreaId }
			::= { wingCfgDevDynRouteOspfAreaTable 1 }

		
		WingCfgDevDynRouteOspfAreaEntry ::=
			SEQUENCE { 
				wingCfgDevDynRouteOspfAreaId
					WingIdentifier,
				wingCfgDevDynRouteOspfAreaAuthentication
					DisplayString,
				wingCfgDevDynRouteOspfAreaRange
					DisplayString,
				wingCfgDevDynRouteOspfAreaType
					DisplayString,
				wingCfgDevDynRouteOspfAreaDefaultCost
					Unsigned32,
				wingCfgDevDynRouteOspfAreaTranslateType
					DisplayString
			 }

		-- 1.3.6.1.4.1.1916.2.131.50.1.3.18.28.3.1.1
		wingCfgDevDynRouteOspfAreaId OBJECT-TYPE
			SYNTAX WingIdentifier
			MAX-ACCESS read-only
			STATUS current
			DESCRIPTION
				"OSPF area related parameters
				
				XPath: /wing-config/device[mac=key1]/dynamic_router_ospf/ospf_area[ospf_area_id=key2]/ospf_area_id"
			::= { wingCfgDevDynRouteOspfAreaEntry 1 }

		
		-- 1.3.6.1.4.1.1916.2.131.50.1.3.18.28.3.1.3
		wingCfgDevDynRouteOspfAreaAuthentication OBJECT-TYPE
			SYNTAX DisplayString
			MAX-ACCESS read-write
			STATUS current
			DESCRIPTION
				"OSPF authentication type
				
				Values:
				simple-password,
				message-digest,
				none
				
				XPath: /wing-config/device[mac=key1]/dynamic_router_ospf/ospf_area[ospf_area_id=key2]/authentication"
			DEFVAL { "none" }
			::= { wingCfgDevDynRouteOspfAreaEntry 3 }

		
		-- 1.3.6.1.4.1.1916.2.131.50.1.3.18.28.3.1.4
		wingCfgDevDynRouteOspfAreaRange OBJECT-TYPE
			SYNTAX DisplayString
			MAX-ACCESS read-only
			STATUS current
			DESCRIPTION
				"Specifies the routes matching address/mask for summarization
				
				XPath: /wing-config/device[mac=key1]/dynamic_router_ospf/ospf_area[ospf_area_id=key2]/range"
			::= { wingCfgDevDynRouteOspfAreaEntry 4 }

		
		-- 1.3.6.1.4.1.1916.2.131.50.1.3.18.28.3.1.5
		wingCfgDevDynRouteOspfAreaType OBJECT-TYPE
			SYNTAX DisplayString
			MAX-ACCESS read-write
			STATUS current
			DESCRIPTION
				"Type of this OSPF area
				
				Values:
				stub,
				totally-stub,
				nssa,
				totally-nssa,
				non-stub
				
				XPath: /wing-config/device[mac=key1]/dynamic_router_ospf/ospf_area[ospf_area_id=key2]/area_type/type"
			DEFVAL { "non-stub" }
			::= { wingCfgDevDynRouteOspfAreaEntry 5 }

		
		-- 1.3.6.1.4.1.1916.2.131.50.1.3.18.28.3.1.6
		wingCfgDevDynRouteOspfAreaDefaultCost OBJECT-TYPE
			SYNTAX Unsigned32 (1..16777215)
			MAX-ACCESS read-write
			STATUS current
			DESCRIPTION
				"Default summary cost that will be advertised if this are is stub
				
				XPath: /wing-config/device[mac=key1]/dynamic_router_ospf/ospf_area[ospf_area_id=key2]/area_type/default_cost"
			::= { wingCfgDevDynRouteOspfAreaEntry 6 }

		
		-- 1.3.6.1.4.1.1916.2.131.50.1.3.18.28.3.1.7
		wingCfgDevDynRouteOspfAreaTranslateType OBJECT-TYPE
			SYNTAX DisplayString
			MAX-ACCESS read-write
			STATUS current
			DESCRIPTION
				"Configures if/how LSA Type 7 message shall be translated
				
				Values:
				translate-always,
				translate-candidate,
				translate-never
				
				XPath: /wing-config/device[mac=key1]/dynamic_router_ospf/ospf_area[ospf_area_id=key2]/area_type/translate_type"
			::= { wingCfgDevDynRouteOspfAreaEntry 7 }

		
		-- 1.3.6.1.4.1.1916.2.131.50.1.3.18.28.4
		wingCfgDevDynRouteDefaultInfoTable OBJECT-TYPE
			SYNTAX SEQUENCE OF WingCfgDevDynRouteDefaultInfoEntry
			MAX-ACCESS not-accessible
			STATUS current
			DESCRIPTION
				"Description."
			::= { wingCfgDevDynRoute 4 }
-- Dyn Route Default Info.
-- 
-- XPath: /wing-config/device[mac=key1]/dynamic_router_ospf/default_information
		
		-- 1.3.6.1.4.1.1916.2.131.50.1.3.18.28.4.1
		wingCfgDevDynRouteDefaultInfoEntry OBJECT-TYPE
			SYNTAX WingCfgDevDynRouteDefaultInfoEntry
			MAX-ACCESS not-accessible
			STATUS current
			DESCRIPTION
				"An entry in the table."
			INDEX { wingCfgDevMac }
			::= { wingCfgDevDynRouteDefaultInfoTable 1 }

		
		WingCfgDevDynRouteDefaultInfoEntry ::=
			SEQUENCE { 
				wingCfgDevDynRouteDefaultInfoOriginate
					TruthValue,
				wingCfgDevDynRouteDefaultInfoAlways
					TruthValue,
				wingCfgDevDynRouteDefaultInfoRtMetric
					Unsigned32,
				wingCfgDevDynRouteDefaultInfoRtMetricType
					DisplayString
			 }

		-- 1.3.6.1.4.1.1916.2.131.50.1.3.18.28.4.1.1
		wingCfgDevDynRouteDefaultInfoOriginate OBJECT-TYPE
			SYNTAX TruthValue
			MAX-ACCESS read-write
			STATUS current
			DESCRIPTION
				"Specifies whether default route should be distributed or not.
				
				XPath: /wing-config/device[mac=key1]/dynamic_router_ospf/default_information/originate"
			::= { wingCfgDevDynRouteDefaultInfoEntry 1 }

		
		-- 1.3.6.1.4.1.1916.2.131.50.1.3.18.28.4.1.2
		wingCfgDevDynRouteDefaultInfoAlways OBJECT-TYPE
			SYNTAX TruthValue
			MAX-ACCESS read-write
			STATUS current
			DESCRIPTION
				"Originate a default route even if one is not present in routing table.
				
				XPath: /wing-config/device[mac=key1]/dynamic_router_ospf/default_information/always"
			::= { wingCfgDevDynRouteDefaultInfoEntry 2 }

		
		-- 1.3.6.1.4.1.1916.2.131.50.1.3.18.28.4.1.3
		wingCfgDevDynRouteDefaultInfoRtMetric OBJECT-TYPE
			SYNTAX Unsigned32 (1..16777214)
			MAX-ACCESS read-write
			STATUS current
			DESCRIPTION
				"Metric for default route.
				
				XPath: /wing-config/device[mac=key1]/dynamic_router_ospf/default_information/default_rt_metric"
			::= { wingCfgDevDynRouteDefaultInfoEntry 3 }

		
		-- 1.3.6.1.4.1.1916.2.131.50.1.3.18.28.4.1.4
		wingCfgDevDynRouteDefaultInfoRtMetricType OBJECT-TYPE
			SYNTAX DisplayString
			MAX-ACCESS read-write
			STATUS current
			DESCRIPTION
				"OSPF exterior metric type for default route.
				
				XPath: /wing-config/device[mac=key1]/dynamic_router_ospf/default_information/default_rt_metric_type"
			::= { wingCfgDevDynRouteDefaultInfoEntry 4 }

		
		-- 1.3.6.1.4.1.1916.2.131.50.1.3.18.28.5
		wingCfgDevDynRouteRedistributeTable OBJECT-TYPE
			SYNTAX SEQUENCE OF WingCfgDevDynRouteRedistributeEntry
			MAX-ACCESS not-accessible
			STATUS current
			DESCRIPTION
				"
				
				/wing-config/device/dynamic_router_cfg/redistribute"
			::= { wingCfgDevDynRoute 5 }

		
		-- 1.3.6.1.4.1.1916.2.131.50.1.3.18.28.5.1
		wingCfgDevDynRouteRedistributeEntry OBJECT-TYPE
			SYNTAX WingCfgDevDynRouteRedistributeEntry
			MAX-ACCESS not-accessible
			STATUS current
			DESCRIPTION
				"An entry in the table."
			INDEX { wingCfgDevMac, wingCfgDevDynRouteRedistributeRouteType }
			::= { wingCfgDevDynRouteRedistributeTable 1 }

		
		WingCfgDevDynRouteRedistributeEntry ::=
			SEQUENCE { 
				wingCfgDevDynRouteRedistributeRouteType
					WingIdentifier,
				wingCfgDevDynRouteRedistributeMetric
					Unsigned32,
				wingCfgDevDynRouteRedistributeMetricType
					DisplayString
			 }

		-- 1.3.6.1.4.1.1916.2.131.50.1.3.18.28.5.1.1
		wingCfgDevDynRouteRedistributeRouteType OBJECT-TYPE
			SYNTAX WingIdentifier
			MAX-ACCESS read-only
			STATUS current
			DESCRIPTION
				"Type of redistributed type
				
				Values:
				connected,
				kernel,
				static
				
				XPath: /wing-config/device[mac=key1]/dynamic_router_ospf/redistribute[route_type=key2]/route_type"
			::= { wingCfgDevDynRouteRedistributeEntry 1 }

		
		-- 1.3.6.1.4.1.1916.2.131.50.1.3.18.28.5.1.3
		wingCfgDevDynRouteRedistributeMetric OBJECT-TYPE
			SYNTAX Unsigned32 (1..16777214)
			MAX-ACCESS read-write
			STATUS current
			DESCRIPTION
				"Metric for redistributed routes
				
				XPath: /wing-config/device[mac=key1]/dynamic_router_ospf/redistribute[route_type=key2]/metric"
			::= { wingCfgDevDynRouteRedistributeEntry 3 }

		
		-- 1.3.6.1.4.1.1916.2.131.50.1.3.18.28.5.1.4
		wingCfgDevDynRouteRedistributeMetricType OBJECT-TYPE
			SYNTAX DisplayString
			MAX-ACCESS read-write
			STATUS current
			DESCRIPTION
				"OSPF exterior metric type for redistributed routes
				
				Values:
				1,
				2
				
				XPath: /wing-config/device[mac=key1]/dynamic_router_ospf/redistribute[route_type=key2]/metric_type"
			::= { wingCfgDevDynRouteRedistributeEntry 4 }

		
		-- 1.3.6.1.4.1.1916.2.131.50.1.3.18.29
		wingCfgDevCriticalRes OBJECT IDENTIFIER ::= { wingCfgDev 29 }

		
		-- 1.3.6.1.4.1.1916.2.131.50.1.3.18.29.1
		wingCfgDevCriticalResMonitorTable OBJECT-TYPE
			SYNTAX SEQUENCE OF WingCfgDevCriticalResMonitorEntry
			MAX-ACCESS not-accessible
			STATUS current
			DESCRIPTION
				"
				
				/wing-config/profile"
			::= { wingCfgDevCriticalRes 1 }

		
		-- 1.3.6.1.4.1.1916.2.131.50.1.3.18.29.1.1
		wingCfgDevCriticalResMonitorEntry OBJECT-TYPE
			SYNTAX WingCfgDevCriticalResMonitorEntry
			MAX-ACCESS not-accessible
			STATUS current
			DESCRIPTION
				"An entry in the table."
			INDEX { wingCfgDevMac }
			::= { wingCfgDevCriticalResMonitorTable 1 }

		
		WingCfgDevCriticalResMonitorEntry ::=
			SEQUENCE { 
				wingCfgDevCriticalResMonitorInt
					Unsigned32
			 }

		-- 1.3.6.1.4.1.1916.2.131.50.1.3.18.29.1.1.1
		wingCfgDevCriticalResMonitorInt OBJECT-TYPE
			SYNTAX Unsigned32 (5..86400)
			UNITS "seconds"
			MAX-ACCESS read-write
			STATUS current
			DESCRIPTION
				"Monitoring frequency
				
				XPath: /wing-config/device[mac=key1]/crm_monitor_interval"
			DEFVAL { 30 }
			::= { wingCfgDevCriticalResMonitorEntry 1 }

		
		-- 1.3.6.1.4.1.1916.2.131.50.1.3.18.29.2
		wingCfgDevCriticalResPolicyTable OBJECT-TYPE
			SYNTAX SEQUENCE OF WingCfgDevCriticalResPolicyEntry
			MAX-ACCESS not-accessible
			STATUS current
			DESCRIPTION
				"
				
				/wing-config/device/critical_resources"
			::= { wingCfgDevCriticalRes 2 }

		
		-- 1.3.6.1.4.1.1916.2.131.50.1.3.18.29.2.1
		wingCfgDevCriticalResPolicyEntry OBJECT-TYPE
			SYNTAX WingCfgDevCriticalResPolicyEntry
			MAX-ACCESS not-accessible
			STATUS current
			DESCRIPTION
				"An entry in the table."
			INDEX { wingCfgDevMac, wingCfgDevCriticalResPolicyVia }
			::= { wingCfgDevCriticalResPolicyTable 1 }

		
		WingCfgDevCriticalResPolicyEntry ::=
			SEQUENCE { 
				wingCfgDevCriticalResPolicyVia
					WingIdentifier,
				wingCfgDevCriticalResPolicyAnyAll
					DisplayString
			 }

		-- 1.3.6.1.4.1.1916.2.131.50.1.3.18.29.2.1.1
		wingCfgDevCriticalResPolicyVia OBJECT-TYPE
			SYNTAX WingIdentifier
			MAX-ACCESS read-only
			STATUS current
			DESCRIPTION
				"
				
				XPath: /wing-config/device[mac=key1]/critical_resources[via=key2]/via"
			::= { wingCfgDevCriticalResPolicyEntry 1 }

		
		-- 1.3.6.1.4.1.1916.2.131.50.1.3.18.29.2.1.3
		wingCfgDevCriticalResPolicyAnyAll OBJECT-TYPE
			SYNTAX DisplayString
			MAX-ACCESS read-write
			STATUS current
			DESCRIPTION
				"
				
				Values:
				any,
				all
				
				XPath: /wing-config/device[mac=key1]/critical_resources[via=key2]/any_all"
			DEFVAL { "any" }
			::= { wingCfgDevCriticalResPolicyEntry 3 }

		
		-- 1.3.6.1.4.1.1916.2.131.50.1.3.18.29.3
		wingCfgDevCriticalResourcesTable OBJECT-TYPE
			SYNTAX SEQUENCE OF WingCfgDevCriticalResourcesEntry
			MAX-ACCESS not-accessible
			STATUS current
			DESCRIPTION
				"
				
				/wing-config/device/critical_resources/resources"
			::= { wingCfgDevCriticalRes 3 }

		
		-- 1.3.6.1.4.1.1916.2.131.50.1.3.18.29.3.1
		wingCfgDevCriticalResourcesEntry OBJECT-TYPE
			SYNTAX WingCfgDevCriticalResourcesEntry
			MAX-ACCESS not-accessible
			STATUS current
			DESCRIPTION
				"An entry in the table."
			INDEX { wingCfgDevMac, wingCfgDevCriticalResPolicyVia, wingCfgDevCriticalResourcesAddr }
			::= { wingCfgDevCriticalResourcesTable 1 }

		
		WingCfgDevCriticalResourcesEntry ::=
			SEQUENCE { 
				wingCfgDevCriticalResourcesAddr
					WingIdentifier,
				wingCfgDevCriticalResourcesMonitorType
					DisplayString,
				wingCfgDevCriticalResourcesVlan
					Unsigned32,
				wingCfgDevCriticalResourcesPort
					DisplayString
			 }

		-- 1.3.6.1.4.1.1916.2.131.50.1.3.18.29.3.1.1
		wingCfgDevCriticalResourcesAddr OBJECT-TYPE
			SYNTAX WingIdentifier
			MAX-ACCESS read-only
			STATUS current
			DESCRIPTION
				"
				
				XPath: /wing-config/device[mac=key1]/critical_resources[via=key2]/resources[address=key3]/address"
			::= { wingCfgDevCriticalResourcesEntry 1 }

		
		-- 1.3.6.1.4.1.1916.2.131.50.1.3.18.29.3.1.3
		wingCfgDevCriticalResourcesMonitorType OBJECT-TYPE
			SYNTAX DisplayString
			MAX-ACCESS read-write
			STATUS current
			DESCRIPTION
				"
				
				Values:
				arp-only,
				arp-and-ping
				
				XPath: /wing-config/device[mac=key1]/critical_resources[via=key2]/resources[address=key3]/monitor_type"
			DEFVAL { "arp-and-ping" }
			::= { wingCfgDevCriticalResourcesEntry 3 }

		
		-- 1.3.6.1.4.1.1916.2.131.50.1.3.18.29.3.1.4
		wingCfgDevCriticalResourcesVlan OBJECT-TYPE
			SYNTAX Unsigned32 (1..4094)
			MAX-ACCESS read-write
			STATUS current
			DESCRIPTION
				"
				
				XPath: /wing-config/device[mac=key1]/critical_resources[via=key2]/resources[address=key3]/vlan"
			::= { wingCfgDevCriticalResourcesEntry 4 }

		
		-- 1.3.6.1.4.1.1916.2.131.50.1.3.18.29.3.1.5
		wingCfgDevCriticalResourcesPort OBJECT-TYPE
			SYNTAX DisplayString
			MAX-ACCESS read-write
			STATUS current
			DESCRIPTION
				"
				
				Values:
				ge1, ge2, ge3, ge4, ge5, ge6, ge7, ge8, xge1, xge2, fe1, fe2, fe3, fe4, me1, up1
				
				XPath: /wing-config/device[mac=key1]/critical_resources[via=key2]/resources[address=key3]/port"
			::= { wingCfgDevCriticalResourcesEntry 5 }

		
-- /wing-config/profile/l2tpv3
		-- 1.3.6.1.4.1.1916.2.131.50.1.3.18.30
		wingCfgDevl2tpv3 OBJECT IDENTIFIER ::= { wingCfgDev 30 }

		
-- /wing-config/device/l2tpv3
		-- 1.3.6.1.4.1.1916.2.131.50.1.3.18.30.1
		wingCfgDevl2tpv3Table OBJECT-TYPE
			SYNTAX SEQUENCE OF WingCfgDevl2tpv3Entry
			MAX-ACCESS not-accessible
			STATUS current
			DESCRIPTION
				"/wing-config/device/l2tpv3"
			::= { wingCfgDevl2tpv3 1 }

		
		-- 1.3.6.1.4.1.1916.2.131.50.1.3.18.30.1.1
		wingCfgDevl2tpv3Entry OBJECT-TYPE
			SYNTAX WingCfgDevl2tpv3Entry
			MAX-ACCESS not-accessible
			STATUS current
			DESCRIPTION
				"An entry in the table."
			INDEX { wingCfgDevMac }
			::= { wingCfgDevl2tpv3Table 1 }

		
		WingCfgDevl2tpv3Entry ::=
			SEQUENCE { 
				wingCfgDevl2tpv3lUdpListenPort
					Unsigned32,
				wingCfgDevl2tpv3RouterId
					DisplayString,
				wingCfgDevl2tpv3HostName
					DisplayString,
				wingCfgDevl2tpv3InterTunnelBridging
					TruthValue
			 }

		-- 1.3.6.1.4.1.1916.2.131.50.1.3.18.30.1.1.1
		wingCfgDevl2tpv3lUdpListenPort OBJECT-TYPE
			SYNTAX Unsigned32
			MAX-ACCESS read-write
			STATUS current
			DESCRIPTION
				"The UDP port on which incoming requests are listened.
				
				XPath: /wing-config/device[mac=key1]/l2tpv3_udp_listen_port"
			::= { wingCfgDevl2tpv3Entry 1 }

		
		-- 1.3.6.1.4.1.1916.2.131.50.1.3.18.30.1.1.2
		wingCfgDevl2tpv3RouterId OBJECT-TYPE
			SYNTAX DisplayString
			MAX-ACCESS read-write
			STATUS current
			DESCRIPTION
				"Router Id used in AVP message for the tunnel.
				
				XPath: /wing-config/device[mac=key1]/l2tpv3_router_id"
			::= { wingCfgDevl2tpv3Entry 2 }

		
		-- 1.3.6.1.4.1.1916.2.131.50.1.3.18.30.1.1.3
		wingCfgDevl2tpv3HostName OBJECT-TYPE
			SYNTAX DisplayString
			MAX-ACCESS read-write
			STATUS current
			DESCRIPTION
				"Host name sent in AVP message for the tunnel.
				
				XPath: /wing-config/device[mac=key1]/l2tpv3_host_name"
			::= { wingCfgDevl2tpv3Entry 3 }

		
		-- 1.3.6.1.4.1.1916.2.131.50.1.3.18.30.1.1.4
		wingCfgDevl2tpv3InterTunnelBridging OBJECT-TYPE
			SYNTAX TruthValue
			MAX-ACCESS read-write
			STATUS current
			DESCRIPTION
				"Enable/Disable Bridge packets between tunnels.
				
				XPath: /wing-config/device[mac=key1]/l2tpv3_inter_tunnel_bridging"
			::= { wingCfgDevl2tpv3Entry 4 }

		
-- /wing-config/device/l2tpv3_tunnel
		-- 1.3.6.1.4.1.1916.2.131.50.1.3.18.30.2
		wingCfgDevl2tpv3TunnelTable OBJECT-TYPE
			SYNTAX SEQUENCE OF WingCfgDevl2tpv3TunnelEntry
			MAX-ACCESS not-accessible
			STATUS current
			DESCRIPTION
				"/wing-config/device/l2tpv3_tunnel"
			::= { wingCfgDevl2tpv3 2 }

		
		-- 1.3.6.1.4.1.1916.2.131.50.1.3.18.30.2.1
		wingCfgDevl2tpv3TunnelEntry OBJECT-TYPE
			SYNTAX WingCfgDevl2tpv3TunnelEntry
			MAX-ACCESS not-accessible
			STATUS current
			DESCRIPTION
				"An entry in the table."
			INDEX { wingCfgDevMac, wingCfgDevl2tpv3TunnelName }
			::= { wingCfgDevl2tpv3TunnelTable 1 }

		
		WingCfgDevl2tpv3TunnelEntry ::=
			SEQUENCE { 
				wingCfgDevl2tpv3TunnelName
					WingIdentifier,
				wingCfgDevl2tpv3TunnelLocalIpAddrss
					DisplayString,
				wingCfgDevl2tpv3TunnelMtu
					Unsigned32,
				wingCfgDevl2tpv3TunnelUseTunnelPolicy
					DisplayString,
				wingCfgDevl2tpv3TunnelHostname
					DisplayString,
				wingCfgDevl2tpv3TunnelRouterId
					DisplayString
			 }

		-- 1.3.6.1.4.1.1916.2.131.50.1.3.18.30.2.1.1
		wingCfgDevl2tpv3TunnelName OBJECT-TYPE
			SYNTAX WingIdentifier
			MAX-ACCESS read-only
			STATUS current
			DESCRIPTION
				"tunnel name.
				
				XPath: /wing-config/device[mac=key1]/l2tpv3_tunnel[name=key2]/name"
			::= { wingCfgDevl2tpv3TunnelEntry 1 }

		
		-- 1.3.6.1.4.1.1916.2.131.50.1.3.18.30.2.1.3
		wingCfgDevl2tpv3TunnelLocalIpAddrss OBJECT-TYPE
			SYNTAX DisplayString
			MAX-ACCESS read-write
			STATUS current
			DESCRIPTION
				"Use this IP as local tunnel endpoint address, instead of the interface IP.
				
				XPath: /wing-config/device[mac=key1]/l2tpv3_tunnel[name=key2]/local_ip_address"
			::= { wingCfgDevl2tpv3TunnelEntry 3 }

		
		-- 1.3.6.1.4.1.1916.2.131.50.1.3.18.30.2.1.4
		wingCfgDevl2tpv3TunnelMtu OBJECT-TYPE
			SYNTAX Unsigned32
			MAX-ACCESS read-write
			STATUS current
			DESCRIPTION
				"MTU for the tunnel.
				
				XPath: /wing-config/device[mac=key1]/l2tpv3_tunnel[name=key2]/mtu"
			::= { wingCfgDevl2tpv3TunnelEntry 4 }

		
		-- 1.3.6.1.4.1.1916.2.131.50.1.3.18.30.2.1.5
		wingCfgDevl2tpv3TunnelUseTunnelPolicy OBJECT-TYPE
			SYNTAX DisplayString
			MAX-ACCESS read-write
			STATUS current
			DESCRIPTION
				"Policy used for the tunnel.
				
				XPath: /wing-config/device[mac=key1]/l2tpv3_tunnel[name=key2]/use_tunnel_policy"
			::= { wingCfgDevl2tpv3TunnelEntry 5 }

		
		-- 1.3.6.1.4.1.1916.2.131.50.1.3.18.30.2.1.6
		wingCfgDevl2tpv3TunnelHostname OBJECT-TYPE
			SYNTAX DisplayString
			MAX-ACCESS read-write
			STATUS current
			DESCRIPTION
				"Tunnel specific hostname.
				
				XPath: /wing-config/device[mac=key1]/l2tpv3_tunnel[name=key2]/tunnel_hostname"
			::= { wingCfgDevl2tpv3TunnelEntry 6 }

		
		-- 1.3.6.1.4.1.1916.2.131.50.1.3.18.30.2.1.7
		wingCfgDevl2tpv3TunnelRouterId OBJECT-TYPE
			SYNTAX DisplayString
			MAX-ACCESS read-write
			STATUS current
			DESCRIPTION
				"Local router-id
				
				XPath: /wing-config/device[mac=key1]/l2tpv3_tunnel[name=key2]/tunnel_router_id"
			::= { wingCfgDevl2tpv3TunnelEntry 7 }

		
-- /wing-config/device/l2tpv3_tunnel/peer
		-- 1.3.6.1.4.1.1916.2.131.50.1.3.18.30.3
		wingCfgDevl2tpv3TunnelPeerTable OBJECT-TYPE
			SYNTAX SEQUENCE OF WingCfgDevl2tpv3TunnelPeerEntry
			MAX-ACCESS not-accessible
			STATUS current
			DESCRIPTION
				"/wing-config/device/l2tpv3_tunnel/peer"
			::= { wingCfgDevl2tpv3 3 }

		
		-- 1.3.6.1.4.1.1916.2.131.50.1.3.18.30.3.1
		wingCfgDevl2tpv3TunnelPeerEntry OBJECT-TYPE
			SYNTAX WingCfgDevl2tpv3TunnelPeerEntry
			MAX-ACCESS not-accessible
			STATUS current
			DESCRIPTION
				"An entry in the table."
			INDEX { wingCfgDevMac, wingCfgDevl2tpv3TunnelName, wingCfgDevl2tpv3TunnelPeerId }
			::= { wingCfgDevl2tpv3TunnelPeerTable 1 }

		
		WingCfgDevl2tpv3TunnelPeerEntry ::=
			SEQUENCE { 
				wingCfgDevl2tpv3TunnelPeerId
					Unsigned32,
				wingCfgDevl2tpv3TunnelPeerIp
					DisplayString,
				wingCfgDev2tpv3TunnelPeerHostName
					DisplayString,
				wingCfgDevl2tpv3TunnelPeerRouterId
					DisplayString,
				wingCfgDevl2tpv3TunnelPeerEncapsulation
					DisplayString,
				wingCfgDevl2tpv3TunnelPeerUDPPort
					Unsigned32
			 }

		-- 1.3.6.1.4.1.1916.2.131.50.1.3.18.30.3.1.1
		wingCfgDevl2tpv3TunnelPeerId OBJECT-TYPE
			SYNTAX Unsigned32 (1..2)
			MAX-ACCESS read-only
			STATUS current
			DESCRIPTION
				"Primary peer to establish the tunnel and secondary peer for failover.
				
				XPath: /wing-config/device[mac=key1]/l2tpv3_tunnel[name=key2]/peer[peer_id=key3]/peer_id"
			::= { wingCfgDevl2tpv3TunnelPeerEntry 1 }

		
		-- 1.3.6.1.4.1.1916.2.131.50.1.3.18.30.3.1.3
		wingCfgDevl2tpv3TunnelPeerIp OBJECT-TYPE
			SYNTAX DisplayString
			MAX-ACCESS read-write
			STATUS current
			DESCRIPTION
				"Peer IP value.
				
				XPath: /wing-config/device[mac=key1]/l2tpv3_tunnel[name=key2]/peer[peer_id=key3]/ip"
			::= { wingCfgDevl2tpv3TunnelPeerEntry 3 }

		
		-- 1.3.6.1.4.1.1916.2.131.50.1.3.18.30.3.1.4
		wingCfgDev2tpv3TunnelPeerHostName OBJECT-TYPE
			SYNTAX DisplayString
			MAX-ACCESS read-write
			STATUS current
			DESCRIPTION
				"Peer hostname.
				
				XPath: /wing-config/device[mac=key1]/l2tpv3_tunnel[name=key2]/peer[peer_id=key3]/hostname"
			::= { wingCfgDevl2tpv3TunnelPeerEntry 4 }

		
		-- 1.3.6.1.4.1.1916.2.131.50.1.3.18.30.3.1.5
		wingCfgDevl2tpv3TunnelPeerRouterId OBJECT-TYPE
			SYNTAX DisplayString
			MAX-ACCESS read-write
			STATUS current
			DESCRIPTION
				"Peer router-id.
				
				XPath: /wing-config/device[mac=key1]/l2tpv3_tunnel[name=key2]/peer[peer_id=key3]/router_id"
			::= { wingCfgDevl2tpv3TunnelPeerEntry 5 }

		
		-- 1.3.6.1.4.1.1916.2.131.50.1.3.18.30.3.1.6
		wingCfgDevl2tpv3TunnelPeerEncapsulation OBJECT-TYPE
			SYNTAX DisplayString
			MAX-ACCESS read-write
			STATUS current
			DESCRIPTION
				"Peer encapsulation protocol.
				
				XPath: /wing-config/device[mac=key1]/l2tpv3_tunnel[name=key2]/peer[peer_id=key3]/encapsulation"
			::= { wingCfgDevl2tpv3TunnelPeerEntry 6 }

		
		-- 1.3.6.1.4.1.1916.2.131.50.1.3.18.30.3.1.7
		wingCfgDevl2tpv3TunnelPeerUDPPort OBJECT-TYPE
			SYNTAX Unsigned32
			MAX-ACCESS read-write
			STATUS current
			DESCRIPTION
				"Peer UDP encapsualtion port.
				
				XPath: /wing-config/device[mac=key1]/l2tpv3_tunnel[name=key2]/peer[peer_id=key3]/udpport"
			::= { wingCfgDevl2tpv3TunnelPeerEntry 7 }

		
-- /wing-config/device/l2tpv3_tunnel/session
		-- 1.3.6.1.4.1.1916.2.131.50.1.3.18.30.4
		wingCfgDevl2tpv3TunnelSessionTable OBJECT-TYPE
			SYNTAX SEQUENCE OF WingCfgDevl2tpv3TunnelSessionEntry
			MAX-ACCESS not-accessible
			STATUS current
			DESCRIPTION
				"/wing-config/device/l2tpv3_tunnel/session"
			::= { wingCfgDevl2tpv3 4 }

		
		-- 1.3.6.1.4.1.1916.2.131.50.1.3.18.30.4.1
		wingCfgDevl2tpv3TunnelSessionEntry OBJECT-TYPE
			SYNTAX WingCfgDevl2tpv3TunnelSessionEntry
			MAX-ACCESS not-accessible
			STATUS current
			DESCRIPTION
				"An entry in the table."
			INDEX { wingCfgDevMac, wingCfgDevl2tpv3TunnelName, wingCfgDevl2tpv3TunnelSessionName }
			::= { wingCfgDevl2tpv3TunnelSessionTable 1 }

		
		WingCfgDevl2tpv3TunnelSessionEntry ::=
			SEQUENCE { 
				wingCfgDevl2tpv3TunnelSessionName
					WingIdentifier,
				wingCfgDevl2tpv3TunnelSessionPseudoWireId
					Unsigned32,
				wingCfgDevl2tpv3TunnelSessionTrafficSourceType
					DisplayString,
				wingCfgDevl2tpv3TunnelSessionTrafficSourceValue
					Unsigned32,
				wingCfgDevl2tpv3TunnelSessionNativeVlan
					DisplayString
			 }

		-- 1.3.6.1.4.1.1916.2.131.50.1.3.18.30.4.1.1
		wingCfgDevl2tpv3TunnelSessionName OBJECT-TYPE
			SYNTAX WingIdentifier
			MAX-ACCESS read-only
			STATUS current
			DESCRIPTION
				"Name of the Session.
				
				XPath: /wing-config/device[mac=key1]/l2tpv3_tunnel[name=key2]/session[name=key3]/name"
			::= { wingCfgDevl2tpv3TunnelSessionEntry 1 }

		
		-- 1.3.6.1.4.1.1916.2.131.50.1.3.18.30.4.1.3
		wingCfgDevl2tpv3TunnelSessionPseudoWireId OBJECT-TYPE
			SYNTAX Unsigned32
			MAX-ACCESS read-write
			STATUS current
			DESCRIPTION
				"Pseudowire Id for the Session.
				
				XPath: /wing-config/device[mac=key1]/l2tpv3_tunnel[name=key2]/session[name=key3]/pseudowire_id"
			::= { wingCfgDevl2tpv3TunnelSessionEntry 3 }

		
		-- 1.3.6.1.4.1.1916.2.131.50.1.3.18.30.4.1.4
		wingCfgDevl2tpv3TunnelSessionTrafficSourceType OBJECT-TYPE
			SYNTAX DisplayString
			MAX-ACCESS read-write
			STATUS current
			DESCRIPTION
				"Tunneled traffic type.
				
				XPath: /wing-config/device[mac=key1]/l2tpv3_tunnel[name=key2]/session[name=key3]/traffic_source_type"
			::= { wingCfgDevl2tpv3TunnelSessionEntry 4 }

		
		-- 1.3.6.1.4.1.1916.2.131.50.1.3.18.30.4.1.5
		wingCfgDevl2tpv3TunnelSessionTrafficSourceValue OBJECT-TYPE
			SYNTAX Unsigned32
			MAX-ACCESS read-only
			STATUS current
			DESCRIPTION
				"The range of VLAN that is tunneled.
				
				XPath: /wing-config/device[mac=key1]/l2tpv3_tunnel[name=key2]/session[name=key3]/traffic_source_value"
			::= { wingCfgDevl2tpv3TunnelSessionEntry 5 }

		
		-- 1.3.6.1.4.1.1916.2.131.50.1.3.18.30.4.1.6
		wingCfgDevl2tpv3TunnelSessionNativeVlan OBJECT-TYPE
			SYNTAX DisplayString
			MAX-ACCESS read-write
			STATUS current
			DESCRIPTION
				"Vlan id which will not be tagged.
				
				XPath: /wing-config/device[mac=key1]/l2tpv3_tunnel[name=key2]/session[name=key3]/native_vlan"
			::= { wingCfgDevl2tpv3TunnelSessionEntry 6 }

		
-- /wing-config/device/l2tpv3_manual_session
		-- 1.3.6.1.4.1.1916.2.131.50.1.3.18.30.5
		wingCfgDevl2tpv3ManualSessionTable OBJECT-TYPE
			SYNTAX SEQUENCE OF WingCfgDevl2tpv3ManualSessionEntry
			MAX-ACCESS not-accessible
			STATUS current
			DESCRIPTION
				"/wing-config/device/l2tpv3_manual_session"
			::= { wingCfgDevl2tpv3 5 }

		
		-- 1.3.6.1.4.1.1916.2.131.50.1.3.18.30.5.1
		wingCfgDevl2tpv3ManualSessionEntry OBJECT-TYPE
			SYNTAX WingCfgDevl2tpv3ManualSessionEntry
			MAX-ACCESS not-accessible
			STATUS current
			DESCRIPTION
				"An entry in the table."
			INDEX { wingCfgDevMac, wingCfgDevl2tpv3ManualSessionName }
			::= { wingCfgDevl2tpv3ManualSessionTable 1 }

		
		WingCfgDevl2tpv3ManualSessionEntry ::=
			SEQUENCE { 
				wingCfgDevl2tpv3ManualSessionName
					WingIdentifier,
				wingCfgDevl2tpv3ManualSessionLocalIpAddr
					DisplayString,
				wingCfgDevl2tpv3ManualSessionPeerIp
					DisplayString,
				wingCfgDevl2tpv3ManualSessionPeerEncapsulation
					DisplayString,
				wingCfgDevl2tpv3ManualSessionPeerUDPPort
					Unsigned32,
				wingCfgDevl2tpv3ManualSessionMtu
					Unsigned32,
				wingCfgDevl2tpv3ManualSessionTrafficSource
					DisplayString,
				wingCfgDevl2tpv3ManualSessionTrafficSourceValue
					Unsigned32,
				wingCfgDevl2tpv3ManualSessionNativeVlan
					DisplayString,
				wingCfgDevl2tpv3ManualSessionLocalSessionId
					Unsigned32,
				wingCfgDevl2tpv3ManualSessionRemoteSessionId
					Unsigned32
			 }

		-- 1.3.6.1.4.1.1916.2.131.50.1.3.18.30.5.1.1
		wingCfgDevl2tpv3ManualSessionName OBJECT-TYPE
			SYNTAX WingIdentifier
			MAX-ACCESS read-only
			STATUS current
			DESCRIPTION
				"Name of the session.
				
				XPath: /wing-config/device[mac=key1]/l2tpv3_manual_session[name=key2]/name"
			::= { wingCfgDevl2tpv3ManualSessionEntry 1 }

		
		-- 1.3.6.1.4.1.1916.2.131.50.1.3.18.30.5.1.3
		wingCfgDevl2tpv3ManualSessionLocalIpAddr OBJECT-TYPE
			SYNTAX DisplayString
			MAX-ACCESS read-write
			STATUS current
			DESCRIPTION
				"Use this IP as local tunnel endpoint address, instead of the interface IP.
				
				XPath: /wing-config/device[mac=key1]/l2tpv3_manual_session[name=key2]/local_ip_address"
			::= { wingCfgDevl2tpv3ManualSessionEntry 3 }

		
		-- 1.3.6.1.4.1.1916.2.131.50.1.3.18.30.5.1.4
		wingCfgDevl2tpv3ManualSessionPeerIp OBJECT-TYPE
			SYNTAX DisplayString
			MAX-ACCESS read-write
			STATUS current
			DESCRIPTION
				"Peer IP value.
				
				XPath: /wing-config/device[mac=key1]/l2tpv3_manual_session[name=key2]/peer/ip"
			::= { wingCfgDevl2tpv3ManualSessionEntry 4 }

		
		-- 1.3.6.1.4.1.1916.2.131.50.1.3.18.30.5.1.5
		wingCfgDevl2tpv3ManualSessionPeerEncapsulation OBJECT-TYPE
			SYNTAX DisplayString
			MAX-ACCESS read-write
			STATUS current
			DESCRIPTION
				"Peer encapsulation protocol.
				
				XPath: /wing-config/device[mac=key1]/l2tpv3_manual_session[name=key2]/peer/encapsulation"
			::= { wingCfgDevl2tpv3ManualSessionEntry 5 }

		
		-- 1.3.6.1.4.1.1916.2.131.50.1.3.18.30.5.1.6
		wingCfgDevl2tpv3ManualSessionPeerUDPPort OBJECT-TYPE
			SYNTAX Unsigned32
			MAX-ACCESS read-write
			STATUS current
			DESCRIPTION
				"Peer UDP encapsualtion port.
				
				XPath: /wing-config/device[mac=key1]/l2tpv3_manual_session[name=key2]/peer/udpport"
			::= { wingCfgDevl2tpv3ManualSessionEntry 6 }

		
		-- 1.3.6.1.4.1.1916.2.131.50.1.3.18.30.5.1.7
		wingCfgDevl2tpv3ManualSessionMtu OBJECT-TYPE
			SYNTAX Unsigned32
			MAX-ACCESS read-write
			STATUS current
			DESCRIPTION
				"MTU for the tunnel.
				
				XPath: /wing-config/device[mac=key1]/l2tpv3_manual_session[name=key2]/mtu"
			::= { wingCfgDevl2tpv3ManualSessionEntry 7 }

		
		-- 1.3.6.1.4.1.1916.2.131.50.1.3.18.30.5.1.8
		wingCfgDevl2tpv3ManualSessionTrafficSource OBJECT-TYPE
			SYNTAX DisplayString
			MAX-ACCESS read-write
			STATUS current
			DESCRIPTION
				"Tunneled traffic type.
				
				XPath: /wing-config/device[mac=key1]/l2tpv3_manual_session[name=key2]/traffic_source/traffic_source_type"
			::= { wingCfgDevl2tpv3ManualSessionEntry 8 }

		
		-- 1.3.6.1.4.1.1916.2.131.50.1.3.18.30.5.1.9
		wingCfgDevl2tpv3ManualSessionTrafficSourceValue OBJECT-TYPE
			SYNTAX Unsigned32
			MAX-ACCESS read-only
			STATUS current
			DESCRIPTION
				"The range of VLAN that is tunneled.
				
				XPath: /wing-config/device[mac=key1]/l2tpv3_manual_session[name=key2]/traffic_source/traffic_source_value"
			::= { wingCfgDevl2tpv3ManualSessionEntry 9 }

		
		-- 1.3.6.1.4.1.1916.2.131.50.1.3.18.30.5.1.10
		wingCfgDevl2tpv3ManualSessionNativeVlan OBJECT-TYPE
			SYNTAX DisplayString
			MAX-ACCESS read-write
			STATUS current
			DESCRIPTION
				"Vlan id which will not be tagged.
				
				XPath: /wing-config/device[mac=key1]/l2tpv3_manual_session[name=key2]/traffic_source/native_vlan"
			::= { wingCfgDevl2tpv3ManualSessionEntry 10 }

		
		-- 1.3.6.1.4.1.1916.2.131.50.1.3.18.30.5.1.11
		wingCfgDevl2tpv3ManualSessionLocalSessionId OBJECT-TYPE
			SYNTAX Unsigned32
			MAX-ACCESS read-write
			STATUS current
			DESCRIPTION
				"Local Session Id. Max limit is platform specific.
				
				XPath: /wing-config/device[mac=key1]/l2tpv3_manual_session[name=key2]/local_session_id"
			::= { wingCfgDevl2tpv3ManualSessionEntry 11 }

		
		-- 1.3.6.1.4.1.1916.2.131.50.1.3.18.30.5.1.12
		wingCfgDevl2tpv3ManualSessionRemoteSessionId OBJECT-TYPE
			SYNTAX Unsigned32
			MAX-ACCESS read-write
			STATUS current
			DESCRIPTION
				"Remote Session Id.
				
				XPath: /wing-config/device[mac=key1]/l2tpv3_manual_session[name=key2]/remote_session_id"
			::= { wingCfgDevl2tpv3ManualSessionEntry 12 }

		
-- /wing-config/device/l2tpv3_manual_session/cookie
		-- 1.3.6.1.4.1.1916.2.131.50.1.3.18.30.6
		wingCfgDevl2tpv3ManualSessionCookieTable OBJECT-TYPE
			SYNTAX SEQUENCE OF WingCfgDevl2tpv3ManualSessionCookieEntry
			MAX-ACCESS not-accessible
			STATUS current
			DESCRIPTION
				"/wing-config/device/l2tpv3_manual_session/cookie"
			::= { wingCfgDevl2tpv3 6 }

		
		-- 1.3.6.1.4.1.1916.2.131.50.1.3.18.30.6.1
		wingCfgDevl2tpv3ManualSessionCookieEntry OBJECT-TYPE
			SYNTAX WingCfgDevl2tpv3ManualSessionCookieEntry
			MAX-ACCESS not-accessible
			STATUS current
			DESCRIPTION
				"An entry in the table."
			INDEX { wingCfgDevMac, wingCfgDevl2tpv3ManualSessionName, wingCfgDevl2tpv3ManualSessionCookieEndpoint }
			::= { wingCfgDevl2tpv3ManualSessionCookieTable 1 }

		
		WingCfgDevl2tpv3ManualSessionCookieEntry ::=
			SEQUENCE { 
				wingCfgDevl2tpv3ManualSessionCookieEndpoint
					WingIdentifier,
				wingCfgDevl2tpv3ManualSessionCookieSize
					DisplayString,
				wingCfgDevl2tpv3ManualSessionCookieVal1
					DisplayString,
				wingCfgDevl2tpv3ManualSessionCookieVal2
					DisplayString
			 }

		-- 1.3.6.1.4.1.1916.2.131.50.1.3.18.30.6.1.1
		wingCfgDevl2tpv3ManualSessionCookieEndpoint OBJECT-TYPE
			SYNTAX WingIdentifier
			MAX-ACCESS read-only
			STATUS current
			DESCRIPTION
				"Local or Remote endpoint.
				
				XPath: /wing-config/device[mac=key1]/l2tpv3_manual_session[name=key2]/cookie[endpoint=key3]/endpoint"
			::= { wingCfgDevl2tpv3ManualSessionCookieEntry 1 }

		
		-- 1.3.6.1.4.1.1916.2.131.50.1.3.18.30.6.1.3
		wingCfgDevl2tpv3ManualSessionCookieSize OBJECT-TYPE
			SYNTAX DisplayString
			MAX-ACCESS read-write
			STATUS current
			DESCRIPTION
				"Cookie Size  0 or 4 or 8.
				
				XPath: /wing-config/device[mac=key1]/l2tpv3_manual_session[name=key2]/cookie[endpoint=key3]/cookie_size"
			::= { wingCfgDevl2tpv3ManualSessionCookieEntry 3 }

		
		-- 1.3.6.1.4.1.1916.2.131.50.1.3.18.30.6.1.4
		wingCfgDevl2tpv3ManualSessionCookieVal1 OBJECT-TYPE
			SYNTAX DisplayString
			MAX-ACCESS read-write
			STATUS current
			DESCRIPTION
				"cookie value firstword.
				
				XPath: /wing-config/device[mac=key1]/l2tpv3_manual_session[name=key2]/cookie[endpoint=key3]/cookie_val_1"
			::= { wingCfgDevl2tpv3ManualSessionCookieEntry 4 }

		
		-- 1.3.6.1.4.1.1916.2.131.50.1.3.18.30.6.1.5
		wingCfgDevl2tpv3ManualSessionCookieVal2 OBJECT-TYPE
			SYNTAX DisplayString
			MAX-ACCESS read-write
			STATUS current
			DESCRIPTION
				"cookie value secondword.
				
				XPath: /wing-config/device[mac=key1]/l2tpv3_manual_session[name=key2]/cookie[endpoint=key3]/cookie_val_2"
			::= { wingCfgDevl2tpv3ManualSessionCookieEntry 5 }

		
		-- 1.3.6.1.4.1.1916.2.131.50.1.3.18.31
		wingCfgDevMcx OBJECT IDENTIFIER ::= { wingCfgDev 31 }

		
		-- 1.3.6.1.4.1.1916.2.131.50.1.3.18.31.1
		wingCfgDevMeshpointDevTable OBJECT-TYPE
			SYNTAX SEQUENCE OF WingCfgDevMeshpointDevEntry
			MAX-ACCESS not-accessible
			STATUS current
			DESCRIPTION
				"
				
				/wing-config/device/meshpoint_device"
			::= { wingCfgDevMcx 1 }

		
		-- 1.3.6.1.4.1.1916.2.131.50.1.3.18.31.1.1
		wingCfgDevMeshpointDevEntry OBJECT-TYPE
			SYNTAX WingCfgDevMeshpointDevEntry
			MAX-ACCESS not-accessible
			STATUS current
			DESCRIPTION
				"An entry in the table."
			INDEX { wingCfgDevMac, wingCfgDevMeshpointDevName }
			::= { wingCfgDevMeshpointDevTable 1 }

		
		WingCfgDevMeshpointDevEntry ::=
			SEQUENCE { 
				wingCfgDevMeshpointDevName
					WingIdentifier,
				wingCfgDevMeshpointDevIsRootDev
					DisplayString,
				wingCfgDevMeshpointDevPreferredRoot
					DisplayString,
				wingCfgDevMeshpointDevPreferredNeighbor
					MacAddress,
				wingCfgDevMeshpointDevPreferredIf
					DisplayString
			 }

		-- 1.3.6.1.4.1.1916.2.131.50.1.3.18.31.1.1.1
		wingCfgDevMeshpointDevName OBJECT-TYPE
			SYNTAX WingIdentifier
			MAX-ACCESS read-only
			STATUS current
			DESCRIPTION
				"
				
				XPath: /wing-config/device[mac=key1]/meshpoint_device[name=key2]/name"
			::= { wingCfgDevMeshpointDevEntry 1 }

		
		-- 1.3.6.1.4.1.1916.2.131.50.1.3.18.31.1.1.3
		wingCfgDevMeshpointDevIsRootDev OBJECT-TYPE
			SYNTAX DisplayString
			MAX-ACCESS read-write
			STATUS current
			DESCRIPTION
				"Overrides whether the meshpoint is a root or not
				
				Values:
				none,
				true,
				false
				
				XPath: /wing-config/device[mac=key1]/meshpoint_device[name=key2]/is_root_dev"
			DEFVAL { "none" }
			::= { wingCfgDevMeshpointDevEntry 3 }

		
		-- 1.3.6.1.4.1.1916.2.131.50.1.3.18.31.1.1.4
		wingCfgDevMeshpointDevPreferredRoot OBJECT-TYPE
			SYNTAX DisplayString
			MAX-ACCESS read-write
			STATUS current
			DESCRIPTION
				"Preferred root MAC address
				
				XPath: /wing-config/device[mac=key1]/meshpoint_device[name=key2]/preferred_root"
			::= { wingCfgDevMeshpointDevEntry 4 }

		
		-- 1.3.6.1.4.1.1916.2.131.50.1.3.18.31.1.1.5
		wingCfgDevMeshpointDevPreferredNeighbor OBJECT-TYPE
			SYNTAX MacAddress
			MAX-ACCESS read-write
			STATUS current
			DESCRIPTION
				"Preferred neighbor MAC address
				
				XPath: /wing-config/device[mac=key1]/meshpoint_device[name=key2]/preferred_neighbor"
			::= { wingCfgDevMeshpointDevEntry 5 }

		
		-- 1.3.6.1.4.1.1916.2.131.50.1.3.18.31.1.1.6
		wingCfgDevMeshpointDevPreferredIf OBJECT-TYPE
			SYNTAX DisplayString
			MAX-ACCESS read-write
			STATUS current
			DESCRIPTION
				"Preferred interface
				
				Values:
				none,
				2.4GHz,
				5GHz
				
				XPath: /wing-config/device[mac=key1]/meshpoint_device[name=key2]/preferred_interface"
			DEFVAL { "none" }
			::= { wingCfgDevMeshpointDevEntry 6 }

		
-- /wing-config/management_policy
		-- 1.3.6.1.4.1.1916.2.131.50.1.3.19
		wingCfgMgmt OBJECT IDENTIFIER ::= { wingConfig 19 }

		
		-- 1.3.6.1.4.1.1916.2.131.50.1.3.19.1
		wingCfgMgmtTable OBJECT-TYPE
			SYNTAX SEQUENCE OF WingCfgMgmtEntry
			MAX-ACCESS not-accessible
			STATUS current
			DESCRIPTION
				"
				
				/wing-config/management_policy"
			::= { wingCfgMgmt 1 }

		
		-- 1.3.6.1.4.1.1916.2.131.50.1.3.19.1.1
		wingCfgMgmtEntry OBJECT-TYPE
			SYNTAX WingCfgMgmtEntry
			MAX-ACCESS not-accessible
			STATUS current
			DESCRIPTION
				"An entry in the table."
			INDEX { wingCfgMgmtName }
			::= { wingCfgMgmtTable 1 }

		
		WingCfgMgmtEntry ::=
			SEQUENCE { 
				wingCfgMgmtName
					WingIdentifier,
				wingCfgMgmtTelnetEnable
					TruthValue,
				wingCfgMgmtTelnetPort
					Unsigned32,
				wingCfgMgmtHttpEnable
					TruthValue,
				wingCfgMgmtHttpsEnable
					TruthValue,
				wingCfgMgmtSshEnable
					TruthValue,
				wingCfgMgmtSshPort
					Unsigned32,
				wingCfgMgmtBannerMotd
					DisplayString
			 }

		-- 1.3.6.1.4.1.1916.2.131.50.1.3.19.1.1.1
		wingCfgMgmtName OBJECT-TYPE
			SYNTAX WingIdentifier
			MAX-ACCESS read-only
			STATUS current
			DESCRIPTION
				"
				
				XPath: /wing-config/management_policy[name=key1]/name"
			::= { wingCfgMgmtEntry 1 }

		
		-- 1.3.6.1.4.1.1916.2.131.50.1.3.19.1.1.3
		wingCfgMgmtTelnetEnable OBJECT-TYPE
			SYNTAX TruthValue
			MAX-ACCESS read-write
			STATUS current
			DESCRIPTION
				"
				
				XPath: /wing-config/management_policy[name=key1]/telnet/enable"
			DEFVAL { false }
			::= { wingCfgMgmtEntry 3 }

		
		-- 1.3.6.1.4.1.1916.2.131.50.1.3.19.1.1.4
		wingCfgMgmtTelnetPort OBJECT-TYPE
			SYNTAX Unsigned32 (1..65535)
			MAX-ACCESS read-write
			STATUS current
			DESCRIPTION
				"
				
				XPath: /wing-config/management_policy[name=key1]/telnet/port"
			DEFVAL { 23 }
			::= { wingCfgMgmtEntry 4 }

		
		-- 1.3.6.1.4.1.1916.2.131.50.1.3.19.1.1.5
		wingCfgMgmtHttpEnable OBJECT-TYPE
			SYNTAX TruthValue
			MAX-ACCESS read-write
			STATUS current
			DESCRIPTION
				"
				
				XPath: /wing-config/management_policy[name=key1]/http/enable"
			DEFVAL { true }
			::= { wingCfgMgmtEntry 5 }

		
		-- 1.3.6.1.4.1.1916.2.131.50.1.3.19.1.1.6
		wingCfgMgmtHttpsEnable OBJECT-TYPE
			SYNTAX TruthValue
			MAX-ACCESS read-write
			STATUS current
			DESCRIPTION
				"
				
				XPath: /wing-config/management_policy[name=key1]/https"
			DEFVAL { false }
			::= { wingCfgMgmtEntry 6 }

		
		-- 1.3.6.1.4.1.1916.2.131.50.1.3.19.1.1.7
		wingCfgMgmtSshEnable OBJECT-TYPE
			SYNTAX TruthValue
			MAX-ACCESS read-write
			STATUS current
			DESCRIPTION
				"
				
				XPath: /wing-config/management_policy[name=key1]/ssh/enable"
			DEFVAL { false }
			::= { wingCfgMgmtEntry 7 }

		
		-- 1.3.6.1.4.1.1916.2.131.50.1.3.19.1.1.8
		wingCfgMgmtSshPort OBJECT-TYPE
			SYNTAX Unsigned32 (1..65535)
			MAX-ACCESS read-write
			STATUS current
			DESCRIPTION
				"
				
				XPath: /wing-config/management_policy[name=key1]/ssh/port"
			DEFVAL { 22 }
			::= { wingCfgMgmtEntry 8 }

		
		-- 1.3.6.1.4.1.1916.2.131.50.1.3.19.1.1.9
		wingCfgMgmtBannerMotd OBJECT-TYPE
			SYNTAX DisplayString (SIZE (0..128))
			MAX-ACCESS read-write
			STATUS current
			DESCRIPTION
				"A message-of-the-day banner displayed to the user on logging into the system over the CLI
				
				XPath: /wing-config/management_policy[name=key1]/banner_motd"
			DEFVAL { "" }
			::= { wingCfgMgmtEntry 9 }

		
-- /wing-config/management_policy/snmp
		-- 1.3.6.1.4.1.1916.2.131.50.1.3.19.2
		wingCfgMgmtSnmp OBJECT IDENTIFIER ::= { wingCfgMgmt 2 }

		
		-- 1.3.6.1.4.1.1916.2.131.50.1.3.19.2.1
		wingCfgMgmtSnmpTable OBJECT-TYPE
			SYNTAX SEQUENCE OF WingCfgMgmtSnmpEntry
			MAX-ACCESS not-accessible
			STATUS current
			DESCRIPTION
				"
				
				/wing-config/management_policy/snmp"
			::= { wingCfgMgmtSnmp 1 }

		
		-- 1.3.6.1.4.1.1916.2.131.50.1.3.19.2.1.1
		wingCfgMgmtSnmpEntry OBJECT-TYPE
			SYNTAX WingCfgMgmtSnmpEntry
			MAX-ACCESS not-accessible
			STATUS current
			DESCRIPTION
				"An entry in the table."
			INDEX { wingCfgMgmtName }
			::= { wingCfgMgmtSnmpTable 1 }

		
		WingCfgMgmtSnmpEntry ::=
			SEQUENCE { 
				wingCfgMgmtSnmpV1Enable
					TruthValue,
				wingCfgMgmtSnmpV2Enable
					TruthValue,
				wingCfgMgmtSnmpV3Enable
					TruthValue,
				wingCfgMgmtSnmpTrapEnable
					TruthValue
			 }

		-- 1.3.6.1.4.1.1916.2.131.50.1.3.19.2.1.1.1
		wingCfgMgmtSnmpV1Enable OBJECT-TYPE
			SYNTAX TruthValue
			MAX-ACCESS read-only
			STATUS current
			DESCRIPTION
				"Enable SNMP version v1
				
				XPath: /wing-config/management_policy[name=key1]/snmp/snmpv1"
			DEFVAL { true }
			::= { wingCfgMgmtSnmpEntry 1 }

		
		-- 1.3.6.1.4.1.1916.2.131.50.1.3.19.2.1.1.2
		wingCfgMgmtSnmpV2Enable OBJECT-TYPE
			SYNTAX TruthValue
			MAX-ACCESS read-only
			STATUS current
			DESCRIPTION
				"Enable SNMP version v2
				
				XPath: /wing-config/management_policy[name=key1]/snmp/snmpv2"
			DEFVAL { true }
			::= { wingCfgMgmtSnmpEntry 2 }

		
		-- 1.3.6.1.4.1.1916.2.131.50.1.3.19.2.1.1.3
		wingCfgMgmtSnmpV3Enable OBJECT-TYPE
			SYNTAX TruthValue
			MAX-ACCESS read-only
			STATUS current
			DESCRIPTION
				"Enable SNMP version v3
				
				XPath: /wing-config/management_policy[name=key1]/snmp/snmpv3"
			DEFVAL { true }
			::= { wingCfgMgmtSnmpEntry 3 }

		
		-- 1.3.6.1.4.1.1916.2.131.50.1.3.19.2.1.1.4
		wingCfgMgmtSnmpTrapEnable OBJECT-TYPE
			SYNTAX TruthValue
			MAX-ACCESS read-only
			STATUS current
			DESCRIPTION
				"Enable trap generation
				
				XPath: /wing-config/management_policy[name=key1]/snmp/trap/enable_traps"
			DEFVAL { false }
			::= { wingCfgMgmtSnmpEntry 4 }

		
		-- 1.3.6.1.4.1.1916.2.131.50.1.3.19.2.2
		wingCfgMgmtSnmpCommunityTable OBJECT-TYPE
			SYNTAX SEQUENCE OF WingCfgMgmtSnmpCommunityEntry
			MAX-ACCESS not-accessible
			STATUS current
			DESCRIPTION
				"
				
				/wing-config/management_policy/snmp/community_string"
			::= { wingCfgMgmtSnmp 2 }

		
		-- 1.3.6.1.4.1.1916.2.131.50.1.3.19.2.2.1
		wingCfgMgmtSnmpCommunityEntry OBJECT-TYPE
			SYNTAX WingCfgMgmtSnmpCommunityEntry
			MAX-ACCESS not-accessible
			STATUS current
			DESCRIPTION
				"An entry in the table."
			INDEX { wingCfgMgmtName, wingCfgMgmtSnmpCommunityName }
			::= { wingCfgMgmtSnmpCommunityTable 1 }

		
		WingCfgMgmtSnmpCommunityEntry ::=
			SEQUENCE { 
				wingCfgMgmtSnmpCommunityName
					WingIdentifier,
				wingCfgMgmtSnmpCommunityAccess
					DisplayString
			 }

		-- 1.3.6.1.4.1.1916.2.131.50.1.3.19.2.2.1.1
		wingCfgMgmtSnmpCommunityName OBJECT-TYPE
			SYNTAX WingIdentifier
			MAX-ACCESS read-only
			STATUS current
			DESCRIPTION
				"SNMP community string
				
				XPath: /wing-config/management_policy[name=key1]/snmp/community_string[name=key2]/name"
			::= { wingCfgMgmtSnmpCommunityEntry 1 }

		
		-- 1.3.6.1.4.1.1916.2.131.50.1.3.19.2.2.1.3
		wingCfgMgmtSnmpCommunityAccess OBJECT-TYPE
			SYNTAX DisplayString
			MAX-ACCESS read-write
			STATUS current
			DESCRIPTION
				"Access privilege with this community string
				
				Values:
				ro
				rw
				
				XPath: /wing-config/management_policy[name=key1]/snmp/community_string[name=key2]/access"
			DEFVAL { "ro" }
			::= { wingCfgMgmtSnmpCommunityEntry 3 }

		
		-- 1.3.6.1.4.1.1916.2.131.50.1.3.19.2.3
		wingCfgMgmtSnmpUsmUserTable OBJECT-TYPE
			SYNTAX SEQUENCE OF WingCfgMgmtSnmpUsmUserEntry
			MAX-ACCESS not-accessible
			STATUS current
			DESCRIPTION
				"
				
				/wing-config/management_policy/snmp/usm"
			::= { wingCfgMgmtSnmp 3 }

		
		-- 1.3.6.1.4.1.1916.2.131.50.1.3.19.2.3.1
		wingCfgMgmtSnmpUsmUserEntry OBJECT-TYPE
			SYNTAX WingCfgMgmtSnmpUsmUserEntry
			MAX-ACCESS not-accessible
			STATUS current
			DESCRIPTION
				"An entry in the table."
			INDEX { wingCfgMgmtName, wingCfgMgmtSnmpUsmUserName }
			::= { wingCfgMgmtSnmpUsmUserTable 1 }

		
		WingCfgMgmtSnmpUsmUserEntry ::=
			SEQUENCE { 
				wingCfgMgmtSnmpUsmUserName
					WingIdentifier,
				wingCfgMgmtSnmpUsmUserAuthentication
					DisplayString,
				wingCfgMgmtSnmpUsmUserEncryption
					DisplayString,
				wingCfgMgmtSnmpUsmUserPassword
					DisplayString
			 }

		-- 1.3.6.1.4.1.1916.2.131.50.1.3.19.2.3.1.1
		wingCfgMgmtSnmpUsmUserName OBJECT-TYPE
			SYNTAX WingIdentifier
			MAX-ACCESS read-only
			STATUS current
			DESCRIPTION
				"SNMPv3 security user name
				
				Values:
				snmpmanager
				snmpoperator
				snmptrap
				
				XPath: /wing-config/management_policy[name=key1]/snmp/usm[user_name=key2]/user_name"
			::= { wingCfgMgmtSnmpUsmUserEntry 1 }

		
		-- 1.3.6.1.4.1.1916.2.131.50.1.3.19.2.3.1.3
		wingCfgMgmtSnmpUsmUserAuthentication OBJECT-TYPE
			SYNTAX DisplayString
			MAX-ACCESS read-write
			STATUS current
			DESCRIPTION
				"Authentication protocol. The default is HMAC-MD5.
				
				Values:
				md5
				
				XPath: /wing-config/management_policy[name=key1]/snmp/usm[user_name=key2]/authentication"
			DEFVAL { "md5" }
			::= { wingCfgMgmtSnmpUsmUserEntry 3 }

		
		-- 1.3.6.1.4.1.1916.2.131.50.1.3.19.2.3.1.4
		wingCfgMgmtSnmpUsmUserEncryption OBJECT-TYPE
			SYNTAX DisplayString
			MAX-ACCESS read-write
			STATUS current
			DESCRIPTION
				"Privacy protocol. The default is CBC-DES.
				
				Values:
				des
				
				XPath: /wing-config/management_policy[name=key1]/snmp/usm[user_name=key2]/encryption"
			DEFVAL { "des" }
			::= { wingCfgMgmtSnmpUsmUserEntry 4 }

		
		-- 1.3.6.1.4.1.1916.2.131.50.1.3.19.2.3.1.5
		wingCfgMgmtSnmpUsmUserPassword OBJECT-TYPE
			SYNTAX DisplayString (SIZE (8..64))
			MAX-ACCESS read-write
			STATUS current
			DESCRIPTION
				"Password for authentication and privacy protocols
				
				XPath: /wing-config/management_policy[name=key1]/snmp/usm[user_name=key2]/password"
			::= { wingCfgMgmtSnmpUsmUserEntry 5 }

		
		-- 1.3.6.1.4.1.1916.2.131.50.1.3.19.5
		wingCfgMgmtAdminTable OBJECT-TYPE
			SYNTAX SEQUENCE OF WingCfgMgmtAdminEntry
			MAX-ACCESS not-accessible
			STATUS current
			DESCRIPTION
				"
				
				/wing-config/management_policy/admin"
			::= { wingCfgMgmt 5 }

		
		-- 1.3.6.1.4.1.1916.2.131.50.1.3.19.5.1
		wingCfgMgmtAdminEntry OBJECT-TYPE
			SYNTAX WingCfgMgmtAdminEntry
			MAX-ACCESS not-accessible
			STATUS current
			DESCRIPTION
				"An entry in the table."
			INDEX { wingCfgMgmtName, wingCfgMgmtAdminUsername }
			::= { wingCfgMgmtAdminTable 1 }

		
		WingCfgMgmtAdminEntry ::=
			SEQUENCE { 
				wingCfgMgmtAdminUsername
					WingIdentifier,
				wingCfgMgmtAdminPassword
					DisplayString,
				wingCfgMgmtAdminRole
					DisplayString
			 }

		-- 1.3.6.1.4.1.1916.2.131.50.1.3.19.5.1.1
		wingCfgMgmtAdminUsername OBJECT-TYPE
			SYNTAX WingIdentifier
			MAX-ACCESS read-only
			STATUS current
			DESCRIPTION
				"
				
				XPath: /wing-config/management_policy[name=key1]/admin[username=key2]/username"
			::= { wingCfgMgmtAdminEntry 1 }

		
		-- 1.3.6.1.4.1.1916.2.131.50.1.3.19.5.1.3
		wingCfgMgmtAdminPassword OBJECT-TYPE
			SYNTAX DisplayString (SIZE (1..63))
			MAX-ACCESS read-write
			STATUS current
			DESCRIPTION
				"
				
				XPath: /wing-config/management_policy[name=key1]/admin[username=key2]/password"
			::= { wingCfgMgmtAdminEntry 3 }

		
		-- 1.3.6.1.4.1.1916.2.131.50.1.3.19.5.1.4
		wingCfgMgmtAdminRole OBJECT-TYPE
			SYNTAX DisplayString
			MAX-ACCESS read-write
			STATUS current
			DESCRIPTION
				"
				
				Values:
				system-admin
				network-admin
				security-admin
				monitor
				helpdesk
				web-user-admin
				
				XPath: /wing-config/management_policy[name=key1]/admin[username=key2]/role"
			DEFVAL { "superuser" }
			::= { wingCfgMgmtAdminEntry 4 }

		
-- /wing-config/routing_policy
		-- 1.3.6.1.4.1.1916.2.131.50.1.3.31
		wingCfgRoute OBJECT IDENTIFIER ::= { wingConfig 31 }

		
		-- 1.3.6.1.4.1.1916.2.131.50.1.3.31.1
		wingCfgRouteTable OBJECT-TYPE
			SYNTAX SEQUENCE OF WingCfgRouteEntry
			MAX-ACCESS not-accessible
			STATUS current
			DESCRIPTION
				"
				
				/wing-config/routing_policy"
			::= { wingCfgRoute 1 }

		
		-- 1.3.6.1.4.1.1916.2.131.50.1.3.31.1.1
		wingCfgRouteEntry OBJECT-TYPE
			SYNTAX WingCfgRouteEntry
			MAX-ACCESS not-accessible
			STATUS current
			DESCRIPTION
				"An entry in the table."
			INDEX { wingCfgRouteName }
			::= { wingCfgRouteTable 1 }

		
		WingCfgRouteEntry ::=
			SEQUENCE { 
				wingCfgRouteName
					WingIdentifier,
				wingCfgRouteLogging
					TruthValue,
				wingCfgRouteLocalPbr
					TruthValue,
				wingCfgRouteUseCrm
					TruthValue
			 }

		-- 1.3.6.1.4.1.1916.2.131.50.1.3.31.1.1.1
		wingCfgRouteName OBJECT-TYPE
			SYNTAX WingIdentifier
			MAX-ACCESS read-only
			STATUS current
			DESCRIPTION
				"Name of the Route Map
				
				XPath: /wing-config/routing_policy[name=key1]/name"
			::= { wingCfgRouteEntry 1 }

		
		-- 1.3.6.1.4.1.1916.2.131.50.1.3.31.1.1.3
		wingCfgRouteLogging OBJECT-TYPE
			SYNTAX TruthValue
			MAX-ACCESS read-write
			STATUS current
			DESCRIPTION
				"Enable / disable logging for this Route Map.
				
				XPath: /wing-config/routing_policy[name=key1]/logging"
			DEFVAL { false }
			::= { wingCfgRouteEntry 3 }

		
		-- 1.3.6.1.4.1.1916.2.131.50.1.3.31.1.1.4
		wingCfgRouteLocalPbr OBJECT-TYPE
			SYNTAX TruthValue
			MAX-ACCESS read-write
			STATUS current
			DESCRIPTION
				"Enable/Disable Policy Based Routing for packets generated by the device.
				
				XPath: /wing-config/routing_policy[name=key1]/local_pbr"
			DEFVAL { true }
			::= { wingCfgRouteEntry 4 }

		
		-- 1.3.6.1.4.1.1916.2.131.50.1.3.31.1.1.5
		wingCfgRouteUseCrm OBJECT-TYPE
			SYNTAX TruthValue
			MAX-ACCESS read-write
			STATUS current
			DESCRIPTION
				"Use Critical Resource Monitoring to monitor the status of a link. This will determine the state of next-hop in Route Map, via which Critical Resources are being monitored. Link monitoring is used for failover to a secondary next-hop
				
				XPath: /wing-config/routing_policy[name=key1]/use_crm"
			DEFVAL { true }
			::= { wingCfgRouteEntry 5 }

		
		-- 1.3.6.1.4.1.1916.2.131.50.1.3.31.2
		wingCfgRouteMapTable OBJECT-TYPE
			SYNTAX SEQUENCE OF WingCfgRouteMapEntry
			MAX-ACCESS not-accessible
			STATUS current
			DESCRIPTION
				"
				
				/wing-config/routing_policy"
			::= { wingCfgRoute 2 }

		
		-- 1.3.6.1.4.1.1916.2.131.50.1.3.31.2.1
		wingCfgRouteMapEntry OBJECT-TYPE
			SYNTAX WingCfgRouteMapEntry
			MAX-ACCESS not-accessible
			STATUS current
			DESCRIPTION
				"An entry in the table."
			INDEX { wingCfgRouteName, wingCfgRouteMapPrecedence }
			::= { wingCfgRouteMapTable 1 }

		
		WingCfgRouteMapEntry ::=
			SEQUENCE { 
				wingCfgRouteMapPrecedence
					Unsigned32,
				wingCfgRouteMapMatchClauseAcl
					WingIdentifier,
				wingCfgRouteMapMatchClauseDscp
					Unsigned32,
				wingCfgRouteMapMatchClauseWlan
					WingIdentifier,
				wingCfgRouteMapRolePolicy
					WingIdentifier,
				wingCfgRouteMapUserRole
					WingIdentifier,
				wingCfgRouteMapMatchClauseIncomingInterface
					DisplayString,
				wingCfgRouteMapNextHop1
					DisplayString,
				wingCfgRouteMapNextHop2
					DisplayString,
				wingCfgRouteMapSetClauseDefaultNextHop
					DisplayString,
				wingCfgRouteMapSetClauseFallback
					TruthValue,
				wingCfgRouteMapSetClauseMarkDscp
					Unsigned32
			 }

		-- 1.3.6.1.4.1.1916.2.131.50.1.3.31.2.1.1
		wingCfgRouteMapPrecedence OBJECT-TYPE
			SYNTAX Unsigned32 (1..100)
			MAX-ACCESS read-only
			STATUS current
			DESCRIPTION
				"
				
				XPath: /wing-config/routing_policy[name=key1]/route_map[precedence=key2]/precedence"
			::= { wingCfgRouteMapEntry 1 }

		
		-- 1.3.6.1.4.1.1916.2.131.50.1.3.31.2.1.3
		wingCfgRouteMapMatchClauseAcl OBJECT-TYPE
			SYNTAX WingIdentifier
			MAX-ACCESS read-write
			STATUS current
			DESCRIPTION
				"IP access list to be used as match criterion for the route map.
				
				XPath: /wing-config/routing_policy[name=key1]/route_map[precedence=key2]/match_clause_acl"
			::= { wingCfgRouteMapEntry 3 }

		
		-- 1.3.6.1.4.1.1916.2.131.50.1.3.31.2.1.4
		wingCfgRouteMapMatchClauseDscp OBJECT-TYPE
			SYNTAX Unsigned32 (0..63)
			MAX-ACCESS read-write
			STATUS current
			DESCRIPTION
				"IP DSCP value to be used as match criterion for the route map.
				
				XPath: /wing-config/routing_policy[name=key1]/route_map[precedence=key2]/match_clause_dscp"
			::= { wingCfgRouteMapEntry 4 }

		
		-- 1.3.6.1.4.1.1916.2.131.50.1.3.31.2.1.5
		wingCfgRouteMapMatchClauseWlan OBJECT-TYPE
			SYNTAX WingIdentifier
			MAX-ACCESS read-write
			STATUS current
			DESCRIPTION
				"WLAN to be used as match criterion for the route map.
				
				XPath: /wing-config/routing_policy[name=key1]/route_map[precedence=key2]/match_clause_wlan"
			::= { wingCfgRouteMapEntry 5 }

		
		-- 1.3.6.1.4.1.1916.2.131.50.1.3.31.2.1.6
		wingCfgRouteMapRolePolicy OBJECT-TYPE
			SYNTAX WingIdentifier
			MAX-ACCESS read-write
			STATUS current
			DESCRIPTION
				"
				
				XPath: /wing-config/routing_policy[name=key1]/route_map[precedence=key2]/match_clause_role/role_policy"
			::= { wingCfgRouteMapEntry 6 }

		
		-- 1.3.6.1.4.1.1916.2.131.50.1.3.31.2.1.7
		wingCfgRouteMapUserRole OBJECT-TYPE
			SYNTAX WingIdentifier
			MAX-ACCESS read-write
			STATUS current
			DESCRIPTION
				"
				
				XPath: /wing-config/routing_policy[name=key1]/route_map[precedence=key2]/match_clause_role/user_role"
			::= { wingCfgRouteMapEntry 7 }

		
		-- 1.3.6.1.4.1.1916.2.131.50.1.3.31.2.1.8
		wingCfgRouteMapMatchClauseIncomingInterface OBJECT-TYPE
			SYNTAX DisplayString
			MAX-ACCESS read-write
			STATUS current
			DESCRIPTION
				"Name of the interface on which the packet is received. This can be a VLAN or a WWAN interface
				
				XPath: /wing-config/routing_policy[name=key1]/route_map[precedence=key2]/match_clause_incoming_interface"
			::= { wingCfgRouteMapEntry 8 }

		
		-- 1.3.6.1.4.1.1916.2.131.50.1.3.31.2.1.9
		wingCfgRouteMapNextHop1 OBJECT-TYPE
			SYNTAX DisplayString
			MAX-ACCESS read-write
			STATUS current
			DESCRIPTION
				"
				
				XPath: /wing-config/routing_policy[name=key1]/route_map[precedence=key2]/set_clause_next_hop/next_hop1"
			::= { wingCfgRouteMapEntry 9 }

		
		-- 1.3.6.1.4.1.1916.2.131.50.1.3.31.2.1.11
		wingCfgRouteMapNextHop2 OBJECT-TYPE
			SYNTAX DisplayString
			MAX-ACCESS read-write
			STATUS current
			DESCRIPTION
				"
				
				XPath: /wing-config/routing_policy[name=key1]/route_map[precedence=key2]/set_clause_next_hop/next_hop2"
			::= { wingCfgRouteMapEntry 11 }

		
		-- 1.3.6.1.4.1.1916.2.131.50.1.3.31.2.1.13
		wingCfgRouteMapSetClauseDefaultNextHop OBJECT-TYPE
			SYNTAX DisplayString
			MAX-ACCESS read-write
			STATUS current
			DESCRIPTION
				"
				
				XPath: /wing-config/routing_policy[name=key1]/route_map[precedence=key2]/set_clause_default_next_hop"
			::= { wingCfgRouteMapEntry 13 }

		
		-- 1.3.6.1.4.1.1916.2.131.50.1.3.31.2.1.14
		wingCfgRouteMapSetClauseFallback OBJECT-TYPE
			SYNTAX TruthValue
			MAX-ACCESS read-write
			STATUS current
			DESCRIPTION
				"Fallback to destination based routing if none of the next-hops are reachable
				
				XPath: /wing-config/routing_policy[name=key1]/route_map[precedence=key2]/set_clause_fallback"
			DEFVAL { true }
			::= { wingCfgRouteMapEntry 14 }

		
		-- 1.3.6.1.4.1.1916.2.131.50.1.3.31.2.1.15
		wingCfgRouteMapSetClauseMarkDscp OBJECT-TYPE
			SYNTAX Unsigned32 (0..63)
			MAX-ACCESS read-write
			STATUS current
			DESCRIPTION
				"
				
				XPath: /wing-config/routing_policy[name=key1]/route_map[precedence=key2]/set_clause_mark_dscp"
			::= { wingCfgRouteMapEntry 15 }

		
		-- 1.3.6.1.4.1.1916.2.131.50.1.3.32
		wingCfgl2tpv3Policy OBJECT IDENTIFIER ::= { wingConfig 32 }

		
		-- 1.3.6.1.4.1.1916.2.131.50.1.3.32.1
		wingCfgl2tpv3PolicyTable OBJECT-TYPE
			SYNTAX SEQUENCE OF WingCfgl2tpv3PolicyEntry
			MAX-ACCESS not-accessible
			STATUS current
			DESCRIPTION
				"wing Cfg l2tpv3 Policy Table"
			::= { wingCfgl2tpv3Policy 1 }

		
		-- 1.3.6.1.4.1.1916.2.131.50.1.3.32.1.1
		wingCfgl2tpv3PolicyEntry OBJECT-TYPE
			SYNTAX WingCfgl2tpv3PolicyEntry
			MAX-ACCESS not-accessible
			STATUS current
			DESCRIPTION
				"An entry in the table."
			INDEX { wingCfgl2tpv3PolicyName }
			::= { wingCfgl2tpv3PolicyTable 1 }

		
		WingCfgl2tpv3PolicyEntry ::=
			SEQUENCE { 
				wingCfgl2tpv3PolicyName
					WingIdentifier,
				wingCfgl2tpv3PolicyHelloInterval
					Unsigned32,
				wingCfgl2tpv3PolicyRetryAttempts
					Unsigned32,
				wingCfgl2tpv3PolicyRetryInterval
					Unsigned32,
				wingCfgl2tpv3PolicyHideAVPs
					TruthValue,
				wingCfgl2tpv3PolicyCookieSize
					DisplayString,
				wingCfgl2tpv3PolicyRxWindowSize
					Unsigned32,
				wingCfgl2tpv3PolicyTxWindowSize
					Unsigned32,
				wingCfgl2tpv3PolicySequencingRequired
					TruthValue,
				wingCfgl2tpv3PolicyReconnectInterval
					Unsigned32,
				wingCfgl2tpv3PolicyReconnectAttempts
					Unsigned32
			 }

		-- 1.3.6.1.4.1.1916.2.131.50.1.3.32.1.1.1
		wingCfgl2tpv3PolicyName OBJECT-TYPE
			SYNTAX WingIdentifier (SIZE (1..31))
			MAX-ACCESS read-only
			STATUS current
			DESCRIPTION
				"l2tpv3 Policy Name.
				
				XPath: /wing-config/l2tpv3_policy[name=key1]/name"
			::= { wingCfgl2tpv3PolicyEntry 1 }

		
		-- 1.3.6.1.4.1.1916.2.131.50.1.3.32.1.1.3
		wingCfgl2tpv3PolicyHelloInterval OBJECT-TYPE
			SYNTAX Unsigned32 (1..3600)
			MAX-ACCESS read-write
			STATUS current
			DESCRIPTION
				"Time in seconds for sending Hello Keepalive packets.
				
				XPath: /wing-config/l2tpv3_policy[name=key1]/hello_interval"
			::= { wingCfgl2tpv3PolicyEntry 3 }

		
		-- 1.3.6.1.4.1.1916.2.131.50.1.3.32.1.1.4
		wingCfgl2tpv3PolicyRetryAttempts OBJECT-TYPE
			SYNTAX Unsigned32 (1..10)
			MAX-ACCESS read-write
			STATUS current
			DESCRIPTION
				"Number tries before declaring a peer dead.
				
				XPath: /wing-config/l2tpv3_policy[name=key1]/retry_attempts"
			::= { wingCfgl2tpv3PolicyEntry 4 }

		
		-- 1.3.6.1.4.1.1916.2.131.50.1.3.32.1.1.5
		wingCfgl2tpv3PolicyRetryInterval OBJECT-TYPE
			SYNTAX Unsigned32 (1..250)
			MAX-ACCESS read-write
			STATUS current
			DESCRIPTION
				"Time between successive retries.
				
				XPath: /wing-config/l2tpv3_policy[name=key1]/retry_interval"
			::= { wingCfgl2tpv3PolicyEntry 5 }

		
		-- 1.3.6.1.4.1.1916.2.131.50.1.3.32.1.1.6
		wingCfgl2tpv3PolicyHideAVPs OBJECT-TYPE
			SYNTAX TruthValue
			MAX-ACCESS read-write
			STATUS current
			DESCRIPTION
				"Hide the AVPs.
				
				XPath: /wing-config/l2tpv3_policy[name=key1]/hide_avps"
			::= { wingCfgl2tpv3PolicyEntry 6 }

		
		-- 1.3.6.1.4.1.1916.2.131.50.1.3.32.1.1.7
		wingCfgl2tpv3PolicyCookieSize OBJECT-TYPE
			SYNTAX DisplayString
			MAX-ACCESS read-write
			STATUS current
			DESCRIPTION
				"Size of the Cookies in the session.

                                 Values:
                                 0,
                                 4,
                                 8  
				
				XPath: /wing-config/l2tpv3_policy[name=key1]/cookie_size"
			::= { wingCfgl2tpv3PolicyEntry 7 }

		
		-- 1.3.6.1.4.1.1916.2.131.50.1.3.32.1.1.8
		wingCfgl2tpv3PolicyRxWindowSize OBJECT-TYPE
			SYNTAX Unsigned32 (1..15)
			MAX-ACCESS read-write
			STATUS current
			DESCRIPTION
				"Rx Window size.
				
				XPath: /wing-config/l2tpv3_policy[name=key1]/rx_window_size"
			::= { wingCfgl2tpv3PolicyEntry 8 }

		
		-- 1.3.6.1.4.1.1916.2.131.50.1.3.32.1.1.9
		wingCfgl2tpv3PolicyTxWindowSize OBJECT-TYPE
			SYNTAX Unsigned32 (1..15)
			MAX-ACCESS read-write
			STATUS current
			DESCRIPTION
				"Tx Window size.
				
				XPath: /wing-config/l2tpv3_policy[name=key1]/tx_window_size"
			::= { wingCfgl2tpv3PolicyEntry 9 }

		
		-- 1.3.6.1.4.1.1916.2.131.50.1.3.32.1.1.10
		wingCfgl2tpv3PolicySequencingRequired OBJECT-TYPE
			SYNTAX TruthValue
			MAX-ACCESS read-write
			STATUS current
			DESCRIPTION
				"Sequence the packets receive/sent.
				
				XPath: /wing-config/l2tpv3_policy[name=key1]/sequencing_required"
			::= { wingCfgl2tpv3PolicyEntry 10 }

		
		-- 1.3.6.1.4.1.1916.2.131.50.1.3.32.1.1.11
		wingCfgl2tpv3PolicyReconnectInterval OBJECT-TYPE
			SYNTAX Unsigned32 (1..3600)
			MAX-ACCESS read-write
			STATUS current
			DESCRIPTION
				"Time between two sucessive retry attempts.
				
				XPath: /wing-config/l2tpv3_policy[name=key1]/reconnect_interval"
			::= { wingCfgl2tpv3PolicyEntry 11 }

		
		-- 1.3.6.1.4.1.1916.2.131.50.1.3.32.1.1.12
		wingCfgl2tpv3PolicyReconnectAttempts OBJECT-TYPE
			SYNTAX Unsigned32 (0..250)
			MAX-ACCESS read-write
			STATUS current
			DESCRIPTION
				"Number of reconnect to peer attempts, 0: try to reconnect for ever.
				
				XPath: /wing-config/l2tpv3_policy[name=key1]/reconnect_attempts"
			::= { wingCfgl2tpv3PolicyEntry 12 }

		
		-- 1.3.6.1.4.1.1916.2.131.50.1.3.33
		wingCfgLegacyAp OBJECT IDENTIFIER ::= { wingConfig 33 }

		
		-- 1.3.6.1.4.1.1916.2.131.50.1.3.33.1
		wingCfgLegacyApTable OBJECT-TYPE
			SYNTAX SEQUENCE OF WingCfgLegacyApEntry
			MAX-ACCESS not-accessible
			STATUS current
			DESCRIPTION
				"Legacy AP (AP300) configuraion.
				
				/wing-config/ap300"
			::= { wingCfgLegacyAp 1 }

		
		-- 1.3.6.1.4.1.1916.2.131.50.1.3.33.1.1
		wingCfgLegacyApEntry OBJECT-TYPE
			SYNTAX WingCfgLegacyApEntry
			MAX-ACCESS not-accessible
			STATUS current
			DESCRIPTION
				"An entry in the table."
			INDEX { wingCfgLegacyApIndex }
			::= { wingCfgLegacyApTable 1 }

		
		WingCfgLegacyApEntry ::=
			SEQUENCE { 
				wingCfgLegacyApIndex
					WingIdentifier,
				wingCfgLegacyApCountryCode
					DisplayString,
				wingCfgLegacyApLed
					TruthValue,
				wingCfgLegacyApLocation
					DisplayString,
				wingCfgLegacyApIpAddr
					DisplayString,
				wingCfgLegacyApGateway
					DisplayString,
				wingCfgLegacyApPreferredControllerGroup
					DisplayString
			 }

		-- 1.3.6.1.4.1.1916.2.131.50.1.3.33.1.1.1
		wingCfgLegacyApIndex OBJECT-TYPE
			SYNTAX WingIdentifier
			MAX-ACCESS read-only
			STATUS current
			DESCRIPTION
				"AP index.
				
				Values:
				MAC address in string format with - as the sepearator,
				e.g. 00-A0-F8-BC-E9-21
				default-ap300
				
				XPath: /wing-config/ap300[mac=key1]/mac"
			::= { wingCfgLegacyApEntry 1 }

		
		-- 1.3.6.1.4.1.1916.2.131.50.1.3.33.1.1.3
		wingCfgLegacyApCountryCode OBJECT-TYPE
			SYNTAX DisplayString
			MAX-ACCESS read-write
			STATUS current
			DESCRIPTION
				"The country of operation.
				
				Values:
				not-set ae ai an ar at au ba bb be bg bh bm bo br bs bw by
				ca ch cl cn co cr cx cy cz de dk do dz ec ee eg es fi fk fr
				gb gf gp gr gt gu gy hk hn hr ht hu id ie il in is it jm jo
				jp ke kr kw ky kz lb li lk lt lu lv ma md mk mq mt mx my mp
				me nf ng ni nl no nu nz na om pa pe ph pk pl pr pt py qa
				ro rs ru sa se sg si sk sv th tr tn tt tw ua us uy ve vg vi
				vn za
				
				XPath: /wing-config/ap300[mac=key1]/country_code"
			::= { wingCfgLegacyApEntry 3 }

		
		-- 1.3.6.1.4.1.1916.2.131.50.1.3.33.1.1.4
		wingCfgLegacyApLed OBJECT-TYPE
			SYNTAX TruthValue
			MAX-ACCESS read-write
			STATUS current
			DESCRIPTION
				"Turn LEDs on/off on the AP.
				
				XPath: /wing-config/ap300[mac=key1]/led"
			DEFVAL { true }
			::= { wingCfgLegacyApEntry 4 }

		
		-- 1.3.6.1.4.1.1916.2.131.50.1.3.33.1.1.5
		wingCfgLegacyApLocation OBJECT-TYPE
			SYNTAX DisplayString (SIZE (0..64))
			MAX-ACCESS read-write
			STATUS current
			DESCRIPTION
				"The location of this AP.
				
				XPath: /wing-config/ap300[mac=key1]/location"
			::= { wingCfgLegacyApEntry 5 }

		
		-- 1.3.6.1.4.1.1916.2.131.50.1.3.33.1.1.6
		wingCfgLegacyApIpAddr OBJECT-TYPE
			SYNTAX DisplayString
			MAX-ACCESS read-write
			STATUS current
			DESCRIPTION
				"The IP address for AP adoption, network mask /32
				has to be specified. (e.g. 10.0.0.1/8)
				
				XPath: /wing-config/ap300[mac=key1]/ap300_ip_address"
			::= { wingCfgLegacyApEntry 6 }

		
		-- 1.3.6.1.4.1.1916.2.131.50.1.3.33.1.1.7
		wingCfgLegacyApGateway OBJECT-TYPE
			SYNTAX DisplayString
			MAX-ACCESS read-write
			STATUS current
			DESCRIPTION
				"The IP gateway for AP adoption (e.g. 10.0.0.1).
				
				XPath: /wing-config/ap300[mac=key1]/ap300_gw"
			::= { wingCfgLegacyApEntry 7 }

		
		-- 1.3.6.1.4.1.1916.2.131.50.1.3.33.1.1.8
		wingCfgLegacyApPreferredControllerGroup OBJECT-TYPE
			SYNTAX DisplayString (SIZE (0..64))
			MAX-ACCESS read-write
			STATUS current
			DESCRIPTION
				"Controller which the AP will prefer for adoption.
				
				XPath: /wing-config/ap300[mac=key1]/preferred_controller_group"
			::= { wingCfgLegacyApEntry 8 }

		
		-- 1.3.6.1.4.1.1916.2.131.50.1.3.33.2
		wingCfgLegacyApIfTable OBJECT-TYPE
			SYNTAX SEQUENCE OF WingCfgLegacyApIfEntry
			MAX-ACCESS not-accessible
			STATUS current
			DESCRIPTION
				"Legacy AP radio interface configuration.
				
				/wing-config/ap300/interface"
			::= { wingCfgLegacyAp 2 }

		
		-- 1.3.6.1.4.1.1916.2.131.50.1.3.33.2.1
		wingCfgLegacyApIfEntry OBJECT-TYPE
			SYNTAX WingCfgLegacyApIfEntry
			MAX-ACCESS not-accessible
			STATUS current
			DESCRIPTION
				"An entry in the table."
			INDEX { wingCfgLegacyApIndex, wingCfgLegacyApIfName }
			::= { wingCfgLegacyApIfTable 1 }

		
		WingCfgLegacyApIfEntry ::=
			SEQUENCE { 
				wingCfgLegacyApIfName
					WingIdentifier,
				wingCfgLegacyApIfDescr
					DisplayString,
				wingCfgLegacyApIfShutdown
					TruthValue,
				wingCfgLegacyApIfRfMode
					DisplayString,
				wingCfgLegacyApIfAntennaDiversity
					TruthValue,
				wingCfgLegacyApIfBeaconInterval
					DisplayString,
				wingCfgLegacyApIfChannel
					DisplayString,
				wingCfgLegacyApIfMaxClients
					Unsigned32,
				wingCfgLegacyApIfPlacement
					DisplayString,
				wingCfgLegacyApIfPower
					Unsigned32,
				wingCfgLegacyApIfPreambleShort
					TruthValue,
				wingCfgLegacyApIfOnChannelScan
					TruthValue,
				wingCfgLegacyApIfRtsThreshold
					Unsigned32,
				wingCfgLegacyApIfQosPolicy
					WingIdentifier,
				wingCfgLegacyApIfWirelessClientPower
					Unsigned32
			 }

		-- 1.3.6.1.4.1.1916.2.131.50.1.3.33.2.1.1
		wingCfgLegacyApIfName OBJECT-TYPE
			SYNTAX WingIdentifier
			MAX-ACCESS read-only
			STATUS current
			DESCRIPTION
				"Radio interface name.
				
				XPath: /wing-config/ap300[mac=key1]/interface[name=key2]/name"
			::= { wingCfgLegacyApIfEntry 1 }

		
		-- 1.3.6.1.4.1.1916.2.131.50.1.3.33.2.1.3
		wingCfgLegacyApIfDescr OBJECT-TYPE
			SYNTAX DisplayString (SIZE (0..64))
			MAX-ACCESS read-write
			STATUS current
			DESCRIPTION
				"Description for the radio.
				
				XPath: /wing-config/ap300[mac=key1]/interface[name=key2]/description"
			::= { wingCfgLegacyApIfEntry 3 }

		
		-- 1.3.6.1.4.1.1916.2.131.50.1.3.33.2.1.4
		wingCfgLegacyApIfShutdown OBJECT-TYPE
			SYNTAX TruthValue
			MAX-ACCESS read-write
			STATUS current
			DESCRIPTION
				"Shutdown the radio interface.
				
				XPath: /wing-config/ap300[mac=key1]/interface[name=key2]/shutdown"
			DEFVAL { false }
			::= { wingCfgLegacyApIfEntry 4 }

		
		-- 1.3.6.1.4.1.1916.2.131.50.1.3.33.2.1.5
		wingCfgLegacyApIfRfMode OBJECT-TYPE
			SYNTAX DisplayString
			MAX-ACCESS read-write
			STATUS current
			DESCRIPTION
				"The rf-mode of operation for the radio.
				
				Values:
				2.4GHz-wlan
				5GHz-wlan
				sensor
				
				XPath: /wing-config/ap300[mac=key1]/interface[name=key2]/rf_mode"
			::= { wingCfgLegacyApIfEntry 5 }

		
		-- 1.3.6.1.4.1.1916.2.131.50.1.3.33.2.1.6
		wingCfgLegacyApIfAntennaDiversity OBJECT-TYPE
			SYNTAX TruthValue
			MAX-ACCESS read-write
			STATUS current
			DESCRIPTION
				"Whether the radio should enable antenna diversity
				for transmit frames at non-11n data-rates.
				
				XPath: /wing-config/ap300[mac=key1]/interface[name=key2]/antenna_diversity"
			DEFVAL { false }
			::= { wingCfgLegacyApIfEntry 6 }

		
		-- 1.3.6.1.4.1.1916.2.131.50.1.3.33.2.1.7
		wingCfgLegacyApIfBeaconInterval OBJECT-TYPE
			SYNTAX DisplayString
			UNITS "milliseconds"
			MAX-ACCESS read-write
			STATUS current
			DESCRIPTION
				"The beacon interval.
				
				Values:
				50
				100
				200
				
				XPath: /wing-config/ap300[mac=key1]/interface[name=key2]/beacon_interval"
			DEFVAL { "100" }
			::= { wingCfgLegacyApIfEntry 7 }

		
		-- 1.3.6.1.4.1.1916.2.131.50.1.3.33.2.1.8
		wingCfgLegacyApIfChannel OBJECT-TYPE
			SYNTAX DisplayString
			MAX-ACCESS read-write
			STATUS current
			DESCRIPTION
				"Channel of operation for the radio.
				
				Values:
				1 2 3 4 5 6 7 8 9 10 11 12 13 14 36 40 44 48 52 56 60 64
				100 104 108 112 116 120 124 128 132 136 140 149 153 157
				161 165 34 38 42 46 acs smart
				
				XPath: /wing-config/ap300[mac=key1]/interface[name=key2]/channel"
			DEFVAL { "smart" }
			::= { wingCfgLegacyApIfEntry 8 }

		
		-- 1.3.6.1.4.1.1916.2.131.50.1.3.33.2.1.9
		wingCfgLegacyApIfMaxClients OBJECT-TYPE
			SYNTAX Unsigned32 (0..256)
			MAX-ACCESS read-write
			STATUS current
			DESCRIPTION
				"The maximum number of clients allowed to associate with
				the radio subject to AP limit.
				
				XPath: /wing-config/ap300[mac=key1]/interface[name=key2]/max_clients"
			DEFVAL { 256 }
			::= { wingCfgLegacyApIfEntry 9 }

		
		-- 1.3.6.1.4.1.1916.2.131.50.1.3.33.2.1.10
		wingCfgLegacyApIfPlacement OBJECT-TYPE
			SYNTAX DisplayString
			MAX-ACCESS read-write
			STATUS current
			DESCRIPTION
				"Location where the radio is operating.
				
				Values:
				indoor
				outdoor
				
				XPath: /wing-config/ap300[mac=key1]/interface[name=key2]/placement"
			DEFVAL { "indoor" }
			::= { wingCfgLegacyApIfEntry 10 }

		
		-- 1.3.6.1.4.1.1916.2.131.50.1.3.33.2.1.11
		wingCfgLegacyApIfPower OBJECT-TYPE
			SYNTAX Unsigned32 (1..20)
			UNITS "dBm"
			MAX-ACCESS read-write
			STATUS current
			DESCRIPTION
				"Transmit power of the radio.  A setting of 0 indicates
				Smart RF is managing the power.
				
				XPath: /wing-config/ap300[mac=key1]/interface[name=key2]/power"
			DEFVAL { 20 }
			::= { wingCfgLegacyApIfEntry 11 }

		
		-- 1.3.6.1.4.1.1916.2.131.50.1.3.33.2.1.12
		wingCfgLegacyApIfPreambleShort OBJECT-TYPE
			SYNTAX TruthValue
			MAX-ACCESS read-write
			STATUS current
			DESCRIPTION
				"Use short preambles on the radio.
				
				XPath: /wing-config/ap300[mac=key1]/interface[name=key2]/preamble_short"
			DEFVAL { false }
			::= { wingCfgLegacyApIfEntry 12 }

		
		-- 1.3.6.1.4.1.1916.2.131.50.1.3.33.2.1.13
		wingCfgLegacyApIfOnChannelScan OBJECT-TYPE
			SYNTAX TruthValue
			MAX-ACCESS read-write
			STATUS current
			DESCRIPTION
				"Enable/disable on channel scan on the radio.
				
				XPath: /wing-config/ap300[mac=key1]/interface[name=key2]/on_channel_scan"
			DEFVAL { false }
			::= { wingCfgLegacyApIfEntry 13 }

		
		-- 1.3.6.1.4.1.1916.2.131.50.1.3.33.2.1.14
		wingCfgLegacyApIfRtsThreshold OBJECT-TYPE
			SYNTAX Unsigned32 (1..2347)
			UNITS "bytes"
			MAX-ACCESS read-write
			STATUS current
			DESCRIPTION
				"RTS threshold on the radio.
				
				XPath: /wing-config/ap300[mac=key1]/interface[name=key2]/rts_threshold"
			DEFVAL { 2347 }
			::= { wingCfgLegacyApIfEntry 14 }

		
		-- 1.3.6.1.4.1.1916.2.131.50.1.3.33.2.1.15
		wingCfgLegacyApIfQosPolicy OBJECT-TYPE
			SYNTAX WingIdentifier
			MAX-ACCESS read-write
			STATUS current
			DESCRIPTION
				"QOS policy on the radio.
				
				XPath: /wing-config/ap300[mac=key1]/interface[name=key2]/qos_policy"
			::= { wingCfgLegacyApIfEntry 15 }

		
		-- 1.3.6.1.4.1.1916.2.131.50.1.3.33.2.1.16
		wingCfgLegacyApIfWirelessClientPower OBJECT-TYPE
			SYNTAX Unsigned32 (0..20)
			UNITS "dBm"
			MAX-ACCESS read-write
			STATUS current
			DESCRIPTION
				"Transmit power indicated to wireless clients
				for transmission.
				
				XPath: /wing-config/ap300[mac=key1]/interface[name=key2]/wireless_client_power"
			::= { wingCfgLegacyApIfEntry 16 }

		
		-- 1.3.6.1.4.1.1916.2.131.50.1.3.33.3
		wingCfgLegacyApIfWlanBssMapTable OBJECT-TYPE
			SYNTAX SEQUENCE OF WingCfgLegacyApIfWlanBssMapEntry
			MAX-ACCESS not-accessible
			STATUS current
			DESCRIPTION
				"WLANs enabled on this radio.
				
				/wing-config/ap300/interface/wlanbssmap"
			::= { wingCfgLegacyAp 3 }

		
		-- 1.3.6.1.4.1.1916.2.131.50.1.3.33.3.1
		wingCfgLegacyApIfWlanBssMapEntry OBJECT-TYPE
			SYNTAX WingCfgLegacyApIfWlanBssMapEntry
			MAX-ACCESS not-accessible
			STATUS current
			DESCRIPTION
				"An entry in the table."
			INDEX { wingCfgLegacyApIndex, wingCfgLegacyApIfName, wingCfgLegacyApIfWlanBssMapWlan }
			::= { wingCfgLegacyApIfWlanBssMapTable 1 }

		
		WingCfgLegacyApIfWlanBssMapEntry ::=
			SEQUENCE { 
				wingCfgLegacyApIfWlanBssMapWlan
					WingIdentifier,
				wingCfgLegacyApIfWlanBssMapBss
					Unsigned32,
				wingCfgLegacyApIfWlanBssMapPrimary
					TruthValue
			 }

		-- 1.3.6.1.4.1.1916.2.131.50.1.3.33.3.1.1
		wingCfgLegacyApIfWlanBssMapWlan OBJECT-TYPE
			SYNTAX WingIdentifier
			MAX-ACCESS read-only
			STATUS current
			DESCRIPTION
				"Name of the WLAN (it must have been already created
				and configured).
				
				XPath: /wing-config/ap300[mac=key1]/interface[name=key2]/wlanbssmap[wlan=key3]/wlan"
			::= { wingCfgLegacyApIfWlanBssMapEntry 1 }

		
		-- 1.3.6.1.4.1.1916.2.131.50.1.3.33.3.1.3
		wingCfgLegacyApIfWlanBssMapBss OBJECT-TYPE
			SYNTAX Unsigned32 (1..4)
			MAX-ACCESS read-write
			STATUS current
			DESCRIPTION
				"BSS number on the radio where this WLAN is to be mapped.
				
				XPath: /wing-config/ap300[mac=key1]/interface[name=key2]/wlanbssmap[wlan=key3]/bss"
			::= { wingCfgLegacyApIfWlanBssMapEntry 3 }

		
		-- 1.3.6.1.4.1.1916.2.131.50.1.3.33.3.1.4
		wingCfgLegacyApIfWlanBssMapPrimary OBJECT-TYPE
			SYNTAX TruthValue
			MAX-ACCESS read-write
			STATUS current
			DESCRIPTION
				"Make this WLAN the primary WLAN if there are multiple WLANs
				on its BSS.
				
				XPath: /wing-config/ap300[mac=key1]/interface[name=key2]/wlanbssmap[wlan=key3]/primary"
			::= { wingCfgLegacyApIfWlanBssMapEntry 4 }

		
-- Alternate read-only implementation of configuration tables
-- used by known network management applications.
		-- 1.3.6.1.4.1.1916.2.131.50.1.3.34
		wingCfgAlt OBJECT IDENTIFIER ::= { wingConfig 34 }

		
		-- 1.3.6.1.4.1.1916.2.131.50.1.3.34.1
		wingCfgAltDevTable OBJECT-TYPE
			SYNTAX SEQUENCE OF WingCfgAltDevEntry
			MAX-ACCESS not-accessible
			STATUS current
			DESCRIPTION
				"Copy of wingCfgDevTable.
				
				/wing-config/device"
			::= { wingCfgAlt 1 }

		
		-- 1.3.6.1.4.1.1916.2.131.50.1.3.34.1.1
		wingCfgAltDevEntry OBJECT-TYPE
			SYNTAX WingCfgAltDevEntry
			MAX-ACCESS not-accessible
			STATUS current
			DESCRIPTION
				"An entry in the table."
			INDEX { wingCfgAltDevMac }
			::= { wingCfgAltDevTable 1 }

		
		WingCfgAltDevEntry ::=
			SEQUENCE { 
				wingCfgAltDevMac
					MacAddress,
				wingCfgAltDevHostname
					DisplayString,
				wingCfgAltDevBuilding
					DisplayString,
				wingCfgAltDevFloor
					DisplayString,
				wingCfgAltDevNumRadios
					Unsigned32,
				wingCfgAltDevProfileName
					WingIdentifier,
				wingCfgAltDevRfDomainName
					WingIdentifier,
				wingCfgAltDevHttpsTrustpoint
					DisplayString,
				wingCfgAltDevRadiusCaTrustpoint
					DisplayString,
				wingCfgAltDevRadiusServerTrustpoint
					DisplayString,
				wingCfgAltDevSshRsaKey
					WingIdentifier,
				wingCfgAltDevHasOverrides
					TruthValue
			 }

		-- 1.3.6.1.4.1.1916.2.131.50.1.3.34.1.1.1
		wingCfgAltDevMac OBJECT-TYPE
			SYNTAX MacAddress
			MAX-ACCESS read-only
			STATUS current
			DESCRIPTION
				"
				
				XPath: /wing-config/device[mac=key1]/mac"
			::= { wingCfgAltDevEntry 1 }

		
		-- 1.3.6.1.4.1.1916.2.131.50.1.3.34.1.1.3
		wingCfgAltDevHostname OBJECT-TYPE
			SYNTAX DisplayString (SIZE (64))
			MAX-ACCESS read-only
			STATUS current
			DESCRIPTION
				"
				
				XPath: /wing-config/device[mac=key1]/hostname"
			::= { wingCfgAltDevEntry 3 }

		
		-- 1.3.6.1.4.1.1916.2.131.50.1.3.34.1.1.4
		wingCfgAltDevBuilding OBJECT-TYPE
			SYNTAX DisplayString (SIZE (64))
			MAX-ACCESS read-only
			STATUS current
			DESCRIPTION
				"
				
				XPath: /wing-config/device[mac=key1]/building"
			::= { wingCfgAltDevEntry 4 }

		
		-- 1.3.6.1.4.1.1916.2.131.50.1.3.34.1.1.5
		wingCfgAltDevFloor OBJECT-TYPE
			SYNTAX DisplayString (SIZE (32))
			MAX-ACCESS read-only
			STATUS current
			DESCRIPTION
				"
				
				XPath: /wing-config/device[mac=key1]/floor"
			::= { wingCfgAltDevEntry 5 }

		
		-- 1.3.6.1.4.1.1916.2.131.50.1.3.34.1.1.6
		wingCfgAltDevNumRadios OBJECT-TYPE
			SYNTAX Unsigned32 (0..3)
			MAX-ACCESS read-only
			STATUS current
			DESCRIPTION
				"
				
				XPath: /wing-config/device[mac=key1]/num_radios"
			::= { wingCfgAltDevEntry 6 }

		
		-- 1.3.6.1.4.1.1916.2.131.50.1.3.34.1.1.7
		wingCfgAltDevProfileName OBJECT-TYPE
			SYNTAX WingIdentifier
			MAX-ACCESS read-only
			STATUS current
			DESCRIPTION
				"
				
				XPath: /wing-config/device[mac=key1]/profile_name"
			::= { wingCfgAltDevEntry 7 }

		
		-- 1.3.6.1.4.1.1916.2.131.50.1.3.34.1.1.8
		wingCfgAltDevRfDomainName OBJECT-TYPE
			SYNTAX WingIdentifier
			MAX-ACCESS read-only
			STATUS current
			DESCRIPTION
				"
				
				XPath: /wing-config/device[mac=key1]/rf_domain_name"
			::= { wingCfgAltDevEntry 8 }

		
		-- 1.3.6.1.4.1.1916.2.131.50.1.3.34.1.1.9
		wingCfgAltDevHttpsTrustpoint OBJECT-TYPE
			SYNTAX DisplayString (SIZE (1..32))
			MAX-ACCESS read-only
			STATUS current
			DESCRIPTION
				"
				
				XPath: /wing-config/device[mac=key1]/https-trustpoint"
			DEFVAL { "default-trustpoint" }
			::= { wingCfgAltDevEntry 9 }

		
		-- 1.3.6.1.4.1.1916.2.131.50.1.3.34.1.1.10
		wingCfgAltDevRadiusCaTrustpoint OBJECT-TYPE
			SYNTAX DisplayString (SIZE (1..32))
			MAX-ACCESS read-only
			STATUS current
			DESCRIPTION
				"
				
				XPath: /wing-config/device[mac=key1]/radius-ca-trustpoint"
			::= { wingCfgAltDevEntry 10 }

		
		-- 1.3.6.1.4.1.1916.2.131.50.1.3.34.1.1.11
		wingCfgAltDevRadiusServerTrustpoint OBJECT-TYPE
			SYNTAX DisplayString (SIZE (1..32))
			MAX-ACCESS read-only
			STATUS current
			DESCRIPTION
				"
				
				XPath: /wing-config/device[mac=key1]/radius-server-trustpoint"
			DEFVAL { "default-trustpoint" }
			::= { wingCfgAltDevEntry 11 }

		
		-- 1.3.6.1.4.1.1916.2.131.50.1.3.34.1.1.12
		wingCfgAltDevSshRsaKey OBJECT-TYPE
			SYNTAX WingIdentifier
			MAX-ACCESS read-only
			STATUS current
			DESCRIPTION
				"
				
				XPath: /wing-config/device[mac=key1]/ssh-rsa-key"
			DEFVAL { "default_rsa_key" }
			::= { wingCfgAltDevEntry 12 }

		
		-- 1.3.6.1.4.1.1916.2.131.50.1.3.34.1.1.13
		wingCfgAltDevHasOverrides OBJECT-TYPE
			SYNTAX TruthValue
			MAX-ACCESS read-only
			STATUS current
			DESCRIPTION
				"read only value to indicate whether the device has at least one override
				
				XPath: /wing-config/device[mac=key1]/has_overrides"
			DEFVAL { false }
			::= { wingCfgAltDevEntry 13 }

		
		-- 1.3.6.1.4.1.1916.2.131.50.1.3.34.2
		wingCfgAltDevIfTable OBJECT-TYPE
			SYNTAX SEQUENCE OF WingCfgAltDevIfEntry
			MAX-ACCESS not-accessible
			STATUS current
			DESCRIPTION
				"Copy of wingCfgDevIfTable.
				
				/wing-config/device/interface"
			::= { wingCfgAlt 2 }

		
		-- 1.3.6.1.4.1.1916.2.131.50.1.3.34.2.1
		wingCfgAltDevIfEntry OBJECT-TYPE
			SYNTAX WingCfgAltDevIfEntry
			MAX-ACCESS not-accessible
			STATUS current
			DESCRIPTION
				"An entry in the table."
			INDEX { wingCfgAltDevMac, wingCfgAltDevIfName }
			::= { wingCfgAltDevIfTable 1 }

		
		WingCfgAltDevIfEntry ::=
			SEQUENCE { 
				wingCfgAltDevIfName
					WingIdentifier,
				wingCfgAltDevIfDescription
					DisplayString,
				wingCfgAltDevIfType
					DisplayString,
				wingCfgAltDevIfShutdown
					TruthValue,
				wingCfgAltDevIfIpInAcl
					WingIdentifier,
				wingCfgAltDevIfMacInAcl
					WingIdentifier
			 }

		-- 1.3.6.1.4.1.1916.2.131.50.1.3.34.2.1.1
		wingCfgAltDevIfName OBJECT-TYPE
			SYNTAX WingIdentifier
			MAX-ACCESS read-only
			STATUS current
			DESCRIPTION
				"
				
				XPath: /wing-config/device[mac=key1]/interface[name=key2]/name"
			::= { wingCfgAltDevIfEntry 1 }

		
		-- 1.3.6.1.4.1.1916.2.131.50.1.3.34.2.1.3
		wingCfgAltDevIfDescription OBJECT-TYPE
			SYNTAX DisplayString
			MAX-ACCESS read-only
			STATUS current
			DESCRIPTION
				"
				
				XPath: /wing-config/device[mac=key1]/interface[name=key2]/description"
			::= { wingCfgAltDevIfEntry 3 }

		
		-- 1.3.6.1.4.1.1916.2.131.50.1.3.34.2.1.4
		wingCfgAltDevIfType OBJECT-TYPE
			SYNTAX DisplayString
			MAX-ACCESS read-only
			STATUS current
			DESCRIPTION
				"Hardware type of the network interface
				
				Values:
				ethernet
				vlan
				radio
				port_channel
				
				XPath: /wing-config/device[mac=key1]/interface[name=key2]/type"
			::= { wingCfgAltDevIfEntry 4 }

		
		-- 1.3.6.1.4.1.1916.2.131.50.1.3.34.2.1.5
		wingCfgAltDevIfShutdown OBJECT-TYPE
			SYNTAX TruthValue
			MAX-ACCESS read-only
			STATUS current
			DESCRIPTION
				"
				
				XPath: /wing-config/device[mac=key1]/interface[name=key2]/shutdown"
			DEFVAL { false }
			::= { wingCfgAltDevIfEntry 5 }

		
		-- 1.3.6.1.4.1.1916.2.131.50.1.3.34.2.1.6
		wingCfgAltDevIfIpInAcl OBJECT-TYPE
			SYNTAX WingIdentifier
			MAX-ACCESS read-only
			STATUS current
			DESCRIPTION
				"
				
				XPath: /wing-config/device[mac=key1]/interface[name=key2]/ip_in_acl"
			::= { wingCfgAltDevIfEntry 6 }

		
		-- 1.3.6.1.4.1.1916.2.131.50.1.3.34.2.1.7
		wingCfgAltDevIfMacInAcl OBJECT-TYPE
			SYNTAX WingIdentifier
			MAX-ACCESS read-only
			STATUS current
			DESCRIPTION
				"
				
				XPath: /wing-config/device[mac=key1]/interface[name=key2]/mac_in_acl"
			::= { wingCfgAltDevIfEntry 7 }

		
		-- 1.3.6.1.4.1.1916.2.131.50.1.3.34.3
		wingCfgAltDevIfRadioBssmapTable OBJECT-TYPE
			SYNTAX SEQUENCE OF WingCfgAltDevIfRadioBssmapEntry
			MAX-ACCESS not-accessible
			STATUS current
			DESCRIPTION
				"Copy of wingCfgDevIfRadioBssmapTable.
				
				/wing-config/device/interface/wlanbssmap"
			::= { wingCfgAlt 3 }

		
		-- 1.3.6.1.4.1.1916.2.131.50.1.3.34.3.1
		wingCfgAltDevIfRadioBssmapEntry OBJECT-TYPE
			SYNTAX WingCfgAltDevIfRadioBssmapEntry
			MAX-ACCESS not-accessible
			STATUS current
			DESCRIPTION
				"An entry in the table."
			INDEX { wingCfgAltDevMac, wingCfgAltDevIfName, wingCfgAltDevIfRadioBssmapWlan }
			::= { wingCfgAltDevIfRadioBssmapTable 1 }

		
		WingCfgAltDevIfRadioBssmapEntry ::=
			SEQUENCE { 
				wingCfgAltDevIfRadioBssmapWlan
					WingIdentifier,
				wingCfgAltDevIfRadioBssmapBss
					Unsigned32,
				wingCfgAltDevIfRadioBssmapPrimary
					TruthValue
			 }

		-- 1.3.6.1.4.1.1916.2.131.50.1.3.34.3.1.1
		wingCfgAltDevIfRadioBssmapWlan OBJECT-TYPE
			SYNTAX WingIdentifier
			MAX-ACCESS read-only
			STATUS current
			DESCRIPTION
				"
				
				XPath: /wing-config/device[mac=key1]/interface[name=key2]/wlanbssmap[wlan=key3]/wlan"
			::= { wingCfgAltDevIfRadioBssmapEntry 1 }

		
		-- 1.3.6.1.4.1.1916.2.131.50.1.3.34.3.1.3
		wingCfgAltDevIfRadioBssmapBss OBJECT-TYPE
			SYNTAX Unsigned32 (1..8)
			MAX-ACCESS read-only
			STATUS current
			DESCRIPTION
				"
				
				XPath: /wing-config/device[mac=key1]/interface[name=key2]/wlanbssmap[wlan=key3]/bss"
			::= { wingCfgAltDevIfRadioBssmapEntry 3 }

		
		-- 1.3.6.1.4.1.1916.2.131.50.1.3.34.3.1.4
		wingCfgAltDevIfRadioBssmapPrimary OBJECT-TYPE
			SYNTAX TruthValue
			MAX-ACCESS read-only
			STATUS current
			DESCRIPTION
				"
				
				XPath: /wing-config/device[mac=key1]/interface[name=key2]/wlanbssmap[wlan=key3]/primary"
			::= { wingCfgAltDevIfRadioBssmapEntry 4 }

		
		-- 1.3.6.1.4.1.1916.2.131.50.1.3.35
		wingCfgMcx OBJECT IDENTIFIER ::= { wingConfig 35 }

		
		-- 1.3.6.1.4.1.1916.2.131.50.1.3.35.1
		wingCfgMcxMeshpointTable OBJECT-TYPE
			SYNTAX SEQUENCE OF WingCfgMcxMeshpointEntry
			MAX-ACCESS not-accessible
			STATUS current
			DESCRIPTION
				"
				
				/wing-config/meshpoint"
			::= { wingCfgMcx 1 }

		
		-- 1.3.6.1.4.1.1916.2.131.50.1.3.35.1.1
		wingCfgMcxMeshpointEntry OBJECT-TYPE
			SYNTAX WingCfgMcxMeshpointEntry
			MAX-ACCESS not-accessible
			STATUS current
			DESCRIPTION
				"An entry in the table."
			INDEX { wingCfgMcxMeshpointName }
			::= { wingCfgMcxMeshpointTable 1 }

		
		WingCfgMcxMeshpointEntry ::=
			SEQUENCE { 
				wingCfgMcxMeshpointName
					WingIdentifier,
				wingCfgMcxMeshpointShutdown
					TruthValue,
				wingCfgMcxMeshpointMeshid
					DisplayString,
				wingCfgMcxMeshpointDescription
					DisplayString,
				wingCfgMcxMeshpointBeaconFormat
					DisplayString,
				wingCfgMcxMeshpointControlVlan
					Unsigned32,
				wingCfgMcxMeshpointNeighborInactivityTimeout
					Unsigned32,
				wingCfgMcxMeshpointQosPolicy
					WingIdentifier,
				wingCfgMcxMeshpointSecurityMode
					DisplayString,
				wingCfgMcxMeshpointWpa2Psk
					DisplayString,
				wingCfgMcxMeshpointWpa2KeyRotationUnicast
					Unsigned32,
				wingCfgMcxMeshpointWpa2KeyRotationBroadcast
					Unsigned32,
				wingCfgMcxMeshpointIsRoot
					TruthValue,
				wingCfgMcxMeshpointMonitorCriticalResources
					TruthValue,
				wingCfgMcxMeshpointMonitorPriPortLink
					TruthValue
			 }

		-- 1.3.6.1.4.1.1916.2.131.50.1.3.35.1.1.1
		wingCfgMcxMeshpointName OBJECT-TYPE
			SYNTAX WingIdentifier
			MAX-ACCESS read-write
			STATUS current
			DESCRIPTION
				"
				
				XPath: /wing-config/meshpoint[name=key1]/name"
			::= { wingCfgMcxMeshpointEntry 1 }

		
		-- 1.3.6.1.4.1.1916.2.131.50.1.3.35.1.1.3
		wingCfgMcxMeshpointShutdown OBJECT-TYPE
			SYNTAX TruthValue
			MAX-ACCESS read-write
			STATUS current
			DESCRIPTION
				"
				
				XPath: /wing-config/meshpoint[name=key1]/shutdown"
			DEFVAL { false }
			::= { wingCfgMcxMeshpointEntry 3 }

		
		-- 1.3.6.1.4.1.1916.2.131.50.1.3.35.1.1.4
		wingCfgMcxMeshpointMeshid OBJECT-TYPE
			SYNTAX DisplayString (SIZE (0..32))
			MAX-ACCESS read-write
			STATUS current
			DESCRIPTION
				"Mesh Identifier for this MP.
				
				XPath: /wing-config/meshpoint[name=key1]/meshid"
			::= { wingCfgMcxMeshpointEntry 4 }

		
		-- 1.3.6.1.4.1.1916.2.131.50.1.3.35.1.1.5
		wingCfgMcxMeshpointDescription OBJECT-TYPE
			SYNTAX DisplayString (SIZE (1..64))
			MAX-ACCESS read-write
			STATUS current
			DESCRIPTION
				"Descriptive text about this MP.
				
				XPath: /wing-config/meshpoint[name=key1]/description"
			::= { wingCfgMcxMeshpointEntry 5 }

		
		-- 1.3.6.1.4.1.1916.2.131.50.1.3.35.1.1.6
		wingCfgMcxMeshpointBeaconFormat OBJECT-TYPE
			SYNTAX DisplayString
			MAX-ACCESS read-write
			STATUS current
			DESCRIPTION
				"
				
				Values:
				mesh-point;
				enum
				access-point
				
				XPath: /wing-config/meshpoint[name=key1]/beacon_format"
			DEFVAL { "mesh-point" }
			::= { wingCfgMcxMeshpointEntry 6 }

		
		-- 1.3.6.1.4.1.1916.2.131.50.1.3.35.1.1.7
		wingCfgMcxMeshpointControlVlan OBJECT-TYPE
			SYNTAX Unsigned32 (1..4094)
			MAX-ACCESS read-write
			STATUS current
			DESCRIPTION
				"VLAN for meshpoint control traffic
				
				XPath: /wing-config/meshpoint[name=key1]/control_vlan"
			DEFVAL { 1 }
			::= { wingCfgMcxMeshpointEntry 7 }

		
		-- 1.3.6.1.4.1.1916.2.131.50.1.3.35.1.1.8
		wingCfgMcxMeshpointNeighborInactivityTimeout OBJECT-TYPE
			SYNTAX Unsigned32 (60..86400)
			UNITS "seconds"
			MAX-ACCESS read-write
			STATUS current
			DESCRIPTION
				"If a frame is not received from a neighbor for this amount of time, the neighbor has its client resource revoked.
				
				XPath: /wing-config/meshpoint[name=key1]/neighbor_inactivity_timeout"
			DEFVAL { 120 }
			::= { wingCfgMcxMeshpointEntry 8 }

		
		-- 1.3.6.1.4.1.1916.2.131.50.1.3.35.1.1.9
		wingCfgMcxMeshpointQosPolicy OBJECT-TYPE
			SYNTAX WingIdentifier
			MAX-ACCESS read-write
			STATUS current
			DESCRIPTION
				"
				
				XPath: /wing-config/meshpoint[name=key1]/qos_policy"
			::= { wingCfgMcxMeshpointEntry 9 }

		
		-- 1.3.6.1.4.1.1916.2.131.50.1.3.35.1.1.10
		wingCfgMcxMeshpointSecurityMode OBJECT-TYPE
			SYNTAX DisplayString
			MAX-ACCESS read-write
			STATUS current
			DESCRIPTION
				"
				
				Values:
				none;
				enum
				psk
				
				XPath: /wing-config/meshpoint[name=key1]/security_mode"
			DEFVAL { "none" }
			::= { wingCfgMcxMeshpointEntry 10 }

		
		-- 1.3.6.1.4.1.1916.2.131.50.1.3.35.1.1.11
		wingCfgMcxMeshpointWpa2Psk OBJECT-TYPE
			SYNTAX DisplayString (SIZE (8..64))
			MAX-ACCESS read-write
			STATUS current
			DESCRIPTION
				"
				
				XPath: /wing-config/meshpoint[name=key1]/wpa2_psk"
			::= { wingCfgMcxMeshpointEntry 11 }

		
		-- 1.3.6.1.4.1.1916.2.131.50.1.3.35.1.1.12
		wingCfgMcxMeshpointWpa2KeyRotationUnicast OBJECT-TYPE
			SYNTAX Unsigned32 (30..86400)
			UNITS "seconds"
			MAX-ACCESS read-write
			STATUS current
			DESCRIPTION
				"
				
				XPath: /wing-config/meshpoint[name=key1]/wpa2_key_rotation_unicast"
			::= { wingCfgMcxMeshpointEntry 12 }

		
		-- 1.3.6.1.4.1.1916.2.131.50.1.3.35.1.1.13
		wingCfgMcxMeshpointWpa2KeyRotationBroadcast OBJECT-TYPE
			SYNTAX Unsigned32 (30..86400)
			UNITS "seconds"
			MAX-ACCESS read-write
			STATUS current
			DESCRIPTION
				"
				
				XPath: /wing-config/meshpoint[name=key1]/wpa2_key_rotation_broadcast"
			::= { wingCfgMcxMeshpointEntry 13 }

		
		-- 1.3.6.1.4.1.1916.2.131.50.1.3.35.1.1.14
		wingCfgMcxMeshpointIsRoot OBJECT-TYPE
			SYNTAX TruthValue
			MAX-ACCESS read-write
			STATUS current
			DESCRIPTION
				"
				
				XPath: /wing-config/meshpoint[name=key1]/is_root"
			DEFVAL { false }
			::= { wingCfgMcxMeshpointEntry 14 }

		
		-- 1.3.6.1.4.1.1916.2.131.50.1.3.35.1.1.15
		wingCfgMcxMeshpointMonitorCriticalResources OBJECT-TYPE
			SYNTAX TruthValue
			MAX-ACCESS read-write
			STATUS current
			DESCRIPTION
				"
				
				XPath: /wing-config/meshpoint[name=key1]/monitor_critical_resources"
			DEFVAL { false }
			::= { wingCfgMcxMeshpointEntry 15 }

		
		-- 1.3.6.1.4.1.1916.2.131.50.1.3.35.1.1.16
		wingCfgMcxMeshpointMonitorPriPortLink OBJECT-TYPE
			SYNTAX TruthValue
			MAX-ACCESS read-write
			STATUS current
			DESCRIPTION
				"
				
				XPath: /wing-config/meshpoint[name=key1]/monitor_pri_port_link"
			DEFVAL { false }
			::= { wingCfgMcxMeshpointEntry 16 }

		
		-- 1.3.6.1.4.1.1916.2.131.50.1.3.35.2
		wingCfgMcxMeshpointQosTable OBJECT-TYPE
			SYNTAX SEQUENCE OF WingCfgMcxMeshpointQosEntry
			MAX-ACCESS not-accessible
			STATUS current
			DESCRIPTION
				"
				
				/wing-config/meshpoint"
			::= { wingCfgMcx 2 }

		
		-- 1.3.6.1.4.1.1916.2.131.50.1.3.35.2.1
		wingCfgMcxMeshpointQosEntry OBJECT-TYPE
			SYNTAX WingCfgMcxMeshpointQosEntry
			MAX-ACCESS not-accessible
			STATUS current
			DESCRIPTION
				"An entry in the table."
			INDEX { wingCfgMcxMeshpointName }
			::= { wingCfgMcxMeshpointQosTable 1 }

		
		WingCfgMcxMeshpointQosEntry ::=
			SEQUENCE { 
				wingCfgMcxMeshpointQosName
					WingIdentifier,
				wingCfgMcxMeshpointQosMeshpointRlDownEnable
					TruthValue,
				wingCfgMcxMeshpointQosMeshpointRlDownRate
					Unsigned32,
				wingCfgMcxMeshpointQosMeshpointRlDownBurstSize
					Unsigned32,
				wingCfgMcxMeshpointQosMeshpointRlDownThreshBackground
					Unsigned32,
				wingCfgMcxMeshpointQosMeshpointRlDownThreshBestEffort
					Unsigned32,
				wingCfgMcxMeshpointQosMeshpointRlDownThreshVoice
					Unsigned32,
				wingCfgMcxMeshpointQosMeshpointRlDownThreshVideo
					Unsigned32,
				wingCfgMcxMeshpointQosMeshpointRlUpEnable
					TruthValue,
				wingCfgMcxMeshpointQosMeshpointRlUpRate
					Unsigned32,
				wingCfgMcxMeshpointQosMeshpointRlUpBurstSize
					Unsigned32,
				wingCfgMcxMeshpointQosMeshpointRlUpThreshBackground
					Unsigned32,
				wingCfgMcxMeshpointQosMeshpointRlUpThreshBestEffort
					Unsigned32,
				wingCfgMcxMeshpointQosMeshpointRlUpThreshVoice
					Unsigned32,
				wingCfgMcxMeshpointQosMeshpointRlUpThreshVideo
					Unsigned32,
				wingCfgMcxMeshpointQosNeighborRlDownEnable
					TruthValue,
				wingCfgMcxMeshpointQosNeighborRlDownRate
					Unsigned32,
				wingCfgMcxMeshpointQosNeighborRlDownBurstSize
					Unsigned32,
				wingCfgMcxMeshpointQosNeighborRlDownThreshBackground
					Unsigned32,
				wingCfgMcxMeshpointQosNeighborRlDownThreshBestEffort
					Unsigned32,
				wingCfgMcxMeshpointQosNeighborRlDownThreshVoice
					Unsigned32,
				wingCfgMcxMeshpointQosNeighborRlDownThreshVideo
					Unsigned32,
				wingCfgMcxMeshpointQosNeighborRlUpEnable
					TruthValue,
				wingCfgMcxMeshpointQosNeighborRlUpRate
					Unsigned32,
				wingCfgMcxMeshpointQosNeighborRlUpBurstSize
					Unsigned32,
				wingCfgMcxMeshpointQosNeighborRlUpThreshBackground
					Unsigned32,
				wingCfgMcxMeshpointQosNeighborRlUpThreshBestEffort
					Unsigned32,
				wingCfgMcxMeshpointQosNeighborRlUpThreshVoice
					Unsigned32,
				wingCfgMcxMeshpointQosNeighborRlUpThreshVideo
					Unsigned32,
				wingCfgMcxMeshpointQosAddr
					DisplayString,
				wingCfgMcxMeshpointQosPriority
					DisplayString
			 }

		-- 1.3.6.1.4.1.1916.2.131.50.1.3.35.2.1.1
		wingCfgMcxMeshpointQosName OBJECT-TYPE
			SYNTAX WingIdentifier
			MAX-ACCESS read-write
			STATUS current
			DESCRIPTION
				"
				
				XPath: /wing-config/meshpoint[name=key1]/name"
			::= { wingCfgMcxMeshpointQosEntry 1 }

		
		-- 1.3.6.1.4.1.1916.2.131.50.1.3.35.2.1.3
		wingCfgMcxMeshpointQosMeshpointRlDownEnable OBJECT-TYPE
			SYNTAX TruthValue
			MAX-ACCESS read-write
			STATUS current
			DESCRIPTION
				"Enable downstream (to air) traffic rate limiting on a MP.
				
				XPath: /wing-config/meshpoint[name=key1]/meshpoint_rl_down_enable"
			DEFVAL { false }
			::= { wingCfgMcxMeshpointQosEntry 3 }

		
		-- 1.3.6.1.4.1.1916.2.131.50.1.3.35.2.1.4
		wingCfgMcxMeshpointQosMeshpointRlDownRate OBJECT-TYPE
			SYNTAX Unsigned32 (50..1000000)
			UNITS "kbps"
			MAX-ACCESS read-write
			STATUS current
			DESCRIPTION
				"Traffic rate for downstream (to air) rate limiting on a MP.
				
				XPath: /wing-config/meshpoint[name=key1]/meshpoint_rl_down_rate"
			DEFVAL { 5000 }
			::= { wingCfgMcxMeshpointQosEntry 4 }

		
		-- 1.3.6.1.4.1.1916.2.131.50.1.3.35.2.1.5
		wingCfgMcxMeshpointQosMeshpointRlDownBurstSize OBJECT-TYPE
			SYNTAX Unsigned32 (2..1024)
			UNITS "kbytes"
			MAX-ACCESS read-write
			STATUS current
			DESCRIPTION
				"Maximum burst size for downstream (to air) rate limiting on a MP.
				
				XPath: /wing-config/meshpoint[name=key1]/meshpoint_rl_down_burst_size"
			DEFVAL { 320 }
			::= { wingCfgMcxMeshpointQosEntry 5 }

		
		-- 1.3.6.1.4.1.1916.2.131.50.1.3.35.2.1.6
		wingCfgMcxMeshpointQosMeshpointRlDownThreshBackground OBJECT-TYPE
			SYNTAX Unsigned32 (0..100)
			UNITS "%"
			MAX-ACCESS read-write
			STATUS current
			DESCRIPTION
				"Random early detection threshold in % of Maximum burst size for low priority traffic (downstream, to air, rate limiting on a MP).
				
				XPath: /wing-config/meshpoint[name=key1]/meshpoint_rl_down_thresh_background"
			DEFVAL { 50 }
			::= { wingCfgMcxMeshpointQosEntry 6 }

		
		-- 1.3.6.1.4.1.1916.2.131.50.1.3.35.2.1.7
		wingCfgMcxMeshpointQosMeshpointRlDownThreshBestEffort OBJECT-TYPE
			SYNTAX Unsigned32 (0..100)
			UNITS "%"
			MAX-ACCESS read-write
			STATUS current
			DESCRIPTION
				"Random early detection threshold in % of Maximum burst size for normal priority traffic (downstream, to air, rate limiting on a MP).
				
				XPath: /wing-config/meshpoint[name=key1]/meshpoint_rl_down_thresh_best_effort"
			DEFVAL { 50 }
			::= { wingCfgMcxMeshpointQosEntry 7 }

		
		-- 1.3.6.1.4.1.1916.2.131.50.1.3.35.2.1.8
		wingCfgMcxMeshpointQosMeshpointRlDownThreshVoice OBJECT-TYPE
			SYNTAX Unsigned32 (0..100)
			UNITS "%"
			MAX-ACCESS read-write
			STATUS current
			DESCRIPTION
				"Random early detection threshold in % of Maximum burst size for voice traffic (downstream, to air, rate limiting on a MP).
				
				XPath: /wing-config/meshpoint[name=key1]/meshpoint_rl_down_thresh_voice"
			DEFVAL { 0 }
			::= { wingCfgMcxMeshpointQosEntry 8 }

		
		-- 1.3.6.1.4.1.1916.2.131.50.1.3.35.2.1.9
		wingCfgMcxMeshpointQosMeshpointRlDownThreshVideo OBJECT-TYPE
			SYNTAX Unsigned32 (0..100)
			UNITS "%"
			MAX-ACCESS read-write
			STATUS current
			DESCRIPTION
				"Random early detection threshold in % of Maximum burst size for video traffic (downstream, to air, rate limiting on a MP).
				
				XPath: /wing-config/meshpoint[name=key1]/meshpoint_rl_down_thresh_video"
			DEFVAL { 25 }
			::= { wingCfgMcxMeshpointQosEntry 9 }

		
		-- 1.3.6.1.4.1.1916.2.131.50.1.3.35.2.1.10
		wingCfgMcxMeshpointQosMeshpointRlUpEnable OBJECT-TYPE
			SYNTAX TruthValue
			MAX-ACCESS read-write
			STATUS current
			DESCRIPTION
				"Enable upstream (from air) traffic rate limiting on a MP.
				
				XPath: /wing-config/meshpoint[name=key1]/meshpoint_rl_up_enable"
			DEFVAL { false }
			::= { wingCfgMcxMeshpointQosEntry 10 }

		
		-- 1.3.6.1.4.1.1916.2.131.50.1.3.35.2.1.11
		wingCfgMcxMeshpointQosMeshpointRlUpRate OBJECT-TYPE
			SYNTAX Unsigned32 (50..1000000)
			UNITS "kbps"
			MAX-ACCESS read-write
			STATUS current
			DESCRIPTION
				"Traffic rate for upstream (from air) rate limiting on a MP.
				
				XPath: /wing-config/meshpoint[name=key1]/meshpoint_rl_up_rate"
			DEFVAL { 5000 }
			::= { wingCfgMcxMeshpointQosEntry 11 }

		
		-- 1.3.6.1.4.1.1916.2.131.50.1.3.35.2.1.12
		wingCfgMcxMeshpointQosMeshpointRlUpBurstSize OBJECT-TYPE
			SYNTAX Unsigned32 (2..1024)
			UNITS "kbytes"
			MAX-ACCESS read-write
			STATUS current
			DESCRIPTION
				"Maximum burst size for upstream (from air) rate limiting on a MP.
				
				XPath: /wing-config/meshpoint[name=key1]/meshpoint_rl_up_burst_size"
			DEFVAL { 320 }
			::= { wingCfgMcxMeshpointQosEntry 12 }

		
		-- 1.3.6.1.4.1.1916.2.131.50.1.3.35.2.1.13
		wingCfgMcxMeshpointQosMeshpointRlUpThreshBackground OBJECT-TYPE
			SYNTAX Unsigned32 (0..100)
			UNITS "%"
			MAX-ACCESS read-write
			STATUS current
			DESCRIPTION
				"Random early detection threshold in % of Maximum burst size for low priority traffic (upstream, from air, rate limiting on a MP).
				
				XPath: /wing-config/meshpoint[name=key1]/meshpoint_rl_up_thresh_background"
			DEFVAL { 50 }
			::= { wingCfgMcxMeshpointQosEntry 13 }

		
		-- 1.3.6.1.4.1.1916.2.131.50.1.3.35.2.1.14
		wingCfgMcxMeshpointQosMeshpointRlUpThreshBestEffort OBJECT-TYPE
			SYNTAX Unsigned32 (0..100)
			UNITS "%"
			MAX-ACCESS read-write
			STATUS current
			DESCRIPTION
				"Random early detection threshold in % of Maximum burst size for normal priority traffic (upstream, from air, rate limiting on a MP).
				
				XPath: /wing-config/meshpoint[name=key1]/meshpoint_rl_up_thresh_best_effort"
			DEFVAL { 50 }
			::= { wingCfgMcxMeshpointQosEntry 14 }

		
		-- 1.3.6.1.4.1.1916.2.131.50.1.3.35.2.1.15
		wingCfgMcxMeshpointQosMeshpointRlUpThreshVoice OBJECT-TYPE
			SYNTAX Unsigned32 (0..100)
			UNITS "%"
			MAX-ACCESS read-write
			STATUS current
			DESCRIPTION
				"Random early detection threshold in % of Maximum burst size for voice traffic (upstream, from air, rate limiting on a MP).
				
				XPath: /wing-config/meshpoint[name=key1]/meshpoint_rl_up_thresh_voice"
			DEFVAL { 0 }
			::= { wingCfgMcxMeshpointQosEntry 15 }

		
		-- 1.3.6.1.4.1.1916.2.131.50.1.3.35.2.1.16
		wingCfgMcxMeshpointQosMeshpointRlUpThreshVideo OBJECT-TYPE
			SYNTAX Unsigned32 (0..100)
			UNITS "%"
			MAX-ACCESS read-write
			STATUS current
			DESCRIPTION
				"Random early detection threshold in % of Maximum burst size for video traffic (upstream, from air, rate limiting on a MP).
				
				XPath: /wing-config/meshpoint[name=key1]/meshpoint_rl_up_thresh_video"
			DEFVAL { 25 }
			::= { wingCfgMcxMeshpointQosEntry 16 }

		
		-- 1.3.6.1.4.1.1916.2.131.50.1.3.35.2.1.17
		wingCfgMcxMeshpointQosNeighborRlDownEnable OBJECT-TYPE
			SYNTAX TruthValue
			MAX-ACCESS read-write
			STATUS current
			DESCRIPTION
				"Enable downstream (to air) traffic rate limiting for Neighbors on a MP.
				
				XPath: /wing-config/meshpoint[name=key1]/neighbor_rl_down_enable"
			DEFVAL { false }
			::= { wingCfgMcxMeshpointQosEntry 17 }

		
		-- 1.3.6.1.4.1.1916.2.131.50.1.3.35.2.1.18
		wingCfgMcxMeshpointQosNeighborRlDownRate OBJECT-TYPE
			SYNTAX Unsigned32 (50..1000000)
			UNITS "kbps"
			MAX-ACCESS read-write
			STATUS current
			DESCRIPTION
				"Traffic rate for downstream (to air) rate limiting for Neighbors on a MP.
				
				XPath: /wing-config/meshpoint[name=key1]/neighbor_rl_down_rate"
			DEFVAL { 1000 }
			::= { wingCfgMcxMeshpointQosEntry 18 }

		
		-- 1.3.6.1.4.1.1916.2.131.50.1.3.35.2.1.19
		wingCfgMcxMeshpointQosNeighborRlDownBurstSize OBJECT-TYPE
			SYNTAX Unsigned32 (2..1024)
			UNITS "kbytes"
			MAX-ACCESS read-write
			STATUS current
			DESCRIPTION
				"Maximum burst size for downstream (to air) rate limiting for Neighbors on a MP.
				
				XPath: /wing-config/meshpoint[name=key1]/neighbor_rl_down_burst_size"
			DEFVAL { 64 }
			::= { wingCfgMcxMeshpointQosEntry 19 }

		
		-- 1.3.6.1.4.1.1916.2.131.50.1.3.35.2.1.20
		wingCfgMcxMeshpointQosNeighborRlDownThreshBackground OBJECT-TYPE
			SYNTAX Unsigned32 (0..100)
			UNITS "%"
			MAX-ACCESS read-write
			STATUS current
			DESCRIPTION
				"Random early detection threshold in % of Maximum burst size for low priority traffic (downstream, to air, rate limiting for neighbors on a MP.
				
				XPath: /wing-config/meshpoint[name=key1]/neighbor_rl_down_thresh_background"
			DEFVAL { 50 }
			::= { wingCfgMcxMeshpointQosEntry 20 }

		
		-- 1.3.6.1.4.1.1916.2.131.50.1.3.35.2.1.21
		wingCfgMcxMeshpointQosNeighborRlDownThreshBestEffort OBJECT-TYPE
			SYNTAX Unsigned32 (0..100)
			UNITS "%"
			MAX-ACCESS read-write
			STATUS current
			DESCRIPTION
				"Random early detection threshold in % of Maximum burst size for low priority traffic (downstream, to air, rate limiting for neighbors on a MP).
				
				XPath: /wing-config/meshpoint[name=key1]/neighbor_rl_down_thresh_best_effort"
			DEFVAL { 50 }
			::= { wingCfgMcxMeshpointQosEntry 21 }

		
		-- 1.3.6.1.4.1.1916.2.131.50.1.3.35.2.1.22
		wingCfgMcxMeshpointQosNeighborRlDownThreshVoice OBJECT-TYPE
			SYNTAX Unsigned32 (0..100)
			UNITS "%"
			MAX-ACCESS read-write
			STATUS current
			DESCRIPTION
				"Random early detection threshold in % of Maximum burst size for voice traffic (downstream, to air, rate limiting for neighbors on a MP).
				
				XPath: /wing-config/meshpoint[name=key1]/neighbor_rl_down_thresh_voice"
			DEFVAL { 0 }
			::= { wingCfgMcxMeshpointQosEntry 22 }

		
		-- 1.3.6.1.4.1.1916.2.131.50.1.3.35.2.1.23
		wingCfgMcxMeshpointQosNeighborRlDownThreshVideo OBJECT-TYPE
			SYNTAX Unsigned32 (0..100)
			UNITS "%"
			MAX-ACCESS read-write
			STATUS current
			DESCRIPTION
				"Random early detection threshold in % of Maximum burst size for video traffic (downstream, to air, rate limiting for neighbors on a MP).
				
				XPath: /wing-config/meshpoint[name=key1]/neighbor_rl_down_thresh_video"
			DEFVAL { 25 }
			::= { wingCfgMcxMeshpointQosEntry 23 }

		
		-- 1.3.6.1.4.1.1916.2.131.50.1.3.35.2.1.24
		wingCfgMcxMeshpointQosNeighborRlUpEnable OBJECT-TYPE
			SYNTAX TruthValue
			MAX-ACCESS read-write
			STATUS current
			DESCRIPTION
				"Enable upstream (from air) traffic rate limiting for Neighbors on a MP.
				
				XPath: /wing-config/meshpoint[name=key1]/neighbor_rl_up_enable"
			DEFVAL { false }
			::= { wingCfgMcxMeshpointQosEntry 24 }

		
		-- 1.3.6.1.4.1.1916.2.131.50.1.3.35.2.1.25
		wingCfgMcxMeshpointQosNeighborRlUpRate OBJECT-TYPE
			SYNTAX Unsigned32 (50..1000000)
			UNITS "kbps"
			MAX-ACCESS read-write
			STATUS current
			DESCRIPTION
				"Traffic rate for upstream (from air) rate limiting for Neighbors on a MP.
				
				XPath: /wing-config/meshpoint[name=key1]/neighbor_rl_up_rate"
			DEFVAL { 1000 }
			::= { wingCfgMcxMeshpointQosEntry 25 }

		
		-- 1.3.6.1.4.1.1916.2.131.50.1.3.35.2.1.26
		wingCfgMcxMeshpointQosNeighborRlUpBurstSize OBJECT-TYPE
			SYNTAX Unsigned32 (2..1024)
			UNITS "kbytes"
			MAX-ACCESS read-write
			STATUS current
			DESCRIPTION
				"Maximum burst size for upstream (from air) rate limiting for Neighbors on a MP.
				
				XPath: /wing-config/meshpoint[name=key1]/neighbor_rl_up_burst_size"
			DEFVAL { 64 }
			::= { wingCfgMcxMeshpointQosEntry 26 }

		
		-- 1.3.6.1.4.1.1916.2.131.50.1.3.35.2.1.27
		wingCfgMcxMeshpointQosNeighborRlUpThreshBackground OBJECT-TYPE
			SYNTAX Unsigned32 (0..100)
			UNITS "%"
			MAX-ACCESS read-write
			STATUS current
			DESCRIPTION
				"Random early detection threshold in % of Maximum burst size for low priority traffic (upstream, from air, rate limiting for neighbors on a MP).
				
				XPath: /wing-config/meshpoint[name=key1]/neighbor_rl_up_thresh_background"
			DEFVAL { 50 }
			::= { wingCfgMcxMeshpointQosEntry 27 }

		
		-- 1.3.6.1.4.1.1916.2.131.50.1.3.35.2.1.28
		wingCfgMcxMeshpointQosNeighborRlUpThreshBestEffort OBJECT-TYPE
			SYNTAX Unsigned32 (0..100)
			UNITS "%"
			MAX-ACCESS read-write
			STATUS current
			DESCRIPTION
				"Random early detection threshold in % of Maximum burst size for normal priority traffic (upstream, from air, rate limiting for neighbors on a MP).
				
				XPath: /wing-config/meshpoint[name=key1]/neighbor_rl_up_thresh_best_effort"
			DEFVAL { 50 }
			::= { wingCfgMcxMeshpointQosEntry 28 }

		
		-- 1.3.6.1.4.1.1916.2.131.50.1.3.35.2.1.29
		wingCfgMcxMeshpointQosNeighborRlUpThreshVoice OBJECT-TYPE
			SYNTAX Unsigned32 (0..100)
			UNITS "%"
			MAX-ACCESS read-write
			STATUS current
			DESCRIPTION
				"Random early detection threshold in % of Maximum burst size for voice traffic (upstream, from air, rate limiting for neighbors on a MP).
				
				XPath: /wing-config/meshpoint[name=key1]/neighbor_rl_up_thresh_voice"
			DEFVAL { 0 }
			::= { wingCfgMcxMeshpointQosEntry 29 }

		
		-- 1.3.6.1.4.1.1916.2.131.50.1.3.35.2.1.30
		wingCfgMcxMeshpointQosNeighborRlUpThreshVideo OBJECT-TYPE
			SYNTAX Unsigned32 (0..100)
			UNITS "%"
			MAX-ACCESS read-write
			STATUS current
			DESCRIPTION
				"Random early detection threshold in % of Maximum burst size for video traffic (upstream, from air, rate limiting for neighbors on a MP).
				
				XPath: /wing-config/meshpoint[name=key1]/neighbor_rl_up_thresh_video"
			DEFVAL { 25 }
			::= { wingCfgMcxMeshpointQosEntry 30 }

		
		-- 1.3.6.1.4.1.1916.2.131.50.1.3.35.2.1.31
		wingCfgMcxMeshpointQosAddr OBJECT-TYPE
			SYNTAX DisplayString
			MAX-ACCESS read-write
			STATUS current
			DESCRIPTION
				"Multicast IP address of the traffic stream that should be selected for accelerated delivery
				
				XPath: /wing-config/meshpoint[name=key1]/addr"
			::= { wingCfgMcxMeshpointQosEntry 31 }

		
		-- 1.3.6.1.4.1.1916.2.131.50.1.3.35.2.1.32
		wingCfgMcxMeshpointQosPriority OBJECT-TYPE
			SYNTAX DisplayString
			MAX-ACCESS read-write
			STATUS current
			DESCRIPTION
				"The forwarding qos classification (traffic class)
				
				Values:
				trust,
				voice,
				video,
				best-effort,
				background
				
				XPath: /wing-config/meshpoint[name=key1]/priority"
			DEFVAL { "trust" }
			::= { wingCfgMcxMeshpointQosEntry 32 }

		
		-- 1.3.6.1.4.1.1916.2.131.50.1.4
		wingStats OBJECT IDENTIFIER ::= { wingObjects 4 }

		
-- /wing-stats/noc
		-- 1.3.6.1.4.1.1916.2.131.50.1.4.1
		wingStatsNoc OBJECT IDENTIFIER ::= { wingStats 1 }
		
		-- 1.3.6.1.4.1.1916.2.131.50.1.4.1.2
		wingStatsNocDevTable OBJECT-TYPE
			SYNTAX SEQUENCE OF WingStatsNocDevEntry
			MAX-ACCESS not-accessible
			STATUS current
			DESCRIPTION
				"
				
				/wing-stats/noc/device-list"
			::= { wingStatsNoc 2 }

		
		-- 1.3.6.1.4.1.1916.2.131.50.1.4.1.2.1
		wingStatsNocDevEntry OBJECT-TYPE
			SYNTAX WingStatsNocDevEntry
			MAX-ACCESS not-accessible
			STATUS current
			DESCRIPTION
				"An entry in the table."
			INDEX { wingStatsNocDevMac }
			::= { wingStatsNocDevTable 1 }

		
		WingStatsNocDevEntry ::=
			SEQUENCE { 
				wingStatsNocDevMac
					MacAddress,
				wingStatsNocDevHostname
					DisplayString,
				wingStatsNocDevType
					DisplayString,
				wingStatsNocDevClusterName
					DisplayString,
				wingStatsNocDevRfDomainName
					DisplayString,
				wingStatsNocDevAdoptedBy
					DisplayString,
				wingStatsNocDevOnline
					TruthValue,
				wingStatsNocDevReporter
					MacAddress,
				wingStatsNocDevLastUpdate
					Unsigned32,
				wingStatsNocDevHasRadio
					TruthValue,
				wingStatsNocDevIsController
					TruthValue,
				wingStatsNocDevProfileName
					DisplayString
			 }

		-- 1.3.6.1.4.1.1916.2.131.50.1.4.1.2.1.1
		wingStatsNocDevMac OBJECT-TYPE
			SYNTAX MacAddress
			MAX-ACCESS read-only
			STATUS current
			DESCRIPTION
				"Device mac address
				
				XPath: /wing-stats/noc/device-list[mac=key1]/mac"
			::= { wingStatsNocDevEntry 1 }

		
		-- 1.3.6.1.4.1.1916.2.131.50.1.4.1.2.1.2
		wingStatsNocDevHostname OBJECT-TYPE
			SYNTAX DisplayString (SIZE (64))
			MAX-ACCESS read-only
			STATUS current
			DESCRIPTION
				"
				
				XPath: /wing-stats/noc/device-list[mac=key1]/hostname"
			::= { wingStatsNocDevEntry 2 }

		
		-- 1.3.6.1.4.1.1916.2.131.50.1.4.1.2.1.3
		wingStatsNocDevType OBJECT-TYPE
			SYNTAX DisplayString
			MAX-ACCESS read-only
			STATUS current
			DESCRIPTION
				"Device type
				
				XPath: /wing-stats/noc/device-list[mac=key1]/type"
			::= { wingStatsNocDevEntry 3 }

		
		-- 1.3.6.1.4.1.1916.2.131.50.1.4.1.2.1.4
		wingStatsNocDevClusterName OBJECT-TYPE
			SYNTAX DisplayString (SIZE (64))
			MAX-ACCESS read-only
			STATUS current
			DESCRIPTION
				"Name of the cluster this device belongs to,
				applicable to switch device
				
				XPath: /wing-stats/noc/device-list[mac=key1]/cluster_name"
			::= { wingStatsNocDevEntry 4 }

		
		-- 1.3.6.1.4.1.1916.2.131.50.1.4.1.2.1.5
		wingStatsNocDevRfDomainName OBJECT-TYPE
			SYNTAX DisplayString (SIZE (64))
			MAX-ACCESS read-only
			STATUS current
			DESCRIPTION
				"Rf-domain that this device currently resides in
				
				XPath: /wing-stats/noc/device-list[mac=key1]/rf_domain_name"
			::= { wingStatsNocDevEntry 5 }

		
		-- 1.3.6.1.4.1.1916.2.131.50.1.4.1.2.1.6
		wingStatsNocDevAdoptedBy OBJECT-TYPE
			SYNTAX DisplayString (SIZE (64))
			MAX-ACCESS read-only
			STATUS current
			DESCRIPTION
				"Mac address of parent switch that adopts this device (AP)
				
				XPath: /wing-stats/noc/device-list[mac=key1]/adopted_by"
			::= { wingStatsNocDevEntry 6 }

		
		-- 1.3.6.1.4.1.1916.2.131.50.1.4.1.2.1.7
		wingStatsNocDevOnline OBJECT-TYPE
			SYNTAX TruthValue
			MAX-ACCESS read-only
			STATUS current
			DESCRIPTION
				"
				
				XPath: /wing-stats/noc/device-list[mac=key1]/online"
			::= { wingStatsNocDevEntry 7 }

		
		-- 1.3.6.1.4.1.1916.2.131.50.1.4.1.2.1.8
		wingStatsNocDevReporter OBJECT-TYPE
			SYNTAX MacAddress
			MAX-ACCESS read-only
			STATUS current
			DESCRIPTION
				"Device mac address of the reporting controller
				
				XPath: /wing-stats/noc/device-list[mac=key1]/reporter"
			::= { wingStatsNocDevEntry 8 }

		
		-- 1.3.6.1.4.1.1916.2.131.50.1.4.1.2.1.9
		wingStatsNocDevLastUpdate OBJECT-TYPE
			SYNTAX Unsigned32
			MAX-ACCESS read-only
			STATUS current
			DESCRIPTION
				"The last UTC timestamp from the originating rf-domain manager
				
				XPath: /wing-stats/noc/device-list[mac=key1]/last_update"
			::= { wingStatsNocDevEntry 9 }

		
		-- 1.3.6.1.4.1.1916.2.131.50.1.4.1.2.1.10
		wingStatsNocDevHasRadio OBJECT-TYPE
			SYNTAX TruthValue
			MAX-ACCESS read-only
			STATUS current
			DESCRIPTION
				"Whether the device has wireless radio that can
				service clients
				
				XPath: /wing-stats/noc/device-list[mac=key1]/has_radio"
			::= { wingStatsNocDevEntry 10 }

		
		-- 1.3.6.1.4.1.1916.2.131.50.1.4.1.2.1.11
		wingStatsNocDevIsController OBJECT-TYPE
			SYNTAX TruthValue
			MAX-ACCESS read-only
			STATUS current
			DESCRIPTION
				"Whether the device is a controller device
				
				XPath: /wing-stats/noc/device-list[mac=key1]/is_controller"
			::= { wingStatsNocDevEntry 11 }

		
		-- 1.3.6.1.4.1.1916.2.131.50.1.4.1.2.1.12
		wingStatsNocDevProfileName OBJECT-TYPE
			SYNTAX DisplayString (SIZE (64))
			MAX-ACCESS read-only
			STATUS current
			DESCRIPTION
				"Profile name that this device is using
				
				XPath: /wing-stats/noc/device-list[mac=key1]/profile_name"
			::= { wingStatsNocDevEntry 12 }

		
-- /wing-stats/noc/adoption
		-- 1.3.6.1.4.1.1916.2.131.50.1.4.1.9
		wingStatsNocAdopt OBJECT IDENTIFIER ::= { wingStatsNoc 9 }

		
		-- 1.3.6.1.4.1.1916.2.131.50.1.4.1.9.1
		wingStatsNocAdoptDevTable OBJECT-TYPE
			SYNTAX SEQUENCE OF WingStatsNocAdoptDevEntry
			MAX-ACCESS not-accessible
			STATUS current
			DESCRIPTION
				"Status of currently adopted devices.
				
				/wing-stats/noc/adoption/adopted_device"
			::= { wingStatsNocAdopt 1 }

		
		-- 1.3.6.1.4.1.1916.2.131.50.1.4.1.9.1.1
		wingStatsNocAdoptDevEntry OBJECT-TYPE
			SYNTAX WingStatsNocAdoptDevEntry
			MAX-ACCESS not-accessible
			STATUS current
			DESCRIPTION
				"An entry in the table."
			INDEX { wingStatsNocAdoptDevMac }
			::= { wingStatsNocAdoptDevTable 1 }

		
		WingStatsNocAdoptDevEntry ::=
			SEQUENCE { 
				wingStatsNocAdoptDevMac
					MacAddress,
				wingStatsNocAdoptDevType
					DisplayString,
				wingStatsNocAdoptDevHostname
					DisplayString,
				wingStatsNocAdoptDevVersion
					DisplayString,
				wingStatsNocAdoptDevSerialNo
					DisplayString,
				wingStatsNocAdoptDevRfDomainName
					DisplayString,
				wingStatsNocAdoptDevOnline
					TruthValue,
				wingStatsNocAdoptDevBy
					MacAddress,
				wingStatsNocAdoptDevLastAdoption
					Unsigned32,
				wingStatsNocAdoptDevModelNumber
					DisplayString,
				wingStatsNocAdoptDevStartup
					Unsigned32,
				wingStatsNocAdoptDevCfgStatus
					DisplayString,
				wingStatsNocAdoptDevProductName
					DisplayString
			 }

		-- 1.3.6.1.4.1.1916.2.131.50.1.4.1.9.1.1.1
		wingStatsNocAdoptDevMac OBJECT-TYPE
			SYNTAX MacAddress
			MAX-ACCESS read-only
			STATUS current
			DESCRIPTION
				"Device MAC
				
				XPath: /wing-stats/noc/adoption/adopted_device[mac=key1]/mac"
			::= { wingStatsNocAdoptDevEntry 1 }

		
		-- 1.3.6.1.4.1.1916.2.131.50.1.4.1.9.1.1.2
		wingStatsNocAdoptDevType OBJECT-TYPE
			SYNTAX DisplayString
			MAX-ACCESS read-only
			STATUS current
			DESCRIPTION
				"Device type
				
				XPath: /wing-stats/noc/adoption/adopted_device[mac=key1]/type"
			::= { wingStatsNocAdoptDevEntry 2 }

		
		-- 1.3.6.1.4.1.1916.2.131.50.1.4.1.9.1.1.3
		wingStatsNocAdoptDevHostname OBJECT-TYPE
			SYNTAX DisplayString
			MAX-ACCESS read-only
			STATUS current
			DESCRIPTION
				"Device hostname
				
				XPath: /wing-stats/noc/adoption/adopted_device[mac=key1]/hostname"
			::= { wingStatsNocAdoptDevEntry 3 }

		
		-- 1.3.6.1.4.1.1916.2.131.50.1.4.1.9.1.1.4
		wingStatsNocAdoptDevVersion OBJECT-TYPE
			SYNTAX DisplayString
			MAX-ACCESS read-only
			STATUS current
			DESCRIPTION
				"Device software version
				
				XPath: /wing-stats/noc/adoption/adopted_device[mac=key1]/version"
			::= { wingStatsNocAdoptDevEntry 4 }

		
		-- 1.3.6.1.4.1.1916.2.131.50.1.4.1.9.1.1.5
		wingStatsNocAdoptDevSerialNo OBJECT-TYPE
			SYNTAX DisplayString
			MAX-ACCESS read-only
			STATUS current
			DESCRIPTION
				"Device serial number
				
				XPath: /wing-stats/noc/adoption/adopted_device[mac=key1]/serial-no"
			::= { wingStatsNocAdoptDevEntry 5 }

		
		-- 1.3.6.1.4.1.1916.2.131.50.1.4.1.9.1.1.6
		wingStatsNocAdoptDevRfDomainName OBJECT-TYPE
			SYNTAX DisplayString
			MAX-ACCESS read-only
			STATUS current
			DESCRIPTION
				"Device RF Domain name
				
				XPath: /wing-stats/noc/adoption/adopted_device[mac=key1]/rf_domain_name"
			::= { wingStatsNocAdoptDevEntry 6 }

		
		-- 1.3.6.1.4.1.1916.2.131.50.1.4.1.9.1.1.7
		wingStatsNocAdoptDevOnline OBJECT-TYPE
			SYNTAX TruthValue
			MAX-ACCESS read-only
			STATUS current
			DESCRIPTION
				"Device online status
				
				XPath: /wing-stats/noc/adoption/adopted_device[mac=key1]/online"
			::= { wingStatsNocAdoptDevEntry 7 }

		
		-- 1.3.6.1.4.1.1916.2.131.50.1.4.1.9.1.1.8
		wingStatsNocAdoptDevBy OBJECT-TYPE
			SYNTAX MacAddress
			MAX-ACCESS read-only
			STATUS current
			DESCRIPTION
				"MAC address of the adopting device.
				
				XPath: /wing-stats/noc/adoption/adopted_device[mac=key1]/adopted_by"
			::= { wingStatsNocAdoptDevEntry 8 }

		
		-- 1.3.6.1.4.1.1916.2.131.50.1.4.1.9.1.1.9
		wingStatsNocAdoptDevLastAdoption OBJECT-TYPE
			SYNTAX Unsigned32
			MAX-ACCESS read-only
			STATUS current
			DESCRIPTION
				"UTC timestamp of the last adoption.
				
				XPath: /wing-stats/noc/adoption/adopted_device[mac=key1]/last_adoption"
			::= { wingStatsNocAdoptDevEntry 9 }

		
		-- 1.3.6.1.4.1.1916.2.131.50.1.4.1.9.1.1.10
		wingStatsNocAdoptDevModelNumber OBJECT-TYPE
			SYNTAX DisplayString
			MAX-ACCESS read-only
			STATUS current
			DESCRIPTION
				"Device model number.
				
				XPath: /wing-stats/noc/adoption/adopted_device[mac=key1]/model_number"
			::= { wingStatsNocAdoptDevEntry 10 }

		
		-- 1.3.6.1.4.1.1916.2.131.50.1.4.1.9.1.1.11
		wingStatsNocAdoptDevStartup OBJECT-TYPE
			SYNTAX Unsigned32
			MAX-ACCESS read-only
			STATUS current
			DESCRIPTION
				"UTC timestamp of device startup. The value 0 indicates that
				the timestamp is not available.
				
				XPath: /wing-stats/noc/adoption/adopted_device[mac=key1]/startup"
			::= { wingStatsNocAdoptDevEntry 11 }

		
		-- 1.3.6.1.4.1.1916.2.131.50.1.4.1.9.1.1.12
		wingStatsNocAdoptDevCfgStatus OBJECT-TYPE
			SYNTAX DisplayString
			MAX-ACCESS read-only
			STATUS current
			DESCRIPTION
				"The configuration status of the device, e.g., pending.
				
				XPath: /wing-stats/noc/adoption/adopted_device[mac=key1]/cfg_status"
			::= { wingStatsNocAdoptDevEntry 12 }

		
		-- 1.3.6.1.4.1.1916.2.131.50.1.4.1.9.1.1.13
		wingStatsNocAdoptDevProductName OBJECT-TYPE
			SYNTAX DisplayString (SIZE (0..32))
			MAX-ACCESS read-only
			STATUS current
			DESCRIPTION
				"Product name string
				
				XPath: /wing-stats/noc/adoption/adopted_device[mac=key1]/product-name"
			::= { wingStatsNocAdoptDevEntry 13 }

		
		-- 1.3.6.1.4.1.1916.2.131.50.1.4.1.9.2
		wingStatsNocAdoptPendingDevTable OBJECT-TYPE
			SYNTAX SEQUENCE OF WingStatsNocAdoptPendingDevEntry
			MAX-ACCESS not-accessible
			STATUS current
			DESCRIPTION
				"Status of devices not adopted.
				
				Xpath: /wing-stats/noc/adoption/pending_device"
			::= { wingStatsNocAdopt 2 }

		
		-- 1.3.6.1.4.1.1916.2.131.50.1.4.1.9.2.1
		wingStatsNocAdoptPendingDevEntry OBJECT-TYPE
			SYNTAX WingStatsNocAdoptPendingDevEntry
			MAX-ACCESS not-accessible
			STATUS current
			DESCRIPTION
				"An entry in the table."
			INDEX { wingStatsNocAdoptPendingDevMac }
			::= { wingStatsNocAdoptPendingDevTable 1 }

		
		WingStatsNocAdoptPendingDevEntry ::=
			SEQUENCE { 
				wingStatsNocAdoptPendingDevMac
					MacAddress,
				wingStatsNocAdoptPendingDevType
					DisplayString,
				wingStatsNocAdoptPendingDevTarget
					DisplayString,
				wingStatsNocAdoptPendingDevDisOption
					DisplayString,
				wingStatsNocAdoptPendingDevVersion
					DisplayString,
				wingStatsNocAdoptPendingDevSerialNumber
					DisplayString,
				wingStatsNocAdoptPendingDevReason
					DisplayString,
				wingStatsNocAdoptPendingDevNumRadios
					Unsigned32,
				wingStatsNocAdoptPendingDevIp
					DisplayString,
				wingStatsNocAdoptPendingDevVlan
					Unsigned32
			 }

		-- 1.3.6.1.4.1.1916.2.131.50.1.4.1.9.2.1.1
		wingStatsNocAdoptPendingDevMac OBJECT-TYPE
			SYNTAX MacAddress
			MAX-ACCESS read-only
			STATUS current
			DESCRIPTION
				"Device MAC
				
				XPath: /wing-stats/noc/adoption/pending_device[mac=key1]/mac"
			::= { wingStatsNocAdoptPendingDevEntry 1 }

		
		-- 1.3.6.1.4.1.1916.2.131.50.1.4.1.9.2.1.2
		wingStatsNocAdoptPendingDevType OBJECT-TYPE
			SYNTAX DisplayString
			MAX-ACCESS read-only
			STATUS current
			DESCRIPTION
				"Device type
				
				XPath: /wing-stats/noc/adoption/pending_device[mac=key1]/type"
			::= { wingStatsNocAdoptPendingDevEntry 2 }

		
		-- 1.3.6.1.4.1.1916.2.131.50.1.4.1.9.2.1.3
		wingStatsNocAdoptPendingDevTarget OBJECT-TYPE
			SYNTAX DisplayString
			MAX-ACCESS read-only
			STATUS current
			DESCRIPTION
				"Target information for the Device.
				
				XPath: /wing-stats/noc/adoption/pending_device[mac=key1]/target"
			::= { wingStatsNocAdoptPendingDevEntry 3 }

		
		-- 1.3.6.1.4.1.1916.2.131.50.1.4.1.9.2.1.4
		wingStatsNocAdoptPendingDevDisOption OBJECT-TYPE
			SYNTAX DisplayString
			MAX-ACCESS read-only
			STATUS current
			DESCRIPTION
				"Discovery option provided by the device.
				
				XPath: /wing-stats/noc/adoption/pending_device[mac=key1]/dis_option"
			::= { wingStatsNocAdoptPendingDevEntry 4 }

		
		-- 1.3.6.1.4.1.1916.2.131.50.1.4.1.9.2.1.5
		wingStatsNocAdoptPendingDevVersion OBJECT-TYPE
			SYNTAX DisplayString
			MAX-ACCESS read-only
			STATUS current
			DESCRIPTION
				"Device software version
				
				XPath: /wing-stats/noc/adoption/pending_device[mac=key1]/version"
			::= { wingStatsNocAdoptPendingDevEntry 5 }

		
		-- 1.3.6.1.4.1.1916.2.131.50.1.4.1.9.2.1.6
		wingStatsNocAdoptPendingDevSerialNumber OBJECT-TYPE
			SYNTAX DisplayString
			MAX-ACCESS read-only
			STATUS current
			DESCRIPTION
				"Device serial number
				
				XPath: /wing-stats/noc/adoption/pending_device[mac=key1]/serial_number"
			::= { wingStatsNocAdoptPendingDevEntry 6 }

		
		-- 1.3.6.1.4.1.1916.2.131.50.1.4.1.9.2.1.7
		wingStatsNocAdoptPendingDevReason OBJECT-TYPE
			SYNTAX DisplayString
			MAX-ACCESS read-only
			STATUS current
			DESCRIPTION
				"Reason for adoption pending.
				
				XPath: /wing-stats/noc/adoption/pending_device[mac=key1]/reason"
			::= { wingStatsNocAdoptPendingDevEntry 7 }

		
		-- 1.3.6.1.4.1.1916.2.131.50.1.4.1.9.2.1.8
		wingStatsNocAdoptPendingDevNumRadios OBJECT-TYPE
			SYNTAX Unsigned32
			MAX-ACCESS read-only
			STATUS current
			DESCRIPTION
				"Number of Radios available in the device.
				
				XPath: /wing-stats/noc/adoption/pending_device[mac=key1]/num_radios"
			::= { wingStatsNocAdoptPendingDevEntry 8 }

		
		-- 1.3.6.1.4.1.1916.2.131.50.1.4.1.9.2.1.9
		wingStatsNocAdoptPendingDevIp OBJECT-TYPE
			SYNTAX DisplayString
			MAX-ACCESS read-only
			STATUS current
			DESCRIPTION
				"IP address configured on the device.
				
				XPath: /wing-stats/noc/adoption/pending_device[mac=key1]/ip"
			::= { wingStatsNocAdoptPendingDevEntry 9 }

		
		-- 1.3.6.1.4.1.1916.2.131.50.1.4.1.9.2.1.10
		wingStatsNocAdoptPendingDevVlan OBJECT-TYPE
			SYNTAX Unsigned32
			MAX-ACCESS read-only
			STATUS current
			DESCRIPTION
				"VLAN of the Device. The value 0 indicates that the VLAN
				is not applicable.
				
				XPath: /wing-stats/noc/adoption/pending_device[mac=key1]/vlan"
			::= { wingStatsNocAdoptPendingDevEntry 10 }

		
-- /wing-stats/device
		-- 1.3.6.1.4.1.1916.2.131.50.1.4.2
		wingStatsDev OBJECT IDENTIFIER ::= { wingStats 2 }

		
		-- 1.3.6.1.4.1.1916.2.131.50.1.4.2.1
		wingStatsDevTable OBJECT-TYPE
			SYNTAX SEQUENCE OF WingStatsDevEntry
			MAX-ACCESS not-accessible
			STATUS current
			DESCRIPTION
				"Status of configured and/or discovered devices.
				
				/wing-stats/device"
			::= { wingStatsDev 1 }

		
		-- 1.3.6.1.4.1.1916.2.131.50.1.4.2.1.1
		wingStatsDevEntry OBJECT-TYPE
			SYNTAX WingStatsDevEntry
			MAX-ACCESS not-accessible
			STATUS current
			DESCRIPTION
				"An entry in the table."
			INDEX { wingStatsDevMac }
			::= { wingStatsDevTable 1 }

		
		WingStatsDevEntry ::=
			SEQUENCE { 
				wingStatsDevMac
					MacAddress,
				wingStatsDevType
					DisplayString,
				wingStatsDevHostname
					DisplayString,
				wingStatsDevVersion
					DisplayString,
				wingStatsDevSerialNo
					DisplayString,
				wingStatsDevRfDomainName
					DisplayString,
				wingStatsDevOnline
					TruthValue
			 }

		-- 1.3.6.1.4.1.1916.2.131.50.1.4.2.1.1.1
		wingStatsDevMac OBJECT-TYPE
			SYNTAX MacAddress
			MAX-ACCESS read-only
			STATUS current
			DESCRIPTION
				"Device MAC
				
				XPath: /wing-stats/device[mac=key1]/mac"
			::= { wingStatsDevEntry 1 }

		
		-- 1.3.6.1.4.1.1916.2.131.50.1.4.2.1.1.2
		wingStatsDevType OBJECT-TYPE
			SYNTAX DisplayString
			MAX-ACCESS read-only
			STATUS current
			DESCRIPTION
				"Device type
				
				XPath: /wing-stats/device[mac=key1]/base/type"
			::= { wingStatsDevEntry 2 }

		
		-- 1.3.6.1.4.1.1916.2.131.50.1.4.2.1.1.3
		wingStatsDevHostname OBJECT-TYPE
			SYNTAX DisplayString
			MAX-ACCESS read-only
			STATUS current
			DESCRIPTION
				"Device hostname
				
				XPath: /wing-stats/device[mac=key1]/base/hostname"
			::= { wingStatsDevEntry 3 }

		
		-- 1.3.6.1.4.1.1916.2.131.50.1.4.2.1.1.4
		wingStatsDevVersion OBJECT-TYPE
			SYNTAX DisplayString
			MAX-ACCESS read-only
			STATUS current
			DESCRIPTION
				"Device software version
				
				XPath: /wing-stats/device[mac=key1]/base/version"
			::= { wingStatsDevEntry 4 }

		
		-- 1.3.6.1.4.1.1916.2.131.50.1.4.2.1.1.5
		wingStatsDevSerialNo OBJECT-TYPE
			SYNTAX DisplayString
			MAX-ACCESS read-only
			STATUS current
			DESCRIPTION
				"Device serial number
				
				XPath: /wing-stats/device[mac=key1]/base/serial-no"
			::= { wingStatsDevEntry 5 }

		
		-- 1.3.6.1.4.1.1916.2.131.50.1.4.2.1.1.6
		wingStatsDevRfDomainName OBJECT-TYPE
			SYNTAX DisplayString
			MAX-ACCESS read-only
			STATUS current
			DESCRIPTION
				"Device RF Domain name
				
				XPath: /wing-stats/device[mac=key1]/base/rf_domain_name"
			::= { wingStatsDevEntry 6 }

		
		-- 1.3.6.1.4.1.1916.2.131.50.1.4.2.1.1.7
		wingStatsDevOnline OBJECT-TYPE
			SYNTAX TruthValue
			MAX-ACCESS read-only
			STATUS current
			DESCRIPTION
				"Device online status
				
				XPath: /wing-stats/device[mac=key1]/base/online"
			::= { wingStatsDevEntry 7 }

		
-- /wing-stats/device/sysinfo
		-- 1.3.6.1.4.1.1916.2.131.50.1.4.2.2
		wingStatsDevSysInfo OBJECT IDENTIFIER ::= { wingStatsDev 2 }

		
		-- 1.3.6.1.4.1.1916.2.131.50.1.4.2.2.1
		wingStatsDevSysInfoTable OBJECT-TYPE
			SYNTAX SEQUENCE OF WingStatsDevSysInfoEntry
			MAX-ACCESS not-accessible
			STATUS current
			DESCRIPTION
				"
				
				/wing-stats/device/sysinfo"
			::= { wingStatsDevSysInfo 1 }

		
		-- 1.3.6.1.4.1.1916.2.131.50.1.4.2.2.1.1
		wingStatsDevSysInfoEntry OBJECT-TYPE
			SYNTAX WingStatsDevSysInfoEntry
			MAX-ACCESS not-accessible
			STATUS current
			DESCRIPTION
				"An entry in the table."
			INDEX { wingStatsDevMac }
			::= { wingStatsDevSysInfoTable 1 }

		
		WingStatsDevSysInfoEntry ::=
			SEQUENCE { 
				wingStatsDevSysInfoFreeMem
					Unsigned32,
				wingStatsDevSysInfoTotalMem
					Unsigned32,
				wingStatsDevSysInfoFreeRamCurrent
					Unsigned32,
				wingStatsDevSysInfoFreeRamLimit
					Unsigned32,
				wingStatsDevSysInfoFdMax
					Unsigned32,
				wingStatsDevSysInfoFdCurrent
					Unsigned32,
				wingStatsDevSysInfoFdLimit
					Unsigned32,
				wingStatsDevSysInfoLoadLimitS0
					Unsigned32,
				wingStatsDevSysInfoLoadLimitS1
					Unsigned32,
				wingStatsDevSysInfoLoadLimitS2
					Unsigned32,
				wingStatsDevSysInfoBufferCurrent0
					Unsigned32,
				wingStatsDevSysInfoBufferCurrent1
					Unsigned32,
				wingStatsDevSysInfoBufferCurrent2
					Unsigned32,
				wingStatsDevSysInfoBufferCurrent3
					Unsigned32,
				wingStatsDevSysInfoBufferCurrent4
					Unsigned32,
				wingStatsDevSysInfoBufferCurrent5
					Unsigned32,
				wingStatsDevSysInfoBufferCurrent6
					Unsigned32,
				wingStatsDevSysInfoBufferCurrent7
					Unsigned32,
				wingStatsDevSysInfoBufferCurrent8
					Unsigned32,
				wingStatsDevSysInfoBufferCurrent9
					Unsigned32,
				wingStatsDevSysInfoBufferCurrent10
					Unsigned32,
				wingStatsDevSysInfoBufferCurrent11
					Unsigned32,
				wingStatsDevSysInfoBufferCurrent12
					Unsigned32,
				wingStatsDevSysInfoBufferTotal0
					Unsigned32,
				wingStatsDevSysInfoBufferTotal1
					Unsigned32,
				wingStatsDevSysInfoBufferTotal2
					Unsigned32,
				wingStatsDevSysInfoBufferTotal3
					Unsigned32,
				wingStatsDevSysInfoBufferTotal4
					Unsigned32,
				wingStatsDevSysInfoBufferTotal5
					Unsigned32,
				wingStatsDevSysInfoBufferTotal6
					Unsigned32,
				wingStatsDevSysInfoBufferTotal7
					Unsigned32,
				wingStatsDevSysInfoBufferTotal8
					Unsigned32,
				wingStatsDevSysInfoBufferTotal9
					Unsigned32,
				wingStatsDevSysInfoBufferTotal10
					Unsigned32,
				wingStatsDevSysInfoBufferTotal11
					Unsigned32,
				wingStatsDevSysInfoBufferTotal12
					Unsigned32
			 }

		-- 1.3.6.1.4.1.1916.2.131.50.1.4.2.2.1.1.1
		wingStatsDevSysInfoFreeMem OBJECT-TYPE
			SYNTAX Unsigned32
			MAX-ACCESS read-only
			STATUS current
			DESCRIPTION
				"Available ram in megabytes
				
				XPath: /wing-stats/device[mac=key1]/sysinfo/free_mem"
			::= { wingStatsDevSysInfoEntry 1 }

		
		-- 1.3.6.1.4.1.1916.2.131.50.1.4.2.2.1.1.2
		wingStatsDevSysInfoTotalMem OBJECT-TYPE
			SYNTAX Unsigned32
			MAX-ACCESS read-only
			STATUS current
			DESCRIPTION
				"Total system ram in megabytes
				
				XPath: /wing-stats/device[mac=key1]/sysinfo/total_mem"
			::= { wingStatsDevSysInfoEntry 2 }

		
		-- 1.3.6.1.4.1.1916.2.131.50.1.4.2.2.1.1.3
		wingStatsDevSysInfoFreeRamCurrent OBJECT-TYPE
			SYNTAX Unsigned32
			MAX-ACCESS read-only
			STATUS current
			DESCRIPTION
				"10 times the percentage of currently free RAM
				(687 => 68.7% is free)
				
				XPath: /wing-stats/device[mac=key1]/sysinfo/free_ram_limit_current"
			::= { wingStatsDevSysInfoEntry 3 }

		
		-- 1.3.6.1.4.1.1916.2.131.50.1.4.2.2.1.1.4
		wingStatsDevSysInfoFreeRamLimit OBJECT-TYPE
			SYNTAX Unsigned32
			MAX-ACCESS read-only
			STATUS current
			DESCRIPTION
				"10 times the recommended minimum available RAM
				(100 => 10% needed)
				
				XPath: /wing-stats/device[mac=key1]/sysinfo/free_ram_limit_limit"
			::= { wingStatsDevSysInfoEntry 4 }

		
		-- 1.3.6.1.4.1.1916.2.131.50.1.4.2.2.1.1.5
		wingStatsDevSysInfoFdMax OBJECT-TYPE
			SYNTAX Unsigned32
			MAX-ACCESS read-only
			STATUS current
			DESCRIPTION
				"Used to calculate the number of 'used' file descriptors
				(fdMax - fdCurrent)
				
				XPath: /wing-stats/device[mac=key1]/sysinfo/fd_max"
			::= { wingStatsDevSysInfoEntry 5 }

		
		-- 1.3.6.1.4.1.1916.2.131.50.1.4.2.2.1.1.6
		wingStatsDevSysInfoFdCurrent OBJECT-TYPE
			SYNTAX Unsigned32
			MAX-ACCESS read-only
			STATUS current
			DESCRIPTION
				"The number of file descriptors currently in use
				
				XPath: /wing-stats/device[mac=key1]/sysinfo/fd_current"
			::= { wingStatsDevSysInfoEntry 6 }

		
		-- 1.3.6.1.4.1.1916.2.131.50.1.4.2.2.1.1.7
		wingStatsDevSysInfoFdLimit OBJECT-TYPE
			SYNTAX Unsigned32
			MAX-ACCESS read-only
			STATUS current
			DESCRIPTION
				"The maximum number of file descriptors
				
				XPath: /wing-stats/device[mac=key1]/sysinfo/fd_limit_limit"
			::= { wingStatsDevSysInfoEntry 7 }

		
		-- 1.3.6.1.4.1.1916.2.131.50.1.4.2.2.1.1.8
		wingStatsDevSysInfoLoadLimitS0 OBJECT-TYPE
			SYNTAX Unsigned32
			MAX-ACCESS read-only
			STATUS current
			DESCRIPTION
				"10 times the average cpu load over the last minute
				(2 => .2 % cpu load)
				
				XPath: /wing-stats/device[mac=key1]/sysinfo/load_limit_s0"
			::= { wingStatsDevSysInfoEntry 8 }

		
		-- 1.3.6.1.4.1.1916.2.131.50.1.4.2.2.1.1.9
		wingStatsDevSysInfoLoadLimitS1 OBJECT-TYPE
			SYNTAX Unsigned32
			MAX-ACCESS read-only
			STATUS current
			DESCRIPTION
				"10 times the average cpu load over the last five minutes
				(2 => .2 % cpu load)
				
				XPath: /wing-stats/device[mac=key1]/sysinfo/load_limit_s1"
			::= { wingStatsDevSysInfoEntry 9 }

		
		-- 1.3.6.1.4.1.1916.2.131.50.1.4.2.2.1.1.10
		wingStatsDevSysInfoLoadLimitS2 OBJECT-TYPE
			SYNTAX Unsigned32
			MAX-ACCESS read-only
			STATUS current
			DESCRIPTION
				"10 times the average cpu load over the last fifteen minutes
				(2 => .2 % cpu load)
				
				XPath: /wing-stats/device[mac=key1]/sysinfo/load_limit_s2"
			::= { wingStatsDevSysInfoEntry 10 }

		
		-- 1.3.6.1.4.1.1916.2.131.50.1.4.2.2.1.1.11
		wingStatsDevSysInfoBufferCurrent0 OBJECT-TYPE
			SYNTAX Unsigned32
			MAX-ACCESS read-only
			STATUS current
			DESCRIPTION
				"The current number of 32 byte buffers in use
				
				XPath: /wing-stats/device[mac=key1]/sysinfo/b_limit_c0"
			::= { wingStatsDevSysInfoEntry 11 }

		
		-- 1.3.6.1.4.1.1916.2.131.50.1.4.2.2.1.1.12
		wingStatsDevSysInfoBufferCurrent1 OBJECT-TYPE
			SYNTAX Unsigned32
			MAX-ACCESS read-only
			STATUS current
			DESCRIPTION
				"The current number of 64 byte buffers in use
				
				XPath: /wing-stats/device[mac=key1]/sysinfo/b_limit_c1"
			::= { wingStatsDevSysInfoEntry 12 }

		
		-- 1.3.6.1.4.1.1916.2.131.50.1.4.2.2.1.1.13
		wingStatsDevSysInfoBufferCurrent2 OBJECT-TYPE
			SYNTAX Unsigned32
			MAX-ACCESS read-only
			STATUS current
			DESCRIPTION
				"The current number of 128 byte buffers in use
				
				XPath: /wing-stats/device[mac=key1]/sysinfo/b_limit_c2"
			::= { wingStatsDevSysInfoEntry 13 }

		
		-- 1.3.6.1.4.1.1916.2.131.50.1.4.2.2.1.1.14
		wingStatsDevSysInfoBufferCurrent3 OBJECT-TYPE
			SYNTAX Unsigned32
			MAX-ACCESS read-only
			STATUS current
			DESCRIPTION
				"The current number of 256 byte buffers in use
				
				XPath: /wing-stats/device[mac=key1]/sysinfo/b_limit_c3"
			::= { wingStatsDevSysInfoEntry 14 }

		
		-- 1.3.6.1.4.1.1916.2.131.50.1.4.2.2.1.1.15
		wingStatsDevSysInfoBufferCurrent4 OBJECT-TYPE
			SYNTAX Unsigned32
			MAX-ACCESS read-only
			STATUS current
			DESCRIPTION
				"The current number of 512 byte buffers in use
				
				XPath: /wing-stats/device[mac=key1]/sysinfo/b_limit_c4"
			::= { wingStatsDevSysInfoEntry 15 }

		
		-- 1.3.6.1.4.1.1916.2.131.50.1.4.2.2.1.1.16
		wingStatsDevSysInfoBufferCurrent5 OBJECT-TYPE
			SYNTAX Unsigned32
			MAX-ACCESS read-only
			STATUS current
			DESCRIPTION
				"The current number of 1Kb buffers in use
				
				XPath: /wing-stats/device[mac=key1]/sysinfo/b_limit_c5"
			::= { wingStatsDevSysInfoEntry 16 }

		
		-- 1.3.6.1.4.1.1916.2.131.50.1.4.2.2.1.1.17
		wingStatsDevSysInfoBufferCurrent6 OBJECT-TYPE
			SYNTAX Unsigned32
			MAX-ACCESS read-only
			STATUS current
			DESCRIPTION
				"The current number of 2Kb buffers in use
				
				XPath: /wing-stats/device[mac=key1]/sysinfo/b_limit_c6"
			::= { wingStatsDevSysInfoEntry 17 }

		
		-- 1.3.6.1.4.1.1916.2.131.50.1.4.2.2.1.1.18
		wingStatsDevSysInfoBufferCurrent7 OBJECT-TYPE
			SYNTAX Unsigned32
			MAX-ACCESS read-only
			STATUS current
			DESCRIPTION
				"The current number of 4Kb byte buffers in use
				
				XPath: /wing-stats/device[mac=key1]/sysinfo/b_limit_c7"
			::= { wingStatsDevSysInfoEntry 18 }

		
		-- 1.3.6.1.4.1.1916.2.131.50.1.4.2.2.1.1.19
		wingStatsDevSysInfoBufferCurrent8 OBJECT-TYPE
			SYNTAX Unsigned32
			MAX-ACCESS read-only
			STATUS current
			DESCRIPTION
				"The current number of 8Kb byte buffers in use
				
				XPath: /wing-stats/device[mac=key1]/sysinfo/b_limit_c8"
			::= { wingStatsDevSysInfoEntry 19 }

		
		-- 1.3.6.1.4.1.1916.2.131.50.1.4.2.2.1.1.20
		wingStatsDevSysInfoBufferCurrent9 OBJECT-TYPE
			SYNTAX Unsigned32
			MAX-ACCESS read-only
			STATUS current
			DESCRIPTION
				"The current number of 16Kb buffers in use
				
				XPath: /wing-stats/device[mac=key1]/sysinfo/b_limit_c9"
			::= { wingStatsDevSysInfoEntry 20 }

		
		-- 1.3.6.1.4.1.1916.2.131.50.1.4.2.2.1.1.21
		wingStatsDevSysInfoBufferCurrent10 OBJECT-TYPE
			SYNTAX Unsigned32
			MAX-ACCESS read-only
			STATUS current
			DESCRIPTION
				"The current number of 32Kb buffers in use
				
				XPath: /wing-stats/device[mac=key1]/sysinfo/b_limit_c10"
			::= { wingStatsDevSysInfoEntry 21 }

		
		-- 1.3.6.1.4.1.1916.2.131.50.1.4.2.2.1.1.22
		wingStatsDevSysInfoBufferCurrent11 OBJECT-TYPE
			SYNTAX Unsigned32
			MAX-ACCESS read-only
			STATUS current
			DESCRIPTION
				"The current number of 64Kb buffers in use
				
				XPath: /wing-stats/device[mac=key1]/sysinfo/b_limit_c11"
			::= { wingStatsDevSysInfoEntry 22 }

		
		-- 1.3.6.1.4.1.1916.2.131.50.1.4.2.2.1.1.23
		wingStatsDevSysInfoBufferCurrent12 OBJECT-TYPE
			SYNTAX Unsigned32
			MAX-ACCESS read-only
			STATUS current
			DESCRIPTION
				"The current number of 128Kb buffers in use
				
				XPath: /wing-stats/device[mac=key1]/sysinfo/b_limit_c12"
			::= { wingStatsDevSysInfoEntry 23 }

		
		-- 1.3.6.1.4.1.1916.2.131.50.1.4.2.2.1.1.24
		wingStatsDevSysInfoBufferTotal0 OBJECT-TYPE
			SYNTAX Unsigned32
			MAX-ACCESS read-only
			STATUS current
			DESCRIPTION
				"The total number of 32 byte buffers available
				
				XPath: /wing-stats/device[mac=key1]/sysinfo/b_limit_l0"
			::= { wingStatsDevSysInfoEntry 24 }

		
		-- 1.3.6.1.4.1.1916.2.131.50.1.4.2.2.1.1.25
		wingStatsDevSysInfoBufferTotal1 OBJECT-TYPE
			SYNTAX Unsigned32
			MAX-ACCESS read-only
			STATUS current
			DESCRIPTION
				"The total number of 64 byte buffers available
				
				XPath: /wing-stats/device[mac=key1]/sysinfo/b_limit_l1"
			::= { wingStatsDevSysInfoEntry 25 }

		
		-- 1.3.6.1.4.1.1916.2.131.50.1.4.2.2.1.1.26
		wingStatsDevSysInfoBufferTotal2 OBJECT-TYPE
			SYNTAX Unsigned32
			MAX-ACCESS read-only
			STATUS current
			DESCRIPTION
				"The total number of 128 byte buffers available
				
				XPath: /wing-stats/device[mac=key1]/sysinfo/b_limit_l2"
			::= { wingStatsDevSysInfoEntry 26 }

		
		-- 1.3.6.1.4.1.1916.2.131.50.1.4.2.2.1.1.27
		wingStatsDevSysInfoBufferTotal3 OBJECT-TYPE
			SYNTAX Unsigned32
			MAX-ACCESS read-only
			STATUS current
			DESCRIPTION
				"The total number of 256 byte buffers available
				
				XPath: /wing-stats/device[mac=key1]/sysinfo/b_limit_l3"
			::= { wingStatsDevSysInfoEntry 27 }

		
		-- 1.3.6.1.4.1.1916.2.131.50.1.4.2.2.1.1.28
		wingStatsDevSysInfoBufferTotal4 OBJECT-TYPE
			SYNTAX Unsigned32
			MAX-ACCESS read-only
			STATUS current
			DESCRIPTION
				"The total number of 512 byte buffers available
				
				XPath: /wing-stats/device[mac=key1]/sysinfo/b_limit_l4"
			::= { wingStatsDevSysInfoEntry 28 }

		
		-- 1.3.6.1.4.1.1916.2.131.50.1.4.2.2.1.1.29
		wingStatsDevSysInfoBufferTotal5 OBJECT-TYPE
			SYNTAX Unsigned32
			MAX-ACCESS read-only
			STATUS current
			DESCRIPTION
				"The total number of 1Kb buffers available
				
				XPath: /wing-stats/device[mac=key1]/sysinfo/b_limit_l5"
			::= { wingStatsDevSysInfoEntry 29 }

		
		-- 1.3.6.1.4.1.1916.2.131.50.1.4.2.2.1.1.30
		wingStatsDevSysInfoBufferTotal6 OBJECT-TYPE
			SYNTAX Unsigned32
			MAX-ACCESS read-only
			STATUS current
			DESCRIPTION
				"The total number of 2Kb buffers available
				
				XPath: /wing-stats/device[mac=key1]/sysinfo/b_limit_l6"
			::= { wingStatsDevSysInfoEntry 30 }

		
		-- 1.3.6.1.4.1.1916.2.131.50.1.4.2.2.1.1.31
		wingStatsDevSysInfoBufferTotal7 OBJECT-TYPE
			SYNTAX Unsigned32
			MAX-ACCESS read-only
			STATUS current
			DESCRIPTION
				"The total number of 4Kb buffers available
				
				XPath: /wing-stats/device[mac=key1]/sysinfo/b_limit_l7"
			::= { wingStatsDevSysInfoEntry 31 }

		
		-- 1.3.6.1.4.1.1916.2.131.50.1.4.2.2.1.1.32
		wingStatsDevSysInfoBufferTotal8 OBJECT-TYPE
			SYNTAX Unsigned32
			MAX-ACCESS read-only
			STATUS current
			DESCRIPTION
				"The total number of 8Kb buffers available
				
				XPath: /wing-stats/device[mac=key1]/sysinfo/b_limit_l8"
			::= { wingStatsDevSysInfoEntry 32 }

		
		-- 1.3.6.1.4.1.1916.2.131.50.1.4.2.2.1.1.33
		wingStatsDevSysInfoBufferTotal9 OBJECT-TYPE
			SYNTAX Unsigned32
			MAX-ACCESS read-only
			STATUS current
			DESCRIPTION
				"The total number of 16Kb buffers available
				
				XPath: /wing-stats/device[mac=key1]/sysinfo/b_limit_l9"
			::= { wingStatsDevSysInfoEntry 33 }

		
		-- 1.3.6.1.4.1.1916.2.131.50.1.4.2.2.1.1.34
		wingStatsDevSysInfoBufferTotal10 OBJECT-TYPE
			SYNTAX Unsigned32
			MAX-ACCESS read-only
			STATUS current
			DESCRIPTION
				"The total number of 32Kb buffers available
				
				XPath: /wing-stats/device[mac=key1]/sysinfo/b_limit_l10"
			::= { wingStatsDevSysInfoEntry 34 }

		
		-- 1.3.6.1.4.1.1916.2.131.50.1.4.2.2.1.1.35
		wingStatsDevSysInfoBufferTotal11 OBJECT-TYPE
			SYNTAX Unsigned32
			MAX-ACCESS read-only
			STATUS current
			DESCRIPTION
				"The total number of 64Kb buffers available
				
				XPath: /wing-stats/device[mac=key1]/sysinfo/b_limit_l11"
			::= { wingStatsDevSysInfoEntry 35 }

		
		-- 1.3.6.1.4.1.1916.2.131.50.1.4.2.2.1.1.36
		wingStatsDevSysInfoBufferTotal12 OBJECT-TYPE
			SYNTAX Unsigned32
			MAX-ACCESS read-only
			STATUS current
			DESCRIPTION
				"The total number of 128Kb buffers available
				
				XPath: /wing-stats/device[mac=key1]/sysinfo/b_limit_l12"
			::= { wingStatsDevSysInfoEntry 36 }

		
-- /wing-stats/device/system
		-- 1.3.6.1.4.1.1916.2.131.50.1.4.2.4
		wingStatsDevSys OBJECT IDENTIFIER ::= { wingStatsDev 4 }

		
		-- 1.3.6.1.4.1.1916.2.131.50.1.4.2.4.1
		wingStatsDevSysTable OBJECT-TYPE
			SYNTAX SEQUENCE OF WingStatsDevSysEntry
			MAX-ACCESS not-accessible
			STATUS current
			DESCRIPTION
				"
				
				/wing-stats/device/system"
			::= { wingStatsDevSys 1 }

		
		-- 1.3.6.1.4.1.1916.2.131.50.1.4.2.4.1.1
		wingStatsDevSysEntry OBJECT-TYPE
			SYNTAX WingStatsDevSysEntry
			MAX-ACCESS not-accessible
			STATUS current
			DESCRIPTION
				"An entry in the table."
			INDEX { wingStatsDevMac }
			::= { wingStatsDevSysTable 1 }

		
		WingStatsDevSysEntry ::=
			SEQUENCE { 
				wingStatsDevSysProductName
					DisplayString,
				wingStatsDevSysSerialNo
					DisplayString,
				wingStatsDevSysVersion
					DisplayString,
				wingStatsDevSysPrimaryVersion
					DisplayString,
				wingStatsDevSysSecondaryVersion
					DisplayString,
				wingStatsDevSysPrimaryBuildDate
					DisplayString,
				wingStatsDevSysSecondaryBuildDate
					DisplayString,
				wingStatsDevSysPrimaryInstallDate
					DisplayString,
				wingStatsDevSysSecondaryInstallDate
					DisplayString,
				wingStatsDevSysBootPartition
					DisplayString,
				wingStatsDevSysNextBoot
					DisplayString,
				wingStatsDevSysIsFallback
					TruthValue,
				wingStatsDevSysImgFallback
					DisplayString,
				wingStatsDevSysUptime
					DisplayString,
				wingStatsDevSysCpu
					DisplayString,
				wingStatsDevSysRam
					DisplayString,
				wingStatsDevSysClock
					DisplayString,
				wingStatsDevSysUpgradeStatus
					DisplayString,
				wingStatsDevSysUpgradeTime
					DisplayString,
				wingStatsDevSysPoeFwVersion
					DisplayString,
				wingStatsDevSysFpgaVersion
					DisplayString,
				wingStatsDevSysModelNumber
					DisplayString
			 }

		-- 1.3.6.1.4.1.1916.2.131.50.1.4.2.4.1.1.1
		wingStatsDevSysProductName OBJECT-TYPE
			SYNTAX DisplayString
			MAX-ACCESS read-only
			STATUS current
			DESCRIPTION
				"Product name string
				
				XPath: /wing-stats/device[mac=key1]/system/product-name"
			::= { wingStatsDevSysEntry 1 }

		
		-- 1.3.6.1.4.1.1916.2.131.50.1.4.2.4.1.1.2
		wingStatsDevSysSerialNo OBJECT-TYPE
			SYNTAX DisplayString
			MAX-ACCESS read-only
			STATUS current
			DESCRIPTION
				"
				
				XPath: /wing-stats/device[mac=key1]/system/serial-no"
			::= { wingStatsDevSysEntry 2 }

		
		-- 1.3.6.1.4.1.1916.2.131.50.1.4.2.4.1.1.3
		wingStatsDevSysVersion OBJECT-TYPE
			SYNTAX DisplayString
			MAX-ACCESS read-only
			STATUS current
			DESCRIPTION
				"Current running device firmware version
				
				XPath: /wing-stats/device[mac=key1]/system/version"
			::= { wingStatsDevSysEntry 3 }

		
		-- 1.3.6.1.4.1.1916.2.131.50.1.4.2.4.1.1.4
		wingStatsDevSysPrimaryVersion OBJECT-TYPE
			SYNTAX DisplayString
			MAX-ACCESS read-only
			STATUS current
			DESCRIPTION
				"Device firmware version installed on primary partition
				
				XPath: /wing-stats/device[mac=key1]/system/primary-version"
			::= { wingStatsDevSysEntry 4 }

		
		-- 1.3.6.1.4.1.1916.2.131.50.1.4.2.4.1.1.5
		wingStatsDevSysSecondaryVersion OBJECT-TYPE
			SYNTAX DisplayString
			MAX-ACCESS read-only
			STATUS current
			DESCRIPTION
				"Device firmware version installed on secondary partition
				
				XPath: /wing-stats/device[mac=key1]/system/secondary-version"
			::= { wingStatsDevSysEntry 5 }

		
		-- 1.3.6.1.4.1.1916.2.131.50.1.4.2.4.1.1.6
		wingStatsDevSysPrimaryBuildDate OBJECT-TYPE
			SYNTAX DisplayString
			MAX-ACCESS read-only
			STATUS current
			DESCRIPTION
				"Firmware build date on primary partition
				
				XPath: /wing-stats/device[mac=key1]/system/primary-build-date"
			::= { wingStatsDevSysEntry 6 }

		
		-- 1.3.6.1.4.1.1916.2.131.50.1.4.2.4.1.1.7
		wingStatsDevSysSecondaryBuildDate OBJECT-TYPE
			SYNTAX DisplayString
			MAX-ACCESS read-only
			STATUS current
			DESCRIPTION
				"Firmware build date on secondary partition
				
				XPath: /wing-stats/device[mac=key1]/system/secondary-build-date"
			::= { wingStatsDevSysEntry 7 }

		
		-- 1.3.6.1.4.1.1916.2.131.50.1.4.2.4.1.1.8
		wingStatsDevSysPrimaryInstallDate OBJECT-TYPE
			SYNTAX DisplayString
			MAX-ACCESS read-only
			STATUS current
			DESCRIPTION
				"Firmware install date on primary partition
				
				XPath: /wing-stats/device[mac=key1]/system/primary-install-date"
			::= { wingStatsDevSysEntry 8 }

		
		-- 1.3.6.1.4.1.1916.2.131.50.1.4.2.4.1.1.9
		wingStatsDevSysSecondaryInstallDate OBJECT-TYPE
			SYNTAX DisplayString
			MAX-ACCESS read-only
			STATUS current
			DESCRIPTION
				"Firmware install date on secondary partition
				
				XPath: /wing-stats/device[mac=key1]/system/secondary-install-date"
			::= { wingStatsDevSysEntry 9 }

		
		-- 1.3.6.1.4.1.1916.2.131.50.1.4.2.4.1.1.10
		wingStatsDevSysBootPartition OBJECT-TYPE
			SYNTAX DisplayString
			MAX-ACCESS read-only
			STATUS current
			DESCRIPTION
				"Current system boot partition name
				
				Values:
				primary,
				secondary,
				unknown
				
				XPath: /wing-stats/device[mac=key1]/system/boot-partition"
			::= { wingStatsDevSysEntry 10 }

		
		-- 1.3.6.1.4.1.1916.2.131.50.1.4.2.4.1.1.11
		wingStatsDevSysNextBoot OBJECT-TYPE
			SYNTAX DisplayString
			MAX-ACCESS read-only
			STATUS current
			DESCRIPTION
				"Next system boot partition name 
				
				Values:
				primary,
				secondary,
				unknown
				
				XPath: /wing-stats/device[mac=key1]/system/next-boot"
			::= { wingStatsDevSysEntry 11 }

		
		-- 1.3.6.1.4.1.1916.2.131.50.1.4.2.4.1.1.12
		wingStatsDevSysIsFallback OBJECT-TYPE
			SYNTAX TruthValue
			MAX-ACCESS read-only
			STATUS current
			DESCRIPTION
				"Whether fallback is enabled or not
				
				XPath: /wing-stats/device[mac=key1]/system/is-fallback"
			::= { wingStatsDevSysEntry 12 }

		
		-- 1.3.6.1.4.1.1916.2.131.50.1.4.2.4.1.1.13
		wingStatsDevSysImgFallback OBJECT-TYPE
			SYNTAX DisplayString
			MAX-ACCESS read-only
			STATUS current
			DESCRIPTION
				"
				
				Values:
				Enabled,
				Disabled
				
				XPath: /wing-stats/device[mac=key1]/system/img-fallback"
			::= { wingStatsDevSysEntry 13 }

		
		-- 1.3.6.1.4.1.1916.2.131.50.1.4.2.4.1.1.14
		wingStatsDevSysUptime OBJECT-TYPE
			SYNTAX DisplayString
			MAX-ACCESS read-only
			STATUS current
			DESCRIPTION
				"Current system uptime
				
				XPath: /wing-stats/device[mac=key1]/system/uptime"
			::= { wingStatsDevSysEntry 14 }

		
		-- 1.3.6.1.4.1.1916.2.131.50.1.4.2.4.1.1.15
		wingStatsDevSysCpu OBJECT-TYPE
			SYNTAX DisplayString
			MAX-ACCESS read-only
			STATUS current
			DESCRIPTION
				"Current cpu info
				
				XPath: /wing-stats/device[mac=key1]/system/cpu"
			::= { wingStatsDevSysEntry 15 }

		
		-- 1.3.6.1.4.1.1916.2.131.50.1.4.2.4.1.1.16
		wingStatsDevSysRam OBJECT-TYPE
			SYNTAX DisplayString
			MAX-ACCESS read-only
			STATUS current
			DESCRIPTION
				"Current system ram info
				
				XPath: /wing-stats/device[mac=key1]/system/ram"
			::= { wingStatsDevSysEntry 16 }

		
		-- 1.3.6.1.4.1.1916.2.131.50.1.4.2.4.1.1.17
		wingStatsDevSysClock OBJECT-TYPE
			SYNTAX DisplayString
			MAX-ACCESS read-only
			STATUS current
			DESCRIPTION
				"Current date and time
				
				XPath: /wing-stats/device[mac=key1]/system/clock"
			::= { wingStatsDevSysEntry 17 }

		
		-- 1.3.6.1.4.1.1916.2.131.50.1.4.2.4.1.1.18
		wingStatsDevSysUpgradeStatus OBJECT-TYPE
			SYNTAX DisplayString
			MAX-ACCESS read-only
			STATUS current
			DESCRIPTION
				"
				
				XPath: /wing-stats/device[mac=key1]/system/upgrade-status/status"
			::= { wingStatsDevSysEntry 18 }

		
		-- 1.3.6.1.4.1.1916.2.131.50.1.4.2.4.1.1.19
		wingStatsDevSysUpgradeTime OBJECT-TYPE
			SYNTAX DisplayString
			MAX-ACCESS read-only
			STATUS current
			DESCRIPTION
				"Time of last upgrade
				
				XPath: /wing-stats/device[mac=key1]/system/upgrade-status/time"
			::= { wingStatsDevSysEntry 19 }

		
		-- 1.3.6.1.4.1.1916.2.131.50.1.4.2.4.1.1.21
		wingStatsDevSysPoeFwVersion OBJECT-TYPE
			SYNTAX DisplayString
			MAX-ACCESS read-only
			STATUS current
			DESCRIPTION
				"Current poe firmware version
				
				XPath: /wing-stats/device[mac=key1]/system/poe-fw-version"
			::= { wingStatsDevSysEntry 21 }

		
		-- 1.3.6.1.4.1.1916.2.131.50.1.4.2.4.1.1.22
		wingStatsDevSysFpgaVersion OBJECT-TYPE
			SYNTAX DisplayString
			MAX-ACCESS read-only
			STATUS current
			DESCRIPTION
				"Current fpga version
				
				XPath: /wing-stats/device[mac=key1]/system/fpga-version"
			::= { wingStatsDevSysEntry 22 }

		
		-- 1.3.6.1.4.1.1916.2.131.50.1.4.2.4.1.1.23
		wingStatsDevSysModelNumber OBJECT-TYPE
			SYNTAX DisplayString
			MAX-ACCESS read-only
			STATUS current
			DESCRIPTION
				"System model number
				
				XPath: /wing-stats/device[mac=key1]/system/model-number"
			::= { wingStatsDevSysEntry 23 }

		
-- /wing-stats/device/interface
		-- 1.3.6.1.4.1.1916.2.131.50.1.4.2.6
		wingStatsDevIf OBJECT IDENTIFIER ::= { wingStatsDev 6 }

		
		-- 1.3.6.1.4.1.1916.2.131.50.1.4.2.6.1
		wingStatsDevIfTable OBJECT-TYPE
			SYNTAX SEQUENCE OF WingStatsDevIfEntry
			MAX-ACCESS not-accessible
			STATUS current
			DESCRIPTION
				"
				
				/wing-stats/device/interface"
			::= { wingStatsDevIf 1 }

		
		-- 1.3.6.1.4.1.1916.2.131.50.1.4.2.6.1.1
		wingStatsDevIfEntry OBJECT-TYPE
			SYNTAX WingStatsDevIfEntry
			MAX-ACCESS not-accessible
			STATUS current
			DESCRIPTION
				"An entry in the table."
			INDEX { wingStatsDevMac, wingStatsDevIfName }
			::= { wingStatsDevIfTable 1 }

		
		WingStatsDevIfEntry ::=
			SEQUENCE { 
				wingStatsDevIfName
					WingIdentifier,
				wingStatsDevIfIndex
					Unsigned32,
				wingStatsDevIfHwType
					DisplayString,
				wingStatsDevIfMode
					DisplayString,
				wingStatsDevIfMac
					MacAddress,
				wingStatsDevIfStatusAdmin
					DisplayString,
				wingStatsDevIfMtu
					Unsigned32,
				wingStatsDevIfGoodOctetsRcv
					Counter64,
				wingStatsDevIfGoodPktsRcv
					Counter64,
				wingStatsDevIfDropEvents
					Counter64,
				wingStatsDevIfUcPktsRcv
					Counter64,
				wingStatsDevIfBrdcPktsRcv
					Counter64,
				wingStatsDevIfMcPktsRcv
					Counter64,
				wingStatsDevIfBadPktsRcv
					Counter64,
				wingStatsDevIfUndersizePkts
					Counter64,
				wingStatsDevIfOversizePkts
					Counter64,
				wingStatsDevIfBadCrc
					Counter64,
				wingStatsDevIfMacRcvError
					Counter64,
				wingStatsDevIfFragmentsPkts
					Counter64,
				wingStatsDevIfJabberPkts
					Counter64,
				wingStatsDevIfGoodOctetsSent
					Counter64,
				wingStatsDevIfGoodPktsSent
					Counter64,
				wingStatsDevIfMacTransmitErr
					Counter64,
				wingStatsDevIfUcPktsSent
					Counter64,
				wingStatsDevIfBrdcPktsSent
					Counter64,
				wingStatsDevIfMcPktsSent
					Counter64,
				wingStatsDevIfLateCollisions
					Counter64,
				wingStatsDevIfExcessiveCollisions
					Counter64,
				wingStatsDevIfCollisions
					Counter64,
				wingStatsDevIfMetric
					Integer32,
				wingStatsDevIfRxFifoErrors
					Counter32,
				wingStatsDevIfRxOverErrors
					Counter32,
				wingStatsDevIfTxWindowErrors
					Counter32,
				wingStatsDevIfTxFifoErrors
					Counter32,
				wingStatsDevIfTxAbortedErrors
					Counter32,
				wingStatsDevIfTxCarrierErrors
					Counter32,
				wingStatsDevIfTxDropped
					Counter32,
				wingStatsDevIfRxLengthErrors
					Counter32,
				wingStatsDevIfRxMissedErrors
					Counter32,
				wingStatsDevIfRxFrameErrors
					Counter32,
				wingStatsDevIfTxErrors
					Counter32,
				wingStatsDevIfTxHeartbeatErrors
					Counter32,
				wingStatsDevIfStatusOper
					DisplayString
			 }

		-- 1.3.6.1.4.1.1916.2.131.50.1.4.2.6.1.1.1
		wingStatsDevIfName OBJECT-TYPE
			SYNTAX WingIdentifier
			MAX-ACCESS read-only
			STATUS current
			DESCRIPTION
				"Interface name. Eg., ge1, vlan1, radio1 ...
				
				XPath: /wing-stats/device[mac=key1]/interface[name=key2]/name"
			::= { wingStatsDevIfEntry 1 }

		
		-- 1.3.6.1.4.1.1916.2.131.50.1.4.2.6.1.1.2
		wingStatsDevIfIndex OBJECT-TYPE
			SYNTAX Unsigned32
			MAX-ACCESS read-only
			STATUS current
			DESCRIPTION
				"Interface index
				
				XPath: /wing-stats/device[mac=key1]/interface[name=key2]/index"
			::= { wingStatsDevIfEntry 2 }

		
		-- 1.3.6.1.4.1.1916.2.131.50.1.4.2.6.1.1.3
		wingStatsDevIfHwType OBJECT-TYPE
			SYNTAX DisplayString
			MAX-ACCESS read-only
			STATUS current
			DESCRIPTION
				"Hardware type of the network interface
				
				Values:
				ethernet,
				vlan,
				radio,
				aggregate,
				ppp
				
				XPath: /wing-stats/device[mac=key1]/interface[name=key2]/hw_type"
			::= { wingStatsDevIfEntry 3 }

		
		-- 1.3.6.1.4.1.1916.2.131.50.1.4.2.6.1.1.4
		wingStatsDevIfMode OBJECT-TYPE
			SYNTAX DisplayString
			MAX-ACCESS read-only
			STATUS current
			DESCRIPTION
				"
				
				Values:
				Layer 2,
				Layer 3
				
				XPath: /wing-stats/device[mac=key1]/interface[name=key2]/mode"
			::= { wingStatsDevIfEntry 4 }

		
		-- 1.3.6.1.4.1.1916.2.131.50.1.4.2.6.1.1.5
		wingStatsDevIfMac OBJECT-TYPE
			SYNTAX MacAddress
			MAX-ACCESS read-only
			STATUS current
			DESCRIPTION
				"Interface MAC address
				
				XPath: /wing-stats/device[mac=key1]/interface[name=key2]/mac"
			::= { wingStatsDevIfEntry 5 }

		
		-- 1.3.6.1.4.1.1916.2.131.50.1.4.2.6.1.1.6
		wingStatsDevIfStatusAdmin OBJECT-TYPE
			SYNTAX DisplayString
			MAX-ACCESS read-only
			STATUS current
			DESCRIPTION
				"Administrative status of interface (up/down)
				
				Values:
				up
				down
				
				XPath: /wing-stats/device[mac=key1]/interface[name=key2]/status_admin"
			::= { wingStatsDevIfEntry 6 }

		
		-- 1.3.6.1.4.1.1916.2.131.50.1.4.2.6.1.1.7
		wingStatsDevIfMtu OBJECT-TYPE
			SYNTAX Unsigned32
			MAX-ACCESS read-only
			STATUS current
			DESCRIPTION
				"Maximum transmission unit
				
				XPath: /wing-stats/device[mac=key1]/interface[name=key2]/mtu"
			::= { wingStatsDevIfEntry 7 }

		
		-- 1.3.6.1.4.1.1916.2.131.50.1.4.2.6.1.1.8
		wingStatsDevIfGoodOctetsRcv OBJECT-TYPE
			SYNTAX Counter64
			MAX-ACCESS read-only
			STATUS current
			DESCRIPTION
				"Total number of bytes received on the interfaces
				
				XPath: /wing-stats/device[mac=key1]/interface[name=key2]/good_octets_rcv"
			::= { wingStatsDevIfEntry 8 }

		
		-- 1.3.6.1.4.1.1916.2.131.50.1.4.2.6.1.1.9
		wingStatsDevIfGoodPktsRcv OBJECT-TYPE
			SYNTAX Counter64
			MAX-ACCESS read-only
			STATUS current
			DESCRIPTION
				"Total number of packets received on the interface
				
				XPath: /wing-stats/device[mac=key1]/interface[name=key2]/good_pkts_rcv"
			::= { wingStatsDevIfEntry 9 }

		
		-- 1.3.6.1.4.1.1916.2.131.50.1.4.2.6.1.1.10
		wingStatsDevIfDropEvents OBJECT-TYPE
			SYNTAX Counter64
			MAX-ACCESS read-only
			STATUS current
			DESCRIPTION
				"Total number of inbound packets dropped on the interface
				
				XPath: /wing-stats/device[mac=key1]/interface[name=key2]/drop_events"
			::= { wingStatsDevIfEntry 10 }

		
		-- 1.3.6.1.4.1.1916.2.131.50.1.4.2.6.1.1.11
		wingStatsDevIfUcPktsRcv OBJECT-TYPE
			SYNTAX Counter64
			MAX-ACCESS read-only
			STATUS current
			DESCRIPTION
				"Total number of unicast packets received on the interface
				
				XPath: /wing-stats/device[mac=key1]/interface[name=key2]/uc_pkts_rcv"
			::= { wingStatsDevIfEntry 11 }

		
		-- 1.3.6.1.4.1.1916.2.131.50.1.4.2.6.1.1.12
		wingStatsDevIfBrdcPktsRcv OBJECT-TYPE
			SYNTAX Counter64
			MAX-ACCESS read-only
			STATUS current
			DESCRIPTION
				"Total number of broadcast packets received on the interface
				
				XPath: /wing-stats/device[mac=key1]/interface[name=key2]/brdc_pkts_rcv"
			::= { wingStatsDevIfEntry 12 }

		
		-- 1.3.6.1.4.1.1916.2.131.50.1.4.2.6.1.1.13
		wingStatsDevIfMcPktsRcv OBJECT-TYPE
			SYNTAX Counter64
			MAX-ACCESS read-only
			STATUS current
			DESCRIPTION
				"Total number of multicast packets received on the interface
				
				XPath: /wing-stats/device[mac=key1]/interface[name=key2]/mc_pkts_rcv"
			::= { wingStatsDevIfEntry 13 }

		
		-- 1.3.6.1.4.1.1916.2.131.50.1.4.2.6.1.1.14
		wingStatsDevIfBadPktsRcv OBJECT-TYPE
			SYNTAX Counter64
			MAX-ACCESS read-only
			STATUS current
			DESCRIPTION
				"Total number of inbound packets received with error
				on the interface
				
				XPath: /wing-stats/device[mac=key1]/interface[name=key2]/bad_pkts_rcv"
			::= { wingStatsDevIfEntry 14 }

		
		-- 1.3.6.1.4.1.1916.2.131.50.1.4.2.6.1.1.15
		wingStatsDevIfUndersizePkts OBJECT-TYPE
			SYNTAX Counter64
			MAX-ACCESS read-only
			STATUS current
			DESCRIPTION
				"Total number of undersize packets received on the interface
				
				XPath: /wing-stats/device[mac=key1]/interface[name=key2]/undersize_pkts"
			::= { wingStatsDevIfEntry 15 }

		
		-- 1.3.6.1.4.1.1916.2.131.50.1.4.2.6.1.1.16
		wingStatsDevIfOversizePkts OBJECT-TYPE
			SYNTAX Counter64
			MAX-ACCESS read-only
			STATUS current
			DESCRIPTION
				"Total number of oversize packets received on the interface
				
				XPath: /wing-stats/device[mac=key1]/interface[name=key2]/oversize_pkts"
			::= { wingStatsDevIfEntry 16 }

		
		-- 1.3.6.1.4.1.1916.2.131.50.1.4.2.6.1.1.17
		wingStatsDevIfBadCrc OBJECT-TYPE
			SYNTAX Counter64
			MAX-ACCESS read-only
			STATUS current
			DESCRIPTION
				"Total number of packets received with bad crc on the interface
				
				XPath: /wing-stats/device[mac=key1]/interface[name=key2]/bad_crc"
			::= { wingStatsDevIfEntry 17 }

		
		-- 1.3.6.1.4.1.1916.2.131.50.1.4.2.6.1.1.18
		wingStatsDevIfMacRcvError OBJECT-TYPE
			SYNTAX Counter64
			MAX-ACCESS read-only
			STATUS current
			DESCRIPTION
				"Total number of packets received with mac error
				on the interface
				
				XPath: /wing-stats/device[mac=key1]/interface[name=key2]/mac_rcv_error"
			::= { wingStatsDevIfEntry 18 }

		
		-- 1.3.6.1.4.1.1916.2.131.50.1.4.2.6.1.1.19
		wingStatsDevIfFragmentsPkts OBJECT-TYPE
			SYNTAX Counter64
			MAX-ACCESS read-only
			STATUS current
			DESCRIPTION
				"Total number of fragmented packets received on the interface
				
				XPath: /wing-stats/device[mac=key1]/interface[name=key2]/fragments_pkts"
			::= { wingStatsDevIfEntry 19 }

		
		-- 1.3.6.1.4.1.1916.2.131.50.1.4.2.6.1.1.20
		wingStatsDevIfJabberPkts OBJECT-TYPE
			SYNTAX Counter64
			MAX-ACCESS read-only
			STATUS current
			DESCRIPTION
				"Total number of jabber packets received on the interface
				
				XPath: /wing-stats/device[mac=key1]/interface[name=key2]/jabber_pkts"
			::= { wingStatsDevIfEntry 20 }

		
		-- 1.3.6.1.4.1.1916.2.131.50.1.4.2.6.1.1.21
		wingStatsDevIfGoodOctetsSent OBJECT-TYPE
			SYNTAX Counter64
			MAX-ACCESS read-only
			STATUS current
			DESCRIPTION
				"Total number of bytes transmitted on the interfaces
				
				XPath: /wing-stats/device[mac=key1]/interface[name=key2]/good_octets_sent"
			::= { wingStatsDevIfEntry 21 }

		
		-- 1.3.6.1.4.1.1916.2.131.50.1.4.2.6.1.1.22
		wingStatsDevIfGoodPktsSent OBJECT-TYPE
			SYNTAX Counter64
			MAX-ACCESS read-only
			STATUS current
			DESCRIPTION
				"Total number of packets transmitted on the interface
				
				XPath: /wing-stats/device[mac=key1]/interface[name=key2]/good_pkts_sent"
			::= { wingStatsDevIfEntry 22 }

		
		-- 1.3.6.1.4.1.1916.2.131.50.1.4.2.6.1.1.23
		wingStatsDevIfMacTransmitErr OBJECT-TYPE
			SYNTAX Counter64
			MAX-ACCESS read-only
			STATUS current
			DESCRIPTION
				"Total number of packets transmitted with mac error on the interface
				
				XPath: /wing-stats/device[mac=key1]/interface[name=key2]/mac_transmit_err"
			::= { wingStatsDevIfEntry 23 }

		
		-- 1.3.6.1.4.1.1916.2.131.50.1.4.2.6.1.1.24
		wingStatsDevIfUcPktsSent OBJECT-TYPE
			SYNTAX Counter64
			MAX-ACCESS read-only
			STATUS current
			DESCRIPTION
				"Total number of unicast packets transmitted on the interface
				
				XPath: /wing-stats/device[mac=key1]/interface[name=key2]/uc_pkts_sent"
			::= { wingStatsDevIfEntry 24 }

		
		-- 1.3.6.1.4.1.1916.2.131.50.1.4.2.6.1.1.25
		wingStatsDevIfBrdcPktsSent OBJECT-TYPE
			SYNTAX Counter64
			MAX-ACCESS read-only
			STATUS current
			DESCRIPTION
				"Total number of broadcast packets transmitted on the interface
				
				XPath: /wing-stats/device[mac=key1]/interface[name=key2]/brdc_pkts_sent"
			::= { wingStatsDevIfEntry 25 }

		
		-- 1.3.6.1.4.1.1916.2.131.50.1.4.2.6.1.1.26
		wingStatsDevIfMcPktsSent OBJECT-TYPE
			SYNTAX Counter64
			MAX-ACCESS read-only
			STATUS current
			DESCRIPTION
				"Total number of multicast packets transmitted on the interface
				
				XPath: /wing-stats/device[mac=key1]/interface[name=key2]/mc_pkts_sent"
			::= { wingStatsDevIfEntry 26 }

		
		-- 1.3.6.1.4.1.1916.2.131.50.1.4.2.6.1.1.27
		wingStatsDevIfLateCollisions OBJECT-TYPE
			SYNTAX Counter64
			MAX-ACCESS read-only
			STATUS current
			DESCRIPTION
				"Total number of late collisions on the interface
				
				XPath: /wing-stats/device[mac=key1]/interface[name=key2]/late_collisions"
			::= { wingStatsDevIfEntry 27 }

		
		-- 1.3.6.1.4.1.1916.2.131.50.1.4.2.6.1.1.28
		wingStatsDevIfExcessiveCollisions OBJECT-TYPE
			SYNTAX Counter64
			MAX-ACCESS read-only
			STATUS current
			DESCRIPTION
				"Total number of excessive collisions on the interface
				
				XPath: /wing-stats/device[mac=key1]/interface[name=key2]/excessive_collisions"
			::= { wingStatsDevIfEntry 28 }

		
		-- 1.3.6.1.4.1.1916.2.131.50.1.4.2.6.1.1.29
		wingStatsDevIfCollisions OBJECT-TYPE
			SYNTAX Counter64
			MAX-ACCESS read-only
			STATUS current
			DESCRIPTION
				"Total number of collisions on the interface
				
				XPath: /wing-stats/device[mac=key1]/interface[name=key2]/collisions"
			::= { wingStatsDevIfEntry 29 }

		
		-- 1.3.6.1.4.1.1916.2.131.50.1.4.2.6.1.1.30
		wingStatsDevIfMetric OBJECT-TYPE
			SYNTAX Integer32
			MAX-ACCESS read-only
			STATUS current
			DESCRIPTION
				"Interface metric
				
				XPath: /wing-stats/device[mac=key1]/interface[name=key2]/metric"
			::= { wingStatsDevIfEntry 30 }

		
		-- 1.3.6.1.4.1.1916.2.131.50.1.4.2.6.1.1.31
		wingStatsDevIfRxFifoErrors OBJECT-TYPE
			SYNTAX Counter32
			MAX-ACCESS read-only
			STATUS current
			DESCRIPTION
				"RX FIFO errors
				
				XPath: /wing-stats/device[mac=key1]/interface[name=key2]/rx_fifo_errors"
			::= { wingStatsDevIfEntry 31 }

		
		-- 1.3.6.1.4.1.1916.2.131.50.1.4.2.6.1.1.32
		wingStatsDevIfRxOverErrors OBJECT-TYPE
			SYNTAX Counter32
			MAX-ACCESS read-only
			STATUS current
			DESCRIPTION
				"RX overflow errors
				
				XPath: /wing-stats/device[mac=key1]/interface[name=key2]/rx_over_errors"
			::= { wingStatsDevIfEntry 32 }

		
		-- 1.3.6.1.4.1.1916.2.131.50.1.4.2.6.1.1.33
		wingStatsDevIfTxWindowErrors OBJECT-TYPE
			SYNTAX Counter32
			MAX-ACCESS read-only
			STATUS current
			DESCRIPTION
				"TX window errors
				
				XPath: /wing-stats/device[mac=key1]/interface[name=key2]/tx_window_errors"
			::= { wingStatsDevIfEntry 33 }

		
		-- 1.3.6.1.4.1.1916.2.131.50.1.4.2.6.1.1.34
		wingStatsDevIfTxFifoErrors OBJECT-TYPE
			SYNTAX Counter32
			MAX-ACCESS read-only
			STATUS current
			DESCRIPTION
				"TX FIFO errors
				
				XPath: /wing-stats/device[mac=key1]/interface[name=key2]/tx_fifo_errors"
			::= { wingStatsDevIfEntry 34 }

		
		-- 1.3.6.1.4.1.1916.2.131.50.1.4.2.6.1.1.35
		wingStatsDevIfTxAbortedErrors OBJECT-TYPE
			SYNTAX Counter32
			MAX-ACCESS read-only
			STATUS current
			DESCRIPTION
				"TX aborted errors
				
				XPath: /wing-stats/device[mac=key1]/interface[name=key2]/tx_aborted_errors"
			::= { wingStatsDevIfEntry 35 }

		
		-- 1.3.6.1.4.1.1916.2.131.50.1.4.2.6.1.1.36
		wingStatsDevIfTxCarrierErrors OBJECT-TYPE
			SYNTAX Counter32
			MAX-ACCESS read-only
			STATUS current
			DESCRIPTION
				"TX carrier errors
				
				XPath: /wing-stats/device[mac=key1]/interface[name=key2]/tx_carrier_errors"
			::= { wingStatsDevIfEntry 36 }

		
		-- 1.3.6.1.4.1.1916.2.131.50.1.4.2.6.1.1.37
		wingStatsDevIfTxDropped OBJECT-TYPE
			SYNTAX Counter32
			MAX-ACCESS read-only
			STATUS current
			DESCRIPTION
				"TX dropped
				
				XPath: /wing-stats/device[mac=key1]/interface[name=key2]/tx_dropped"
			::= { wingStatsDevIfEntry 37 }

		
		-- 1.3.6.1.4.1.1916.2.131.50.1.4.2.6.1.1.38
		wingStatsDevIfRxLengthErrors OBJECT-TYPE
			SYNTAX Counter32
			MAX-ACCESS read-only
			STATUS current
			DESCRIPTION
				"RX length errors
				
				XPath: /wing-stats/device[mac=key1]/interface[name=key2]/rx_length_errors"
			::= { wingStatsDevIfEntry 38 }

		
		-- 1.3.6.1.4.1.1916.2.131.50.1.4.2.6.1.1.39
		wingStatsDevIfRxMissedErrors OBJECT-TYPE
			SYNTAX Counter32
			MAX-ACCESS read-only
			STATUS current
			DESCRIPTION
				"RX length errors
				
				XPath: /wing-stats/device[mac=key1]/interface[name=key2]/rx_missed_errors"
			::= { wingStatsDevIfEntry 39 }

		
		-- 1.3.6.1.4.1.1916.2.131.50.1.4.2.6.1.1.40
		wingStatsDevIfRxFrameErrors OBJECT-TYPE
			SYNTAX Counter32
			MAX-ACCESS read-only
			STATUS current
			DESCRIPTION
				"RX length errors
				
				XPath: /wing-stats/device[mac=key1]/interface[name=key2]/rx_frame_errors"
			::= { wingStatsDevIfEntry 40 }

		
		-- 1.3.6.1.4.1.1916.2.131.50.1.4.2.6.1.1.41
		wingStatsDevIfTxErrors OBJECT-TYPE
			SYNTAX Counter32
			MAX-ACCESS read-only
			STATUS current
			DESCRIPTION
				"TX  errors
				
				XPath: /wing-stats/device[mac=key1]/interface[name=key2]/tx_errors"
			::= { wingStatsDevIfEntry 41 }

		
		-- 1.3.6.1.4.1.1916.2.131.50.1.4.2.6.1.1.42
		wingStatsDevIfTxHeartbeatErrors OBJECT-TYPE
			SYNTAX Counter32
			MAX-ACCESS read-only
			STATUS current
			DESCRIPTION
				"TX heartbeat  errors
				
				XPath: /wing-stats/device[mac=key1]/interface[name=key2]/tx_heartbeat_errors"
			::= { wingStatsDevIfEntry 42 }

		
		-- 1.3.6.1.4.1.1916.2.131.50.1.4.2.6.1.1.43
		wingStatsDevIfStatusOper OBJECT-TYPE
			SYNTAX DisplayString
			MAX-ACCESS read-only
			STATUS current
			DESCRIPTION
				"Operational status of interface (up/down)
				
				Values:
				up
				down
				
				XPath: /wing-stats/device[mac=key1]/interface[name=key2]/status_oper"
			::= { wingStatsDevIfEntry 43 }

		
-- /wing-stats/device/adoption
		-- 1.3.6.1.4.1.1916.2.131.50.1.4.2.8
		wingStatsDevAdopt OBJECT IDENTIFIER ::= { wingStatsDev 8 }

		
		-- 1.3.6.1.4.1.1916.2.131.50.1.4.2.8.2
		wingStatsDevAdoptDevTable OBJECT-TYPE
			SYNTAX SEQUENCE OF WingStatsDevAdoptDevEntry
			MAX-ACCESS not-accessible
			STATUS current
			DESCRIPTION
				"Status of currently adopted devices on AP/Wireless Controller.
				
				/wing-stats/device/adoption/adopted_device"
			::= { wingStatsDevAdopt 2 }

		
		-- 1.3.6.1.4.1.1916.2.131.50.1.4.2.8.2.1
		wingStatsDevAdoptDevEntry OBJECT-TYPE
			SYNTAX WingStatsDevAdoptDevEntry
			MAX-ACCESS not-accessible
			STATUS current
			DESCRIPTION
				"An entry in the table."
			INDEX { wingStatsDevMac, wingStatsDevAdoptDevMac }
			::= { wingStatsDevAdoptDevTable 1 }

		
		WingStatsDevAdoptDevEntry ::=
			SEQUENCE { 
				wingStatsDevAdoptDevMac
					MacAddress,
				wingStatsDevAdoptDevType
					DisplayString,
				wingStatsDevAdoptDevHostname
					DisplayString,
				wingStatsDevAdoptDevVersion
					DisplayString,
				wingStatsDevAdoptDevSerialNo
					DisplayString,
				wingStatsDevAdoptDevRfDomainName
					DisplayString,
				wingStatsDevAdoptDevOnline
					TruthValue,
				wingStatsDevAdoptDevBy
					MacAddress,
				wingStatsDevAdoptDevLastAdoption
					Unsigned32,
				wingStatsDevAdoptDevModelNumber
					DisplayString,
				wingStatsDevAdoptDevStartup
					Unsigned32,
				wingStatsDevAdoptDevCfgStatus
					DisplayString,
				wingStatsDevAdoptDevProductName
					DisplayString
			 }

		-- 1.3.6.1.4.1.1916.2.131.50.1.4.2.8.2.1.1
		wingStatsDevAdoptDevMac OBJECT-TYPE
			SYNTAX MacAddress
			MAX-ACCESS read-only
			STATUS current
			DESCRIPTION
				"Device MAC
				
				XPath: /wing-stats/device[mac=key1]/adoption/adopted_device[mac=key2]/mac"
			::= { wingStatsDevAdoptDevEntry 1 }

		
		-- 1.3.6.1.4.1.1916.2.131.50.1.4.2.8.2.1.2
		wingStatsDevAdoptDevType OBJECT-TYPE
			SYNTAX DisplayString
			MAX-ACCESS read-only
			STATUS current
			DESCRIPTION
				"Device type
				
				XPath: /wing-stats/device[mac=key1]/adoption/adopted_device[mac=key2]/type"
			::= { wingStatsDevAdoptDevEntry 2 }

		
		-- 1.3.6.1.4.1.1916.2.131.50.1.4.2.8.2.1.3
		wingStatsDevAdoptDevHostname OBJECT-TYPE
			SYNTAX DisplayString
			MAX-ACCESS read-only
			STATUS current
			DESCRIPTION
				"Device hostname
				
				XPath: /wing-stats/device[mac=key1]/adoption/adopted_device[mac=key2]/hostname"
			::= { wingStatsDevAdoptDevEntry 3 }

		
		-- 1.3.6.1.4.1.1916.2.131.50.1.4.2.8.2.1.4
		wingStatsDevAdoptDevVersion OBJECT-TYPE
			SYNTAX DisplayString
			MAX-ACCESS read-only
			STATUS current
			DESCRIPTION
				"Device software version
				
				XPath: /wing-stats/device[mac=key1]/adoption/adopted_device[mac=key2]/version"
			::= { wingStatsDevAdoptDevEntry 4 }

		
		-- 1.3.6.1.4.1.1916.2.131.50.1.4.2.8.2.1.5
		wingStatsDevAdoptDevSerialNo OBJECT-TYPE
			SYNTAX DisplayString
			MAX-ACCESS read-only
			STATUS current
			DESCRIPTION
				"Device serial number
				
				XPath: /wing-stats/device[mac=key1]/adoption/adopted_device[mac=key2]/serial-no"
			::= { wingStatsDevAdoptDevEntry 5 }

		
		-- 1.3.6.1.4.1.1916.2.131.50.1.4.2.8.2.1.6
		wingStatsDevAdoptDevRfDomainName OBJECT-TYPE
			SYNTAX DisplayString
			MAX-ACCESS read-only
			STATUS current
			DESCRIPTION
				"Device RF Domain name
				
				XPath: /wing-stats/device[mac=key1]/adoption/adopted_device[mac=key2]/rf_domain_name"
			::= { wingStatsDevAdoptDevEntry 6 }

		
		-- 1.3.6.1.4.1.1916.2.131.50.1.4.2.8.2.1.7
		wingStatsDevAdoptDevOnline OBJECT-TYPE
			SYNTAX TruthValue
			MAX-ACCESS read-only
			STATUS current
			DESCRIPTION
				"Device online status
				
				XPath: /wing-stats/device[mac=key1]/adoption/adopted_device[mac=key2]/online"
			::= { wingStatsDevAdoptDevEntry 7 }

		
		-- 1.3.6.1.4.1.1916.2.131.50.1.4.2.8.2.1.8
		wingStatsDevAdoptDevBy OBJECT-TYPE
			SYNTAX MacAddress
			MAX-ACCESS read-only
			STATUS current
			DESCRIPTION
				"MAC address of the adopting device.
				
				XPath: /wing-stats/device[mac=key1]/adoption/adopted_device[mac=key2]/adopted_by"
			::= { wingStatsDevAdoptDevEntry 8 }

		
		-- 1.3.6.1.4.1.1916.2.131.50.1.4.2.8.2.1.9
		wingStatsDevAdoptDevLastAdoption OBJECT-TYPE
			SYNTAX Unsigned32
			MAX-ACCESS read-only
			STATUS current
			DESCRIPTION
				"UTC timestamp of the last adoption.
				
				XPath: /wing-stats/device[mac=key1]/adoption/adopted_device[mac=key2]/last_adoption"
			::= { wingStatsDevAdoptDevEntry 9 }

		
		-- 1.3.6.1.4.1.1916.2.131.50.1.4.2.8.2.1.10
		wingStatsDevAdoptDevModelNumber OBJECT-TYPE
			SYNTAX DisplayString (SIZE (0..32))
			MAX-ACCESS read-only
			STATUS current
			DESCRIPTION
				"Device model number.
				
				XPath: /wing-stats/device[mac=key1]/adoption/adopted_device[mac=key2]/model_number"
			::= { wingStatsDevAdoptDevEntry 10 }

		
		-- 1.3.6.1.4.1.1916.2.131.50.1.4.2.8.2.1.11
		wingStatsDevAdoptDevStartup OBJECT-TYPE
			SYNTAX Unsigned32
			MAX-ACCESS read-only
			STATUS current
			DESCRIPTION
				"UTC timestamp of device startup.
				
				XPath: /wing-stats/device[mac=key1]/adoption/adopted_device[mac=key2]/startup"
			::= { wingStatsDevAdoptDevEntry 11 }

		
		-- 1.3.6.1.4.1.1916.2.131.50.1.4.2.8.2.1.12
		wingStatsDevAdoptDevCfgStatus OBJECT-TYPE
			SYNTAX DisplayString (SIZE (0..32))
			MAX-ACCESS read-only
			STATUS current
			DESCRIPTION
				"The configuration status of the device, e.g., pending.
				
				XPath: /wing-stats/device[mac=key1]/adoption/adopted_device[mac=key2]/cfg_status"
			::= { wingStatsDevAdoptDevEntry 12 }

		
		-- 1.3.6.1.4.1.1916.2.131.50.1.4.2.8.2.1.13
		wingStatsDevAdoptDevProductName OBJECT-TYPE
			SYNTAX DisplayString (SIZE (0..32))
			MAX-ACCESS read-only
			STATUS current
			DESCRIPTION
				"Product name string
				
				XPath: /wing-stats/device[mac=key1]/adoption/adopted_device[mac=key2]/product-name"
			::= { wingStatsDevAdoptDevEntry 13 }

		
		-- 1.3.6.1.4.1.1916.2.131.50.1.4.2.8.3
		wingStatsDevAdoptPendingDevTable OBJECT-TYPE
			SYNTAX SEQUENCE OF WingStatsDevAdoptPendingDevEntry
			MAX-ACCESS not-accessible
			STATUS current
			DESCRIPTION
				"Status of devices not adopted on AP/Wireless Controller.
				
				Xpath: /wing-stats/device/adoption/pending_device"
			::= { wingStatsDevAdopt 3 }

		
		-- 1.3.6.1.4.1.1916.2.131.50.1.4.2.8.3.1
		wingStatsDevAdoptPendingDevEntry OBJECT-TYPE
			SYNTAX WingStatsDevAdoptPendingDevEntry
			MAX-ACCESS not-accessible
			STATUS current
			DESCRIPTION
				"An entry in the table."
			INDEX { wingStatsDevMac, wingStatsDevAdoptPendingDevMac }
			::= { wingStatsDevAdoptPendingDevTable 1 }

		
		WingStatsDevAdoptPendingDevEntry ::=
			SEQUENCE { 
				wingStatsDevAdoptPendingDevMac
					MacAddress,
				wingStatsDevAdoptPendingDevType
					DisplayString,
				wingStatsDevAdoptPendingDevTarget
					DisplayString,
				wingStatsDevAdoptPendingDevDisOption
					DisplayString,
				wingStatsDevAdoptPendingDevVersion
					DisplayString,
				wingStatsDevAdoptPendingDevSerialNumber
					DisplayString,
				wingStatsDevAdoptPendingDevReason
					DisplayString,
				wingStatsDevAdoptPendingDevNumRadios
					Unsigned32,
				wingStatsDevAdoptPendingDevIp
					DisplayString,
				wingStatsDevAdoptPendingDevVlan
					Unsigned32
			 }

		-- 1.3.6.1.4.1.1916.2.131.50.1.4.2.8.3.1.1
		wingStatsDevAdoptPendingDevMac OBJECT-TYPE
			SYNTAX MacAddress
			MAX-ACCESS read-only
			STATUS current
			DESCRIPTION
				"Device MAC
				
				XPath: /wing-stats/device[mac=key1]/adoption/pending_device[mac=key2]/mac"
			::= { wingStatsDevAdoptPendingDevEntry 1 }

		
		-- 1.3.6.1.4.1.1916.2.131.50.1.4.2.8.3.1.2
		wingStatsDevAdoptPendingDevType OBJECT-TYPE
			SYNTAX DisplayString
			MAX-ACCESS read-only
			STATUS current
			DESCRIPTION
				"Device type
				
				XPath: /wing-stats/device[mac=key1]/adoption/pending_device[mac=key2]/type"
			::= { wingStatsDevAdoptPendingDevEntry 2 }

		
		-- 1.3.6.1.4.1.1916.2.131.50.1.4.2.8.3.1.3
		wingStatsDevAdoptPendingDevTarget OBJECT-TYPE
			SYNTAX DisplayString
			MAX-ACCESS read-only
			STATUS current
			DESCRIPTION
				"Target information for the Device.
				
				XPath: /wing-stats/device[mac=key1]/adoption/pending_device[mac=key2]/target"
			::= { wingStatsDevAdoptPendingDevEntry 3 }

		
		-- 1.3.6.1.4.1.1916.2.131.50.1.4.2.8.3.1.4
		wingStatsDevAdoptPendingDevDisOption OBJECT-TYPE
			SYNTAX DisplayString
			MAX-ACCESS read-only
			STATUS current
			DESCRIPTION
				"Discovery option provided by the device.
				
				XPath: /wing-stats/device[mac=key1]/adoption/pending_device[mac=key2]/dis_option"
			::= { wingStatsDevAdoptPendingDevEntry 4 }

		
		-- 1.3.6.1.4.1.1916.2.131.50.1.4.2.8.3.1.5
		wingStatsDevAdoptPendingDevVersion OBJECT-TYPE
			SYNTAX DisplayString
			MAX-ACCESS read-only
			STATUS current
			DESCRIPTION
				"Device software version
				
				XPath: /wing-stats/device[mac=key1]/adoption/pending_device[mac=key2]/version"
			::= { wingStatsDevAdoptPendingDevEntry 5 }

		
		-- 1.3.6.1.4.1.1916.2.131.50.1.4.2.8.3.1.6
		wingStatsDevAdoptPendingDevSerialNumber OBJECT-TYPE
			SYNTAX DisplayString
			MAX-ACCESS read-only
			STATUS current
			DESCRIPTION
				"Device serial number
				
				XPath: /wing-stats/device[mac=key1]/adoption/pending_device[mac=key2]/serial_number"
			::= { wingStatsDevAdoptPendingDevEntry 6 }

		
		-- 1.3.6.1.4.1.1916.2.131.50.1.4.2.8.3.1.7
		wingStatsDevAdoptPendingDevReason OBJECT-TYPE
			SYNTAX DisplayString
			MAX-ACCESS read-only
			STATUS current
			DESCRIPTION
				"Reason for adoption pending.
				
				XPath: /wing-stats/device[mac=key1]/adoption/pending_device[mac=key2]/reason"
			::= { wingStatsDevAdoptPendingDevEntry 7 }

		
		-- 1.3.6.1.4.1.1916.2.131.50.1.4.2.8.3.1.8
		wingStatsDevAdoptPendingDevNumRadios OBJECT-TYPE
			SYNTAX Unsigned32
			MAX-ACCESS read-only
			STATUS current
			DESCRIPTION
				"Number of Radios available in the device.
				
				XPath: /wing-stats/device[mac=key1]/adoption/pending_device[mac=key2]/num_radios"
			::= { wingStatsDevAdoptPendingDevEntry 8 }

		
		-- 1.3.6.1.4.1.1916.2.131.50.1.4.2.8.3.1.9
		wingStatsDevAdoptPendingDevIp OBJECT-TYPE
			SYNTAX DisplayString
			MAX-ACCESS read-only
			STATUS current
			DESCRIPTION
				"IP address configured on the device.
				
				XPath: /wing-stats/device[mac=key1]/adoption/pending_device[mac=key2]/ip"
			::= { wingStatsDevAdoptPendingDevEntry 9 }

		
		-- 1.3.6.1.4.1.1916.2.131.50.1.4.2.8.3.1.10
		wingStatsDevAdoptPendingDevVlan OBJECT-TYPE
			SYNTAX Unsigned32
			MAX-ACCESS read-only
			STATUS current
			DESCRIPTION
				"VLAN of the Device. The value 0 indicates that the VLAN
				is not applicable.
				
				XPath: /wing-stats/device[mac=key1]/adoption/pending_device[mac=key2]/vlan"
			::= { wingStatsDevAdoptPendingDevEntry 10 }

		
-- CDP neighbors
-- /wing-stats/device/cdp-neighbors
		-- 1.3.6.1.4.1.1916.2.131.50.1.4.2.17
		wingStatsDevCdpNeighbor OBJECT IDENTIFIER ::= { wingStatsDev 17 }

		
		-- 1.3.6.1.4.1.1916.2.131.50.1.4.2.17.1
		wingStatsDevCdpNeighborTable OBJECT-TYPE
			SYNTAX SEQUENCE OF WingStatsDevCdpNeighborEntry
			MAX-ACCESS not-accessible
			STATUS current
			DESCRIPTION
				"CDP neighbors
				
				/wing-stats/device/cdp-neighbors"
			::= { wingStatsDevCdpNeighbor 1 }

		
		-- 1.3.6.1.4.1.1916.2.131.50.1.4.2.17.1.1
		wingStatsDevCdpNeighborEntry OBJECT-TYPE
			SYNTAX WingStatsDevCdpNeighborEntry
			MAX-ACCESS not-accessible
			STATUS current
			DESCRIPTION
				"An entry in the table."
			INDEX { wingStatsDevMac, wingStatsDevCdpNeighborIndex }
			::= { wingStatsDevCdpNeighborTable 1 }

		
		WingStatsDevCdpNeighborEntry ::=
			SEQUENCE { 
				wingStatsDevCdpNeighborIndex
					WingIdentifier,
				wingStatsDevCdpNeighborDevId
					DisplayString,
				wingStatsDevCdpNeighborPlatform
					DisplayString,
				wingStatsDevCdpNeighborIpList
					DisplayString,
				wingStatsDevCdpNeighborPortId
					DisplayString,
				wingStatsDevCdpNeighborTtl
					Unsigned32,
				wingStatsDevCdpNeighborLocalPort
					DisplayString,
				wingStatsDevCdpNeighborDuplex
					DisplayString,
				wingStatsDevCdpNeighborAdvertisedVersion
					Unsigned32,
				wingStatsDevCdpNeighborVtpDomain
					DisplayString,
				wingStatsDevCdpNeighborNativeVlan
					Unsigned32,
				wingStatsDevCdpNeighborUntrustedPortCos
					Unsigned32,
				wingStatsDevCdpNeighborMgmtAddrList
					DisplayString,
				wingStatsDevCdpNeighborVersion
					DisplayString
			 }

		-- 1.3.6.1.4.1.1916.2.131.50.1.4.2.17.1.1.1
		wingStatsDevCdpNeighborIndex OBJECT-TYPE
			SYNTAX WingIdentifier
			MAX-ACCESS read-only
			STATUS current
			DESCRIPTION
				"Unique ID for each neighbor in the form of Device ID:Local Port
				
				XPath: /wing-stats/device[mac=key1]/cdp-neighbors[neighbor_id=key2]/neighbor_id"
			::= { wingStatsDevCdpNeighborEntry 1 }

		
		-- 1.3.6.1.4.1.1916.2.131.50.1.4.2.17.1.1.2
		wingStatsDevCdpNeighborDevId OBJECT-TYPE
			SYNTAX DisplayString
			MAX-ACCESS read-only
			STATUS current
			DESCRIPTION
				"Device ID
				
				XPath: /wing-stats/device[mac=key1]/cdp-neighbors[neighbor_id=key2]/dev_id"
			::= { wingStatsDevCdpNeighborEntry 2 }

		
		-- 1.3.6.1.4.1.1916.2.131.50.1.4.2.17.1.1.3
		wingStatsDevCdpNeighborPlatform OBJECT-TYPE
			SYNTAX DisplayString
			MAX-ACCESS read-only
			STATUS current
			DESCRIPTION
				"Platform
				
				XPath: /wing-stats/device[mac=key1]/cdp-neighbors[neighbor_id=key2]/platform"
			::= { wingStatsDevCdpNeighborEntry 3 }

		
		-- 1.3.6.1.4.1.1916.2.131.50.1.4.2.17.1.1.4
		wingStatsDevCdpNeighborIpList OBJECT-TYPE
			SYNTAX DisplayString
			MAX-ACCESS read-only
			STATUS current
			DESCRIPTION
				"IP addresses
				
				XPath: /wing-stats/device[mac=key1]/cdp-neighbors[neighbor_id=key2]/ip_list"
			::= { wingStatsDevCdpNeighborEntry 4 }

		
		-- 1.3.6.1.4.1.1916.2.131.50.1.4.2.17.1.1.5
		wingStatsDevCdpNeighborPortId OBJECT-TYPE
			SYNTAX DisplayString
			MAX-ACCESS read-only
			STATUS current
			DESCRIPTION
				"Port ID (outgoing port)
				
				XPath: /wing-stats/device[mac=key1]/cdp-neighbors[neighbor_id=key2]/port_id"
			::= { wingStatsDevCdpNeighborEntry 5 }

		
		-- 1.3.6.1.4.1.1916.2.131.50.1.4.2.17.1.1.6
		wingStatsDevCdpNeighborTtl OBJECT-TYPE
			SYNTAX Unsigned32
			MAX-ACCESS read-only
			STATUS current
			DESCRIPTION
				"Hold time
				
				XPath: /wing-stats/device[mac=key1]/cdp-neighbors[neighbor_id=key2]/ttl"
			::= { wingStatsDevCdpNeighborEntry 6 }

		
		-- 1.3.6.1.4.1.1916.2.131.50.1.4.2.17.1.1.7
		wingStatsDevCdpNeighborLocalPort OBJECT-TYPE
			SYNTAX DisplayString
			MAX-ACCESS read-only
			STATUS current
			DESCRIPTION
				"Local port
				
				XPath: /wing-stats/device[mac=key1]/cdp-neighbors[neighbor_id=key2]/local_port"
			::= { wingStatsDevCdpNeighborEntry 7 }

		
		-- 1.3.6.1.4.1.1916.2.131.50.1.4.2.17.1.1.8
		wingStatsDevCdpNeighborDuplex OBJECT-TYPE
			SYNTAX DisplayString
			MAX-ACCESS read-only
			STATUS current
			DESCRIPTION
				"Duplex
				
				Values:
				full,
				half
				
				XPath: /wing-stats/device[mac=key1]/cdp-neighbors[neighbor_id=key2]/duplex"
			::= { wingStatsDevCdpNeighborEntry 8 }

		
		-- 1.3.6.1.4.1.1916.2.131.50.1.4.2.17.1.1.9
		wingStatsDevCdpNeighborAdvertisedVersion OBJECT-TYPE
			SYNTAX Unsigned32
			MAX-ACCESS read-only
			STATUS current
			DESCRIPTION
				"Advertisement Version
				
				XPath: /wing-stats/device[mac=key1]/cdp-neighbors[neighbor_id=key2]/advertised_version"
			::= { wingStatsDevCdpNeighborEntry 9 }

		
		-- 1.3.6.1.4.1.1916.2.131.50.1.4.2.17.1.1.10
		wingStatsDevCdpNeighborVtpDomain OBJECT-TYPE
			SYNTAX DisplayString
			MAX-ACCESS read-only
			STATUS current
			DESCRIPTION
				"VTP Management Domain
				
				XPath: /wing-stats/device[mac=key1]/cdp-neighbors[neighbor_id=key2]/vtp_domain"
			::= { wingStatsDevCdpNeighborEntry 10 }

		
		-- 1.3.6.1.4.1.1916.2.131.50.1.4.2.17.1.1.11
		wingStatsDevCdpNeighborNativeVlan OBJECT-TYPE
			SYNTAX Unsigned32
			MAX-ACCESS read-only
			STATUS current
			DESCRIPTION
				"Native VLAN
				
				XPath: /wing-stats/device[mac=key1]/cdp-neighbors[neighbor_id=key2]/native_vlan"
			::= { wingStatsDevCdpNeighborEntry 11 }

		
		-- 1.3.6.1.4.1.1916.2.131.50.1.4.2.17.1.1.12
		wingStatsDevCdpNeighborUntrustedPortCos OBJECT-TYPE
			SYNTAX Unsigned32
			MAX-ACCESS read-only
			STATUS current
			DESCRIPTION
				"Untrusted port CoS
				
				XPath: /wing-stats/device[mac=key1]/cdp-neighbors[neighbor_id=key2]/untrusted_port_cos"
			::= { wingStatsDevCdpNeighborEntry 12 }

		
		-- 1.3.6.1.4.1.1916.2.131.50.1.4.2.17.1.1.13
		wingStatsDevCdpNeighborMgmtAddrList OBJECT-TYPE
			SYNTAX DisplayString
			MAX-ACCESS read-only
			STATUS current
			DESCRIPTION
				"the list of management addresses separated by comma
				
				XPath: /wing-stats/device[mac=key1]/cdp-neighbors[neighbor_id=key2]/mgmt_addr_list"
			::= { wingStatsDevCdpNeighborEntry 13 }

		
		-- 1.3.6.1.4.1.1916.2.131.50.1.4.2.17.1.1.14
		wingStatsDevCdpNeighborVersion OBJECT-TYPE
			SYNTAX DisplayString
			MAX-ACCESS read-only
			STATUS current
			DESCRIPTION
				"Version
				
				XPath: /wing-stats/device[mac=key1]/cdp-neighbors[neighbor_id=key2]/version"
			::= { wingStatsDevCdpNeighborEntry 14 }

		
-- Wireless statistics information on AP/Wireless Controller
-- /wing-stats/device/wireless
		-- 1.3.6.1.4.1.1916.2.131.50.1.4.2.25
		wingStatsDevWl OBJECT IDENTIFIER ::= { wingStatsDev 25 }

		
-- /wing-stats/device/wireless/ap-info
		-- 1.3.6.1.4.1.1916.2.131.50.1.4.2.25.1
		wingStatsDevWlApInfo OBJECT IDENTIFIER ::= { wingStatsDevWl 1 }

		
		-- 1.3.6.1.4.1.1916.2.131.50.1.4.2.25.1.1
		wingStatsDevWlApInfoTable OBJECT-TYPE
			SYNTAX SEQUENCE OF WingStatsDevWlApInfoEntry
			MAX-ACCESS not-accessible
			STATUS current
			DESCRIPTION
				"Status of managed Access Points
				
				/wing-stats/device/wireless/ap-info"
			::= { wingStatsDevWlApInfo 1 }

		
		-- 1.3.6.1.4.1.1916.2.131.50.1.4.2.25.1.1.1
		wingStatsDevWlApInfoEntry OBJECT-TYPE
			SYNTAX WingStatsDevWlApInfoEntry
			MAX-ACCESS not-accessible
			STATUS current
			DESCRIPTION
				"An entry in the table."
			INDEX { wingStatsDevMac, wingStatsDevWlApInfoMac }
			::= { wingStatsDevWlApInfoTable 1 }

		
		WingStatsDevWlApInfoEntry ::=
			SEQUENCE { 
				wingStatsDevWlApInfoMac
					MacAddress,
				wingStatsDevWlApInfoFaultDetected
					TruthValue,
				wingStatsDevWlApInfoNumRadios
					Unsigned32,
				wingStatsDevWlApInfoNumClients
					Unsigned32,
				wingStatsDevWlApInfoLastCalTime
					DisplayString,
				wingStatsDevWlApInfoType
					DisplayString,
				wingStatsDevWlApInfoStatsMode
					DisplayString,
				wingStatsDevWlApInfoStatsInterval
					Unsigned32,
				wingStatsDevWlApInfoHostname
					DisplayString,
				wingStatsDevWlApInfoRfDomainName
					DisplayString,
				wingStatsDevWlApInfoLocation
					DisplayString,
				wingStatsDevWlApInfoAdoptedTo
					MacAddress,
				wingStatsDevWlApInfoIp
					DisplayString
			 }

		-- 1.3.6.1.4.1.1916.2.131.50.1.4.2.25.1.1.1.1
		wingStatsDevWlApInfoMac OBJECT-TYPE
			SYNTAX MacAddress
			MAX-ACCESS read-only
			STATUS current
			DESCRIPTION
				"AP MAC address
				
				XPath: /wing-stats/device[mac=key1]/wireless/ap-info[mac=key2]/mac"
			::= { wingStatsDevWlApInfoEntry 1 }

		
		-- 1.3.6.1.4.1.1916.2.131.50.1.4.2.25.1.1.1.2
		wingStatsDevWlApInfoFaultDetected OBJECT-TYPE
			SYNTAX TruthValue
			MAX-ACCESS read-only
			STATUS current
			DESCRIPTION
				"Whether any fault has been detected on the AP
				
				XPath: /wing-stats/device[mac=key1]/wireless/ap-info[mac=key2]/fault_detected"
			::= { wingStatsDevWlApInfoEntry 2 }

		
		-- 1.3.6.1.4.1.1916.2.131.50.1.4.2.25.1.1.1.3
		wingStatsDevWlApInfoNumRadios OBJECT-TYPE
			SYNTAX Unsigned32
			MAX-ACCESS read-only
			STATUS current
			DESCRIPTION
				"Number of radios on the AP
				
				XPath: /wing-stats/device[mac=key1]/wireless/ap-info[mac=key2]/num_radios"
			::= { wingStatsDevWlApInfoEntry 3 }

		
		-- 1.3.6.1.4.1.1916.2.131.50.1.4.2.25.1.1.1.4
		wingStatsDevWlApInfoNumClients OBJECT-TYPE
			SYNTAX Unsigned32
			MAX-ACCESS read-only
			STATUS current
			DESCRIPTION
				"Number of wireless clients on the AP
				
				XPath: /wing-stats/device[mac=key1]/wireless/ap-info[mac=key2]/num_clients"
			::= { wingStatsDevWlApInfoEntry 4 }

		
		-- 1.3.6.1.4.1.1916.2.131.50.1.4.2.25.1.1.1.5
		wingStatsDevWlApInfoLastCalTime OBJECT-TYPE
			SYNTAX DisplayString (SIZE (0..64))
			MAX-ACCESS read-only
			STATUS current
			DESCRIPTION
				"Last Smart-RF Calibration time on the AP
				
				XPath: /wing-stats/device[mac=key1]/wireless/ap-info[mac=key2]/last_cal_time"
			::= { wingStatsDevWlApInfoEntry 5 }

		
		-- 1.3.6.1.4.1.1916.2.131.50.1.4.2.25.1.1.1.6
		wingStatsDevWlApInfoType OBJECT-TYPE
			SYNTAX DisplayString (SIZE (0..32))
			MAX-ACCESS read-only
			STATUS current
			DESCRIPTION
				"AP device type
				
				XPath: /wing-stats/device[mac=key1]/wireless/ap-info[mac=key2]/type"
			::= { wingStatsDevWlApInfoEntry 6 }

		
		-- 1.3.6.1.4.1.1916.2.131.50.1.4.2.25.1.1.1.7
		wingStatsDevWlApInfoStatsMode OBJECT-TYPE
			SYNTAX DisplayString (SIZE (0..32))
			MAX-ACCESS read-only
			STATUS current
			DESCRIPTION
				"Statistics update mode
				
				Values:
				auto
				fixed
				
				XPath: /wing-stats/device[mac=key1]/wireless/ap-info[mac=key2]/stats_mode"
			::= { wingStatsDevWlApInfoEntry 7 }

		
		-- 1.3.6.1.4.1.1916.2.131.50.1.4.2.25.1.1.1.8
		wingStatsDevWlApInfoStatsInterval OBJECT-TYPE
			SYNTAX Unsigned32
			MAX-ACCESS read-only
			STATUS current
			DESCRIPTION
				"The current statistics update interval in seconds
				
				XPath: /wing-stats/device[mac=key1]/wireless/ap-info[mac=key2]/stats_interval"
			::= { wingStatsDevWlApInfoEntry 8 }

		
		-- 1.3.6.1.4.1.1916.2.131.50.1.4.2.25.1.1.1.9
		wingStatsDevWlApInfoHostname OBJECT-TYPE
			SYNTAX DisplayString (SIZE (0..64))
			MAX-ACCESS read-only
			STATUS current
			DESCRIPTION
				"Hostname of the AP
				
				XPath: /wing-stats/device[mac=key1]/wireless/ap-info[mac=key2]/hostname"
			::= { wingStatsDevWlApInfoEntry 9 }

		
		-- 1.3.6.1.4.1.1916.2.131.50.1.4.2.25.1.1.1.10
		wingStatsDevWlApInfoRfDomainName OBJECT-TYPE
			SYNTAX DisplayString (SIZE (0..64))
			MAX-ACCESS read-only
			STATUS current
			DESCRIPTION
				"RF Domain name of the AP
				
				XPath: /wing-stats/device[mac=key1]/wireless/ap-info[mac=key2]/rf_domain_name"
			::= { wingStatsDevWlApInfoEntry 10 }

		
		-- 1.3.6.1.4.1.1916.2.131.50.1.4.2.25.1.1.1.11
		wingStatsDevWlApInfoLocation OBJECT-TYPE
			SYNTAX DisplayString (SIZE (0..64))
			MAX-ACCESS read-only
			STATUS current
			DESCRIPTION
				"Location description of the AP
				
				XPath: /wing-stats/device[mac=key1]/wireless/ap-info[mac=key2]/location"
			::= { wingStatsDevWlApInfoEntry 11 }

		
		-- 1.3.6.1.4.1.1916.2.131.50.1.4.2.25.1.1.1.12
		wingStatsDevWlApInfoAdoptedTo OBJECT-TYPE
			SYNTAX MacAddress
			MAX-ACCESS read-only
			STATUS current
			DESCRIPTION
				"MAC address of the parent wireless controller that the AP
				is adopted to.
				
				XPath: /wing-stats/device[mac=key1]/wireless/ap-info[mac=key2]/adopted_to"
			::= { wingStatsDevWlApInfoEntry 12 }

		
		-- 1.3.6.1.4.1.1916.2.131.50.1.4.2.25.1.1.1.13
		wingStatsDevWlApInfoIp OBJECT-TYPE
			SYNTAX DisplayString (SIZE (0..32))
			MAX-ACCESS read-only
			STATUS current
			DESCRIPTION
				"Adopted AP IP address
				
				XPath: /wing-stats/device[mac=key1]/wireless/ap-info[mac=key2]/ip"
			::= { wingStatsDevWlApInfoEntry 13 }

		
-- /wing-stats/device/wireless/client
		-- 1.3.6.1.4.1.1916.2.131.50.1.4.2.25.3
		wingStatsDevWlClient OBJECT IDENTIFIER ::= { wingStatsDevWl 3 }

		
		-- 1.3.6.1.4.1.1916.2.131.50.1.4.2.25.3.1
		wingStatsDevWlClientTable OBJECT-TYPE
			SYNTAX SEQUENCE OF WingStatsDevWlClientEntry
			MAX-ACCESS not-accessible
			STATUS current
			DESCRIPTION
				"Status of wireless clients associated currently
				on AP/Wireless Controller.
				
				/wing-stats/device/wireless/client"
			::= { wingStatsDevWlClient 1 }

		
		-- 1.3.6.1.4.1.1916.2.131.50.1.4.2.25.3.1.1
		wingStatsDevWlClientEntry OBJECT-TYPE
			SYNTAX WingStatsDevWlClientEntry
			MAX-ACCESS not-accessible
			STATUS current
			DESCRIPTION
				"An entry in the table"
			INDEX { wingStatsDevMac, wingStatsDevWlClientMac }
			::= { wingStatsDevWlClientTable 1 }

		
		WingStatsDevWlClientEntry ::=
			SEQUENCE { 
				wingStatsDevWlClientMac
					MacAddress,
				wingStatsDevWlClientMacName
					DisplayString,
				wingStatsDevWlClientVendor
					DisplayString,
				wingStatsDevWlClientBss
					MacAddress,
				wingStatsDevWlClientAp
					MacAddress,
				wingStatsDevWlClientRadioNum
					Unsigned32,
				wingStatsDevWlClientRadioType
					DisplayString,
				wingStatsDevWlClientRadioEnc
					DisplayString,
				wingStatsDevWlClientRadioAuth
					DisplayString,
				wingStatsDevWlClientWlan
					DisplayString,
				wingStatsDevWlClientState
					DisplayString,
				wingStatsDevWlClientHotspotAuthed
					TruthValue,
				wingStatsDevWlClientVlan
					Unsigned32,
				wingStatsDevWlClientUserName
					DisplayString,
				wingStatsDevWlClientIp
					DisplayString,
				wingStatsDevWlClientRfdName
					DisplayString,
				wingStatsDevWlClientHostname
					DisplayString,
				wingStatsDevWlClientLocation
					DisplayString,
				wingStatsDevWlClientRadioId
					DisplayString,
				wingStatsDevWlClientRadioAlias
					DisplayString
			 }

		-- 1.3.6.1.4.1.1916.2.131.50.1.4.2.25.3.1.1.1
		wingStatsDevWlClientMac OBJECT-TYPE
			SYNTAX MacAddress
			MAX-ACCESS read-only
			STATUS current
			DESCRIPTION
				"Client MAC
				
				XPath: /wing-stats/device[mac=key1]/wireless/client[mac=key2]/mac"
			::= { wingStatsDevWlClientEntry 1 }

		
		-- 1.3.6.1.4.1.1916.2.131.50.1.4.2.25.3.1.1.2
		wingStatsDevWlClientMacName OBJECT-TYPE
			SYNTAX DisplayString
			MAX-ACCESS read-only
			STATUS current
			DESCRIPTION
				"Hostname of the client which could be obtained from
				packet sniffing or by manually configured via
				mac-name configuration.
				
				XPath: /wing-stats/device[mac=key1]/wireless/client[mac=key2]/hostname"
			::= { wingStatsDevWlClientEntry 2 }

		
		-- 1.3.6.1.4.1.1916.2.131.50.1.4.2.25.3.1.1.3
		wingStatsDevWlClientVendor OBJECT-TYPE
			SYNTAX DisplayString
			MAX-ACCESS read-only
			STATUS current
			DESCRIPTION
				"Client vendor name based on the MAC OUI lookup
				
				XPath: /wing-stats/device[mac=key1]/wireless/client[mac=key2]/vendor"
			::= { wingStatsDevWlClientEntry 3 }

		
		-- 1.3.6.1.4.1.1916.2.131.50.1.4.2.25.3.1.1.4
		wingStatsDevWlClientBss OBJECT-TYPE
			SYNTAX MacAddress
			MAX-ACCESS read-only
			STATUS current
			DESCRIPTION
				"BSSID where the client is associated
				
				XPath: /wing-stats/device[mac=key1]/wireless/client[mac=key2]/bss"
			::= { wingStatsDevWlClientEntry 4 }

		
		-- 1.3.6.1.4.1.1916.2.131.50.1.4.2.25.3.1.1.5
		wingStatsDevWlClientAp OBJECT-TYPE
			SYNTAX MacAddress
			MAX-ACCESS read-only
			STATUS current
			DESCRIPTION
				"MAC address of the AP where the client is associated
				
				XPath: /wing-stats/device[mac=key1]/wireless/client[mac=key2]/ap"
			::= { wingStatsDevWlClientEntry 5 }

		
		-- 1.3.6.1.4.1.1916.2.131.50.1.4.2.25.3.1.1.6
		wingStatsDevWlClientRadioNum OBJECT-TYPE
			SYNTAX Unsigned32
			MAX-ACCESS read-only
			STATUS current
			DESCRIPTION
				"Radio number on AP where the client is associated
				
				XPath: /wing-stats/device[mac=key1]/wireless/client[mac=key2]/radio_num"
			::= { wingStatsDevWlClientEntry 6 }

		
		-- 1.3.6.1.4.1.1916.2.131.50.1.4.2.25.3.1.1.7
		wingStatsDevWlClientRadioType OBJECT-TYPE
			SYNTAX DisplayString
			MAX-ACCESS read-only
			STATUS current
			DESCRIPTION
				"802.11 radio-type of the client
				
				XPath: /wing-stats/device[mac=key1]/wireless/client[mac=key2]/radio_type"
			::= { wingStatsDevWlClientEntry 7 }

		
		-- 1.3.6.1.4.1.1916.2.131.50.1.4.2.25.3.1.1.8
		wingStatsDevWlClientRadioEnc OBJECT-TYPE
			SYNTAX DisplayString
			MAX-ACCESS read-only
			STATUS current
			DESCRIPTION
				"Encryption type
				
				XPath: /wing-stats/device[mac=key1]/wireless/client[mac=key2]/enc"
			::= { wingStatsDevWlClientEntry 8 }

		
		-- 1.3.6.1.4.1.1916.2.131.50.1.4.2.25.3.1.1.9
		wingStatsDevWlClientRadioAuth OBJECT-TYPE
			SYNTAX DisplayString
			MAX-ACCESS read-only
			STATUS current
			DESCRIPTION
				"Authentication type
				
				XPath: /wing-stats/device[mac=key1]/wireless/client[mac=key2]/auth"
			::= { wingStatsDevWlClientEntry 9 }

		
		-- 1.3.6.1.4.1.1916.2.131.50.1.4.2.25.3.1.1.10
		wingStatsDevWlClientWlan OBJECT-TYPE
			SYNTAX DisplayString
			MAX-ACCESS read-only
			STATUS current
			DESCRIPTION
				"WLAN where the client is associated
				
				XPath: /wing-stats/device[mac=key1]/wireless/client[mac=key2]/wlan"
			::= { wingStatsDevWlClientEntry 10 }

		
		-- 1.3.6.1.4.1.1916.2.131.50.1.4.2.25.3.1.1.11
		wingStatsDevWlClientState OBJECT-TYPE
			SYNTAX DisplayString
			MAX-ACCESS read-only
			STATUS current
			DESCRIPTION
				"Current state of the client
				
				XPath: /wing-stats/device[mac=key1]/wireless/client[mac=key2]/state"
			::= { wingStatsDevWlClientEntry 11 }

		
		-- 1.3.6.1.4.1.1916.2.131.50.1.4.2.25.3.1.1.12
		wingStatsDevWlClientHotspotAuthed OBJECT-TYPE
			SYNTAX TruthValue
			MAX-ACCESS read-only
			STATUS current
			DESCRIPTION
				"Whether the client has succeeded in guest access
				authentication.
				
				XPath: /wing-stats/device[mac=key1]/wireless/client[mac=key2]/hotspot_authed"
			::= { wingStatsDevWlClientEntry 12 }

		
		-- 1.3.6.1.4.1.1916.2.131.50.1.4.2.25.3.1.1.13
		wingStatsDevWlClientVlan OBJECT-TYPE
			SYNTAX Unsigned32
			MAX-ACCESS read-only
			STATUS current
			DESCRIPTION
				"The VLAN assigned to the client
				
				XPath: /wing-stats/device[mac=key1]/wireless/client[mac=key2]/vlan"
			::= { wingStatsDevWlClientEntry 13 }

		
		-- 1.3.6.1.4.1.1916.2.131.50.1.4.2.25.3.1.1.14
		wingStatsDevWlClientUserName OBJECT-TYPE
			SYNTAX DisplayString
			MAX-ACCESS read-only
			STATUS current
			DESCRIPTION
				"Username of the client, if available
				
				XPath: /wing-stats/device[mac=key1]/wireless/client[mac=key2]/username"
			::= { wingStatsDevWlClientEntry 14 }

		
		-- 1.3.6.1.4.1.1916.2.131.50.1.4.2.25.3.1.1.15
		wingStatsDevWlClientIp OBJECT-TYPE
			SYNTAX DisplayString
			MAX-ACCESS read-only
			STATUS current
			DESCRIPTION
				"IP address of the client (if known)
				
				XPath: /wing-stats/device[mac=key1]/wireless/client[mac=key2]/ip"
			::= { wingStatsDevWlClientEntry 15 }

		
		-- 1.3.6.1.4.1.1916.2.131.50.1.4.2.25.3.1.1.16
		wingStatsDevWlClientRfdName OBJECT-TYPE
			SYNTAX DisplayString
			MAX-ACCESS read-only
			STATUS current
			DESCRIPTION
				"RF Domain that the client is in
				
				XPath: /wing-stats/device[mac=key1]/wireless/client[mac=key2]/rf_domain_name"
			::= { wingStatsDevWlClientEntry 16 }

		
		-- 1.3.6.1.4.1.1916.2.131.50.1.4.2.25.3.1.1.17
		wingStatsDevWlClientHostname OBJECT-TYPE
			SYNTAX DisplayString
			MAX-ACCESS read-only
			STATUS current
			DESCRIPTION
				"Hostname of the AP the client is associated to
				
				XPath: /wing-stats/device[mac=key1]/wireless/client[mac=key2]/ap_hostname"
			::= { wingStatsDevWlClientEntry 17 }

		
		-- 1.3.6.1.4.1.1916.2.131.50.1.4.2.25.3.1.1.18
		wingStatsDevWlClientLocation OBJECT-TYPE
			SYNTAX DisplayString
			MAX-ACCESS read-only
			STATUS current
			DESCRIPTION
				"Location of the AP the client is associated to.
				
				XPath: /wing-stats/device[mac=key1]/wireless/client[mac=key2]/location"
			::= { wingStatsDevWlClientEntry 18 }

		
		-- 1.3.6.1.4.1.1916.2.131.50.1.4.2.25.3.1.1.19
		wingStatsDevWlClientRadioId OBJECT-TYPE
			SYNTAX DisplayString
			MAX-ACCESS read-only
			STATUS current
			DESCRIPTION
				"Unique ID for its associated radio in the form of
				AP-MAC:R%d. E.g., 00-A0-F8-00-00-00:R1
				
				XPath: /wing-stats/device[mac=key1]/wireless/client[mac=key2]/radio_id"
			::= { wingStatsDevWlClientEntry 19 }

		
		-- 1.3.6.1.4.1.1916.2.131.50.1.4.2.25.3.1.1.20
		wingStatsDevWlClientRadioAlias OBJECT-TYPE
			SYNTAX DisplayString
			MAX-ACCESS read-only
			STATUS current
			DESCRIPTION
				"A radio ID alias of its associated radio in the form of
				hostname:R%d. E.g., wm3400-22A24E:R1
				
				XPath: /wing-stats/device[mac=key1]/wireless/client[mac=key2]/radio_alias"
			::= { wingStatsDevWlClientEntry 20 }

		
-- /wing-stats/device/wireless/client-stats
		-- 1.3.6.1.4.1.1916.2.131.50.1.4.2.25.5
		wingStatsDevWlClientStat OBJECT IDENTIFIER ::= { wingStatsDevWl 5 }

		
		-- 1.3.6.1.4.1.1916.2.131.50.1.4.2.25.5.1
		wingStatsDevWlClientStatTable OBJECT-TYPE
			SYNTAX SEQUENCE OF WingStatsDevWlClientStatEntry
			MAX-ACCESS not-accessible
			STATUS current
			DESCRIPTION
				"Statistical information of wireless clients associated
				currently.
				
				/wing-stats/device/wireless/client-stats"
			::= { wingStatsDevWlClientStat 1 }

		
		-- 1.3.6.1.4.1.1916.2.131.50.1.4.2.25.5.1.1
		wingStatsDevWlClientStatEntry OBJECT-TYPE
			SYNTAX WingStatsDevWlClientStatEntry
			MAX-ACCESS not-accessible
			STATUS current
			DESCRIPTION
				"An entry in the table."
			INDEX { wingStatsDevMac, wingStatsDevWlClientStatMac }
			::= { wingStatsDevWlClientStatTable 1 }

		
		WingStatsDevWlClientStatEntry ::=
			SEQUENCE { 
				wingStatsDevWlClientStatMac
					MacAddress,
				wingStatsDevWlClientStatMacName
					DisplayString,
				wingStatsDevWlClientStatVendor
					DisplayString,
				wingStatsDevWlClientStatAp
					MacAddress,
				wingStatsDevWlClientStatTxBytes
					Counter64,
				wingStatsDevWlClientStatRxBytes
					Counter64,
				wingStatsDevWlClientStatTxPkts
					Counter32,
				wingStatsDevWlClientStatRxPkts
					Counter32,
				wingStatsDevWlClientStatTxDropped
					Counter32,
				wingStatsDevWlClientStatRxErrors
					Counter32,
				wingStatsDevWlClientStatTIndex
					Integer32,
				wingStatsDevWlClientStatTxBps
					Unsigned32,
				wingStatsDevWlClientStatRxBps
					Unsigned32,
				wingStatsDevWlClientStatSignal
					Integer32,
				wingStatsDevWlClientStatNoise
					Integer32,
				wingStatsDevWlClientStatSnr
					Integer32,
				wingStatsDevWlClientStatTxRate
					Unsigned32,
				wingStatsDevWlClientStatRxRate
					Unsigned32,
				wingStatsDevWlClientStatErrorRate
					Unsigned32,
				wingStatsDevWlClientStatQIndex
					Integer32
			 }

		-- 1.3.6.1.4.1.1916.2.131.50.1.4.2.25.5.1.1.1
		wingStatsDevWlClientStatMac OBJECT-TYPE
			SYNTAX MacAddress
			MAX-ACCESS read-only
			STATUS current
			DESCRIPTION
				"Client MAC
				
				XPath: /wing-stats/device[mac=key1]/wireless/client-stats[mac=key2]/mac"
			::= { wingStatsDevWlClientStatEntry 1 }

		
		-- 1.3.6.1.4.1.1916.2.131.50.1.4.2.25.5.1.1.2
		wingStatsDevWlClientStatMacName OBJECT-TYPE
			SYNTAX DisplayString (SIZE (0..64))
			MAX-ACCESS read-only
			STATUS current
			DESCRIPTION
				"Hostname of the client which could be obtained from
				packet sniffing or by manually configured via
				mac-name configuration.
				
				XPath: /wing-stats/device[mac=key1]/wireless/client-stats[mac=key2]/hostname"
			::= { wingStatsDevWlClientStatEntry 2 }

		
		-- 1.3.6.1.4.1.1916.2.131.50.1.4.2.25.5.1.1.3
		wingStatsDevWlClientStatVendor OBJECT-TYPE
			SYNTAX DisplayString (SIZE (0..64))
			MAX-ACCESS read-only
			STATUS current
			DESCRIPTION
				"Client vendor name based on the MAC OUI lookup
				
				XPath: /wing-stats/device[mac=key1]/wireless/client-stats[mac=key2]/vendor"
			::= { wingStatsDevWlClientStatEntry 3 }

		
		-- 1.3.6.1.4.1.1916.2.131.50.1.4.2.25.5.1.1.4
		wingStatsDevWlClientStatAp OBJECT-TYPE
			SYNTAX MacAddress
			MAX-ACCESS read-only
			STATUS current
			DESCRIPTION
				"MAC address of AP where the client is associated.
				
				XPath: /wing-stats/device[mac=key1]/wireless/client-stats[mac=key2]/ap"
			::= { wingStatsDevWlClientStatEntry 4 }

		
		-- 1.3.6.1.4.1.1916.2.131.50.1.4.2.25.5.1.1.5
		wingStatsDevWlClientStatTxBytes OBJECT-TYPE
			SYNTAX Counter64
			MAX-ACCESS read-only
			STATUS current
			DESCRIPTION
				"Number of data bytes transmitted from AP to client
				
				XPath: /wing-stats/device[mac=key1]/wireless/client-stats[mac=key2]/tx_bytes"
			::= { wingStatsDevWlClientStatEntry 5 }

		
		-- 1.3.6.1.4.1.1916.2.131.50.1.4.2.25.5.1.1.6
		wingStatsDevWlClientStatRxBytes OBJECT-TYPE
			SYNTAX Counter64
			MAX-ACCESS read-only
			STATUS current
			DESCRIPTION
				"Number of data bytes received from client to AP
				
				XPath: /wing-stats/device[mac=key1]/wireless/client-stats[mac=key2]/rx_bytes"
			::= { wingStatsDevWlClientStatEntry 6 }

		
		-- 1.3.6.1.4.1.1916.2.131.50.1.4.2.25.5.1.1.7
		wingStatsDevWlClientStatTxPkts OBJECT-TYPE
			SYNTAX Counter32
			MAX-ACCESS read-only
			STATUS current
			DESCRIPTION
				"Number of packets of data transmitted from AP to client
				
				XPath: /wing-stats/device[mac=key1]/wireless/client-stats[mac=key2]/tx_pkts"
			::= { wingStatsDevWlClientStatEntry 7 }

		
		-- 1.3.6.1.4.1.1916.2.131.50.1.4.2.25.5.1.1.8
		wingStatsDevWlClientStatRxPkts OBJECT-TYPE
			SYNTAX Counter32
			MAX-ACCESS read-only
			STATUS current
			DESCRIPTION
				"Number of packets of data received from client to AP
				
				XPath: /wing-stats/device[mac=key1]/wireless/client-stats[mac=key2]/rx_pkts"
			::= { wingStatsDevWlClientStatEntry 8 }

		
		-- 1.3.6.1.4.1.1916.2.131.50.1.4.2.25.5.1.1.9
		wingStatsDevWlClientStatTxDropped OBJECT-TYPE
			SYNTAX Counter32
			MAX-ACCESS read-only
			STATUS current
			DESCRIPTION
				"Number of packets of data dropped on transmission
				
				XPath: /wing-stats/device[mac=key1]/wireless/client-stats[mac=key2]/tx_dropped"
			::= { wingStatsDevWlClientStatEntry 9 }

		
		-- 1.3.6.1.4.1.1916.2.131.50.1.4.2.25.5.1.1.10
		wingStatsDevWlClientStatRxErrors OBJECT-TYPE
			SYNTAX Counter32
			MAX-ACCESS read-only
			STATUS current
			DESCRIPTION
				"Number of packets of data received with errors
				
				XPath: /wing-stats/device[mac=key1]/wireless/client-stats[mac=key2]/rx_errors"
			::= { wingStatsDevWlClientStatEntry 10 }

		
		-- 1.3.6.1.4.1.1916.2.131.50.1.4.2.25.5.1.1.11
		wingStatsDevWlClientStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/device[mac=key1]/wireless/client-stats[mac=key2]/t_index"
			::= { wingStatsDevWlClientStatEntry 11 }

		
		-- 1.3.6.1.4.1.1916.2.131.50.1.4.2.25.5.1.1.12
		wingStatsDevWlClientStatTxBps OBJECT-TYPE
			SYNTAX Unsigned32
			UNITS "kbps"
			MAX-ACCESS read-only
			STATUS current
			DESCRIPTION
				"User data transmit rate
				
				XPath: /wing-stats/device[mac=key1]/wireless/client-stats[mac=key2]/tx_bps"
			::= { wingStatsDevWlClientStatEntry 12 }

		
		-- 1.3.6.1.4.1.1916.2.131.50.1.4.2.25.5.1.1.13
		wingStatsDevWlClientStatRxBps OBJECT-TYPE
			SYNTAX Unsigned32
			UNITS "kbps"
			MAX-ACCESS read-only
			STATUS current
			DESCRIPTION
				"User data receive rate
				
				XPath: /wing-stats/device[mac=key1]/wireless/client-stats[mac=key2]/rx_bps"
			::= { wingStatsDevWlClientStatEntry 13 }

		
		-- 1.3.6.1.4.1.1916.2.131.50.1.4.2.25.5.1.1.14
		wingStatsDevWlClientStatSignal OBJECT-TYPE
			SYNTAX Integer32
			UNITS "dbm"
			MAX-ACCESS read-only
			STATUS current
			DESCRIPTION
				"Signal strength
				
				XPath: /wing-stats/device[mac=key1]/wireless/client-stats[mac=key2]/signal"
			::= { wingStatsDevWlClientStatEntry 14 }

		
		-- 1.3.6.1.4.1.1916.2.131.50.1.4.2.25.5.1.1.15
		wingStatsDevWlClientStatNoise OBJECT-TYPE
			SYNTAX Integer32
			UNITS "dbm"
			MAX-ACCESS read-only
			STATUS current
			DESCRIPTION
				"Noise level in units of dbm
				
				XPath: /wing-stats/device[mac=key1]/wireless/client-stats[mac=key2]/noise"
			::= { wingStatsDevWlClientStatEntry 15 }

		
		-- 1.3.6.1.4.1.1916.2.131.50.1.4.2.25.5.1.1.16
		wingStatsDevWlClientStatSnr OBJECT-TYPE
			SYNTAX Integer32
			UNITS "db"
			MAX-ACCESS read-only
			STATUS current
			DESCRIPTION
				"Signal to noise ratio in units of db
				
				XPath: /wing-stats/device[mac=key1]/wireless/client-stats[mac=key2]/snr"
			::= { wingStatsDevWlClientStatEntry 16 }

		
		-- 1.3.6.1.4.1.1916.2.131.50.1.4.2.25.5.1.1.17
		wingStatsDevWlClientStatTxRate OBJECT-TYPE
			SYNTAX Unsigned32
			UNITS "Mbps"
			MAX-ACCESS read-only
			STATUS current
			DESCRIPTION
				"The effective phy-layer transmit rate
				
				XPath: /wing-stats/device[mac=key1]/wireless/client-stats[mac=key2]/tx_rate"
			::= { wingStatsDevWlClientStatEntry 17 }

		
		-- 1.3.6.1.4.1.1916.2.131.50.1.4.2.25.5.1.1.18
		wingStatsDevWlClientStatRxRate OBJECT-TYPE
			SYNTAX Unsigned32
			UNITS "Mbps"
			MAX-ACCESS read-only
			STATUS current
			DESCRIPTION
				"The effective phy-layer receive rate
				
				XPath: /wing-stats/device[mac=key1]/wireless/client-stats[mac=key2]/rx_rate"
			::= { wingStatsDevWlClientStatEntry 18 }

		
		-- 1.3.6.1.4.1.1916.2.131.50.1.4.2.25.5.1.1.19
		wingStatsDevWlClientStatErrorRate OBJECT-TYPE
			SYNTAX Unsigned32
			MAX-ACCESS read-only
			STATUS current
			DESCRIPTION
				"Ratio of errors to rx-packets in percentage
				
				XPath: /wing-stats/device[mac=key1]/wireless/client-stats[mac=key2]/error_rate"
			::= { wingStatsDevWlClientStatEntry 19 }

		
		-- 1.3.6.1.4.1.1916.2.131.50.1.4.2.25.5.1.1.20
		wingStatsDevWlClientStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/device[mac=key1]/wireless/client-stats[mac=key2]/q_index"
			::= { wingStatsDevWlClientStatEntry 20 }

		
-- /wing-stats/device/wireless/radio
		-- 1.3.6.1.4.1.1916.2.131.50.1.4.2.25.9
		wingStatsDevWlRadio OBJECT IDENTIFIER ::= { wingStatsDevWl 9 }

		
		-- 1.3.6.1.4.1.1916.2.131.50.1.4.2.25.9.1
		wingStatsDevWlRadioTable OBJECT-TYPE
			SYNTAX SEQUENCE OF WingStatsDevWlRadioEntry
			MAX-ACCESS not-accessible
			STATUS current
			DESCRIPTION
				"Status of radios on AP
				
				/wing-stats/device/wireless/radio"
			::= { wingStatsDevWlRadio 1 }

		
		-- 1.3.6.1.4.1.1916.2.131.50.1.4.2.25.9.1.1
		wingStatsDevWlRadioEntry OBJECT-TYPE
			SYNTAX WingStatsDevWlRadioEntry
			MAX-ACCESS not-accessible
			STATUS current
			DESCRIPTION
				"An entry in the table."
			INDEX { wingStatsDevMac, wingStatsDevWlRadioId }
			::= { wingStatsDevWlRadioTable 1 }

		
		WingStatsDevWlRadioEntry ::=
			SEQUENCE { 
				wingStatsDevWlRadioId
					WingIdentifier,
				wingStatsDevWlRadioDeviceMac
					MacAddress,
				wingStatsDevWlRadioAlias
					WingIdentifier,
				wingStatsDevWlRadioMac
					MacAddress,
				wingStatsDevWlRadioType
					DisplayString,
				wingStatsDevWlRadioHostname
					DisplayString,
				wingStatsDevWlRadioRfdName
					DisplayString,
				wingStatsDevWlRadioLocation
					DisplayString,
				wingStatsDevWlRadioState
					DisplayString,
				wingStatsDevWlRadioCurChannel
					DisplayString,
				wingStatsDevWlRadioConfigChannel
					DisplayString,
				wingStatsDevWlRadioCurPower
					Unsigned32,
				wingStatsDevWlRadioConfigPower
					DisplayString,
				wingStatsDevWlRadioMaxUserRate
					Unsigned32,
				wingStatsDevWlRadioNumClient
					Unsigned32,
				wingStatsDevWlRadioProtocol
					Unsigned32
			 }

		-- 1.3.6.1.4.1.1916.2.131.50.1.4.2.25.9.1.1.1
		wingStatsDevWlRadioId OBJECT-TYPE
			SYNTAX WingIdentifier
			MAX-ACCESS read-only
			STATUS current
			DESCRIPTION
				"Unique ID for each radio interface in the form of
				AP-MAC:R%d. E.g., 00-A0-F8-00-00-00:R1
				
				XPath: /wing-stats/device[mac=key1]/wireless/radio[radio_id=key2]/radio_id"
			::= { wingStatsDevWlRadioEntry 1 }

		
		-- 1.3.6.1.4.1.1916.2.131.50.1.4.2.25.9.1.1.2
		wingStatsDevWlRadioDeviceMac OBJECT-TYPE
			SYNTAX MacAddress
			MAX-ACCESS read-only
			STATUS current
			DESCRIPTION
				"MAC address of the AP the radio belongs to.
				
				XPath: /wing-stats/device[mac=key1]/wireless/radio[radio_id=key2]/device_mac"
			::= { wingStatsDevWlRadioEntry 2 }

		
		-- 1.3.6.1.4.1.1916.2.131.50.1.4.2.25.9.1.1.3
		wingStatsDevWlRadioAlias OBJECT-TYPE
			SYNTAX WingIdentifier
			MAX-ACCESS read-only
			STATUS current
			DESCRIPTION
				"An alias to radio id in the form of hostname:R%d.
				E.g., wm3400-22A24E:R1
				
				XPath: /wing-stats/device[mac=key1]/wireless/radio[radio_id=key2]/radio_alias"
			::= { wingStatsDevWlRadioEntry 3 }

		
		-- 1.3.6.1.4.1.1916.2.131.50.1.4.2.25.9.1.1.4
		wingStatsDevWlRadioMac OBJECT-TYPE
			SYNTAX MacAddress
			MAX-ACCESS read-only
			STATUS current
			DESCRIPTION
				"MAC address of the radio interface
				
				XPath: /wing-stats/device[mac=key1]/wireless/radio[radio_id=key2]/radio_mac"
			::= { wingStatsDevWlRadioEntry 4 }

		
		-- 1.3.6.1.4.1.1916.2.131.50.1.4.2.25.9.1.1.5
		wingStatsDevWlRadioType OBJECT-TYPE
			SYNTAX DisplayString (SIZE (0..64))
			MAX-ACCESS read-only
			STATUS current
			DESCRIPTION
				"802.11 radio-type
				
				Values:
				2.4GHz-wlan
				5GHz-wlan
				sensor
				
				XPath: /wing-stats/device[mac=key1]/wireless/radio[radio_id=key2]/radio_type"
			::= { wingStatsDevWlRadioEntry 5 }

		
		-- 1.3.6.1.4.1.1916.2.131.50.1.4.2.25.9.1.1.6
		wingStatsDevWlRadioHostname OBJECT-TYPE
			SYNTAX DisplayString (SIZE (0..64))
			MAX-ACCESS read-only
			STATUS current
			DESCRIPTION
				"Hostname of the AP device
				
				XPath: /wing-stats/device[mac=key1]/wireless/radio[radio_id=key2]/hostname"
			::= { wingStatsDevWlRadioEntry 6 }

		
		-- 1.3.6.1.4.1.1916.2.131.50.1.4.2.25.9.1.1.7
		wingStatsDevWlRadioRfdName OBJECT-TYPE
			SYNTAX DisplayString (SIZE (0..64))
			MAX-ACCESS read-only
			STATUS current
			DESCRIPTION
				"RF Domain name of the AP device
				
				XPath: /wing-stats/device[mac=key1]/wireless/radio[radio_id=key2]/rf_domain_name"
			::= { wingStatsDevWlRadioEntry 7 }

		
		-- 1.3.6.1.4.1.1916.2.131.50.1.4.2.25.9.1.1.8
		wingStatsDevWlRadioLocation OBJECT-TYPE
			SYNTAX DisplayString (SIZE (0..64))
			MAX-ACCESS read-only
			STATUS current
			DESCRIPTION
				"Location description of the AP device
				
				XPath: /wing-stats/device[mac=key1]/wireless/radio[radio_id=key2]/location"
			::= { wingStatsDevWlRadioEntry 8 }

		
		-- 1.3.6.1.4.1.1916.2.131.50.1.4.2.25.9.1.1.9
		wingStatsDevWlRadioState OBJECT-TYPE
			SYNTAX DisplayString (SIZE (0..64))
			MAX-ACCESS read-only
			STATUS current
			DESCRIPTION
				"Radio state
				
				XPath: /wing-stats/device[mac=key1]/wireless/radio[radio_id=key2]/state"
			::= { wingStatsDevWlRadioEntry 9 }

		
		-- 1.3.6.1.4.1.1916.2.131.50.1.4.2.25.9.1.1.10
		wingStatsDevWlRadioCurChannel OBJECT-TYPE
			SYNTAX DisplayString (SIZE (0..16))
			MAX-ACCESS read-only
			STATUS current
			DESCRIPTION
				"Current channel the radio is operating at
				
				XPath: /wing-stats/device[mac=key1]/wireless/radio[radio_id=key2]/current_channel"
			::= { wingStatsDevWlRadioEntry 10 }

		
		-- 1.3.6.1.4.1.1916.2.131.50.1.4.2.25.9.1.1.11
		wingStatsDevWlRadioConfigChannel OBJECT-TYPE
			SYNTAX DisplayString (SIZE (0..64))
			MAX-ACCESS read-only
			STATUS current
			DESCRIPTION
				"Configured channel for the radio
				
				XPath: /wing-stats/device[mac=key1]/wireless/radio[radio_id=key2]/config_channel"
			::= { wingStatsDevWlRadioEntry 11 }

		
		-- 1.3.6.1.4.1.1916.2.131.50.1.4.2.25.9.1.1.12
		wingStatsDevWlRadioCurPower OBJECT-TYPE
			SYNTAX Unsigned32
			UNITS "dBm"
			MAX-ACCESS read-only
			STATUS current
			DESCRIPTION
				"Current power the radio is operating at
				
				XPath: /wing-stats/device[mac=key1]/wireless/radio[radio_id=key2]/current_power"
			::= { wingStatsDevWlRadioEntry 12 }

		
		-- 1.3.6.1.4.1.1916.2.131.50.1.4.2.25.9.1.1.13
		wingStatsDevWlRadioConfigPower OBJECT-TYPE
			SYNTAX DisplayString (SIZE (0..16))
			MAX-ACCESS read-only
			STATUS current
			DESCRIPTION
				"Configured power for the radio
				
				XPath: /wing-stats/device[mac=key1]/wireless/radio[radio_id=key2]/config_power"
			::= { wingStatsDevWlRadioEntry 13 }

		
		-- 1.3.6.1.4.1.1916.2.131.50.1.4.2.25.9.1.1.14
		wingStatsDevWlRadioMaxUserRate OBJECT-TYPE
			SYNTAX Unsigned32
			UNITS "kbps"
			MAX-ACCESS read-only
			STATUS current
			DESCRIPTION
				"Theoretic maximum user-level data rate
				
				XPath: /wing-stats/device[mac=key1]/wireless/radio[radio_id=key2]/max_user_rate"
			::= { wingStatsDevWlRadioEntry 14 }

		
		-- 1.3.6.1.4.1.1916.2.131.50.1.4.2.25.9.1.1.15
		wingStatsDevWlRadioNumClient OBJECT-TYPE
			SYNTAX Unsigned32
			MAX-ACCESS read-only
			STATUS current
			DESCRIPTION
				"Number of clients associated to the radio
				
				XPath: /wing-stats/device[mac=key1]/wireless/radio[radio_id=key2]/num_clients"
			::= { wingStatsDevWlRadioEntry 15 }

		
		-- 1.3.6.1.4.1.1916.2.131.50.1.4.2.25.9.1.1.16
		wingStatsDevWlRadioProtocol OBJECT-TYPE
			SYNTAX Unsigned32
			MAX-ACCESS read-only
			STATUS current
			DESCRIPTION
				"Bit map of protocols currently enabled on the radio.
				
				Bit position:
				The Least Significant Bit corresponds to the first bit
				in the map. The next bit corresponds to the second bit
				and so on. Unused bits are ignored.
				
				bit position  meaning
				============  =======
				0             dot11a
				1             dot11b
				2             dot11g
				3             dot11an
				4             dot11gn
				
				Bit values:
				1 - enabled
				0 - disabled
				
				XPath: /wing-stats/device[mac=key1]/wireless/radio[radio_id=key2]/protocol"
			::= { wingStatsDevWlRadioEntry 16 }

		
-- /wing-stats/device/wireless/radio-stats
		-- 1.3.6.1.4.1.1916.2.131.50.1.4.2.25.10
		wingStatsDevWlRadioStat OBJECT IDENTIFIER ::= { wingStatsDevWl 10 }

		
		-- 1.3.6.1.4.1.1916.2.131.50.1.4.2.25.10.1
		wingStatsDevWlRadioStatTable OBJECT-TYPE
			SYNTAX SEQUENCE OF WingStatsDevWlRadioStatEntry
			MAX-ACCESS not-accessible
			STATUS current
			DESCRIPTION
				"Traffic and RF statistics of radios on AP
				
				/wing-stats/device/wireless/radio-stats"
			::= { wingStatsDevWlRadioStat 1 }

		
		-- 1.3.6.1.4.1.1916.2.131.50.1.4.2.25.10.1.1
		wingStatsDevWlRadioStatEntry OBJECT-TYPE
			SYNTAX WingStatsDevWlRadioStatEntry
			MAX-ACCESS not-accessible
			STATUS current
			DESCRIPTION
				"An entry in the table."
			INDEX { wingStatsDevMac, wingStatsDevWlRadioStatId }
			::= { wingStatsDevWlRadioStatTable 1 }

		
		WingStatsDevWlRadioStatEntry ::=
			SEQUENCE { 
				wingStatsDevWlRadioStatId
					WingIdentifier,
				wingStatsDevWlRadioStatDeviceMac
					MacAddress,
				wingStatsDevWlRadioStatAlias
					WingIdentifier,
				wingStatsDevWlRadioStatMac
					MacAddress,
				wingStatsDevWlRadioStatType
					DisplayString,
				wingStatsDevWlRadioStatTxBytes
					Counter64,
				wingStatsDevWlRadioStatRxBytes
					Counter64,
				wingStatsDevWlRadioStatTxPkts
					Counter32,
				wingStatsDevWlRadioStatRxPkts
					Counter32,
				wingStatsDevWlRadioStatTxDropped
					Counter32,
				wingStatsDevWlRadioStatRxErrors
					Counter32,
				wingStatsDevWlRadioStatTIndex
					Integer32,
				wingStatsDevWlRadioStatTxBps
					Unsigned32,
				wingStatsDevWlRadioStatRxBps
					Unsigned32,
				wingStatsDevWlRadioStatSignal
					Integer32,
				wingStatsDevWlRadioStatNoise
					Integer32,
				wingStatsDevWlRadioStatSnr
					Integer32,
				wingStatsDevWlRadioStatTxRate
					Unsigned32,
				wingStatsDevWlRadioStatRxRate
					Unsigned32,
				wingStatsDevWlRadioStatErrorRate
					Unsigned32,
				wingStatsDevWlRadioStatQIndex
					Integer32,
				wingStatsDevWlRadioStatNumClients
					Unsigned32,
				wingStatsDevWlRadioStatNumBClients
					Unsigned32,
				wingStatsDevWlRadioStatNumBgClients
					Unsigned32,
				wingStatsDevWlRadioStatNumBgnClients
					Unsigned32,
				wingStatsDevWlRadioStatNumAClients
					Unsigned32,
				wingStatsDevWlRadioStatNumAnClients
					Unsigned32,
				wingStatsDevWlRadioStatMediumErrorRate
					Unsigned32,
				wingStatsDevWlRadioStatTxRetries
					Counter64,
				wingStatsDevWlRadioStatTxRetriedBytes
					Counter64
			 }

		-- 1.3.6.1.4.1.1916.2.131.50.1.4.2.25.10.1.1.1
		wingStatsDevWlRadioStatId OBJECT-TYPE
			SYNTAX WingIdentifier
			MAX-ACCESS read-only
			STATUS current
			DESCRIPTION
				"Unique ID for each radio interface in the form of
				AP-MAC:R%d. E.g., 00-A0-F8-00-00-00:R1
				
				XPath: /wing-stats/device[mac=key1]/wireless/radio-stats[radio_id=key2]/radio_id"
			::= { wingStatsDevWlRadioStatEntry 1 }

		
		-- 1.3.6.1.4.1.1916.2.131.50.1.4.2.25.10.1.1.2
		wingStatsDevWlRadioStatDeviceMac OBJECT-TYPE
			SYNTAX MacAddress
			MAX-ACCESS read-only
			STATUS current
			DESCRIPTION
				"MAC address of AP the radio belongs to
				
				XPath: /wing-stats/device[mac=key1]/wireless/radio-stats[radio_id=key2]/device_mac"
			::= { wingStatsDevWlRadioStatEntry 2 }

		
		-- 1.3.6.1.4.1.1916.2.131.50.1.4.2.25.10.1.1.3
		wingStatsDevWlRadioStatAlias OBJECT-TYPE
			SYNTAX WingIdentifier
			MAX-ACCESS read-only
			STATUS current
			DESCRIPTION
				"An alias to radio id in the form of hostname:R%d.
				E.g., wm3400-22A24E:R1
				
				XPath: /wing-stats/device[mac=key1]/wireless/radio-stats[radio_id=key2]/radio_alias"
			::= { wingStatsDevWlRadioStatEntry 3 }

		
		-- 1.3.6.1.4.1.1916.2.131.50.1.4.2.25.10.1.1.4
		wingStatsDevWlRadioStatMac OBJECT-TYPE
			SYNTAX MacAddress
			MAX-ACCESS read-only
			STATUS current
			DESCRIPTION
				"MAC address of the radio
				
				XPath: /wing-stats/device[mac=key1]/wireless/radio-stats[radio_id=key2]/radio_mac"
			::= { wingStatsDevWlRadioStatEntry 4 }

		
		-- 1.3.6.1.4.1.1916.2.131.50.1.4.2.25.10.1.1.5
		wingStatsDevWlRadioStatType OBJECT-TYPE
			SYNTAX DisplayString
			MAX-ACCESS read-only
			STATUS current
			DESCRIPTION
				"802.11 radio-type
				
				Values:
				2.4GHz-wlan
				5GHz-wlan
				sensor
				
				XPath: /wing-stats/device[mac=key1]/wireless/radio-stats[radio_id=key2]/radio_type"
			::= { wingStatsDevWlRadioStatEntry 5 }

		
		-- 1.3.6.1.4.1.1916.2.131.50.1.4.2.25.10.1.1.6
		wingStatsDevWlRadioStatTxBytes OBJECT-TYPE
			SYNTAX Counter64
			MAX-ACCESS read-only
			STATUS current
			DESCRIPTION
				"Number of data bytes transmitted from radio to clients
				
				XPath: /wing-stats/device[mac=key1]/wireless/radio-stats[radio_id=key2]/tx_bytes"
			::= { wingStatsDevWlRadioStatEntry 6 }

		
		-- 1.3.6.1.4.1.1916.2.131.50.1.4.2.25.10.1.1.7
		wingStatsDevWlRadioStatRxBytes OBJECT-TYPE
			SYNTAX Counter64
			MAX-ACCESS read-only
			STATUS current
			DESCRIPTION
				"Number of data bytes received from clients to radio
				
				XPath: /wing-stats/device[mac=key1]/wireless/radio-stats[radio_id=key2]/rx_bytes"
			::= { wingStatsDevWlRadioStatEntry 7 }

		
		-- 1.3.6.1.4.1.1916.2.131.50.1.4.2.25.10.1.1.8
		wingStatsDevWlRadioStatTxPkts OBJECT-TYPE
			SYNTAX Counter32
			MAX-ACCESS read-only
			STATUS current
			DESCRIPTION
				"Number of packets of data transmitted from radio to clients
				
				XPath: /wing-stats/device[mac=key1]/wireless/radio-stats[radio_id=key2]/tx_pkts"
			::= { wingStatsDevWlRadioStatEntry 8 }

		
		-- 1.3.6.1.4.1.1916.2.131.50.1.4.2.25.10.1.1.9
		wingStatsDevWlRadioStatRxPkts OBJECT-TYPE
			SYNTAX Counter32
			MAX-ACCESS read-only
			STATUS current
			DESCRIPTION
				"Number of packets of data received from clients to radio
				
				XPath: /wing-stats/device[mac=key1]/wireless/radio-stats[radio_id=key2]/rx_pkts"
			::= { wingStatsDevWlRadioStatEntry 9 }

		
		-- 1.3.6.1.4.1.1916.2.131.50.1.4.2.25.10.1.1.10
		wingStatsDevWlRadioStatTxDropped OBJECT-TYPE
			SYNTAX Counter32
			MAX-ACCESS read-only
			STATUS current
			DESCRIPTION
				"Number of packets of data dropped on transmission
				
				XPath: /wing-stats/device[mac=key1]/wireless/radio-stats[radio_id=key2]/tx_dropped"
			::= { wingStatsDevWlRadioStatEntry 10 }

		
		-- 1.3.6.1.4.1.1916.2.131.50.1.4.2.25.10.1.1.11
		wingStatsDevWlRadioStatRxErrors OBJECT-TYPE
			SYNTAX Counter32
			MAX-ACCESS read-only
			STATUS current
			DESCRIPTION
				"Number of packets of data received with errors
				
				XPath: /wing-stats/device[mac=key1]/wireless/radio-stats[radio_id=key2]/rx_errors"
			::= { wingStatsDevWlRadioStatEntry 11 }

		
		-- 1.3.6.1.4.1.1916.2.131.50.1.4.2.25.10.1.1.12
		wingStatsDevWlRadioStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/device[mac=key1]/wireless/radio-stats[radio_id=key2]/t_index"
			::= { wingStatsDevWlRadioStatEntry 12 }

		
		-- 1.3.6.1.4.1.1916.2.131.50.1.4.2.25.10.1.1.13
		wingStatsDevWlRadioStatTxBps OBJECT-TYPE
			SYNTAX Unsigned32
			UNITS "kbps"
			MAX-ACCESS read-only
			STATUS current
			DESCRIPTION
				"User data transmit rate
				
				XPath: /wing-stats/device[mac=key1]/wireless/radio-stats[radio_id=key2]/tx_bps"
			::= { wingStatsDevWlRadioStatEntry 13 }

		
		-- 1.3.6.1.4.1.1916.2.131.50.1.4.2.25.10.1.1.14
		wingStatsDevWlRadioStatRxBps OBJECT-TYPE
			SYNTAX Unsigned32
			UNITS "kbps"
			MAX-ACCESS read-only
			STATUS current
			DESCRIPTION
				"User data receive rate
				
				XPath: /wing-stats/device[mac=key1]/wireless/radio-stats[radio_id=key2]/rx_bps"
			::= { wingStatsDevWlRadioStatEntry 14 }

		
		-- 1.3.6.1.4.1.1916.2.131.50.1.4.2.25.10.1.1.15
		wingStatsDevWlRadioStatSignal OBJECT-TYPE
			SYNTAX Integer32
			UNITS "dbm"
			MAX-ACCESS read-only
			STATUS current
			DESCRIPTION
				"Signal strength in units of dbm
				
				XPath: /wing-stats/device[mac=key1]/wireless/radio-stats[radio_id=key2]/signal"
			::= { wingStatsDevWlRadioStatEntry 15 }

		
		-- 1.3.6.1.4.1.1916.2.131.50.1.4.2.25.10.1.1.16
		wingStatsDevWlRadioStatNoise OBJECT-TYPE
			SYNTAX Integer32
			UNITS "dbm"
			MAX-ACCESS read-only
			STATUS current
			DESCRIPTION
				"Noise level in units of dbm
				
				XPath: /wing-stats/device[mac=key1]/wireless/radio-stats[radio_id=key2]/noise"
			::= { wingStatsDevWlRadioStatEntry 16 }

		
		-- 1.3.6.1.4.1.1916.2.131.50.1.4.2.25.10.1.1.17
		wingStatsDevWlRadioStatSnr OBJECT-TYPE
			SYNTAX Integer32
			UNITS "db"
			MAX-ACCESS read-only
			STATUS current
			DESCRIPTION
				"Signal to noise ratio in units of db
				
				XPath: /wing-stats/device[mac=key1]/wireless/radio-stats[radio_id=key2]/snr"
			::= { wingStatsDevWlRadioStatEntry 17 }

		
		-- 1.3.6.1.4.1.1916.2.131.50.1.4.2.25.10.1.1.18
		wingStatsDevWlRadioStatTxRate OBJECT-TYPE
			SYNTAX Unsigned32
			UNITS "Mbps"
			MAX-ACCESS read-only
			STATUS current
			DESCRIPTION
				"The effective phy-layer transmit rate
				
				XPath: /wing-stats/device[mac=key1]/wireless/radio-stats[radio_id=key2]/tx_rate"
			::= { wingStatsDevWlRadioStatEntry 18 }

		
		-- 1.3.6.1.4.1.1916.2.131.50.1.4.2.25.10.1.1.19
		wingStatsDevWlRadioStatRxRate OBJECT-TYPE
			SYNTAX Unsigned32
			UNITS "Mbps"
			MAX-ACCESS read-only
			STATUS current
			DESCRIPTION
				"The effective phy-layer receive rate
				
				XPath: /wing-stats/device[mac=key1]/wireless/radio-stats[radio_id=key2]/rx_rate"
			::= { wingStatsDevWlRadioStatEntry 19 }

		
		-- 1.3.6.1.4.1.1916.2.131.50.1.4.2.25.10.1.1.20
		wingStatsDevWlRadioStatErrorRate OBJECT-TYPE
			SYNTAX Unsigned32
			MAX-ACCESS read-only
			STATUS current
			DESCRIPTION
				"Ratio of errors to rx-packets in percentage
				
				XPath: /wing-stats/device[mac=key1]/wireless/radio-stats[radio_id=key2]/error_rate"
			::= { wingStatsDevWlRadioStatEntry 20 }

		
		-- 1.3.6.1.4.1.1916.2.131.50.1.4.2.25.10.1.1.21
		wingStatsDevWlRadioStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/device[mac=key1]/wireless/radio-stats[radio_id=key2]/q_index"
			::= { wingStatsDevWlRadioStatEntry 21 }

		
		-- 1.3.6.1.4.1.1916.2.131.50.1.4.2.25.10.1.1.22
		wingStatsDevWlRadioStatNumClients OBJECT-TYPE
			SYNTAX Unsigned32
			MAX-ACCESS read-only
			STATUS current
			DESCRIPTION
				"Total number of clients
				
				XPath: /wing-stats/device[mac=key1]/wireless/radio-stats[radio_id=key2]/num_clients"
			::= { wingStatsDevWlRadioStatEntry 22 }

		
		-- 1.3.6.1.4.1.1916.2.131.50.1.4.2.25.10.1.1.23
		wingStatsDevWlRadioStatNumBClients OBJECT-TYPE
			SYNTAX Unsigned32
			MAX-ACCESS read-only
			STATUS current
			DESCRIPTION
				"Number of 11b clients
				
				XPath: /wing-stats/device[mac=key1]/wireless/radio-stats[radio_id=key2]/num_b_clients"
			::= { wingStatsDevWlRadioStatEntry 23 }

		
		-- 1.3.6.1.4.1.1916.2.131.50.1.4.2.25.10.1.1.24
		wingStatsDevWlRadioStatNumBgClients OBJECT-TYPE
			SYNTAX Unsigned32
			MAX-ACCESS read-only
			STATUS current
			DESCRIPTION
				"Number of 11bg clients
				
				XPath: /wing-stats/device[mac=key1]/wireless/radio-stats[radio_id=key2]/num_bg_clients"
			::= { wingStatsDevWlRadioStatEntry 24 }

		
		-- 1.3.6.1.4.1.1916.2.131.50.1.4.2.25.10.1.1.25
		wingStatsDevWlRadioStatNumBgnClients OBJECT-TYPE
			SYNTAX Unsigned32
			MAX-ACCESS read-only
			STATUS current
			DESCRIPTION
				"Number of 11bgn clients
				
				XPath: /wing-stats/device[mac=key1]/wireless/radio-stats[radio_id=key2]/num_bgn_clients"
			::= { wingStatsDevWlRadioStatEntry 25 }

		
		-- 1.3.6.1.4.1.1916.2.131.50.1.4.2.25.10.1.1.26
		wingStatsDevWlRadioStatNumAClients OBJECT-TYPE
			SYNTAX Unsigned32
			MAX-ACCESS read-only
			STATUS current
			DESCRIPTION
				"Number of 11a clients
				
				XPath: /wing-stats/device[mac=key1]/wireless/radio-stats[radio_id=key2]/num_a_clients"
			::= { wingStatsDevWlRadioStatEntry 26 }

		
		-- 1.3.6.1.4.1.1916.2.131.50.1.4.2.25.10.1.1.27
		wingStatsDevWlRadioStatNumAnClients OBJECT-TYPE
			SYNTAX Unsigned32
			MAX-ACCESS read-only
			STATUS current
			DESCRIPTION
				"Number of 11an clients
				
				XPath: /wing-stats/device[mac=key1]/wireless/radio-stats[radio_id=key2]/num_an_clients"
			::= { wingStatsDevWlRadioStatEntry 27 }

		
		-- 1.3.6.1.4.1.1916.2.131.50.1.4.2.25.10.1.1.28
		wingStatsDevWlRadioStatMediumErrorRate OBJECT-TYPE
			SYNTAX Unsigned32
			MAX-ACCESS read-only
			STATUS current
			DESCRIPTION
				"Ratio of medium errors and rx-retries to rx-packets
				in percentage
				
				XPath: /wing-stats/device[mac=key1]/wireless/radio-stats[radio_id=key2]/medium_error_rate"
			::= { wingStatsDevWlRadioStatEntry 28 }

		
		-- 1.3.6.1.4.1.1916.2.131.50.1.4.2.25.10.1.1.29
		wingStatsDevWlRadioStatTxRetries OBJECT-TYPE
			SYNTAX Counter64
			MAX-ACCESS read-only
			STATUS current
			DESCRIPTION
				"Total number of retries
				
				XPath: /wing-stats/device[mac=key1]/wireless/radio-stats[radio_id=key2]/tx_retries"
			::= { wingStatsDevWlRadioStatEntry 29 }

		
		-- 1.3.6.1.4.1.1916.2.131.50.1.4.2.25.10.1.1.30
		wingStatsDevWlRadioStatTxRetriedBytes OBJECT-TYPE
			SYNTAX Counter64
			MAX-ACCESS read-only
			STATUS current
			DESCRIPTION
				"Total retried bytes excluding bytes sent
				
				XPath: /wing-stats/device[mac=key1]/wireless/radio-stats[radio_id=key2]/tx_retried_bytes"
			::= { wingStatsDevWlRadioStatEntry 30 }

		
		-- 1.3.6.1.4.1.1916.2.131.50.1.4.2.25.20
		wingStatsDevWlApDetectTable OBJECT-TYPE
			SYNTAX SEQUENCE OF WingStatsDevWlApDetectEntry
			MAX-ACCESS not-accessible
			STATUS current
			DESCRIPTION
				"Unsanctioned APs seen
				
				/wing-stats/device/wireless/apdetection-aptable"
			::= { wingStatsDevWl 20 }

		
		-- 1.3.6.1.4.1.1916.2.131.50.1.4.2.25.20.1
		wingStatsDevWlApDetectEntry OBJECT-TYPE
			SYNTAX WingStatsDevWlApDetectEntry
			MAX-ACCESS not-accessible
			STATUS current
			DESCRIPTION
				"An entry in the table."
			INDEX { wingStatsDevMac, wingStatsDevWlApDetectMac }
			::= { wingStatsDevWlApDetectTable 1 }

		
		WingStatsDevWlApDetectEntry ::=
			SEQUENCE { 
				wingStatsDevWlApDetectMac
					MacAddress,
				wingStatsDevWlApDetectVendor
					DisplayString,
				wingStatsDevWlApDetectChannel
					DisplayString,
				wingStatsDevWlApDetectRadioType
					DisplayString,
				wingStatsDevWlApDetectApMode
					DisplayString,
				wingStatsDevWlApDetectSsid
					DisplayString,
				wingStatsDevWlApDetectRssi
					Integer32,
				wingStatsDevWlApDetectLastSeen
					Unsigned32,
				wingStatsDevWlApDetectFirstSeen
					Unsigned32,
				wingStatsDevWlApDetectEncryption
					TruthValue,
				wingStatsDevWlApDetectReportingApMac
					MacAddress,
				wingStatsDevWlApDetectReportingApRadioNum
					Unsigned32
			 }

		-- 1.3.6.1.4.1.1916.2.131.50.1.4.2.25.20.1.1
		wingStatsDevWlApDetectMac OBJECT-TYPE
			SYNTAX MacAddress
			MAX-ACCESS read-only
			STATUS current
			DESCRIPTION
				"Bssid address of the unsanctioned AP.
				
				XPath: /wing-stats/device[mac=key1]/wireless/apdetection-aptable[mac=key2]/mac"
			::= { wingStatsDevWlApDetectEntry 1 }

		
		-- 1.3.6.1.4.1.1916.2.131.50.1.4.2.25.20.1.2
		wingStatsDevWlApDetectVendor OBJECT-TYPE
			SYNTAX DisplayString (SIZE (0..64))
			MAX-ACCESS read-only
			STATUS current
			DESCRIPTION
				"Vendor name based on mac OUI lookup for the unsanctioned AP.
				
				XPath: /wing-stats/device[mac=key1]/wireless/apdetection-aptable[mac=key2]/vendor"
			::= { wingStatsDevWlApDetectEntry 2 }

		
		-- 1.3.6.1.4.1.1916.2.131.50.1.4.2.25.20.1.3
		wingStatsDevWlApDetectChannel OBJECT-TYPE
			SYNTAX DisplayString (SIZE (1..16))
			MAX-ACCESS read-only
			STATUS current
			DESCRIPTION
				"Channel information of the unsanctioned AP.
				
				XPath: /wing-stats/device[mac=key1]/wireless/apdetection-aptable[mac=key2]/channel"
			::= { wingStatsDevWlApDetectEntry 3 }

		
		-- 1.3.6.1.4.1.1916.2.131.50.1.4.2.25.20.1.4
		wingStatsDevWlApDetectRadioType OBJECT-TYPE
			SYNTAX DisplayString
			MAX-ACCESS read-only
			STATUS current
			DESCRIPTION
				"Radio type of the unsanctioned AP.
				
				Values:
				11a
				11b
				11g
				11bg
				11an
				11bgn
				
				XPath: /wing-stats/device[mac=key1]/wireless/apdetection-aptable[mac=key2]/dot11_radio_type"
			::= { wingStatsDevWlApDetectEntry 4 }

		
		-- 1.3.6.1.4.1.1916.2.131.50.1.4.2.25.20.1.5
		wingStatsDevWlApDetectApMode OBJECT-TYPE
			SYNTAX DisplayString
			MAX-ACCESS read-only
			STATUS current
			DESCRIPTION
				"Operating mode of the unsanctioned AP.
				
				Values:
				ap
				adhoc
				
				XPath: /wing-stats/device[mac=key1]/wireless/apdetection-aptable[mac=key2]/ap_mode"
			::= { wingStatsDevWlApDetectEntry 5 }

		
		-- 1.3.6.1.4.1.1916.2.131.50.1.4.2.25.20.1.6
		wingStatsDevWlApDetectSsid OBJECT-TYPE
			SYNTAX DisplayString (SIZE (1..255))
			MAX-ACCESS read-only
			STATUS current
			DESCRIPTION
				"ssid of the unsanctioned AP.
				
				XPath: /wing-stats/device[mac=key1]/wireless/apdetection-aptable[mac=key2]/ssid"
			::= { wingStatsDevWlApDetectEntry 6 }

		
		-- 1.3.6.1.4.1.1916.2.131.50.1.4.2.25.20.1.7
		wingStatsDevWlApDetectRssi OBJECT-TYPE
			SYNTAX Integer32
			UNITS "dBm"
			MAX-ACCESS read-only
			STATUS current
			DESCRIPTION
				"Signal strength of the unsanctioned AP.
				
				XPath: /wing-stats/device[mac=key1]/wireless/apdetection-aptable[mac=key2]/rssi"
			::= { wingStatsDevWlApDetectEntry 7 }

		
		-- 1.3.6.1.4.1.1916.2.131.50.1.4.2.25.20.1.8
		wingStatsDevWlApDetectLastSeen OBJECT-TYPE
			SYNTAX Unsigned32
			UNITS "seconds"
			MAX-ACCESS read-only
			STATUS current
			DESCRIPTION
				"Seconds ago from the current time the unsanctioned AP was
				last seen.
				
				XPath: /wing-stats/device[mac=key1]/wireless/apdetection-aptable[mac=key2]/last_seen"
			::= { wingStatsDevWlApDetectEntry 8 }

		
		-- 1.3.6.1.4.1.1916.2.131.50.1.4.2.25.20.1.9
		wingStatsDevWlApDetectFirstSeen OBJECT-TYPE
			SYNTAX Unsigned32
			UNITS "seconds"
			MAX-ACCESS read-only
			STATUS current
			DESCRIPTION
				"Seconds ago from the current time the unsanctioned AP was
				first seen.
				
				XPath: /wing-stats/device[mac=key1]/wireless/apdetection-aptable[mac=key2]/first_seen"
			::= { wingStatsDevWlApDetectEntry 9 }

		
		-- 1.3.6.1.4.1.1916.2.131.50.1.4.2.25.20.1.10
		wingStatsDevWlApDetectEncryption OBJECT-TYPE
			SYNTAX TruthValue
			MAX-ACCESS read-only
			STATUS current
			DESCRIPTION
				"Whether the unsanctioned AP supports data encryption.
				
				XPath: /wing-stats/device[mac=key1]/wireless/apdetection-aptable[mac=key2]/encryption"
			::= { wingStatsDevWlApDetectEntry 10 }

		
		-- 1.3.6.1.4.1.1916.2.131.50.1.4.2.25.20.1.11
		wingStatsDevWlApDetectReportingApMac OBJECT-TYPE
			SYNTAX MacAddress
			MAX-ACCESS read-only
			STATUS current
			DESCRIPTION
				"Mac address of the AP reporting this unsanctioned AP entry.
				
				XPath: /wing-stats/device[mac=key1]/wireless/apdetection-aptable[mac=key2]/reporting_ap_mac"
			::= { wingStatsDevWlApDetectEntry 11 }

		
		-- 1.3.6.1.4.1.1916.2.131.50.1.4.2.25.20.1.12
		wingStatsDevWlApDetectReportingApRadioNum OBJECT-TYPE
			SYNTAX Unsigned32
			MAX-ACCESS read-only
			STATUS current
			DESCRIPTION
				"Radio number on the AP reporting this unsanctioned AP entry.
				
				XPath: /wing-stats/device[mac=key1]/wireless/apdetection-aptable[mac=key2]/reporting_ap_radio_num"
			::= { wingStatsDevWlApDetectEntry 12 }

		
		-- 1.3.6.1.4.1.1916.2.131.50.1.4.2.25.21
		wingStatsDevWlMcx OBJECT IDENTIFIER ::= { wingStatsDevWl 21 }

		
		-- 1.3.6.1.4.1.1916.2.131.50.1.4.2.25.21.1
		wingStatsDevWlMcxMeshpointTable OBJECT-TYPE
			SYNTAX SEQUENCE OF WingStatsDevWlMcxMeshpointEntry
			MAX-ACCESS not-accessible
			STATUS current
			DESCRIPTION
				"
				
				/wing-stats/device/wireless/meshpoint"
			::= { wingStatsDevWlMcx 1 }

		
		-- 1.3.6.1.4.1.1916.2.131.50.1.4.2.25.21.1.1
		wingStatsDevWlMcxMeshpointEntry OBJECT-TYPE
			SYNTAX WingStatsDevWlMcxMeshpointEntry
			MAX-ACCESS not-accessible
			STATUS current
			DESCRIPTION
				"An entry in the table."
			INDEX { wingStatsDevMac, wingStatsDevWlMcxMeshpointMpid }
			::= { wingStatsDevWlMcxMeshpointTable 1 }

		
		WingStatsDevWlMcxMeshpointEntry ::=
			SEQUENCE { 
				wingStatsDevWlMcxMeshpointMpid
					WingIdentifier,
				wingStatsDevWlMcxMeshpointName
					WingIdentifier,
				wingStatsDevWlMcxMeshpointHostname
					DisplayString,
				wingStatsDevWlMcxMeshpointDeviceMac
					DisplayString,
				wingStatsDevWlMcxMeshpointIsRoot
					TruthValue,
				wingStatsDevWlMcxMeshpointIsCfgRoot
					TruthValue,
				wingStatsDevWlMcxMeshpointRootMpid
					DisplayString,
				wingStatsDevWlMcxMeshpointNextHop
					DisplayString,
				wingStatsDevWlMcxMeshpointRootHops
					Unsigned32,
				wingStatsDevWlMcxMeshpointIfidCnt
					Unsigned32
			 }

		-- 1.3.6.1.4.1.1916.2.131.50.1.4.2.25.21.1.1.1
		wingStatsDevWlMcxMeshpointMpid OBJECT-TYPE
			SYNTAX WingIdentifier
			MAX-ACCESS read-only
			STATUS current
			DESCRIPTION
				"Mesh Point MAC address
				
				XPath: /wing-stats/device[mac=key1]/wireless/meshpoint[mpid=key2]/mpid"
			::= { wingStatsDevWlMcxMeshpointEntry 1 }

		
		-- 1.3.6.1.4.1.1916.2.131.50.1.4.2.25.21.1.1.3
		wingStatsDevWlMcxMeshpointName OBJECT-TYPE
			SYNTAX WingIdentifier
			MAX-ACCESS read-only
			STATUS current
			DESCRIPTION
				"
				
				XPath: /wing-stats/device[mac=key1]/wireless/meshpoint[mpid=key2]/name"
			::= { wingStatsDevWlMcxMeshpointEntry 3 }

		
		-- 1.3.6.1.4.1.1916.2.131.50.1.4.2.25.21.1.1.4
		wingStatsDevWlMcxMeshpointHostname OBJECT-TYPE
			SYNTAX DisplayString (SIZE (64))
			MAX-ACCESS read-only
			STATUS current
			DESCRIPTION
				"hostname of the AP device
				
				XPath: /wing-stats/device[mac=key1]/wireless/meshpoint[mpid=key2]/hostname"
			::= { wingStatsDevWlMcxMeshpointEntry 4 }

		
		-- 1.3.6.1.4.1.1916.2.131.50.1.4.2.25.21.1.1.5
		wingStatsDevWlMcxMeshpointDeviceMac OBJECT-TYPE
			SYNTAX DisplayString
			MAX-ACCESS read-only
			STATUS current
			DESCRIPTION
				"Device MAC address
				
				XPath: /wing-stats/device[mac=key1]/wireless/meshpoint[mpid=key2]/device_mac"
			::= { wingStatsDevWlMcxMeshpointEntry 5 }

		
		-- 1.3.6.1.4.1.1916.2.131.50.1.4.2.25.21.1.1.6
		wingStatsDevWlMcxMeshpointIsRoot OBJECT-TYPE
			SYNTAX TruthValue
			MAX-ACCESS read-only
			STATUS current
			DESCRIPTION
				"Acting as root or non-root
				
				XPath: /wing-stats/device[mac=key1]/wireless/meshpoint[mpid=key2]/is_root"
			::= { wingStatsDevWlMcxMeshpointEntry 6 }

		
		-- 1.3.6.1.4.1.1916.2.131.50.1.4.2.25.21.1.1.7
		wingStatsDevWlMcxMeshpointIsCfgRoot OBJECT-TYPE
			SYNTAX TruthValue
			MAX-ACCESS read-only
			STATUS current
			DESCRIPTION
				"Configured as root device, is_root can be false due to dynamic factors
				
				XPath: /wing-stats/device[mac=key1]/wireless/meshpoint[mpid=key2]/is_cfg_root"
			::= { wingStatsDevWlMcxMeshpointEntry 7 }

		
		-- 1.3.6.1.4.1.1916.2.131.50.1.4.2.25.21.1.1.8
		wingStatsDevWlMcxMeshpointRootMpid OBJECT-TYPE
			SYNTAX DisplayString
			MAX-ACCESS read-only
			STATUS current
			DESCRIPTION
				"Root mesh point MAC address
				
				XPath: /wing-stats/device[mac=key1]/wireless/meshpoint[mpid=key2]/root_mpid"
			::= { wingStatsDevWlMcxMeshpointEntry 8 }

		
		-- 1.3.6.1.4.1.1916.2.131.50.1.4.2.25.21.1.1.9
		wingStatsDevWlMcxMeshpointNextHop OBJECT-TYPE
			SYNTAX DisplayString
			MAX-ACCESS read-only
			STATUS current
			DESCRIPTION
				"Next IFID hop to root
				
				XPath: /wing-stats/device[mac=key1]/wireless/meshpoint[mpid=key2]/next_hop"
			::= { wingStatsDevWlMcxMeshpointEntry 9 }

		
		-- 1.3.6.1.4.1.1916.2.131.50.1.4.2.25.21.1.1.10
		wingStatsDevWlMcxMeshpointRootHops OBJECT-TYPE
			SYNTAX Unsigned32
			MAX-ACCESS read-only
			STATUS current
			DESCRIPTION
				"Hops to root
				
				XPath: /wing-stats/device[mac=key1]/wireless/meshpoint[mpid=key2]/root_hops"
			::= { wingStatsDevWlMcxMeshpointEntry 10 }

		
		-- 1.3.6.1.4.1.1916.2.131.50.1.4.2.25.21.1.1.11
		wingStatsDevWlMcxMeshpointIfidCnt OBJECT-TYPE
			SYNTAX Unsigned32
			MAX-ACCESS read-only
			STATUS current
			DESCRIPTION
				"Number of IFID entries
				
				XPath: /wing-stats/device[mac=key1]/wireless/meshpoint[mpid=key2]/ifid_cnt"
			::= { wingStatsDevWlMcxMeshpointEntry 11 }

		
		-- 1.3.6.1.4.1.1916.2.131.50.1.4.2.25.21.2
		wingStatsDevWlMcxMeshpointIfidDataTable OBJECT-TYPE
			SYNTAX SEQUENCE OF WingStatsDevWlMcxMeshpointIfidDataEntry
			MAX-ACCESS not-accessible
			STATUS current
			DESCRIPTION
				"
				
				/wing-stats/device/wireless/meshpoint/ifid_data"
			::= { wingStatsDevWlMcx 2 }

		
		-- 1.3.6.1.4.1.1916.2.131.50.1.4.2.25.21.2.1
		wingStatsDevWlMcxMeshpointIfidDataEntry OBJECT-TYPE
			SYNTAX WingStatsDevWlMcxMeshpointIfidDataEntry
			MAX-ACCESS not-accessible
			STATUS current
			DESCRIPTION
				"An entry in the table."
			INDEX { wingStatsDevMac, wingStatsDevWlMcxMeshpointMpid, wingStatsDevWlMcxMeshpointIfid }
			::= { wingStatsDevWlMcxMeshpointIfidDataTable 1 }

		
		WingStatsDevWlMcxMeshpointIfidDataEntry ::=
			SEQUENCE { 
				wingStatsDevWlMcxMeshpointIfid
					WingIdentifier,
				wingStatsDevWlMcxMeshpointIfidDataDesc
					DisplayString
			 }

		-- 1.3.6.1.4.1.1916.2.131.50.1.4.2.25.21.2.1.1
		wingStatsDevWlMcxMeshpointIfid OBJECT-TYPE
			SYNTAX WingIdentifier
			MAX-ACCESS read-only
			STATUS current
			DESCRIPTION
				"
				
				XPath: /wing-stats/device[mac=key1]/wireless/meshpoint[mpid=key2]/ifid_data[ifid=key3]/ifid"
			::= { wingStatsDevWlMcxMeshpointIfidDataEntry 1 }

		
		-- 1.3.6.1.4.1.1916.2.131.50.1.4.2.25.21.2.1.3
		wingStatsDevWlMcxMeshpointIfidDataDesc OBJECT-TYPE
			SYNTAX DisplayString (SIZE (24))
			MAX-ACCESS read-only
			STATUS current
			DESCRIPTION
				"Description of interface
				
				XPath: /wing-stats/device[mac=key1]/wireless/meshpoint[mpid=key2]/ifid_data[ifid=key3]/desc"
			::= { wingStatsDevWlMcxMeshpointIfidDataEntry 3 }

		
		-- 1.3.6.1.4.1.1916.2.131.50.1.4.2.25.21.3
		wingStatsDevWlMcxMeshpointStatsTable OBJECT-TYPE
			SYNTAX SEQUENCE OF WingStatsDevWlMcxMeshpointStatsEntry
			MAX-ACCESS not-accessible
			STATUS current
			DESCRIPTION
				"
				
				/wing-stats/device/wireless/meshpoint-stats"
			::= { wingStatsDevWlMcx 3 }

		
		-- 1.3.6.1.4.1.1916.2.131.50.1.4.2.25.21.3.1
		wingStatsDevWlMcxMeshpointStatsEntry OBJECT-TYPE
			SYNTAX WingStatsDevWlMcxMeshpointStatsEntry
			MAX-ACCESS not-accessible
			STATUS current
			DESCRIPTION
				"An entry in the table."
			INDEX { wingStatsDevMac, wingStatsDevWlMcxMeshpointStatsName }
			::= { wingStatsDevWlMcxMeshpointStatsTable 1 }

		
		WingStatsDevWlMcxMeshpointStatsEntry ::=
			SEQUENCE { 
				wingStatsDevWlMcxMeshpointStatsName
					WingIdentifier,
				wingStatsDevWlMcxMeshpointStatsMeshid
					DisplayString,
				wingStatsDevWlMcxMeshpointStatsNumRadios
					Unsigned32,
				wingStatsDevWlMcxMeshpointStatsNumNeighbors
					Unsigned32,
				wingStatsDevWlMcxMeshpointStatsTxBytes
					Counter64,
				wingStatsDevWlMcxMeshpointStatsRxBytes
					Counter64,
				wingStatsDevWlMcxMeshpointStatsTxPkts
					Unsigned32,
				wingStatsDevWlMcxMeshpointStatsRxPkts
					Unsigned32,
				wingStatsDevWlMcxMeshpointStatsTxDropped
					Unsigned32,
				wingStatsDevWlMcxMeshpointStatsRxErrors
					Unsigned32,
				wingStatsDevWlMcxMeshpointStatsTIndex
					Unsigned32,
				wingStatsDevWlMcxMeshpointStatsTotalBytes
					Counter64,
				wingStatsDevWlMcxMeshpointStatsTotalPkts
					Unsigned32,
				wingStatsDevWlMcxMeshpointStatsTxBps
					Unsigned32,
				wingStatsDevWlMcxMeshpointStatsRxBps
					Unsigned32,
				wingStatsDevWlMcxMeshpointStatsTotalBps
					Unsigned32,
				wingStatsDevWlMcxMeshpointStatsTxPps
					Unsigned32,
				wingStatsDevWlMcxMeshpointStatsRxPps
					Unsigned32,
				wingStatsDevWlMcxMeshpointStatsTotalPps
					Unsigned32,
				wingStatsDevWlMcxMeshpointStatsTxBcmcPkts
					Counter64,
				wingStatsDevWlMcxMeshpointStatsRxBcmcPkts
					Counter64,
				wingStatsDevWlMcxMeshpointStatsTotalBcmcPkts
					Counter64,
				wingStatsDevWlMcxMeshpointStatsTxMgmtPkts
					Counter64,
				wingStatsDevWlMcxMeshpointStatsRxMgmtPkts
					Counter64,
				wingStatsDevWlMcxMeshpointStatsTotalMgmtPkts
					Counter64,
				wingStatsDevWlMcxMeshpointStatsMaxUserRate
					Unsigned32
			 }

		-- 1.3.6.1.4.1.1916.2.131.50.1.4.2.25.21.3.1.1
		wingStatsDevWlMcxMeshpointStatsName OBJECT-TYPE
			SYNTAX WingIdentifier
			MAX-ACCESS read-only
			STATUS current
			DESCRIPTION
				"
				
				XPath: /wing-stats/device[mac=key1]/wireless/meshpoint-stats[name=key2]/name"
			::= { wingStatsDevWlMcxMeshpointStatsEntry 1 }

		
		-- 1.3.6.1.4.1.1916.2.131.50.1.4.2.25.21.3.1.3
		wingStatsDevWlMcxMeshpointStatsMeshid OBJECT-TYPE
			SYNTAX DisplayString (SIZE (32))
			MAX-ACCESS read-only
			STATUS current
			DESCRIPTION
				"Mesh Point Identifier for this MP.
				
				XPath: /wing-stats/device[mac=key1]/wireless/meshpoint-stats[name=key2]/meshid"
			::= { wingStatsDevWlMcxMeshpointStatsEntry 3 }

		
		-- 1.3.6.1.4.1.1916.2.131.50.1.4.2.25.21.3.1.4
		wingStatsDevWlMcxMeshpointStatsNumRadios OBJECT-TYPE
			SYNTAX Unsigned32
			MAX-ACCESS read-only
			STATUS current
			DESCRIPTION
				"
				
				XPath: /wing-stats/device[mac=key1]/wireless/meshpoint-stats[name=key2]/num_radios"
			::= { wingStatsDevWlMcxMeshpointStatsEntry 4 }

		
		-- 1.3.6.1.4.1.1916.2.131.50.1.4.2.25.21.3.1.5
		wingStatsDevWlMcxMeshpointStatsNumNeighbors OBJECT-TYPE
			SYNTAX Unsigned32
			MAX-ACCESS read-only
			STATUS current
			DESCRIPTION
				"number of neighbors resourced to this meshpoint
				
				XPath: /wing-stats/device[mac=key1]/wireless/meshpoint-stats[name=key2]/num_neighbors"
			::= { wingStatsDevWlMcxMeshpointStatsEntry 5 }

		
		-- 1.3.6.1.4.1.1916.2.131.50.1.4.2.25.21.3.1.6
		wingStatsDevWlMcxMeshpointStatsTxBytes OBJECT-TYPE
			SYNTAX Counter64
			MAX-ACCESS read-only
			STATUS current
			DESCRIPTION
				"Number of data bytes transmitted - from AP to client
				
				XPath: /wing-stats/device[mac=key1]/wireless/meshpoint-stats[name=key2]/tx_bytes"
			::= { wingStatsDevWlMcxMeshpointStatsEntry 6 }

		
		-- 1.3.6.1.4.1.1916.2.131.50.1.4.2.25.21.3.1.7
		wingStatsDevWlMcxMeshpointStatsRxBytes OBJECT-TYPE
			SYNTAX Counter64
			MAX-ACCESS read-only
			STATUS current
			DESCRIPTION
				"Number of data bytes received - from client to AP
				
				XPath: /wing-stats/device[mac=key1]/wireless/meshpoint-stats[name=key2]/rx_bytes"
			::= { wingStatsDevWlMcxMeshpointStatsEntry 7 }

		
		-- 1.3.6.1.4.1.1916.2.131.50.1.4.2.25.21.3.1.8
		wingStatsDevWlMcxMeshpointStatsTxPkts OBJECT-TYPE
			SYNTAX Unsigned32
			MAX-ACCESS read-only
			STATUS current
			DESCRIPTION
				"Number of packets of data transmitted - from AP to node
				
				XPath: /wing-stats/device[mac=key1]/wireless/meshpoint-stats[name=key2]/tx_pkts"
			::= { wingStatsDevWlMcxMeshpointStatsEntry 8 }

		
		-- 1.3.6.1.4.1.1916.2.131.50.1.4.2.25.21.3.1.9
		wingStatsDevWlMcxMeshpointStatsRxPkts OBJECT-TYPE
			SYNTAX Unsigned32
			MAX-ACCESS read-only
			STATUS current
			DESCRIPTION
				"Number of packets of data received - from client to AP
				
				XPath: /wing-stats/device[mac=key1]/wireless/meshpoint-stats[name=key2]/rx_pkts"
			::= { wingStatsDevWlMcxMeshpointStatsEntry 9 }

		
		-- 1.3.6.1.4.1.1916.2.131.50.1.4.2.25.21.3.1.10
		wingStatsDevWlMcxMeshpointStatsTxDropped OBJECT-TYPE
			SYNTAX Unsigned32
			MAX-ACCESS read-only
			STATUS current
			DESCRIPTION
				"Number of packets of data dropped on transmission
				
				XPath: /wing-stats/device[mac=key1]/wireless/meshpoint-stats[name=key2]/tx_dropped"
			::= { wingStatsDevWlMcxMeshpointStatsEntry 10 }

		
		-- 1.3.6.1.4.1.1916.2.131.50.1.4.2.25.21.3.1.11
		wingStatsDevWlMcxMeshpointStatsRxErrors OBJECT-TYPE
			SYNTAX Unsigned32
			MAX-ACCESS read-only
			STATUS current
			DESCRIPTION
				"Number of packets of data received with errors 
				
				XPath: /wing-stats/device[mac=key1]/wireless/meshpoint-stats[name=key2]/rx_errors"
			::= { wingStatsDevWlMcxMeshpointStatsEntry 11 }

		
		-- 1.3.6.1.4.1.1916.2.131.50.1.4.2.25.21.3.1.12
		wingStatsDevWlMcxMeshpointStatsTIndex OBJECT-TYPE
			SYNTAX Unsigned32
			MAX-ACCESS read-only
			STATUS current
			DESCRIPTION
				"
				
				XPath: /wing-stats/device[mac=key1]/wireless/meshpoint-stats[name=key2]/t_index"
			::= { wingStatsDevWlMcxMeshpointStatsEntry 12 }

		
		-- 1.3.6.1.4.1.1916.2.131.50.1.4.2.25.21.3.1.13
		wingStatsDevWlMcxMeshpointStatsTotalBytes OBJECT-TYPE
			SYNTAX Counter64
			MAX-ACCESS read-only
			STATUS current
			DESCRIPTION
				"Total mumber of data bytes through this node
				
				XPath: /wing-stats/device[mac=key1]/wireless/meshpoint-stats[name=key2]/total_bytes"
			::= { wingStatsDevWlMcxMeshpointStatsEntry 13 }

		
		-- 1.3.6.1.4.1.1916.2.131.50.1.4.2.25.21.3.1.14
		wingStatsDevWlMcxMeshpointStatsTotalPkts OBJECT-TYPE
			SYNTAX Unsigned32
			MAX-ACCESS read-only
			STATUS current
			DESCRIPTION
				"Total mumber of packets through this node
				
				XPath: /wing-stats/device[mac=key1]/wireless/meshpoint-stats[name=key2]/total_pkts"
			::= { wingStatsDevWlMcxMeshpointStatsEntry 14 }

		
		-- 1.3.6.1.4.1.1916.2.131.50.1.4.2.25.21.3.1.15
		wingStatsDevWlMcxMeshpointStatsTxBps OBJECT-TYPE
			SYNTAX Unsigned32
			UNITS "kbps"
			MAX-ACCESS read-only
			STATUS current
			DESCRIPTION
				"user data transmit rate
				
				XPath: /wing-stats/device[mac=key1]/wireless/meshpoint-stats[name=key2]/tx_bps"
			::= { wingStatsDevWlMcxMeshpointStatsEntry 15 }

		
		-- 1.3.6.1.4.1.1916.2.131.50.1.4.2.25.21.3.1.16
		wingStatsDevWlMcxMeshpointStatsRxBps OBJECT-TYPE
			SYNTAX Unsigned32
			UNITS "kbps"
			MAX-ACCESS read-only
			STATUS current
			DESCRIPTION
				"user data receive rate
				
				XPath: /wing-stats/device[mac=key1]/wireless/meshpoint-stats[name=key2]/rx_bps"
			::= { wingStatsDevWlMcxMeshpointStatsEntry 16 }

		
		-- 1.3.6.1.4.1.1916.2.131.50.1.4.2.25.21.3.1.17
		wingStatsDevWlMcxMeshpointStatsTotalBps OBJECT-TYPE
			SYNTAX Unsigned32
			UNITS "kbps"
			MAX-ACCESS read-only
			STATUS current
			DESCRIPTION
				"total user data rate
				
				XPath: /wing-stats/device[mac=key1]/wireless/meshpoint-stats[name=key2]/total_bps"
			::= { wingStatsDevWlMcxMeshpointStatsEntry 17 }

		
		-- 1.3.6.1.4.1.1916.2.131.50.1.4.2.25.21.3.1.18
		wingStatsDevWlMcxMeshpointStatsTxPps OBJECT-TYPE
			SYNTAX Unsigned32
			MAX-ACCESS read-only
			STATUS current
			DESCRIPTION
				"transmitting packet rate - AP to client
				
				XPath: /wing-stats/device[mac=key1]/wireless/meshpoint-stats[name=key2]/tx_pps"
			::= { wingStatsDevWlMcxMeshpointStatsEntry 18 }

		
		-- 1.3.6.1.4.1.1916.2.131.50.1.4.2.25.21.3.1.19
		wingStatsDevWlMcxMeshpointStatsRxPps OBJECT-TYPE
			SYNTAX Unsigned32
			MAX-ACCESS read-only
			STATUS current
			DESCRIPTION
				"receiving packet rate - client to AP
				
				XPath: /wing-stats/device[mac=key1]/wireless/meshpoint-stats[name=key2]/rx_pps"
			::= { wingStatsDevWlMcxMeshpointStatsEntry 19 }

		
		-- 1.3.6.1.4.1.1916.2.131.50.1.4.2.25.21.3.1.20
		wingStatsDevWlMcxMeshpointStatsTotalPps OBJECT-TYPE
			SYNTAX Unsigned32
			MAX-ACCESS read-only
			STATUS current
			DESCRIPTION
				"total packet rate
				
				XPath: /wing-stats/device[mac=key1]/wireless/meshpoint-stats[name=key2]/total_pps"
			::= { wingStatsDevWlMcxMeshpointStatsEntry 20 }

		
		-- 1.3.6.1.4.1.1916.2.131.50.1.4.2.25.21.3.1.21
		wingStatsDevWlMcxMeshpointStatsTxBcmcPkts OBJECT-TYPE
			SYNTAX Counter64
			MAX-ACCESS read-only
			STATUS current
			DESCRIPTION
				"Number of broadcast packets transmitted by the node
				
				XPath: /wing-stats/device[mac=key1]/wireless/meshpoint-stats[name=key2]/tx_bcmc_pkts"
			::= { wingStatsDevWlMcxMeshpointStatsEntry 21 }

		
		-- 1.3.6.1.4.1.1916.2.131.50.1.4.2.25.21.3.1.22
		wingStatsDevWlMcxMeshpointStatsRxBcmcPkts OBJECT-TYPE
			SYNTAX Counter64
			MAX-ACCESS read-only
			STATUS current
			DESCRIPTION
				"Number of broadcast packets of received by the node
				
				XPath: /wing-stats/device[mac=key1]/wireless/meshpoint-stats[name=key2]/rx_bcmc_pkts"
			::= { wingStatsDevWlMcxMeshpointStatsEntry 22 }

		
		-- 1.3.6.1.4.1.1916.2.131.50.1.4.2.25.21.3.1.23
		wingStatsDevWlMcxMeshpointStatsTotalBcmcPkts OBJECT-TYPE
			SYNTAX Counter64
			MAX-ACCESS read-only
			STATUS current
			DESCRIPTION
				"Total number of broadcast packets through this node
				
				XPath: /wing-stats/device[mac=key1]/wireless/meshpoint-stats[name=key2]/total_bcmc_pkts"
			::= { wingStatsDevWlMcxMeshpointStatsEntry 23 }

		
		-- 1.3.6.1.4.1.1916.2.131.50.1.4.2.25.21.3.1.24
		wingStatsDevWlMcxMeshpointStatsTxMgmtPkts OBJECT-TYPE
			SYNTAX Counter64
			MAX-ACCESS read-only
			STATUS current
			DESCRIPTION
				"Number of management packets of transmitted by the node
				
				XPath: /wing-stats/device[mac=key1]/wireless/meshpoint-stats[name=key2]/tx_mgmt_pkts"
			::= { wingStatsDevWlMcxMeshpointStatsEntry 24 }

		
		-- 1.3.6.1.4.1.1916.2.131.50.1.4.2.25.21.3.1.25
		wingStatsDevWlMcxMeshpointStatsRxMgmtPkts OBJECT-TYPE
			SYNTAX Counter64
			MAX-ACCESS read-only
			STATUS current
			DESCRIPTION
				"Number of management packets of received by the node
				
				XPath: /wing-stats/device[mac=key1]/wireless/meshpoint-stats[name=key2]/rx_mgmt_pkts"
			::= { wingStatsDevWlMcxMeshpointStatsEntry 25 }

		
		-- 1.3.6.1.4.1.1916.2.131.50.1.4.2.25.21.3.1.26
		wingStatsDevWlMcxMeshpointStatsTotalMgmtPkts OBJECT-TYPE
			SYNTAX Counter64
			MAX-ACCESS read-only
			STATUS current
			DESCRIPTION
				"Total Number of management packets Through the domain
				
				XPath: /wing-stats/device[mac=key1]/wireless/meshpoint-stats[name=key2]/total_mgmt_pkts"
			::= { wingStatsDevWlMcxMeshpointStatsEntry 26 }

		
		-- 1.3.6.1.4.1.1916.2.131.50.1.4.2.25.21.3.1.27
		wingStatsDevWlMcxMeshpointStatsMaxUserRate OBJECT-TYPE
			SYNTAX Unsigned32
			UNITS "kbps"
			MAX-ACCESS read-only
			STATUS current
			DESCRIPTION
				"Theoretic maximum user-level data rate
				
				XPath: /wing-stats/device[mac=key1]/wireless/meshpoint-stats[name=key2]/max_user_rate"
			::= { wingStatsDevWlMcxMeshpointStatsEntry 27 }

		
		-- 1.3.6.1.4.1.1916.2.131.50.1.4.2.25.21.4
		wingStatsDevWlMcxMeshpointNeighborsTable OBJECT-TYPE
			SYNTAX SEQUENCE OF WingStatsDevWlMcxMeshpointNeighborsEntry
			MAX-ACCESS not-accessible
			STATUS current
			DESCRIPTION
				"
				
				/wing-stats/device/wireless/meshpoint-neighbors"
			::= { wingStatsDevWlMcx 4 }

		
		-- 1.3.6.1.4.1.1916.2.131.50.1.4.2.25.21.4.1
		wingStatsDevWlMcxMeshpointNeighborsEntry OBJECT-TYPE
			SYNTAX WingStatsDevWlMcxMeshpointNeighborsEntry
			MAX-ACCESS not-accessible
			STATUS current
			DESCRIPTION
				"An entry in the table."
			INDEX { wingStatsDevMac, wingStatsDevWlMcxMeshpointNeighborsMpid }
			::= { wingStatsDevWlMcxMeshpointNeighborsTable 1 }

		
		WingStatsDevWlMcxMeshpointNeighborsEntry ::=
			SEQUENCE { 
				wingStatsDevWlMcxMeshpointNeighborsMpid
					WingIdentifier,
				wingStatsDevWlMcxMeshpointNeighborsName
					WingIdentifier,
				wingStatsDevWlMcxMeshpointNeighborsHostname
					DisplayString,
				wingStatsDevWlMcxMeshpointNeighborsDeviceMac
					DisplayString,
				wingStatsDevWlMcxMeshpointNeighborsNumEntries
					Unsigned32
			 }

		-- 1.3.6.1.4.1.1916.2.131.50.1.4.2.25.21.4.1.1
		wingStatsDevWlMcxMeshpointNeighborsMpid OBJECT-TYPE
			SYNTAX WingIdentifier
			MAX-ACCESS read-only
			STATUS current
			DESCRIPTION
				"Mesh Point MAC address
				
				XPath: /wing-stats/device[mac=key1]/wireless/meshpoint-neighbors[mpid=key2]/mpid"
			::= { wingStatsDevWlMcxMeshpointNeighborsEntry 1 }

		
		-- 1.3.6.1.4.1.1916.2.131.50.1.4.2.25.21.4.1.3
		wingStatsDevWlMcxMeshpointNeighborsName OBJECT-TYPE
			SYNTAX WingIdentifier
			MAX-ACCESS read-only
			STATUS current
			DESCRIPTION
				"
				
				XPath: /wing-stats/device[mac=key1]/wireless/meshpoint-neighbors[mpid=key2]/name"
			::= { wingStatsDevWlMcxMeshpointNeighborsEntry 3 }

		
		-- 1.3.6.1.4.1.1916.2.131.50.1.4.2.25.21.4.1.4
		wingStatsDevWlMcxMeshpointNeighborsHostname OBJECT-TYPE
			SYNTAX DisplayString (SIZE (64))
			MAX-ACCESS read-only
			STATUS current
			DESCRIPTION
				"hostname of the AP device
				
				XPath: /wing-stats/device[mac=key1]/wireless/meshpoint-neighbors[mpid=key2]/hostname"
			::= { wingStatsDevWlMcxMeshpointNeighborsEntry 4 }

		
		-- 1.3.6.1.4.1.1916.2.131.50.1.4.2.25.21.4.1.5
		wingStatsDevWlMcxMeshpointNeighborsDeviceMac OBJECT-TYPE
			SYNTAX DisplayString
			MAX-ACCESS read-only
			STATUS current
			DESCRIPTION
				"Device MAC address
				
				XPath: /wing-stats/device[mac=key1]/wireless/meshpoint-neighbors[mpid=key2]/device_mac"
			::= { wingStatsDevWlMcxMeshpointNeighborsEntry 5 }

		
		-- 1.3.6.1.4.1.1916.2.131.50.1.4.2.25.21.4.1.6
		wingStatsDevWlMcxMeshpointNeighborsNumEntries OBJECT-TYPE
			SYNTAX Unsigned32
			MAX-ACCESS read-only
			STATUS current
			DESCRIPTION
				"Number of entries on for this table
				
				XPath: /wing-stats/device[mac=key1]/wireless/meshpoint-neighbors[mpid=key2]/num_entries"
			::= { wingStatsDevWlMcxMeshpointNeighborsEntry 6 }

		
		-- 1.3.6.1.4.1.1916.2.131.50.1.4.2.25.21.5
		wingStatsDevWlMcxMeshpointNeighborsEntriesTable OBJECT-TYPE
			SYNTAX SEQUENCE OF WingStatsDevWlMcxMeshpointNeighborsEntriesEntry
			MAX-ACCESS not-accessible
			STATUS current
			DESCRIPTION
				"
				
				/wing-stats/device/wireless/meshpoint-neighbors/entries"
			::= { wingStatsDevWlMcx 5 }

		
		-- 1.3.6.1.4.1.1916.2.131.50.1.4.2.25.21.5.1
		wingStatsDevWlMcxMeshpointNeighborsEntriesEntry OBJECT-TYPE
			SYNTAX WingStatsDevWlMcxMeshpointNeighborsEntriesEntry
			MAX-ACCESS not-accessible
			STATUS current
			DESCRIPTION
				"An entry in the table."
			INDEX { wingStatsDevMac, wingStatsDevWlMcxMeshpointNeighborsMpid, wingStatsDevWlMcxMeshpointNeighborsEntriesIndex }
			::= { wingStatsDevWlMcxMeshpointNeighborsEntriesTable 1 }

		
		WingStatsDevWlMcxMeshpointNeighborsEntriesEntry ::=
			SEQUENCE { 
				wingStatsDevWlMcxMeshpointNeighborsEntriesIndex
					Unsigned32,
				wingStatsDevWlMcxMeshpointNeighborsEntriesNeighborIfid
					DisplayString,
				wingStatsDevWlMcxMeshpointNeighborsEntriesNeighborMpid
					DisplayString,
				wingStatsDevWlMcxMeshpointNeighborsEntriesBoundRoot
					DisplayString,
				wingStatsDevWlMcxMeshpointNeighborsEntriesRootMetric
					Unsigned32,
				wingStatsDevWlMcxMeshpointNeighborsEntriesRootHops
					Unsigned32,
				wingStatsDevWlMcxMeshpointNeighborsEntriesValid
					TruthValue,
				wingStatsDevWlMcxMeshpointNeighborsEntriesRoot
					TruthValue,
				wingStatsDevWlMcxMeshpointNeighborsEntriesProxy
					TruthValue,
				wingStatsDevWlMcxMeshpointNeighborsEntriesGeoReference
					TruthValue,
				wingStatsDevWlMcxMeshpointNeighborsEntriesMobile
					TruthValue,
				wingStatsDevWlMcxMeshpointNeighborsEntriesInterfaceId
					WingIdentifier,
				wingStatsDevWlMcxMeshpointNeighborsEntriesAuthState
					DisplayString,
				wingStatsDevWlMcxMeshpointNeighborsEntriesRank
					DisplayString,
				wingStatsDevWlMcxMeshpointNeighborsEntriesResourced
					TruthValue,
				wingStatsDevWlMcxMeshpointNeighborsEntriesLinkQuality
					Unsigned32,
				wingStatsDevWlMcxMeshpointNeighborsEntriesLinkMetric
					Unsigned32,
				wingStatsDevWlMcxMeshpointNeighborsEntriesAge
					Integer32
			 }

		-- 1.3.6.1.4.1.1916.2.131.50.1.4.2.25.21.5.1.1
		wingStatsDevWlMcxMeshpointNeighborsEntriesIndex OBJECT-TYPE
			SYNTAX Unsigned32 (1..4294967295)
			MAX-ACCESS read-only
			STATUS current
			DESCRIPTION
				"Entries Index
				
				XPath: /wing-stats/device[mac=key1]/wireless/meshpoint-neighbors[mpid=key2]/entries[entry_idx=key3]/entry_idx"
			::= { wingStatsDevWlMcxMeshpointNeighborsEntriesEntry 1 }

		
		-- 1.3.6.1.4.1.1916.2.131.50.1.4.2.25.21.5.1.2
		wingStatsDevWlMcxMeshpointNeighborsEntriesNeighborIfid OBJECT-TYPE
			SYNTAX DisplayString
			MAX-ACCESS read-only
			STATUS current
			DESCRIPTION
				"Neighbor interface MAC address
				
				XPath: /wing-stats/device[mac=key1]/wireless/meshpoint-neighbors[mpid=key2]/entries[entry_idx=key3]/neighbor_ifid"
			::= { wingStatsDevWlMcxMeshpointNeighborsEntriesEntry 2 }

		
		-- 1.3.6.1.4.1.1916.2.131.50.1.4.2.25.21.5.1.3
		wingStatsDevWlMcxMeshpointNeighborsEntriesNeighborMpid OBJECT-TYPE
			SYNTAX DisplayString
			MAX-ACCESS read-only
			STATUS current
			DESCRIPTION
				"Neighbor mesh point MAC address
				
				XPath: /wing-stats/device[mac=key1]/wireless/meshpoint-neighbors[mpid=key2]/entries[entry_idx=key3]/neighbor_mpid"
			::= { wingStatsDevWlMcxMeshpointNeighborsEntriesEntry 3 }

		
		-- 1.3.6.1.4.1.1916.2.131.50.1.4.2.25.21.5.1.4
		wingStatsDevWlMcxMeshpointNeighborsEntriesBoundRoot OBJECT-TYPE
			SYNTAX DisplayString
			MAX-ACCESS read-only
			STATUS current
			DESCRIPTION
				"Neighbor's bound root MAC address
				
				XPath: /wing-stats/device[mac=key1]/wireless/meshpoint-neighbors[mpid=key2]/entries[entry_idx=key3]/bound_root"
			::= { wingStatsDevWlMcxMeshpointNeighborsEntriesEntry 4 }

		
		-- 1.3.6.1.4.1.1916.2.131.50.1.4.2.25.21.5.1.5
		wingStatsDevWlMcxMeshpointNeighborsEntriesRootMetric OBJECT-TYPE
			SYNTAX Unsigned32
			MAX-ACCESS read-only
			STATUS current
			DESCRIPTION
				"Route metric to root
				
				XPath: /wing-stats/device[mac=key1]/wireless/meshpoint-neighbors[mpid=key2]/entries[entry_idx=key3]/root_metric"
			::= { wingStatsDevWlMcxMeshpointNeighborsEntriesEntry 5 }

		
		-- 1.3.6.1.4.1.1916.2.131.50.1.4.2.25.21.5.1.6
		wingStatsDevWlMcxMeshpointNeighborsEntriesRootHops OBJECT-TYPE
			SYNTAX Unsigned32
			MAX-ACCESS read-only
			STATUS current
			DESCRIPTION
				"Hops to root
				
				XPath: /wing-stats/device[mac=key1]/wireless/meshpoint-neighbors[mpid=key2]/entries[entry_idx=key3]/root_hops"
			::= { wingStatsDevWlMcxMeshpointNeighborsEntriesEntry 6 }

		
		-- 1.3.6.1.4.1.1916.2.131.50.1.4.2.25.21.5.1.7
		wingStatsDevWlMcxMeshpointNeighborsEntriesValid OBJECT-TYPE
			SYNTAX TruthValue
			MAX-ACCESS read-only
			STATUS current
			DESCRIPTION
				"Mesh point services are valid
				
				XPath: /wing-stats/device[mac=key1]/wireless/meshpoint-neighbors[mpid=key2]/entries[entry_idx=key3]/valid"
			::= { wingStatsDevWlMcxMeshpointNeighborsEntriesEntry 7 }

		
		-- 1.3.6.1.4.1.1916.2.131.50.1.4.2.25.21.5.1.8
		wingStatsDevWlMcxMeshpointNeighborsEntriesRoot OBJECT-TYPE
			SYNTAX TruthValue
			MAX-ACCESS read-only
			STATUS current
			DESCRIPTION
				"Mesh point is a root
				
				XPath: /wing-stats/device[mac=key1]/wireless/meshpoint-neighbors[mpid=key2]/entries[entry_idx=key3]/root"
			::= { wingStatsDevWlMcxMeshpointNeighborsEntriesEntry 8 }

		
		-- 1.3.6.1.4.1.1916.2.131.50.1.4.2.25.21.5.1.9
		wingStatsDevWlMcxMeshpointNeighborsEntriesProxy OBJECT-TYPE
			SYNTAX TruthValue
			MAX-ACCESS read-only
			STATUS current
			DESCRIPTION
				"Mesh point can proxy for others
				
				XPath: /wing-stats/device[mac=key1]/wireless/meshpoint-neighbors[mpid=key2]/entries[entry_idx=key3]/proxy"
			::= { wingStatsDevWlMcxMeshpointNeighborsEntriesEntry 9 }

		
		-- 1.3.6.1.4.1.1916.2.131.50.1.4.2.25.21.5.1.10
		wingStatsDevWlMcxMeshpointNeighborsEntriesGeoReference OBJECT-TYPE
			SYNTAX TruthValue
			MAX-ACCESS read-only
			STATUS current
			DESCRIPTION
				"Mesh point can provide a geo reference
				
				XPath: /wing-stats/device[mac=key1]/wireless/meshpoint-neighbors[mpid=key2]/entries[entry_idx=key3]/geo_reference"
			::= { wingStatsDevWlMcxMeshpointNeighborsEntriesEntry 10 }

		
		-- 1.3.6.1.4.1.1916.2.131.50.1.4.2.25.21.5.1.11
		wingStatsDevWlMcxMeshpointNeighborsEntriesMobile OBJECT-TYPE
			SYNTAX TruthValue
			MAX-ACCESS read-only
			STATUS current
			DESCRIPTION
				"Mesh point is mobile
				
				XPath: /wing-stats/device[mac=key1]/wireless/meshpoint-neighbors[mpid=key2]/entries[entry_idx=key3]/mobile"
			::= { wingStatsDevWlMcxMeshpointNeighborsEntriesEntry 11 }

		
		-- 1.3.6.1.4.1.1916.2.131.50.1.4.2.25.21.5.1.12
		wingStatsDevWlMcxMeshpointNeighborsEntriesInterfaceId OBJECT-TYPE
			SYNTAX WingIdentifier
			MAX-ACCESS read-only
			STATUS current
			DESCRIPTION
				"Unique ID for each interfacce in the form of AP-MAC:%c%d. E.g., 00-A0-F8-00-00-00:R1
				
				XPath: /wing-stats/device[mac=key1]/wireless/meshpoint-neighbors[mpid=key2]/entries[entry_idx=key3]/interface_id"
			::= { wingStatsDevWlMcxMeshpointNeighborsEntriesEntry 12 }

		
		-- 1.3.6.1.4.1.1916.2.131.50.1.4.2.25.21.5.1.13
		wingStatsDevWlMcxMeshpointNeighborsEntriesAuthState OBJECT-TYPE
			SYNTAX DisplayString
			MAX-ACCESS read-only
			STATUS current
			DESCRIPTION
				"Authorization state
				
				Values:
				Init,
				Enabled,
				Failed,
				In
				Progress,
				N/A
				
				XPath: /wing-stats/device[mac=key1]/wireless/meshpoint-neighbors[mpid=key2]/entries[entry_idx=key3]/auth_state"
			::= { wingStatsDevWlMcxMeshpointNeighborsEntriesEntry 13 }

		
		-- 1.3.6.1.4.1.1916.2.131.50.1.4.2.25.21.5.1.14
		wingStatsDevWlMcxMeshpointNeighborsEntriesRank OBJECT-TYPE
			SYNTAX DisplayString
			MAX-ACCESS read-only
			STATUS current
			DESCRIPTION
				"Ranking
				
				Values:
				8,
				7,
				6,
				5,
				4,
				3,
				2,
				1,
				0,
				-1
				
				XPath: /wing-stats/device[mac=key1]/wireless/meshpoint-neighbors[mpid=key2]/entries[entry_idx=key3]/rank"
			::= { wingStatsDevWlMcxMeshpointNeighborsEntriesEntry 14 }

		
		-- 1.3.6.1.4.1.1916.2.131.50.1.4.2.25.21.5.1.15
		wingStatsDevWlMcxMeshpointNeighborsEntriesResourced OBJECT-TYPE
			SYNTAX TruthValue
			MAX-ACCESS read-only
			STATUS current
			DESCRIPTION
				"Neighbor has an Client resource
				
				XPath: /wing-stats/device[mac=key1]/wireless/meshpoint-neighbors[mpid=key2]/entries[entry_idx=key3]/resourced"
			::= { wingStatsDevWlMcxMeshpointNeighborsEntriesEntry 15 }

		
		-- 1.3.6.1.4.1.1916.2.131.50.1.4.2.25.21.5.1.16
		wingStatsDevWlMcxMeshpointNeighborsEntriesLinkQuality OBJECT-TYPE
			SYNTAX Unsigned32
			MAX-ACCESS read-only
			STATUS current
			DESCRIPTION
				"Link Quality
				
				XPath: /wing-stats/device[mac=key1]/wireless/meshpoint-neighbors[mpid=key2]/entries[entry_idx=key3]/link_quality"
			::= { wingStatsDevWlMcxMeshpointNeighborsEntriesEntry 16 }

		
		-- 1.3.6.1.4.1.1916.2.131.50.1.4.2.25.21.5.1.17
		wingStatsDevWlMcxMeshpointNeighborsEntriesLinkMetric OBJECT-TYPE
			SYNTAX Unsigned32
			MAX-ACCESS read-only
			STATUS current
			DESCRIPTION
				"Route metric to neighbor
				
				XPath: /wing-stats/device[mac=key1]/wireless/meshpoint-neighbors[mpid=key2]/entries[entry_idx=key3]/link_metric"
			::= { wingStatsDevWlMcxMeshpointNeighborsEntriesEntry 17 }

		
		-- 1.3.6.1.4.1.1916.2.131.50.1.4.2.25.21.5.1.18
		wingStatsDevWlMcxMeshpointNeighborsEntriesAge OBJECT-TYPE
			SYNTAX Integer32
			MAX-ACCESS read-only
			STATUS current
			DESCRIPTION
				"Last time used
				
				XPath: /wing-stats/device[mac=key1]/wireless/meshpoint-neighbors[mpid=key2]/entries[entry_idx=key3]/age"
			::= { wingStatsDevWlMcxMeshpointNeighborsEntriesEntry 18 }

		
		-- 1.3.6.1.4.1.1916.2.131.50.1.4.2.25.21.6
		wingStatsDevWlMcxMeshpointPathsTable OBJECT-TYPE
			SYNTAX SEQUENCE OF WingStatsDevWlMcxMeshpointPathsEntry
			MAX-ACCESS not-accessible
			STATUS current
			DESCRIPTION
				"
				
				/wing-stats/device/wireless/meshpoint-paths"
			::= { wingStatsDevWlMcx 6 }

		
		-- 1.3.6.1.4.1.1916.2.131.50.1.4.2.25.21.6.1
		wingStatsDevWlMcxMeshpointPathsEntry OBJECT-TYPE
			SYNTAX WingStatsDevWlMcxMeshpointPathsEntry
			MAX-ACCESS not-accessible
			STATUS current
			DESCRIPTION
				"An entry in the table."
			INDEX { wingStatsDevMac, wingStatsDevWlMcxMeshpointPathsMpid }
			::= { wingStatsDevWlMcxMeshpointPathsTable 1 }

		
		WingStatsDevWlMcxMeshpointPathsEntry ::=
			SEQUENCE { 
				wingStatsDevWlMcxMeshpointPathsMpid
					WingIdentifier,
				wingStatsDevWlMcxMeshpointPathsName
					WingIdentifier,
				wingStatsDevWlMcxMeshpointPathsHostname
					DisplayString,
				wingStatsDevWlMcxMeshpointPathsDeviceMac
					DisplayString,
				wingStatsDevWlMcxMeshpointPathsNumEntries
					Unsigned32
			 }

		-- 1.3.6.1.4.1.1916.2.131.50.1.4.2.25.21.6.1.1
		wingStatsDevWlMcxMeshpointPathsMpid OBJECT-TYPE
			SYNTAX WingIdentifier
			MAX-ACCESS read-only
			STATUS current
			DESCRIPTION
				"Mesh Point MAC address
				
				XPath: /wing-stats/device[mac=key1]/wireless/meshpoint-paths[mpid=key2]/mpid"
			::= { wingStatsDevWlMcxMeshpointPathsEntry 1 }

		
		-- 1.3.6.1.4.1.1916.2.131.50.1.4.2.25.21.6.1.3
		wingStatsDevWlMcxMeshpointPathsName OBJECT-TYPE
			SYNTAX WingIdentifier
			MAX-ACCESS read-only
			STATUS current
			DESCRIPTION
				"
				
				XPath: /wing-stats/device[mac=key1]/wireless/meshpoint-paths[mpid=key2]/name"
			::= { wingStatsDevWlMcxMeshpointPathsEntry 3 }

		
		-- 1.3.6.1.4.1.1916.2.131.50.1.4.2.25.21.6.1.4
		wingStatsDevWlMcxMeshpointPathsHostname OBJECT-TYPE
			SYNTAX DisplayString (SIZE (64))
			MAX-ACCESS read-only
			STATUS current
			DESCRIPTION
				"hostname of the AP device
				
				XPath: /wing-stats/device[mac=key1]/wireless/meshpoint-paths[mpid=key2]/hostname"
			::= { wingStatsDevWlMcxMeshpointPathsEntry 4 }

		
		-- 1.3.6.1.4.1.1916.2.131.50.1.4.2.25.21.6.1.5
		wingStatsDevWlMcxMeshpointPathsDeviceMac OBJECT-TYPE
			SYNTAX DisplayString
			MAX-ACCESS read-only
			STATUS current
			DESCRIPTION
				"Device MAC address
				
				XPath: /wing-stats/device[mac=key1]/wireless/meshpoint-paths[mpid=key2]/device_mac"
			::= { wingStatsDevWlMcxMeshpointPathsEntry 5 }

		
		-- 1.3.6.1.4.1.1916.2.131.50.1.4.2.25.21.6.1.6
		wingStatsDevWlMcxMeshpointPathsNumEntries OBJECT-TYPE
			SYNTAX Unsigned32
			MAX-ACCESS read-only
			STATUS current
			DESCRIPTION
				"Number of entries on for this table
				
				XPath: /wing-stats/device[mac=key1]/wireless/meshpoint-paths[mpid=key2]/num_entries"
			::= { wingStatsDevWlMcxMeshpointPathsEntry 6 }

		
		-- 1.3.6.1.4.1.1916.2.131.50.1.4.2.25.21.7
		wingStatsDevWlMcxMeshpointPathsEntriesTable OBJECT-TYPE
			SYNTAX SEQUENCE OF WingStatsDevWlMcxMeshpointPathsEntriesEntry
			MAX-ACCESS not-accessible
			STATUS current
			DESCRIPTION
				"
				
				/wing-stats/device/wireless/meshpoint-paths/entries"
			::= { wingStatsDevWlMcx 7 }

		
		-- 1.3.6.1.4.1.1916.2.131.50.1.4.2.25.21.7.1
		wingStatsDevWlMcxMeshpointPathsEntriesEntry OBJECT-TYPE
			SYNTAX WingStatsDevWlMcxMeshpointPathsEntriesEntry
			MAX-ACCESS not-accessible
			STATUS current
			DESCRIPTION
				"An entry in the table."
			INDEX { wingStatsDevMac, wingStatsDevWlMcxMeshpointPathsMpid, wingStatsDevWlMcxMeshpointPathsEntriesIndex }
			::= { wingStatsDevWlMcxMeshpointPathsEntriesTable 1 }

		
		WingStatsDevWlMcxMeshpointPathsEntriesEntry ::=
			SEQUENCE { 
				wingStatsDevWlMcxMeshpointPathsEntriesIndex
					Unsigned32,
				wingStatsDevWlMcxMeshpointPathsEntriesDestMpid
					DisplayString,
				wingStatsDevWlMcxMeshpointPathsEntriesNextHopIfid
					DisplayString,
				wingStatsDevWlMcxMeshpointPathsEntriesPathMetric
					Unsigned32,
				wingStatsDevWlMcxMeshpointPathsEntriesHops
					Unsigned32,
				wingStatsDevWlMcxMeshpointPathsEntriesPathState
					DisplayString,
				wingStatsDevWlMcxMeshpointPathsEntriesBindState
					DisplayString,
				wingStatsDevWlMcxMeshpointPathsEntriesValid
					TruthValue,
				wingStatsDevWlMcxMeshpointPathsEntriesRoot
					TruthValue,
				wingStatsDevWlMcxMeshpointPathsEntriesProxy
					TruthValue,
				wingStatsDevWlMcxMeshpointPathsEntriesGeoReference
					TruthValue,
				wingStatsDevWlMcxMeshpointPathsEntriesMobile
					TruthValue,
				wingStatsDevWlMcxMeshpointPathsEntriesDestinationSequence
					Unsigned32,
				wingStatsDevWlMcxMeshpointPathsEntriesPathTimeout
					Integer32,
				wingStatsDevWlMcxMeshpointPathsEntriesNewRouteTimeout
					Integer32,
				wingStatsDevWlMcxMeshpointPathsEntriesDestMintId
					DisplayString
			 }

		-- 1.3.6.1.4.1.1916.2.131.50.1.4.2.25.21.7.1.1
		wingStatsDevWlMcxMeshpointPathsEntriesIndex OBJECT-TYPE
			SYNTAX Unsigned32 (1..4294967295)
			MAX-ACCESS read-only
			STATUS current
			DESCRIPTION
				"Entries Index
				
				XPath: /wing-stats/device[mac=key1]/wireless/meshpoint-paths[mpid=key2]/entries[entry_idx=key3]/entry_idx"
			::= { wingStatsDevWlMcxMeshpointPathsEntriesEntry 1 }

		
		-- 1.3.6.1.4.1.1916.2.131.50.1.4.2.25.21.7.1.2
		wingStatsDevWlMcxMeshpointPathsEntriesDestMpid OBJECT-TYPE
			SYNTAX DisplayString
			MAX-ACCESS read-only
			STATUS current
			DESCRIPTION
				"Destination mesh point MAC address
				
				XPath: /wing-stats/device[mac=key1]/wireless/meshpoint-paths[mpid=key2]/entries[entry_idx=key3]/dest_mpid"
			::= { wingStatsDevWlMcxMeshpointPathsEntriesEntry 2 }

		
		-- 1.3.6.1.4.1.1916.2.131.50.1.4.2.25.21.7.1.3
		wingStatsDevWlMcxMeshpointPathsEntriesNextHopIfid OBJECT-TYPE
			SYNTAX DisplayString
			MAX-ACCESS read-only
			STATUS current
			DESCRIPTION
				"Next hop interface MAC address
				
				XPath: /wing-stats/device[mac=key1]/wireless/meshpoint-paths[mpid=key2]/entries[entry_idx=key3]/next_hop_ifid"
			::= { wingStatsDevWlMcxMeshpointPathsEntriesEntry 3 }

		
		-- 1.3.6.1.4.1.1916.2.131.50.1.4.2.25.21.7.1.4
		wingStatsDevWlMcxMeshpointPathsEntriesPathMetric OBJECT-TYPE
			SYNTAX Unsigned32
			MAX-ACCESS read-only
			STATUS current
			DESCRIPTION
				"Route metric to destination
				
				XPath: /wing-stats/device[mac=key1]/wireless/meshpoint-paths[mpid=key2]/entries[entry_idx=key3]/path_metric"
			::= { wingStatsDevWlMcxMeshpointPathsEntriesEntry 4 }

		
		-- 1.3.6.1.4.1.1916.2.131.50.1.4.2.25.21.7.1.5
		wingStatsDevWlMcxMeshpointPathsEntriesHops OBJECT-TYPE
			SYNTAX Unsigned32
			MAX-ACCESS read-only
			STATUS current
			DESCRIPTION
				"Hops to destination
				
				XPath: /wing-stats/device[mac=key1]/wireless/meshpoint-paths[mpid=key2]/entries[entry_idx=key3]/hops"
			::= { wingStatsDevWlMcxMeshpointPathsEntriesEntry 5 }

		
		-- 1.3.6.1.4.1.1916.2.131.50.1.4.2.25.21.7.1.6
		wingStatsDevWlMcxMeshpointPathsEntriesPathState OBJECT-TYPE
			SYNTAX DisplayString
			MAX-ACCESS read-only
			STATUS current
			DESCRIPTION
				"Path state
				
				Values:
				Valid,
				Req-Timeout,
				Expired,
				In
				Progress,
				Fwd-To-Root,
				Invalid
				
				XPath: /wing-stats/device[mac=key1]/wireless/meshpoint-paths[mpid=key2]/entries[entry_idx=key3]/path_state"
			::= { wingStatsDevWlMcxMeshpointPathsEntriesEntry 6 }

		
		-- 1.3.6.1.4.1.1916.2.131.50.1.4.2.25.21.7.1.7
		wingStatsDevWlMcxMeshpointPathsEntriesBindState OBJECT-TYPE
			SYNTAX DisplayString
			MAX-ACCESS read-only
			STATUS current
			DESCRIPTION
				"Bind state
				
				Values:
				Bound,
				Unbound,
				Proxy-Upd,
				Disfavored,
				Removed,
				Invalid
				
				XPath: /wing-stats/device[mac=key1]/wireless/meshpoint-paths[mpid=key2]/entries[entry_idx=key3]/bind_state"
			::= { wingStatsDevWlMcxMeshpointPathsEntriesEntry 7 }

		
		-- 1.3.6.1.4.1.1916.2.131.50.1.4.2.25.21.7.1.8
		wingStatsDevWlMcxMeshpointPathsEntriesValid OBJECT-TYPE
			SYNTAX TruthValue
			MAX-ACCESS read-only
			STATUS current
			DESCRIPTION
				"Mesh point services are valid
				
				XPath: /wing-stats/device[mac=key1]/wireless/meshpoint-paths[mpid=key2]/entries[entry_idx=key3]/valid"
			::= { wingStatsDevWlMcxMeshpointPathsEntriesEntry 8 }

		
		-- 1.3.6.1.4.1.1916.2.131.50.1.4.2.25.21.7.1.9
		wingStatsDevWlMcxMeshpointPathsEntriesRoot OBJECT-TYPE
			SYNTAX TruthValue
			MAX-ACCESS read-only
			STATUS current
			DESCRIPTION
				"Mesh point is a root
				
				XPath: /wing-stats/device[mac=key1]/wireless/meshpoint-paths[mpid=key2]/entries[entry_idx=key3]/root"
			::= { wingStatsDevWlMcxMeshpointPathsEntriesEntry 9 }

		
		-- 1.3.6.1.4.1.1916.2.131.50.1.4.2.25.21.7.1.10
		wingStatsDevWlMcxMeshpointPathsEntriesProxy OBJECT-TYPE
			SYNTAX TruthValue
			MAX-ACCESS read-only
			STATUS current
			DESCRIPTION
				"Mesh point can proxy for others
				
				XPath: /wing-stats/device[mac=key1]/wireless/meshpoint-paths[mpid=key2]/entries[entry_idx=key3]/proxy"
			::= { wingStatsDevWlMcxMeshpointPathsEntriesEntry 10 }

		
		-- 1.3.6.1.4.1.1916.2.131.50.1.4.2.25.21.7.1.11
		wingStatsDevWlMcxMeshpointPathsEntriesGeoReference OBJECT-TYPE
			SYNTAX TruthValue
			MAX-ACCESS read-only
			STATUS current
			DESCRIPTION
				"Mesh point can provide a geo reference
				
				XPath: /wing-stats/device[mac=key1]/wireless/meshpoint-paths[mpid=key2]/entries[entry_idx=key3]/geo_reference"
			::= { wingStatsDevWlMcxMeshpointPathsEntriesEntry 11 }

		
		-- 1.3.6.1.4.1.1916.2.131.50.1.4.2.25.21.7.1.12
		wingStatsDevWlMcxMeshpointPathsEntriesMobile OBJECT-TYPE
			SYNTAX TruthValue
			MAX-ACCESS read-only
			STATUS current
			DESCRIPTION
				"Mesh point is mobile
				
				XPath: /wing-stats/device[mac=key1]/wireless/meshpoint-paths[mpid=key2]/entries[entry_idx=key3]/mobile"
			::= { wingStatsDevWlMcxMeshpointPathsEntriesEntry 12 }

		
		-- 1.3.6.1.4.1.1916.2.131.50.1.4.2.25.21.7.1.13
		wingStatsDevWlMcxMeshpointPathsEntriesDestinationSequence OBJECT-TYPE
			SYNTAX Unsigned32
			MAX-ACCESS read-only
			STATUS current
			DESCRIPTION
				"Destination sequence number
				
				XPath: /wing-stats/device[mac=key1]/wireless/meshpoint-paths[mpid=key2]/entries[entry_idx=key3]/destination_sequence"
			::= { wingStatsDevWlMcxMeshpointPathsEntriesEntry 13 }

		
		-- 1.3.6.1.4.1.1916.2.131.50.1.4.2.25.21.7.1.14
		wingStatsDevWlMcxMeshpointPathsEntriesPathTimeout OBJECT-TYPE
			SYNTAX Integer32
			MAX-ACCESS read-only
			STATUS current
			DESCRIPTION
				"Path timeout
				
				XPath: /wing-stats/device[mac=key1]/wireless/meshpoint-paths[mpid=key2]/entries[entry_idx=key3]/path_timeout"
			::= { wingStatsDevWlMcxMeshpointPathsEntriesEntry 14 }

		
		-- 1.3.6.1.4.1.1916.2.131.50.1.4.2.25.21.7.1.15
		wingStatsDevWlMcxMeshpointPathsEntriesNewRouteTimeout OBJECT-TYPE
			SYNTAX Integer32
			MAX-ACCESS read-only
			STATUS current
			DESCRIPTION
				"New route timeout
				
				XPath: /wing-stats/device[mac=key1]/wireless/meshpoint-paths[mpid=key2]/entries[entry_idx=key3]/new_route_timeout"
			::= { wingStatsDevWlMcxMeshpointPathsEntriesEntry 15 }

		
		-- 1.3.6.1.4.1.1916.2.131.50.1.4.2.25.21.7.1.16
		wingStatsDevWlMcxMeshpointPathsEntriesDestMintId OBJECT-TYPE
			SYNTAX DisplayString
			MAX-ACCESS read-only
			STATUS current
			DESCRIPTION
				"Destination MiNT address
				
				XPath: /wing-stats/device[mac=key1]/wireless/meshpoint-paths[mpid=key2]/entries[entry_idx=key3]/dest_mint_id"
			::= { wingStatsDevWlMcxMeshpointPathsEntriesEntry 16 }

		
		-- 1.3.6.1.4.1.1916.2.131.50.1.4.2.25.21.8
		wingStatsDevWlMcxMeshpointRootsTable OBJECT-TYPE
			SYNTAX SEQUENCE OF WingStatsDevWlMcxMeshpointRootsEntry
			MAX-ACCESS not-accessible
			STATUS current
			DESCRIPTION
				"
				
				/wing-stats/device/wireless/meshpoint-roots"
			::= { wingStatsDevWlMcx 8 }

		
		-- 1.3.6.1.4.1.1916.2.131.50.1.4.2.25.21.8.1
		wingStatsDevWlMcxMeshpointRootsEntry OBJECT-TYPE
			SYNTAX WingStatsDevWlMcxMeshpointRootsEntry
			MAX-ACCESS not-accessible
			STATUS current
			DESCRIPTION
				"An entry in the table."
			INDEX { wingStatsDevMac, wingStatsDevWlMcxMeshpointRootsMpid }
			::= { wingStatsDevWlMcxMeshpointRootsTable 1 }

		
		WingStatsDevWlMcxMeshpointRootsEntry ::=
			SEQUENCE { 
				wingStatsDevWlMcxMeshpointRootsMpid
					WingIdentifier,
				wingStatsDevWlMcxMeshpointRootsName
					WingIdentifier,
				wingStatsDevWlMcxMeshpointRootsHostname
					DisplayString,
				wingStatsDevWlMcxMeshpointRootsDeviceMac
					DisplayString,
				wingStatsDevWlMcxMeshpointRootsNumEntries
					Unsigned32
			 }

		-- 1.3.6.1.4.1.1916.2.131.50.1.4.2.25.21.8.1.1
		wingStatsDevWlMcxMeshpointRootsMpid OBJECT-TYPE
			SYNTAX WingIdentifier
			MAX-ACCESS read-only
			STATUS current
			DESCRIPTION
				"Mesh Point MAC address
				
				XPath: /wing-stats/device[mac=key1]/wireless/meshpoint-roots[mpid=key2]/mpid"
			::= { wingStatsDevWlMcxMeshpointRootsEntry 1 }

		
		-- 1.3.6.1.4.1.1916.2.131.50.1.4.2.25.21.8.1.3
		wingStatsDevWlMcxMeshpointRootsName OBJECT-TYPE
			SYNTAX WingIdentifier
			MAX-ACCESS read-only
			STATUS current
			DESCRIPTION
				"
				
				XPath: /wing-stats/device[mac=key1]/wireless/meshpoint-roots[mpid=key2]/name"
			::= { wingStatsDevWlMcxMeshpointRootsEntry 3 }

		
		-- 1.3.6.1.4.1.1916.2.131.50.1.4.2.25.21.8.1.4
		wingStatsDevWlMcxMeshpointRootsHostname OBJECT-TYPE
			SYNTAX DisplayString (SIZE (64))
			MAX-ACCESS read-only
			STATUS current
			DESCRIPTION
				"hostname of the AP device
				
				XPath: /wing-stats/device[mac=key1]/wireless/meshpoint-roots[mpid=key2]/hostname"
			::= { wingStatsDevWlMcxMeshpointRootsEntry 4 }

		
		-- 1.3.6.1.4.1.1916.2.131.50.1.4.2.25.21.8.1.5
		wingStatsDevWlMcxMeshpointRootsDeviceMac OBJECT-TYPE
			SYNTAX DisplayString
			MAX-ACCESS read-only
			STATUS current
			DESCRIPTION
				"Device MAC address
				
				XPath: /wing-stats/device[mac=key1]/wireless/meshpoint-roots[mpid=key2]/device_mac"
			::= { wingStatsDevWlMcxMeshpointRootsEntry 5 }

		
		-- 1.3.6.1.4.1.1916.2.131.50.1.4.2.25.21.8.1.6
		wingStatsDevWlMcxMeshpointRootsNumEntries OBJECT-TYPE
			SYNTAX Unsigned32
			MAX-ACCESS read-only
			STATUS current
			DESCRIPTION
				"Number of entries on for this table
				
				XPath: /wing-stats/device[mac=key1]/wireless/meshpoint-roots[mpid=key2]/num_entries"
			::= { wingStatsDevWlMcxMeshpointRootsEntry 6 }

		
		-- 1.3.6.1.4.1.1916.2.131.50.1.4.2.25.21.9
		wingStatsDevWlMcxMeshpointRootsEntriesTable OBJECT-TYPE
			SYNTAX SEQUENCE OF WingStatsDevWlMcxMeshpointRootsEntriesEntry
			MAX-ACCESS not-accessible
			STATUS current
			DESCRIPTION
				"
				
				/wing-stats/device/wireless/meshpoint-roots/entries"
			::= { wingStatsDevWlMcx 9 }

		
		-- 1.3.6.1.4.1.1916.2.131.50.1.4.2.25.21.9.1
		wingStatsDevWlMcxMeshpointRootsEntriesEntry OBJECT-TYPE
			SYNTAX WingStatsDevWlMcxMeshpointRootsEntriesEntry
			MAX-ACCESS not-accessible
			STATUS current
			DESCRIPTION
				"An entry in the table."
			INDEX { wingStatsDevMac, wingStatsDevWlMcxMeshpointRootsMpid, wingStatsDevWlMcxMeshpointRootsEntriesIndex }
			::= { wingStatsDevWlMcxMeshpointRootsEntriesTable 1 }

		
		WingStatsDevWlMcxMeshpointRootsEntriesEntry ::=
			SEQUENCE { 
				wingStatsDevWlMcxMeshpointRootsEntriesIndex
					Unsigned32,
				wingStatsDevWlMcxMeshpointRootsEntriesRootMpid
					DisplayString,
				wingStatsDevWlMcxMeshpointRootsEntriesNextHopIfid
					DisplayString,
				wingStatsDevWlMcxMeshpointRootsEntriesInterfaceId
					WingIdentifier,
				wingStatsDevWlMcxMeshpointRootsEntriesRecommended
					TruthValue,
				wingStatsDevWlMcxMeshpointRootsEntriesBindFailed
					TruthValue,
				wingStatsDevWlMcxMeshpointRootsEntriesPathFailed
					TruthValue,
				wingStatsDevWlMcxMeshpointRootsEntriesPathMetric
					Unsigned32,
				wingStatsDevWlMcxMeshpointRootsEntriesNeighborBias
					Integer32,
				wingStatsDevWlMcxMeshpointRootsEntriesRootBias
					Integer32
			 }

		-- 1.3.6.1.4.1.1916.2.131.50.1.4.2.25.21.9.1.1
		wingStatsDevWlMcxMeshpointRootsEntriesIndex OBJECT-TYPE
			SYNTAX Unsigned32 (1..4294967295)
			MAX-ACCESS read-write
			STATUS current
			DESCRIPTION
				"Entries Index
				
				XPath: /wing-stats/device[mac=key1]/wireless/meshpoint-roots[mpid=key2]/entries[entry_idx=key3]/entry_idx"
			::= { wingStatsDevWlMcxMeshpointRootsEntriesEntry 1 }

		
		-- 1.3.6.1.4.1.1916.2.131.50.1.4.2.25.21.9.1.2
		wingStatsDevWlMcxMeshpointRootsEntriesRootMpid OBJECT-TYPE
			SYNTAX DisplayString
			MAX-ACCESS read-only
			STATUS current
			DESCRIPTION
				"Root mesh point MAC address
				
				XPath: /wing-stats/device[mac=key1]/wireless/meshpoint-roots[mpid=key2]/entries[entry_idx=key3]/root_mpid"
			::= { wingStatsDevWlMcxMeshpointRootsEntriesEntry 2 }

		
		-- 1.3.6.1.4.1.1916.2.131.50.1.4.2.25.21.9.1.3
		wingStatsDevWlMcxMeshpointRootsEntriesNextHopIfid OBJECT-TYPE
			SYNTAX DisplayString
			MAX-ACCESS read-only
			STATUS current
			DESCRIPTION
				"Next hop interface MAC address
				
				XPath: /wing-stats/device[mac=key1]/wireless/meshpoint-roots[mpid=key2]/entries[entry_idx=key3]/next_hop_ifid"
			::= { wingStatsDevWlMcxMeshpointRootsEntriesEntry 3 }

		
		-- 1.3.6.1.4.1.1916.2.131.50.1.4.2.25.21.9.1.4
		wingStatsDevWlMcxMeshpointRootsEntriesInterfaceId OBJECT-TYPE
			SYNTAX WingIdentifier
			MAX-ACCESS read-only
			STATUS current
			DESCRIPTION
				"Unique ID for each interfacce in the form of AP-MAC:%c%d. E.g., 00-A0-F8-00-00-00:R1
				
				XPath: /wing-stats/device[mac=key1]/wireless/meshpoint-roots[mpid=key2]/entries[entry_idx=key3]/interface_id"
			::= { wingStatsDevWlMcxMeshpointRootsEntriesEntry 4 }

		
		-- 1.3.6.1.4.1.1916.2.131.50.1.4.2.25.21.9.1.5
		wingStatsDevWlMcxMeshpointRootsEntriesRecommended OBJECT-TYPE
			SYNTAX TruthValue
			MAX-ACCESS read-only
			STATUS current
			DESCRIPTION
				"Recommended root
				
				XPath: /wing-stats/device[mac=key1]/wireless/meshpoint-roots[mpid=key2]/entries[entry_idx=key3]/recommended"
			::= { wingStatsDevWlMcxMeshpointRootsEntriesEntry 5 }

		
		-- 1.3.6.1.4.1.1916.2.131.50.1.4.2.25.21.9.1.6
		wingStatsDevWlMcxMeshpointRootsEntriesBindFailed OBJECT-TYPE
			SYNTAX TruthValue
			MAX-ACCESS read-only
			STATUS current
			DESCRIPTION
				"Bind failure
				
				XPath: /wing-stats/device[mac=key1]/wireless/meshpoint-roots[mpid=key2]/entries[entry_idx=key3]/bind_failed"
			::= { wingStatsDevWlMcxMeshpointRootsEntriesEntry 6 }

		
		-- 1.3.6.1.4.1.1916.2.131.50.1.4.2.25.21.9.1.7
		wingStatsDevWlMcxMeshpointRootsEntriesPathFailed OBJECT-TYPE
			SYNTAX TruthValue
			MAX-ACCESS read-only
			STATUS current
			DESCRIPTION
				"Path failure
				
				XPath: /wing-stats/device[mac=key1]/wireless/meshpoint-roots[mpid=key2]/entries[entry_idx=key3]/path_failed"
			::= { wingStatsDevWlMcxMeshpointRootsEntriesEntry 7 }

		
		-- 1.3.6.1.4.1.1916.2.131.50.1.4.2.25.21.9.1.8
		wingStatsDevWlMcxMeshpointRootsEntriesPathMetric OBJECT-TYPE
			SYNTAX Unsigned32
			MAX-ACCESS read-only
			STATUS current
			DESCRIPTION
				"Route metric to destination
				
				XPath: /wing-stats/device[mac=key1]/wireless/meshpoint-roots[mpid=key2]/entries[entry_idx=key3]/path_metric"
			::= { wingStatsDevWlMcxMeshpointRootsEntriesEntry 8 }

		
		-- 1.3.6.1.4.1.1916.2.131.50.1.4.2.25.21.9.1.9
		wingStatsDevWlMcxMeshpointRootsEntriesNeighborBias OBJECT-TYPE
			SYNTAX Integer32
			MAX-ACCESS read-only
			STATUS current
			DESCRIPTION
				"Neighbor bias
				
				XPath: /wing-stats/device[mac=key1]/wireless/meshpoint-roots[mpid=key2]/entries/neighbor_bias"
			::= { wingStatsDevWlMcxMeshpointRootsEntriesEntry 9 }

		
		-- 1.3.6.1.4.1.1916.2.131.50.1.4.2.25.21.9.1.10
		wingStatsDevWlMcxMeshpointRootsEntriesRootBias OBJECT-TYPE
			SYNTAX Integer32
			MAX-ACCESS read-only
			STATUS current
			DESCRIPTION
				"Root bias
				
				XPath: /wing-stats/device[mac=key1]/wireless/meshpoint-roots[mpid=key2]/entries/root_bias"
			::= { wingStatsDevWlMcxMeshpointRootsEntriesEntry 10 }

		
		-- 1.3.6.1.4.1.1916.2.131.50.1.4.2.25.21.10
		wingStatsDevWlMcxMeshpointProxiesTable OBJECT-TYPE
			SYNTAX SEQUENCE OF WingStatsDevWlMcxMeshpointProxiesEntry
			MAX-ACCESS not-accessible
			STATUS current
			DESCRIPTION
				"
				
				/wing-stats/device/wireless/meshpoint-proxies"
			::= { wingStatsDevWlMcx 10 }

		
		-- 1.3.6.1.4.1.1916.2.131.50.1.4.2.25.21.10.1
		wingStatsDevWlMcxMeshpointProxiesEntry OBJECT-TYPE
			SYNTAX WingStatsDevWlMcxMeshpointProxiesEntry
			MAX-ACCESS not-accessible
			STATUS current
			DESCRIPTION
				"An entry in the table."
			INDEX { wingStatsDevMac, wingStatsDevWlMcxMeshpointProxiesMpid }
			::= { wingStatsDevWlMcxMeshpointProxiesTable 1 }

		
		WingStatsDevWlMcxMeshpointProxiesEntry ::=
			SEQUENCE { 
				wingStatsDevWlMcxMeshpointProxiesMpid
					WingIdentifier,
				wingStatsDevWlMcxMeshpointProxiesName
					WingIdentifier,
				wingStatsDevWlMcxMeshpointProxiesHostname
					DisplayString,
				wingStatsDevWlMcxMeshpointProxiesDeviceMac
					DisplayString,
				wingStatsDevWlMcxMeshpointProxiesNumEntries
					Unsigned32
			 }

		-- 1.3.6.1.4.1.1916.2.131.50.1.4.2.25.21.10.1.1
		wingStatsDevWlMcxMeshpointProxiesMpid OBJECT-TYPE
			SYNTAX WingIdentifier
			MAX-ACCESS read-only
			STATUS current
			DESCRIPTION
				"Mesh Point MAC address
				
				XPath: /wing-stats/device[mac=key1]/wireless/meshpoint-proxies[mpid=key2]/mpid"
			::= { wingStatsDevWlMcxMeshpointProxiesEntry 1 }

		
		-- 1.3.6.1.4.1.1916.2.131.50.1.4.2.25.21.10.1.3
		wingStatsDevWlMcxMeshpointProxiesName OBJECT-TYPE
			SYNTAX WingIdentifier
			MAX-ACCESS read-only
			STATUS current
			DESCRIPTION
				"
				
				XPath: /wing-stats/device[mac=key1]/wireless/meshpoint-proxies[mpid=key2]/name"
			::= { wingStatsDevWlMcxMeshpointProxiesEntry 3 }

		
		-- 1.3.6.1.4.1.1916.2.131.50.1.4.2.25.21.10.1.4
		wingStatsDevWlMcxMeshpointProxiesHostname OBJECT-TYPE
			SYNTAX DisplayString (SIZE (64))
			MAX-ACCESS read-only
			STATUS current
			DESCRIPTION
				"hostname of the AP device
				
				XPath: /wing-stats/device[mac=key1]/wireless/meshpoint-proxies[mpid=key2]/hostname"
			::= { wingStatsDevWlMcxMeshpointProxiesEntry 4 }

		
		-- 1.3.6.1.4.1.1916.2.131.50.1.4.2.25.21.10.1.5
		wingStatsDevWlMcxMeshpointProxiesDeviceMac OBJECT-TYPE
			SYNTAX DisplayString
			MAX-ACCESS read-only
			STATUS current
			DESCRIPTION
				"Device MAC address
				
				XPath: /wing-stats/device[mac=key1]/wireless/meshpoint-proxies[mpid=key2]/device_mac"
			::= { wingStatsDevWlMcxMeshpointProxiesEntry 5 }

		
		-- 1.3.6.1.4.1.1916.2.131.50.1.4.2.25.21.10.1.6
		wingStatsDevWlMcxMeshpointProxiesNumEntries OBJECT-TYPE
			SYNTAX Unsigned32
			MAX-ACCESS read-only
			STATUS current
			DESCRIPTION
				"Number of entries on for this table
				
				XPath: /wing-stats/device[mac=key1]/wireless/meshpoint-proxies[mpid=key2]/num_entries"
			::= { wingStatsDevWlMcxMeshpointProxiesEntry 6 }

		
		-- 1.3.6.1.4.1.1916.2.131.50.1.4.2.25.21.11
		wingStatsDevWlMcxMeshpointProxiesEntriesTable OBJECT-TYPE
			SYNTAX SEQUENCE OF WingStatsDevWlMcxMeshpointProxiesEntriesEntry
			MAX-ACCESS not-accessible
			STATUS current
			DESCRIPTION
				"
				
				/wing-stats/device/wireless/meshpoint-proxies/entries"
			::= { wingStatsDevWlMcx 11 }

		
		-- 1.3.6.1.4.1.1916.2.131.50.1.4.2.25.21.11.1
		wingStatsDevWlMcxMeshpointProxiesEntriesEntry OBJECT-TYPE
			SYNTAX WingStatsDevWlMcxMeshpointProxiesEntriesEntry
			MAX-ACCESS not-accessible
			STATUS current
			DESCRIPTION
				"An entry in the table."
			INDEX { wingStatsDevMac, wingStatsDevWlMcxMeshpointProxiesMpid, wingStatsDevWlMcxMeshpointProxiesEntriesIndex }
			::= { wingStatsDevWlMcxMeshpointProxiesEntriesTable 1 }

		
		WingStatsDevWlMcxMeshpointProxiesEntriesEntry ::=
			SEQUENCE { 
				wingStatsDevWlMcxMeshpointProxiesEntriesIndex
					Unsigned32,
				wingStatsDevWlMcxMeshpointProxiesEntriesProxyAddr
					DisplayString,
				wingStatsDevWlMcxMeshpointProxiesEntriesProxyOwner
					DisplayString,
				wingStatsDevWlMcxMeshpointProxiesEntriesPersistence
					DisplayString,
				wingStatsDevWlMcxMeshpointProxiesEntriesAge
					Integer32,
				wingStatsDevWlMcxMeshpointProxiesEntriesVlan
					Unsigned32
			 }

		-- 1.3.6.1.4.1.1916.2.131.50.1.4.2.25.21.11.1.1
		wingStatsDevWlMcxMeshpointProxiesEntriesIndex OBJECT-TYPE
			SYNTAX Unsigned32 (1..4294967295)
			MAX-ACCESS read-only
			STATUS current
			DESCRIPTION
				"Entries Index
				
				XPath: /wing-stats/device[mac=key1]/wireless/meshpoint-proxies[mpid=key2]/entries[entry_idx=key3]/entry_idx"
			::= { wingStatsDevWlMcxMeshpointProxiesEntriesEntry 1 }

		
		-- 1.3.6.1.4.1.1916.2.131.50.1.4.2.25.21.11.1.2
		wingStatsDevWlMcxMeshpointProxiesEntriesProxyAddr OBJECT-TYPE
			SYNTAX DisplayString
			MAX-ACCESS read-only
			STATUS current
			DESCRIPTION
				"Proxy MAC address
				
				XPath: /wing-stats/device[mac=key1]/wireless/meshpoint-proxies[mpid=key2]/entries[entry_idx=key3]/proxy_addr"
			::= { wingStatsDevWlMcxMeshpointProxiesEntriesEntry 2 }

		
		-- 1.3.6.1.4.1.1916.2.131.50.1.4.2.25.21.11.1.3
		wingStatsDevWlMcxMeshpointProxiesEntriesProxyOwner OBJECT-TYPE
			SYNTAX DisplayString
			MAX-ACCESS read-only
			STATUS current
			DESCRIPTION
				"Proxy owner's MAC address
				
				XPath: /wing-stats/device[mac=key1]/wireless/meshpoint-proxies[mpid=key2]/entries[entry_idx=key3]/proxy_owner"
			::= { wingStatsDevWlMcxMeshpointProxiesEntriesEntry 3 }

		
		-- 1.3.6.1.4.1.1916.2.131.50.1.4.2.25.21.11.1.4
		wingStatsDevWlMcxMeshpointProxiesEntriesPersistence OBJECT-TYPE
			SYNTAX DisplayString
			MAX-ACCESS read-only
			STATUS current
			DESCRIPTION
				"Persistence state
				
				Values:
				Timed,
				Untimed,
				Permanent,
				Invalid
				
				XPath: /wing-stats/device[mac=key1]/wireless/meshpoint-proxies[mpid=key2]/entries[entry_idx=key3]/persistence"
			::= { wingStatsDevWlMcxMeshpointProxiesEntriesEntry 4 }

		
		-- 1.3.6.1.4.1.1916.2.131.50.1.4.2.25.21.11.1.5
		wingStatsDevWlMcxMeshpointProxiesEntriesAge OBJECT-TYPE
			SYNTAX Integer32
			MAX-ACCESS read-only
			STATUS current
			DESCRIPTION
				"Last time used
				
				XPath: /wing-stats/device[mac=key1]/wireless/meshpoint-proxies[mpid=key2]/entries[entry_idx=key3]/age"
			::= { wingStatsDevWlMcxMeshpointProxiesEntriesEntry 5 }

		
		-- 1.3.6.1.4.1.1916.2.131.50.1.4.2.25.21.11.1.6
		wingStatsDevWlMcxMeshpointProxiesEntriesVlan OBJECT-TYPE
			SYNTAX Unsigned32
			MAX-ACCESS read-only
			STATUS current
			DESCRIPTION
				"The VLAN assigned to the proxy
				
				XPath: /wing-stats/device[mac=key1]/wireless/meshpoint-proxies[mpid=key2]/entries[entry_idx=key3]/vlan"
			::= { wingStatsDevWlMcxMeshpointProxiesEntriesEntry 6 }
		
		-- 1.3.6.1.4.1.1916.2.131.50.1.4.2.25.21.12
		wingStatsDevWlMcxMeshpointLsaTable OBJECT-TYPE
			SYNTAX SEQUENCE OF WingStatsDevWlMcxMeshpointLsaEntry
			MAX-ACCESS not-accessible
			STATUS current
			DESCRIPTION
				"
				
				/wing-stats/device/wireless/meshpoint-lsa"
			::= { wingStatsDevWlMcx 12 }

		
		-- 1.3.6.1.4.1.1916.2.131.50.1.4.2.25.21.12.1
		wingStatsDevWlMcxMeshpointLsaEntry OBJECT-TYPE
			SYNTAX WingStatsDevWlMcxMeshpointLsaEntry
			MAX-ACCESS not-accessible
			STATUS current
			DESCRIPTION
				"An entry in the table."
			INDEX { wingStatsDevMac, wingStatsDevWlMcxMeshpointLsaMpid }
			::= { wingStatsDevWlMcxMeshpointLsaTable 1 }

		
		WingStatsDevWlMcxMeshpointLsaEntry ::=
			SEQUENCE { 
				wingStatsDevWlMcxMeshpointLsaMpid
					WingIdentifier,
				wingStatsDevWlMcxMeshpointLsaName
					WingIdentifier,
				wingStatsDevWlMcxMeshpointLsaHostname
					DisplayString,
				wingStatsDevWlMcxMeshpointLsaDeviceMac
					DisplayString,
				wingStatsDevWlMcxMeshpointLsaNumEntries
					Unsigned32,
				wingStatsDevWlMcxMeshpointLsaMeshid
					DisplayString,
				wingStatsDevWlMcxMeshpointLsaR0Valid
					TruthValue,
				wingStatsDevWlMcxMeshpointLsaR0mdid
					OCTET STRING,
				wingStatsDevWlMcxMeshpointLsaR0khid
					OCTET STRING
			 }

		-- 1.3.6.1.4.1.1916.2.131.50.1.4.2.25.21.12.1.1
		wingStatsDevWlMcxMeshpointLsaMpid OBJECT-TYPE
			SYNTAX WingIdentifier
			MAX-ACCESS read-only
			STATUS current
			DESCRIPTION
				"Mesh Point MAC address
				
				XPath: /wing-stats/device[mac=key1]/wireless/meshpoint-lsa[mpid=key2]/mpid"
			::= { wingStatsDevWlMcxMeshpointLsaEntry 1 }

		
		-- 1.3.6.1.4.1.1916.2.131.50.1.4.2.25.21.12.1.3
		wingStatsDevWlMcxMeshpointLsaName OBJECT-TYPE
			SYNTAX WingIdentifier
			MAX-ACCESS read-only
			STATUS current
			DESCRIPTION
				"
				
				XPath: /wing-stats/device[mac=key1]/wireless/meshpoint-lsa[mpid=key2]/name"
			::= { wingStatsDevWlMcxMeshpointLsaEntry 3 }

		
		-- 1.3.6.1.4.1.1916.2.131.50.1.4.2.25.21.12.1.4
		wingStatsDevWlMcxMeshpointLsaHostname OBJECT-TYPE
			SYNTAX DisplayString (SIZE (64))
			MAX-ACCESS read-only
			STATUS current
			DESCRIPTION
				"hostname of the AP device
				
				XPath: /wing-stats/device[mac=key1]/wireless/meshpoint-lsa[mpid=key2]/hostname"
			::= { wingStatsDevWlMcxMeshpointLsaEntry 4 }

		
		-- 1.3.6.1.4.1.1916.2.131.50.1.4.2.25.21.12.1.5
		wingStatsDevWlMcxMeshpointLsaDeviceMac OBJECT-TYPE
			SYNTAX DisplayString
			MAX-ACCESS read-only
			STATUS current
			DESCRIPTION
				"Device MAC address
				
				XPath: /wing-stats/device[mac=key1]/wireless/meshpoint-lsa[mpid=key2]/device_mac"
			::= { wingStatsDevWlMcxMeshpointLsaEntry 5 }

		
		-- 1.3.6.1.4.1.1916.2.131.50.1.4.2.25.21.12.1.6
		wingStatsDevWlMcxMeshpointLsaNumEntries OBJECT-TYPE
			SYNTAX Unsigned32
			MAX-ACCESS read-only
			STATUS current
			DESCRIPTION
				"Number of entries on for this table
				
				XPath: /wing-stats/device[mac=key1]/wireless/meshpoint-lsa[mpid=key2]/num_entries"
			::= { wingStatsDevWlMcxMeshpointLsaEntry 6 }

		
		-- 1.3.6.1.4.1.1916.2.131.50.1.4.2.25.21.12.1.7
		wingStatsDevWlMcxMeshpointLsaMeshid OBJECT-TYPE
			SYNTAX DisplayString (SIZE (32))
			MAX-ACCESS read-only
			STATUS current
			DESCRIPTION
				"Mesh Point Identifier for this MP.
				
				XPath: /wing-stats/device[mac=key1]/wireless/meshpoint-lsa[mpid=key2]/meshid"
			::= { wingStatsDevWlMcxMeshpointLsaEntry 7 }

		
		-- 1.3.6.1.4.1.1916.2.131.50.1.4.2.25.21.12.1.8
		wingStatsDevWlMcxMeshpointLsaR0Valid OBJECT-TYPE
			SYNTAX TruthValue
			MAX-ACCESS read-only
			STATUS current
			DESCRIPTION
				"R0 information is valid
				
				XPath: /wing-stats/device[mac=key1]/wireless/meshpoint-lsa[mpid=key2]/r0_valid"
			::= { wingStatsDevWlMcxMeshpointLsaEntry 8 }

		
		-- 1.3.6.1.4.1.1916.2.131.50.1.4.2.25.21.12.1.9
		wingStatsDevWlMcxMeshpointLsaR0mdid OBJECT-TYPE
			SYNTAX OCTET STRING (SIZE (12))
			MAX-ACCESS read-only
			STATUS current
			DESCRIPTION
				"Mesh Point R0 Mesh Domain ID
				
				XPath: /wing-stats/device[mac=key1]/wireless/meshpoint-lsa[mpid=key2]/r0mdid"
			::= { wingStatsDevWlMcxMeshpointLsaEntry 9 }

		
		-- 1.3.6.1.4.1.1916.2.131.50.1.4.2.25.21.12.1.10
		wingStatsDevWlMcxMeshpointLsaR0khid OBJECT-TYPE
			SYNTAX OCTET STRING (SIZE (32))
			MAX-ACCESS read-only
			STATUS current
			DESCRIPTION
				"Mesh Point R0 Key Holder ID
				
				XPath: /wing-stats/device[mac=key1]/wireless/meshpoint-lsa[mpid=key2]/r0khid"
			::= { wingStatsDevWlMcxMeshpointLsaEntry 10 }

		
		-- 1.3.6.1.4.1.1916.2.131.50.1.4.2.25.21.13
		wingStatsDevWlMcxMeshpointLsaEntriesTable OBJECT-TYPE
			SYNTAX SEQUENCE OF WingStatsDevWlMcxMeshpointLsaEntriesEntry
			MAX-ACCESS not-accessible
			STATUS current
			DESCRIPTION
				"
				
				/wing-stats/device/wireless/meshpoint-lsa/entries"
			::= { wingStatsDevWlMcx 13 }

		
		-- 1.3.6.1.4.1.1916.2.131.50.1.4.2.25.21.13.1
		wingStatsDevWlMcxMeshpointLsaEntriesEntry OBJECT-TYPE
			SYNTAX WingStatsDevWlMcxMeshpointLsaEntriesEntry
			MAX-ACCESS not-accessible
			STATUS current
			DESCRIPTION
				"An entry in the table."
			INDEX { wingStatsDevMac, wingStatsDevWlMcxMeshpointLsaMpid, wingStatsDevWlMcxMeshpointLsaEntriesIndex }
			::= { wingStatsDevWlMcxMeshpointLsaEntriesTable 1 }

		
		WingStatsDevWlMcxMeshpointLsaEntriesEntry ::=
			SEQUENCE { 
				wingStatsDevWlMcxMeshpointLsaEntriesIndex
					Unsigned32,
				wingStatsDevWlMcxMeshpointLsaEntriesLinkAddr
					DisplayString,
				wingStatsDevWlMcxMeshpointLsaEntriesInterfaceId
					WingIdentifier,
				wingStatsDevWlMcxMeshpointLsaEntriesKeepAlive
					TruthValue,
				wingStatsDevWlMcxMeshpointLsaEntriesLinkState
					DisplayString,
				wingStatsDevWlMcxMeshpointLsaEntriesLinkTimeout
					Integer32
			 }

		-- 1.3.6.1.4.1.1916.2.131.50.1.4.2.25.21.13.1.1
		wingStatsDevWlMcxMeshpointLsaEntriesIndex OBJECT-TYPE
			SYNTAX Unsigned32 (1..4294967295)
			MAX-ACCESS read-only
			STATUS current
			DESCRIPTION
				"Entries Index
				XPath: /wing-stats/device[mac=key1]/wireless/meshpoint-lsa[mpid=key2]/entries[entry_idx=key3]/entry_idx"
			::= { wingStatsDevWlMcxMeshpointLsaEntriesEntry 1 }

		
		-- 1.3.6.1.4.1.1916.2.131.50.1.4.2.25.21.13.1.2
		wingStatsDevWlMcxMeshpointLsaEntriesLinkAddr OBJECT-TYPE
			SYNTAX DisplayString
			MAX-ACCESS read-only
			STATUS current
			DESCRIPTION
				"Link MAC address
				
				XPath: /wing-stats/device[mac=key1]/wireless/meshpoint-lsa[mpid=key2]/entries[entry_idx=key3]/link_addr"
			::= { wingStatsDevWlMcxMeshpointLsaEntriesEntry 2 }

		
		-- 1.3.6.1.4.1.1916.2.131.50.1.4.2.25.21.13.1.3
		wingStatsDevWlMcxMeshpointLsaEntriesInterfaceId OBJECT-TYPE
			SYNTAX WingIdentifier
			MAX-ACCESS read-only
			STATUS current
			DESCRIPTION
				"Unique ID for each interfacce in the form of AP-MAC:%c%d. E.g., 00-A0-F8-00-00-00:R1
				
				XPath: /wing-stats/device[mac=key1]/wireless/meshpoint-lsa[mpid=key2]/entries[entry_idx=key3]/interface_id"
			::= { wingStatsDevWlMcxMeshpointLsaEntriesEntry 3 }

		
		-- 1.3.6.1.4.1.1916.2.131.50.1.4.2.25.21.13.1.4
		wingStatsDevWlMcxMeshpointLsaEntriesKeepAlive OBJECT-TYPE
			SYNTAX TruthValue
			MAX-ACCESS read-only
			STATUS current
			DESCRIPTION
				"Keep link alive
				
				XPath: /wing-stats/device[mac=key1]/wireless/meshpoint-lsa[mpid=key2]/entries[entry_idx=key3]/keep_alive"
			::= { wingStatsDevWlMcxMeshpointLsaEntriesEntry 4 }

		
		-- 1.3.6.1.4.1.1916.2.131.50.1.4.2.25.21.13.1.5
		wingStatsDevWlMcxMeshpointLsaEntriesLinkState OBJECT-TYPE
			SYNTAX DisplayString
			MAX-ACCESS read-only
			STATUS current
			DESCRIPTION
				"Link state
				
				Values:
				Init,
				Enabled,
				Failed,
				In
				Progress,
				Invalid
				
				XPath: /wing-stats/device[mac=key1]/wireless/meshpoint-lsa[mpid=key2]/entries[entry_idx=key3]/link_state"
			::= { wingStatsDevWlMcxMeshpointLsaEntriesEntry 5 }

		
		-- 1.3.6.1.4.1.1916.2.131.50.1.4.2.25.21.13.1.6
		wingStatsDevWlMcxMeshpointLsaEntriesLinkTimeout OBJECT-TYPE
			SYNTAX Integer32
			MAX-ACCESS read-only
			STATUS current
			DESCRIPTION
				"Link timeout
				
				XPath: /wing-stats/device[mac=key1]/wireless/meshpoint-lsa[mpid=key2]/entries[entry_idx=key3]/link_timeout"
			::= { wingStatsDevWlMcxMeshpointLsaEntriesEntry 6 }
		
		-- 1.3.6.1.4.1.1916.2.131.50.1.4.2.25.21.14
		wingStatsDevWlMcxMeshpointMcastPathsTable OBJECT-TYPE
			SYNTAX SEQUENCE OF WingStatsDevWlMcxMeshpointMcastPathsEntry
			MAX-ACCESS not-accessible
			STATUS current
			DESCRIPTION
				"
				
				/wing-stats/device/wireless/meshpoint-mcast-paths"
			::= { wingStatsDevWlMcx 14 }

		
		-- 1.3.6.1.4.1.1916.2.131.50.1.4.2.25.21.14.1
		wingStatsDevWlMcxMeshpointMcastPathsEntry OBJECT-TYPE
			SYNTAX WingStatsDevWlMcxMeshpointMcastPathsEntry
			MAX-ACCESS not-accessible
			STATUS current
			DESCRIPTION
				"An entry in the table."
			INDEX { wingStatsDevMac, wingStatsDevWlMcxMeshpointMcastPathsMpid }
			::= { wingStatsDevWlMcxMeshpointMcastPathsTable 1 }

		
		WingStatsDevWlMcxMeshpointMcastPathsEntry ::=
			SEQUENCE { 
				wingStatsDevWlMcxMeshpointMcastPathsMpid
					WingIdentifier,
				wingStatsDevWlMcxMeshpointMcastPathsName
					WingIdentifier,
				wingStatsDevWlMcxMeshpointMcastPathsHostname
					DisplayString,
				wingStatsDevWlMcxMeshpointMcastPathsDeviceMac
					DisplayString,
				wingStatsDevWlMcxMeshpointMcastPathsNumEntries
					Unsigned32
			 }

		-- 1.3.6.1.4.1.1916.2.131.50.1.4.2.25.21.14.1.1
		wingStatsDevWlMcxMeshpointMcastPathsMpid OBJECT-TYPE
			SYNTAX WingIdentifier
			MAX-ACCESS read-only
			STATUS current
			DESCRIPTION
				"Mesh Point MAC address
				
				XPath: /wing-stats/device[mac=key1]/wireless/meshpoint-mcast-paths[mpid=key2]/mpid"
			::= { wingStatsDevWlMcxMeshpointMcastPathsEntry 1 }

		
		-- 1.3.6.1.4.1.1916.2.131.50.1.4.2.25.21.14.1.3
		wingStatsDevWlMcxMeshpointMcastPathsName OBJECT-TYPE
			SYNTAX WingIdentifier
			MAX-ACCESS read-only
			STATUS current
			DESCRIPTION
				"
				
				XPath: /wing-stats/device[mac=key1]/wireless/meshpoint-mcast-paths[mpid=key2]/name"
			::= { wingStatsDevWlMcxMeshpointMcastPathsEntry 3 }

		
		-- 1.3.6.1.4.1.1916.2.131.50.1.4.2.25.21.14.1.4
		wingStatsDevWlMcxMeshpointMcastPathsHostname OBJECT-TYPE
			SYNTAX DisplayString (SIZE (64))
			MAX-ACCESS read-only
			STATUS current
			DESCRIPTION
				"hostname of the AP device
				
				XPath: /wing-stats/device[mac=key1]/wireless/meshpoint-mcast-paths[mpid=key2]/hostname"
			::= { wingStatsDevWlMcxMeshpointMcastPathsEntry 4 }

		
		-- 1.3.6.1.4.1.1916.2.131.50.1.4.2.25.21.14.1.5
		wingStatsDevWlMcxMeshpointMcastPathsDeviceMac OBJECT-TYPE
			SYNTAX DisplayString
			MAX-ACCESS read-only
			STATUS current
			DESCRIPTION
				"Device MAC address
				
				XPath: /wing-stats/device[mac=key1]/wireless/meshpoint-mcast-paths[mpid=key2]/device_mac"
			::= { wingStatsDevWlMcxMeshpointMcastPathsEntry 5 }

		
		-- 1.3.6.1.4.1.1916.2.131.50.1.4.2.25.21.14.1.6
		wingStatsDevWlMcxMeshpointMcastPathsNumEntries OBJECT-TYPE
			SYNTAX Unsigned32
			MAX-ACCESS read-only
			STATUS current
			DESCRIPTION
				"Number of entries on for this table
				
				XPath: /wing-stats/device[mac=key1]/wireless/meshpoint-mcast-paths[mpid=key2]/num_entries"
			::= { wingStatsDevWlMcxMeshpointMcastPathsEntry 6 }

		
		-- 1.3.6.1.4.1.1916.2.131.50.1.4.2.25.21.15
		wingStatsDevWlMcxMeshpointMcastPathsEntriesTable OBJECT-TYPE
			SYNTAX SEQUENCE OF WingStatsDevWlMcxMeshpointMcastPathsEntriesEntry
			MAX-ACCESS not-accessible
			STATUS current
			DESCRIPTION
				"
				
				/wing-stats/device/wireless/meshpoint-mcast-paths/entries"
			::= { wingStatsDevWlMcx 15 }

		
		-- 1.3.6.1.4.1.1916.2.131.50.1.4.2.25.21.15.1
		wingStatsDevWlMcxMeshpointMcastPathsEntriesEntry OBJECT-TYPE
			SYNTAX WingStatsDevWlMcxMeshpointMcastPathsEntriesEntry
			MAX-ACCESS not-accessible
			STATUS current
			DESCRIPTION
				"An entry in the table."
			INDEX { wingStatsDevMac, wingStatsDevWlMcxMeshpointMcastPathsMpid, wingStatsDevWlMcxMeshpointMcastPathsEntriesIndex }
			::= { wingStatsDevWlMcxMeshpointMcastPathsEntriesTable 1 }

		
		WingStatsDevWlMcxMeshpointMcastPathsEntriesEntry ::=
			SEQUENCE { 
				wingStatsDevWlMcxMeshpointMcastPathsEntriesIndex
					Unsigned32,
				wingStatsDevWlMcxMeshpointMcastPathsEntriesGroupAddr
					DisplayString,
				wingStatsDevWlMcxMeshpointMcastPathsEntriesMemberAddr
					DisplayString,
				wingStatsDevWlMcxMeshpointMcastPathsEntriesPathTimeout
					Integer32
			 }

		-- 1.3.6.1.4.1.1916.2.131.50.1.4.2.25.21.15.1.1
		wingStatsDevWlMcxMeshpointMcastPathsEntriesIndex OBJECT-TYPE
			SYNTAX Unsigned32 (1..4294967295)
			MAX-ACCESS read-only
			STATUS current
			DESCRIPTION
				"Entries Index
				
				XPath: /wing-stats/device[mac=key1]/wireless/meshpoint-mcast-paths[mpid=key2]/entries[entry_idx=key3]/entry_idx"
			::= { wingStatsDevWlMcxMeshpointMcastPathsEntriesEntry 1 }

		
		-- 1.3.6.1.4.1.1916.2.131.50.1.4.2.25.21.15.1.2
		wingStatsDevWlMcxMeshpointMcastPathsEntriesGroupAddr OBJECT-TYPE
			SYNTAX DisplayString
			MAX-ACCESS read-only
			STATUS current
			DESCRIPTION
				"Group MAC address
				
				XPath: /wing-stats/device[mac=key1]/wireless/meshpoint-mcast-paths[mpid=key2]/entries[entry_idx=key3]/group_addr"
			::= { wingStatsDevWlMcxMeshpointMcastPathsEntriesEntry 2 }

		
		-- 1.3.6.1.4.1.1916.2.131.50.1.4.2.25.21.15.1.3
		wingStatsDevWlMcxMeshpointMcastPathsEntriesMemberAddr OBJECT-TYPE
			SYNTAX DisplayString
			MAX-ACCESS read-only
			STATUS current
			DESCRIPTION
				"Member mesh point MAC address
				
				XPath: /wing-stats/device[mac=key1]/wireless/meshpoint-mcast-paths[mpid=key2]/entries[entry_idx=key3]/member_addr"
			::= { wingStatsDevWlMcxMeshpointMcastPathsEntriesEntry 3 }

		
		-- 1.3.6.1.4.1.1916.2.131.50.1.4.2.25.21.15.1.4
		wingStatsDevWlMcxMeshpointMcastPathsEntriesPathTimeout OBJECT-TYPE
			SYNTAX Integer32
			MAX-ACCESS read-only
			STATUS current
			DESCRIPTION
				"Path timeout
				
				XPath: /wing-stats/device[mac=key1]/wireless/meshpoint-mcast-paths[mpid=key2]/entries[entry_idx=key3]/path_timeout"
			::= { wingStatsDevWlMcxMeshpointMcastPathsEntriesEntry 4 }
		
-- /wing-stats/device/vrrp
		-- 1.3.6.1.4.1.1916.2.131.50.1.4.2.31
		wingStatsDevVrrp OBJECT IDENTIFIER ::= { wingStatsDev 31 }

		
		-- 1.3.6.1.4.1.1916.2.131.50.1.4.2.31.1
		wingStatsDevVrrpGlobalErrTable OBJECT-TYPE
			SYNTAX SEQUENCE OF WingStatsDevVrrpGlobalErrEntry
			MAX-ACCESS not-accessible
			STATUS current
			DESCRIPTION
				"
				
				/wing-stats/device/vrrp/vrrp_router_global_err_stats"
			::= { wingStatsDevVrrp 1 }

		
		-- 1.3.6.1.4.1.1916.2.131.50.1.4.2.31.1.1
		wingStatsDevVrrpGlobalErrEntry OBJECT-TYPE
			SYNTAX WingStatsDevVrrpGlobalErrEntry
			MAX-ACCESS not-accessible
			STATUS current
			DESCRIPTION
				"An entry in the table."
			INDEX { wingStatsDevMac }
			::= { wingStatsDevVrrpGlobalErrTable 1 }

		
		WingStatsDevVrrpGlobalErrEntry ::=
			SEQUENCE { 
				wingStatsDevVrrpGlobalErrIpTtlErrs
					Unsigned32,
				wingStatsDevVrrpGlobalErrVersionMismatch
					Unsigned32,
				wingStatsDevVrrpGlobalErrPacketLenErr
					Unsigned32,
				wingStatsDevVrrpGlobalErrChecksumErr
					Unsigned32,
				wingStatsDevVrrpGlobalErrInvalidVirtualRouterId
					Unsigned32,
				wingStatsDevVrrpGlobalErrAuthMismatch
					Unsigned32,
				wingStatsDevVrrpGlobalErrInvalidTypePackets
					Unsigned32,
				wingStatsDevVrrpGlobalErrLastProtocolErrReason
					DisplayString
			 }

		-- 1.3.6.1.4.1.1916.2.131.50.1.4.2.31.1.1.1
		wingStatsDevVrrpGlobalErrIpTtlErrs OBJECT-TYPE
			SYNTAX Unsigned32
			MAX-ACCESS read-only
			STATUS current
			DESCRIPTION
				"The total number of VRRP packets received by the virtual router with IPv4 TTL not equal to 255.
				
				XPath: /wing-stats/device[mac=key1]/vrrp/vrrp_router_global_err_stats/ip_ttl_errors"
			::= { wingStatsDevVrrpGlobalErrEntry 1 }

		
		-- 1.3.6.1.4.1.1916.2.131.50.1.4.2.31.1.1.2
		wingStatsDevVrrpGlobalErrVersionMismatch OBJECT-TYPE
			SYNTAX Unsigned32
			MAX-ACCESS read-only
			STATUS current
			DESCRIPTION
				"The total number of VRRP packets received with an unknown or unsupported version number
				
				XPath: /wing-stats/device[mac=key1]/vrrp/vrrp_router_global_err_stats/version_mismatch"
			::= { wingStatsDevVrrpGlobalErrEntry 2 }

		
		-- 1.3.6.1.4.1.1916.2.131.50.1.4.2.31.1.1.3
		wingStatsDevVrrpGlobalErrPacketLenErr OBJECT-TYPE
			SYNTAX Unsigned32
			MAX-ACCESS read-only
			STATUS current
			DESCRIPTION
				"The total number of packets received with a packet length less than the length of the VRRP header
				
				XPath: /wing-stats/device[mac=key1]/vrrp/vrrp_router_global_err_stats/packet_len_error"
			::= { wingStatsDevVrrpGlobalErrEntry 3 }

		
		-- 1.3.6.1.4.1.1916.2.131.50.1.4.2.31.1.1.4
		wingStatsDevVrrpGlobalErrChecksumErr OBJECT-TYPE
			SYNTAX Unsigned32
			MAX-ACCESS read-only
			STATUS current
			DESCRIPTION
				"The total number of VRRP packets received with an invalid VRRP checksum value
				
				XPath: /wing-stats/device[mac=key1]/vrrp/vrrp_router_global_err_stats/checksum_err"
			::= { wingStatsDevVrrpGlobalErrEntry 4 }

		
		-- 1.3.6.1.4.1.1916.2.131.50.1.4.2.31.1.1.5
		wingStatsDevVrrpGlobalErrInvalidVirtualRouterId OBJECT-TYPE
			SYNTAX Unsigned32
			MAX-ACCESS read-only
			STATUS current
			DESCRIPTION
				"The total number of VRRP packets received with an invalid VRID for this virtual router
				
				XPath: /wing-stats/device[mac=key1]/vrrp/vrrp_router_global_err_stats/invalid_virtual_router_id"
			::= { wingStatsDevVrrpGlobalErrEntry 5 }

		
		-- 1.3.6.1.4.1.1916.2.131.50.1.4.2.31.1.1.6
		wingStatsDevVrrpGlobalErrAuthMismatch OBJECT-TYPE
			SYNTAX Unsigned32
			MAX-ACCESS read-only
			STATUS current
			DESCRIPTION
				"VRRP authentication mismatch
				
				XPath: /wing-stats/device[mac=key1]/vrrp/vrrp_router_global_err_stats/authentication_mismatch"
			::= { wingStatsDevVrrpGlobalErrEntry 6 }

		
		-- 1.3.6.1.4.1.1916.2.131.50.1.4.2.31.1.1.7
		wingStatsDevVrrpGlobalErrInvalidTypePackets OBJECT-TYPE
			SYNTAX Unsigned32
			MAX-ACCESS read-only
			STATUS current
			DESCRIPTION
				"The total number of VRRP packets send by the virtual router with an invalid value in the 'type' field
				
				XPath: /wing-stats/device[mac=key1]/vrrp/vrrp_router_global_err_stats/invalid_type_packets"
			::= { wingStatsDevVrrpGlobalErrEntry 7 }

		
		-- 1.3.6.1.4.1.1916.2.131.50.1.4.2.31.1.1.8
		wingStatsDevVrrpGlobalErrLastProtocolErrReason OBJECT-TYPE
			SYNTAX DisplayString
			MAX-ACCESS read-only
			STATUS current
			DESCRIPTION
				"This indicates the reason for the last protocol error.  This SHOULD be set to none when no protocol
				
				Values:
				none,
				ip-ttl,
				version,
				packet_len,
				checksum,
				vrid,
				auth,
				invalid_type
				
				XPath: /wing-stats/device[mac=key1]/vrrp/vrrp_router_global_err_stats/last_protocol_error_reason"
			::= { wingStatsDevVrrpGlobalErrEntry 8 }

		
		-- 1.3.6.1.4.1.1916.2.131.50.1.4.2.31.2
		wingStatsDevVrrpOperationTable OBJECT-TYPE
			SYNTAX SEQUENCE OF WingStatsDevVrrpOperationEntry
			MAX-ACCESS not-accessible
			STATUS current
			DESCRIPTION
				"
				
				/wing-stats/device/vrrp/vrrp_operations_summary"
			::= { wingStatsDevVrrp 2 }

		
		-- 1.3.6.1.4.1.1916.2.131.50.1.4.2.31.2.1
		wingStatsDevVrrpOperationEntry OBJECT-TYPE
			SYNTAX WingStatsDevVrrpOperationEntry
			MAX-ACCESS not-accessible
			STATUS current
			DESCRIPTION
				"An entry in the table."
			INDEX { wingStatsDevMac, wingStatsDevVrrpOperationVirtualRouterId }
			::= { wingStatsDevVrrpOperationTable 1 }

		
		WingStatsDevVrrpOperationEntry ::=
			SEQUENCE { 
				wingStatsDevVrrpOperationVirtualRouterId
					Unsigned32,
				wingStatsDevVrrpOperationIfName
					DisplayString,
				wingStatsDevVrrpOperationVersion
					DisplayString,
				wingStatsDevVrrpOperationState
					DisplayString,
				wingStatsDevVrrpOperationPriority
					Unsigned32,
				wingStatsDevVrrpOperationVirtualAddr
					DisplayString,
				wingStatsDevVrrpOperationMasterAddr
					DisplayString,
				wingStatsDevVrrpOperationExpiryTimer
					DisplayString,
				wingStatsDevVrrpOperationMasterDeadTimer
					DisplayString
			 }

		-- 1.3.6.1.4.1.1916.2.131.50.1.4.2.31.2.1.1
		wingStatsDevVrrpOperationVirtualRouterId OBJECT-TYPE
			SYNTAX Unsigned32 (1..255)
			MAX-ACCESS read-only
			STATUS current
			DESCRIPTION
				"Virtual router Identifier
				
				XPath: /wing-stats/device[mac=key1]/vrrp/vrrp_operations_summary[virtual_router_id=key2]/virtual_router_id"
			::= { wingStatsDevVrrpOperationEntry 1 }

		
		-- 1.3.6.1.4.1.1916.2.131.50.1.4.2.31.2.1.3
		wingStatsDevVrrpOperationIfName OBJECT-TYPE
			SYNTAX DisplayString
			MAX-ACCESS read-only
			STATUS current
			DESCRIPTION
				"Name of the interface on which VRRP is running
				
				XPath: /wing-stats/device[mac=key1]/vrrp/vrrp_operations_summary[virtual_router_id=key2]/interface_name"
			::= { wingStatsDevVrrpOperationEntry 3 }

		
		-- 1.3.6.1.4.1.1916.2.131.50.1.4.2.31.2.1.4
		wingStatsDevVrrpOperationVersion OBJECT-TYPE
			SYNTAX DisplayString
			MAX-ACCESS read-only
			STATUS current
			DESCRIPTION
				"VRRP version of this group
				
				Values:
				2,
				3
				
				XPath: /wing-stats/device[mac=key1]/vrrp/vrrp_operations_summary[virtual_router_id=key2]/version"
			::= { wingStatsDevVrrpOperationEntry 4 }

		
		-- 1.3.6.1.4.1.1916.2.131.50.1.4.2.31.2.1.5
		wingStatsDevVrrpOperationState OBJECT-TYPE
			SYNTAX DisplayString
			MAX-ACCESS read-only
			STATUS current
			DESCRIPTION
				"The current state of the virtual router. This object
				
				Values:
				init,
				backup,
				master
				
				XPath: /wing-stats/device[mac=key1]/vrrp/vrrp_operations_summary[virtual_router_id=key2]/state"
			::= { wingStatsDevVrrpOperationEntry 5 }

		
		-- 1.3.6.1.4.1.1916.2.131.50.1.4.2.31.2.1.6
		wingStatsDevVrrpOperationPriority OBJECT-TYPE
			SYNTAX Unsigned32 (0..255)
			MAX-ACCESS read-only
			STATUS current
			DESCRIPTION
				" Runtime VRRP priority for this group. In case of link monitoring this can differ from the configured priority.
				
				XPath: /wing-stats/device[mac=key1]/vrrp/vrrp_operations_summary[virtual_router_id=key2]/operation_priority"
			::= { wingStatsDevVrrpOperationEntry 6 }

		
		-- 1.3.6.1.4.1.1916.2.131.50.1.4.2.31.2.1.7
		wingStatsDevVrrpOperationVirtualAddr OBJECT-TYPE
			SYNTAX DisplayString
			MAX-ACCESS read-only
			STATUS current
			DESCRIPTION
				"Virtual IP address, if more than one specified then the first configured one is selected
				
				XPath: /wing-stats/device[mac=key1]/vrrp/vrrp_operations_summary[virtual_router_id=key2]/virtual_address"
			::= { wingStatsDevVrrpOperationEntry 7 }

		
		-- 1.3.6.1.4.1.1916.2.131.50.1.4.2.31.2.1.8
		wingStatsDevVrrpOperationMasterAddr OBJECT-TYPE
			SYNTAX DisplayString
			MAX-ACCESS read-only
			STATUS current
			DESCRIPTION
				"current master IP address
				
				XPath: /wing-stats/device[mac=key1]/vrrp/vrrp_operations_summary[virtual_router_id=key2]/master_address"
			::= { wingStatsDevVrrpOperationEntry 8 }

		
		-- 1.3.6.1.4.1.1916.2.131.50.1.4.2.31.2.1.9
		wingStatsDevVrrpOperationExpiryTimer OBJECT-TYPE
			SYNTAX DisplayString
			MAX-ACCESS read-only
			STATUS current
			DESCRIPTION
				"How long until the advertisement timer expires
				
				XPath: /wing-stats/device[mac=key1]/vrrp/vrrp_operations_summary[virtual_router_id=key2]/expiry_timer"
			::= { wingStatsDevVrrpOperationEntry 9 }

		
		-- 1.3.6.1.4.1.1916.2.131.50.1.4.2.31.2.1.10
		wingStatsDevVrrpOperationMasterDeadTimer OBJECT-TYPE
			SYNTAX DisplayString
			MAX-ACCESS read-only
			STATUS current
			DESCRIPTION
				"How long until the master is detected as dead timer expires
				
				XPath: /wing-stats/device[mac=key1]/vrrp/vrrp_operations_summary[virtual_router_id=key2]/master_dead_timer"
			::= { wingStatsDevVrrpOperationEntry 10 }

		
		-- 1.3.6.1.4.1.1916.2.131.50.1.4.2.31.3
		wingStatsDevVrrpDetailTable OBJECT-TYPE
			SYNTAX SEQUENCE OF WingStatsDevVrrpDetailEntry
			MAX-ACCESS not-accessible
			STATUS current
			DESCRIPTION
				"
				
				/wing-stats/device/vrrp/vrrp_operations_detail"
			::= { wingStatsDevVrrp 3 }

		
		-- 1.3.6.1.4.1.1916.2.131.50.1.4.2.31.3.1
		wingStatsDevVrrpDetailEntry OBJECT-TYPE
			SYNTAX WingStatsDevVrrpDetailEntry
			MAX-ACCESS not-accessible
			STATUS current
			DESCRIPTION
				"An entry in the table."
			INDEX { wingStatsDevMac, wingStatsDevVrrpDetailVirtualRouterId }
			::= { wingStatsDevVrrpDetailTable 1 }

		
		WingStatsDevVrrpDetailEntry ::=
			SEQUENCE { 
				wingStatsDevVrrpDetailVirtualRouterId
					Unsigned32,
				wingStatsDevVrrpDetailIfName
					DisplayString,
				wingStatsDevVrrpDetailVersion
					DisplayString,
				wingStatsDevVrrpDetailConfiguredPriority
					Unsigned32,
				wingStatsDevVrrpDetailAdvertisementInterval
					DisplayString,
				wingStatsDevVrrpDetailLocalIpAddress
					DisplayString,
				wingStatsDevVrrpDetailIfStatusAdmin
					DisplayString,
				wingStatsDevVrrpDetailVirtualAddressCount
					Unsigned32,
				wingStatsDevVrrpDetailPreempt
					TruthValue,
				wingStatsDevVrrpDetailPreemptDelay
					Unsigned32,
				wingStatsDevVrrpDetailCrmDownAction
					DisplayString,
				wingStatsDevVrrpDetailCrmStatus
					DisplayString,
				wingStatsDevVrrpDetailCfgedDeltaPriority
					Unsigned32,
				wingStatsDevVrrpDetailVirtualMacAddr
					MacAddress,
				wingStatsDevVrrpDetailSyncGroup
					TruthValue,
				wingStatsDevVrrpDetailFailoverSyncGroup
					DisplayString
			 }

		-- 1.3.6.1.4.1.1916.2.131.50.1.4.2.31.3.1.1
		wingStatsDevVrrpDetailVirtualRouterId OBJECT-TYPE
			SYNTAX Unsigned32 (1..255)
			MAX-ACCESS read-only
			STATUS current
			DESCRIPTION
				"Virtual router Identifier
				
				XPath: /wing-stats/device[mac=key1]/vrrp/vrrp_operations_detail[virtual_router_id=key2]/virtual_router_id"
			::= { wingStatsDevVrrpDetailEntry 1 }

		
		-- 1.3.6.1.4.1.1916.2.131.50.1.4.2.31.3.1.3
		wingStatsDevVrrpDetailIfName OBJECT-TYPE
			SYNTAX DisplayString
			MAX-ACCESS read-only
			STATUS current
			DESCRIPTION
				"Name of the interface on which VRRP is running
				
				XPath: /wing-stats/device[mac=key1]/vrrp/vrrp_operations_detail[virtual_router_id=key2]/interface_name"
			::= { wingStatsDevVrrpDetailEntry 3 }

		
		-- 1.3.6.1.4.1.1916.2.131.50.1.4.2.31.3.1.4
		wingStatsDevVrrpDetailVersion OBJECT-TYPE
			SYNTAX DisplayString
			MAX-ACCESS read-only
			STATUS current
			DESCRIPTION
				"VRRP version of this group
				
				Values:
				2,
				3
				
				XPath: /wing-stats/device[mac=key1]/vrrp/vrrp_operations_detail[virtual_router_id=key2]/version"
			::= { wingStatsDevVrrpDetailEntry 4 }

		
		-- 1.3.6.1.4.1.1916.2.131.50.1.4.2.31.3.1.5
		wingStatsDevVrrpDetailConfiguredPriority OBJECT-TYPE
			SYNTAX Unsigned32 (1..254)
			MAX-ACCESS read-only
			STATUS current
			DESCRIPTION
				"the priority to be used for the virtual router master election process.  Higher values imply higher priority.
				
				XPath: /wing-stats/device[mac=key1]/vrrp/vrrp_operations_detail[virtual_router_id=key2]/configured_priority"
			::= { wingStatsDevVrrpDetailEntry 5 }

		
		-- 1.3.6.1.4.1.1916.2.131.50.1.4.2.31.3.1.6
		wingStatsDevVrrpDetailAdvertisementInterval OBJECT-TYPE
			SYNTAX DisplayString
			MAX-ACCESS read-only
			STATUS current
			DESCRIPTION
				"Time interval between sending advertisement messages. Only the master router sends VRRP advertisements
				
				XPath: /wing-stats/device[mac=key1]/vrrp/vrrp_operations_detail[virtual_router_id=key2]/advertisement_interval"
			::= { wingStatsDevVrrpDetailEntry 6 }

		
		-- 1.3.6.1.4.1.1916.2.131.50.1.4.2.31.3.1.7
		wingStatsDevVrrpDetailLocalIpAddress OBJECT-TYPE
			SYNTAX DisplayString
			MAX-ACCESS read-only
			STATUS current
			DESCRIPTION
				"In the case where there are more than one IP Address (associated IP addresses) for a given interface, this will the IP address with highest prefix
				
				XPath: /wing-stats/device[mac=key1]/vrrp/vrrp_operations_detail[virtual_router_id=key2]/local_ip_address"
			::= { wingStatsDevVrrpDetailEntry 7 }

		
		-- 1.3.6.1.4.1.1916.2.131.50.1.4.2.31.3.1.8
		wingStatsDevVrrpDetailIfStatusAdmin OBJECT-TYPE
			SYNTAX DisplayString
			MAX-ACCESS read-only
			STATUS current
			DESCRIPTION
				"Administrative status of interface (up/down)
				
				Values:
				up,
				down,
				up_and_running
				
				XPath: /wing-stats/device[mac=key1]/vrrp/vrrp_operations_detail[virtual_router_id=key2]/interface_status_admin"
			::= { wingStatsDevVrrpDetailEntry 8 }

		
		-- 1.3.6.1.4.1.1916.2.131.50.1.4.2.31.3.1.9
		wingStatsDevVrrpDetailVirtualAddressCount OBJECT-TYPE
			SYNTAX Unsigned32
			MAX-ACCESS read-only
			STATUS current
			DESCRIPTION
				"Number of virtual address(es) configured
				
				XPath: /wing-stats/device[mac=key1]/vrrp/vrrp_operations_detail[virtual_router_id=key2]/virtual_address_count"
			::= { wingStatsDevVrrpDetailEntry 9 }

		
		-- 1.3.6.1.4.1.1916.2.131.50.1.4.2.31.3.1.10
		wingStatsDevVrrpDetailPreempt OBJECT-TYPE
			SYNTAX TruthValue
			MAX-ACCESS read-only
			STATUS current
			DESCRIPTION
				"Controls whether a higher priority backup router will preempt a lower priority master.
				
				XPath: /wing-stats/device[mac=key1]/vrrp/vrrp_operations_detail[virtual_router_id=key2]/preempt"
			::= { wingStatsDevVrrpDetailEntry 10 }

		
		-- 1.3.6.1.4.1.1916.2.131.50.1.4.2.31.3.1.11
		wingStatsDevVrrpDetailPreemptDelay OBJECT-TYPE
			SYNTAX Unsigned32 (0..65535)
			UNITS "seconds"
			MAX-ACCESS read-only
			STATUS current
			DESCRIPTION
				"Delay after which preemption will get triggered
				
				XPath: /wing-stats/device[mac=key1]/vrrp/vrrp_operations_detail[virtual_router_id=key2]/preempt_delay"
			::= { wingStatsDevVrrpDetailEntry 11 }

		
		-- 1.3.6.1.4.1.1916.2.131.50.1.4.2.31.3.1.12
		wingStatsDevVrrpDetailCrmDownAction OBJECT-TYPE
			SYNTAX DisplayString
			MAX-ACCESS read-only
			STATUS current
			DESCRIPTION
				"
				
				Values:
				increment-priority,
				decrement-priority,
				none
				
				XPath: /wing-stats/device[mac=key1]/vrrp/vrrp_operations_detail[virtual_router_id=key2]/crm_down_action"
			::= { wingStatsDevVrrpDetailEntry 12 }

		
		-- 1.3.6.1.4.1.1916.2.131.50.1.4.2.31.3.1.13
		wingStatsDevVrrpDetailCrmStatus OBJECT-TYPE
			SYNTAX DisplayString
			MAX-ACCESS read-only
			STATUS current
			DESCRIPTION
				"
				
				Values:
				up,
				down
				
				XPath: /wing-stats/device[mac=key1]/vrrp/vrrp_operations_detail[virtual_router_id=key2]/crm_status"
			::= { wingStatsDevVrrpDetailEntry 13 }

		
		-- 1.3.6.1.4.1.1916.2.131.50.1.4.2.31.3.1.14
		wingStatsDevVrrpDetailCfgedDeltaPriority OBJECT-TYPE
			SYNTAX Unsigned32
			MAX-ACCESS read-only
			STATUS current
			DESCRIPTION
				"The configured priority will be increment/decremented by this value. Also see description for type field above.
				
				XPath: /wing-stats/device[mac=key1]/vrrp/vrrp_operations_detail[virtual_router_id=key2]/configured_delta_priority"
			::= { wingStatsDevVrrpDetailEntry 14 }

		
		-- 1.3.6.1.4.1.1916.2.131.50.1.4.2.31.3.1.15
		wingStatsDevVrrpDetailVirtualMacAddr OBJECT-TYPE
			SYNTAX MacAddress
			MAX-ACCESS read-only
			STATUS current
			DESCRIPTION
				"virtual mac addresses that is derived from the virtual router id
				
				XPath: /wing-stats/device[mac=key1]/vrrp/vrrp_operations_detail[virtual_router_id=key2]/virtual_mac_address"
			::= { wingStatsDevVrrpDetailEntry 15 }

		
		-- 1.3.6.1.4.1.1916.2.131.50.1.4.2.31.3.1.16
		wingStatsDevVrrpDetailSyncGroup OBJECT-TYPE
			SYNTAX TruthValue
			MAX-ACCESS read-only
			STATUS current
			DESCRIPTION
				"Specifies whether this group is part of vrrp sync group. If it is, then vrrp failover happens when all masters that are part of this group is detected as dead
				
				XPath: /wing-stats/device[mac=key1]/vrrp/vrrp_operations_detail[virtual_router_id=key2]/sync_group"
			::= { wingStatsDevVrrpDetailEntry 16 }

		
		-- 1.3.6.1.4.1.1916.2.131.50.1.4.2.31.3.1.17
		wingStatsDevVrrpDetailFailoverSyncGroup OBJECT-TYPE
			SYNTAX DisplayString
			MAX-ACCESS read-only
			STATUS current
			DESCRIPTION
				"Specifies the operational state of this group
				
				XPath: /wing-stats/device[mac=key1]/vrrp/vrrp_operations_detail[virtual_router_id=key2]/failover_sync_group"
			::= { wingStatsDevVrrpDetailEntry 17 }

		
		-- 1.3.6.1.4.1.1916.2.131.50.1.4.2.31.4
		wingStatsDevVrrpDetailMonitorTable OBJECT-TYPE
			SYNTAX SEQUENCE OF WingStatsDevVrrpDetailMonitorEntry
			MAX-ACCESS not-accessible
			STATUS current
			DESCRIPTION
				"
				
				/wing-stats/device/vrrp/vrrp_operations_detail/monitor"
			::= { wingStatsDevVrrp 4 }

		
		-- 1.3.6.1.4.1.1916.2.131.50.1.4.2.31.4.1
		wingStatsDevVrrpDetailMonitorEntry OBJECT-TYPE
			SYNTAX WingStatsDevVrrpDetailMonitorEntry
			MAX-ACCESS not-accessible
			STATUS current
			DESCRIPTION
				"An entry in the table."
			INDEX { wingStatsDevMac, wingStatsDevVrrpDetailVirtualRouterId, wingStatsDevVrrpDetailMonitorIf }
			::= { wingStatsDevVrrpDetailMonitorTable 1 }

		
		WingStatsDevVrrpDetailMonitorEntry ::=
			SEQUENCE { 
				wingStatsDevVrrpDetailMonitorIf
					WingIdentifier,
				wingStatsDevVrrpDetailMonitorIfStatusAdmin
					DisplayString
			 }

		-- 1.3.6.1.4.1.1916.2.131.50.1.4.2.31.4.1.1
		wingStatsDevVrrpDetailMonitorIf OBJECT-TYPE
			SYNTAX WingIdentifier
			MAX-ACCESS read-only
			STATUS current
			DESCRIPTION
				"Name of the local interface being monitored
				
				XPath: /wing-stats/device[mac=key1]/vrrp/vrrp_operations_detail[virtual_router_id=key2]/monitor[monitor_interface=key3]/monitor_interface"
			::= { wingStatsDevVrrpDetailMonitorEntry 1 }

		
		-- 1.3.6.1.4.1.1916.2.131.50.1.4.2.31.4.1.3
		wingStatsDevVrrpDetailMonitorIfStatusAdmin OBJECT-TYPE
			SYNTAX DisplayString
			MAX-ACCESS read-only
			STATUS current
			DESCRIPTION
				"Administrative status of locally monitored interface
				
				Values:
				up,
				down,
				up_and_running
				
				XPath: /wing-stats/device[mac=key1]/vrrp/vrrp_operations_detail[virtual_router_id=key2]/monitor[monitor_interface=key3]/interface_status_admin"
			::= { wingStatsDevVrrpDetailMonitorEntry 3 }

		
		-- 1.3.6.1.4.1.1916.2.131.50.1.4.2.31.5
		wingStatsDevVrrpRouterStatsTable OBJECT-TYPE
			SYNTAX SEQUENCE OF WingStatsDevVrrpRouterStatsEntry
			MAX-ACCESS not-accessible
			STATUS current
			DESCRIPTION
				"
				
				/wing-stats/device/vrrp/vrrp_router_statistics"
			::= { wingStatsDevVrrp 5 }

		
		-- 1.3.6.1.4.1.1916.2.131.50.1.4.2.31.5.1
		wingStatsDevVrrpRouterStatsEntry OBJECT-TYPE
			SYNTAX WingStatsDevVrrpRouterStatsEntry
			MAX-ACCESS not-accessible
			STATUS current
			DESCRIPTION
				"An entry in the table."
			INDEX { wingStatsDevMac, wingStatsDevVrrpRouterStatsVirtualRouterId }
			::= { wingStatsDevVrrpRouterStatsTable 1 }

		
		WingStatsDevVrrpRouterStatsEntry ::=
			SEQUENCE { 
				wingStatsDevVrrpRouterStatsVirtualRouterId
					Unsigned32,
				wingStatsDevVrrpRouterStatsMasterTransitions
					Unsigned32,
				wingStatsDevVrrpRouterStatsNewMasterReason
					DisplayString,
				wingStatsDevVrrpRouterStatsNumReceivedAdvertisement
					Unsigned32,
				wingStatsDevVrrpRouterStatsAdvertisementIntervalErrs
					Unsigned32,
				wingStatsDevVrrpRouterStatsNumSendAdvertisement
					Unsigned32,
				wingStatsDevVrrpRouterStatsReceivedAdvtInitState
					Unsigned32,
				wingStatsDevVrrpRouterStatsReceivedPriorityZeroPackets
					Unsigned32,
				wingStatsDevVrrpRouterStatsSendPriorityZeroPackets
					Unsigned32,
				wingStatsDevVrrpRouterStatsAddressListErrors
					Unsigned32
			 }

		-- 1.3.6.1.4.1.1916.2.131.50.1.4.2.31.5.1.1
		wingStatsDevVrrpRouterStatsVirtualRouterId OBJECT-TYPE
			SYNTAX Unsigned32 (1..255)
			MAX-ACCESS read-only
			STATUS current
			DESCRIPTION
				"Virtual router Identifier
				
				XPath: /wing-stats/device[mac=key1]/vrrp/vrrp_router_statistics[virtual_router_id=key2]/virtual_router_id"
			::= { wingStatsDevVrrpRouterStatsEntry 1 }

		
		-- 1.3.6.1.4.1.1916.2.131.50.1.4.2.31.5.1.3
		wingStatsDevVrrpRouterStatsMasterTransitions OBJECT-TYPE
			SYNTAX Unsigned32
			MAX-ACCESS read-only
			STATUS current
			DESCRIPTION
				"The total number of times that this virtual router's state has transitioned to MASTER
				
				XPath: /wing-stats/device[mac=key1]/vrrp/vrrp_router_statistics[virtual_router_id=key2]/master_transitions"
			::= { wingStatsDevVrrpRouterStatsEntry 3 }

		
		-- 1.3.6.1.4.1.1916.2.131.50.1.4.2.31.5.1.4
		wingStatsDevVrrpRouterStatsNewMasterReason OBJECT-TYPE
			SYNTAX DisplayString
			MAX-ACCESS read-only
			STATUS current
			DESCRIPTION
				"Reason for becoming a master. This object
				
				Values:
				not-master,
				priority,
				preempted,
				master-no-response,
				critical-resource-monitoring
				
				XPath: /wing-stats/device[mac=key1]/vrrp/vrrp_router_statistics[virtual_router_id=key2]/new_master_reason"
			::= { wingStatsDevVrrpRouterStatsEntry 4 }

		
		-- 1.3.6.1.4.1.1916.2.131.50.1.4.2.31.5.1.5
		wingStatsDevVrrpRouterStatsNumReceivedAdvertisement OBJECT-TYPE
			SYNTAX Unsigned32
			MAX-ACCESS read-only
			STATUS current
			DESCRIPTION
				"Number of advertisement packets received
				
				XPath: /wing-stats/device[mac=key1]/vrrp/vrrp_router_statistics[virtual_router_id=key2]/num_received_advertisement"
			::= { wingStatsDevVrrpRouterStatsEntry 5 }

		
		-- 1.3.6.1.4.1.1916.2.131.50.1.4.2.31.5.1.6
		wingStatsDevVrrpRouterStatsAdvertisementIntervalErrs OBJECT-TYPE
			SYNTAX Unsigned32
			MAX-ACCESS read-only
			STATUS current
			DESCRIPTION
				"The total number of VRRP advertisement packets received for which the advertisement interval is different than the one configured for the local virtual
				
				XPath: /wing-stats/device[mac=key1]/vrrp/vrrp_router_statistics[virtual_router_id=key2]/advertisement_interval_errors"
			::= { wingStatsDevVrrpRouterStatsEntry 6 }

		
		-- 1.3.6.1.4.1.1916.2.131.50.1.4.2.31.5.1.7
		wingStatsDevVrrpRouterStatsNumSendAdvertisement OBJECT-TYPE
			SYNTAX Unsigned32
			MAX-ACCESS read-only
			STATUS current
			DESCRIPTION
				"Number of advertisement packets send
				
				XPath: /wing-stats/device[mac=key1]/vrrp/vrrp_router_statistics[virtual_router_id=key2]/num_send_advertisement"
			::= { wingStatsDevVrrpRouterStatsEntry 7 }

		
		-- 1.3.6.1.4.1.1916.2.131.50.1.4.2.31.5.1.8
		wingStatsDevVrrpRouterStatsReceivedAdvtInitState OBJECT-TYPE
			SYNTAX Unsigned32
			MAX-ACCESS read-only
			STATUS current
			DESCRIPTION
				"The total number of VRRP packets received when the virtual router is in init state
				
				XPath: /wing-stats/device[mac=key1]/vrrp/vrrp_router_statistics[virtual_router_id=key2]/received_advt_init_state"
			::= { wingStatsDevVrrpRouterStatsEntry 8 }

		
		-- 1.3.6.1.4.1.1916.2.131.50.1.4.2.31.5.1.9
		wingStatsDevVrrpRouterStatsReceivedPriorityZeroPackets OBJECT-TYPE
			SYNTAX Unsigned32
			MAX-ACCESS read-only
			STATUS current
			DESCRIPTION
				"The total number of VRRP packets received by the virtual router with priority of '0'
				
				XPath: /wing-stats/device[mac=key1]/vrrp/vrrp_router_statistics[virtual_router_id=key2]/received_priority_zero_packets"
			::= { wingStatsDevVrrpRouterStatsEntry 9 }

		
		-- 1.3.6.1.4.1.1916.2.131.50.1.4.2.31.5.1.10
		wingStatsDevVrrpRouterStatsSendPriorityZeroPackets OBJECT-TYPE
			SYNTAX Unsigned32
			MAX-ACCESS read-only
			STATUS current
			DESCRIPTION
				"The total number of VRRP packets send by the virtual router with priority of '0'
				
				XPath: /wing-stats/device[mac=key1]/vrrp/vrrp_router_statistics[virtual_router_id=key2]/send_priority_zero_packets"
			::= { wingStatsDevVrrpRouterStatsEntry 10 }

		
		-- 1.3.6.1.4.1.1916.2.131.50.1.4.2.31.5.1.11
		wingStatsDevVrrpRouterStatsAddressListErrors OBJECT-TYPE
			SYNTAX Unsigned32
			MAX-ACCESS read-only
			STATUS current
			DESCRIPTION
				"The total number of packets received for which the address list does not match the locally configured list for the virtual router
				
				XPath: /wing-stats/device[mac=key1]/vrrp/vrrp_router_statistics[virtual_router_id=key2]/address_list_errors"
			::= { wingStatsDevVrrpRouterStatsEntry 11 }

		
-- /wing-stats/device/crm
		-- 1.3.6.1.4.1.1916.2.131.50.1.4.2.32
		wingStatsDevCrm OBJECT IDENTIFIER ::= { wingStatsDev 32 }

		
		-- 1.3.6.1.4.1.1916.2.131.50.1.4.2.32.1
		wingStatsDevCrmTable OBJECT-TYPE
			SYNTAX SEQUENCE OF WingStatsDevCrmEntry
			MAX-ACCESS not-accessible
			STATUS current
			DESCRIPTION
				"
				
				/wing-stats/device/crm"
			::= { wingStatsDevCrm 1 }

		
		-- 1.3.6.1.4.1.1916.2.131.50.1.4.2.32.1.1
		wingStatsDevCrmEntry OBJECT-TYPE
			SYNTAX WingStatsDevCrmEntry
			MAX-ACCESS not-accessible
			STATUS current
			DESCRIPTION
				"An entry in the table."
			INDEX { wingStatsDevMac }
			::= { wingStatsDevCrmTable 1 }

		
		WingStatsDevCrmEntry ::=
			SEQUENCE { 
				wingStatsDevCrmMonitorInterval
					Unsigned32
			 }

		-- 1.3.6.1.4.1.1916.2.131.50.1.4.2.32.1.1.1
		wingStatsDevCrmMonitorInterval OBJECT-TYPE
			SYNTAX Unsigned32
			UNITS "seconds"
			MAX-ACCESS read-only
			STATUS current
			DESCRIPTION
				"
				
				XPath: /wing-stats/device[mac=key1]/crm/monitor_interval"
			::= { wingStatsDevCrmEntry 1 }

		
		-- 1.3.6.1.4.1.1916.2.131.50.1.4.2.32.2
		wingStatsDevCrmCriticalResTable OBJECT-TYPE
			SYNTAX SEQUENCE OF WingStatsDevCrmCriticalResEntry
			MAX-ACCESS not-accessible
			STATUS current
			DESCRIPTION
				"
				
				/wing-stats/device/crm/critical_resources"
			::= { wingStatsDevCrm 2 }

		
		-- 1.3.6.1.4.1.1916.2.131.50.1.4.2.32.2.1
		wingStatsDevCrmCriticalResEntry OBJECT-TYPE
			SYNTAX WingStatsDevCrmCriticalResEntry
			MAX-ACCESS not-accessible
			STATUS current
			DESCRIPTION
				"An entry in the table."
			INDEX { wingStatsDevMac, wingStatsDevCrmCriticalResVia }
			::= { wingStatsDevCrmCriticalResTable 1 }

		
		WingStatsDevCrmCriticalResEntry ::=
			SEQUENCE { 
				wingStatsDevCrmCriticalResVia
					WingIdentifier,
				wingStatsDevCrmCriticalResStatus
					DisplayString,
				wingStatsDevCrmCriticalResErrorReason
					DisplayString,
				wingStatsDevCrmCriticalResMode
					DisplayString
			 }

		-- 1.3.6.1.4.1.1916.2.131.50.1.4.2.32.2.1.1
		wingStatsDevCrmCriticalResVia OBJECT-TYPE
			SYNTAX WingIdentifier
			MAX-ACCESS read-only
			STATUS current
			DESCRIPTION
				"
				
				XPath: /wing-stats/device[mac=key1]/crm/critical_resources[via=key2]/via"
			::= { wingStatsDevCrmCriticalResEntry 1 }

		
		-- 1.3.6.1.4.1.1916.2.131.50.1.4.2.32.2.1.3
		wingStatsDevCrmCriticalResStatus OBJECT-TYPE
			SYNTAX DisplayString
			MAX-ACCESS read-only
			STATUS current
			DESCRIPTION
				"
				
				Values:
				up,
				down,
				checking
				
				XPath: /wing-stats/device[mac=key1]/crm/critical_resources[via=key2]/status"
			::= { wingStatsDevCrmCriticalResEntry 3 }

		
		-- 1.3.6.1.4.1.1916.2.131.50.1.4.2.32.2.1.4
		wingStatsDevCrmCriticalResErrorReason OBJECT-TYPE
			SYNTAX DisplayString
			MAX-ACCESS read-only
			STATUS current
			DESCRIPTION
				"
				
				XPath: /wing-stats/device[mac=key1]/crm/critical_resources[via=key2]/error_reason"
			::= { wingStatsDevCrmCriticalResEntry 4 }

		
		-- 1.3.6.1.4.1.1916.2.131.50.1.4.2.32.2.1.5
		wingStatsDevCrmCriticalResMode OBJECT-TYPE
			SYNTAX DisplayString
			MAX-ACCESS read-only
			STATUS current
			DESCRIPTION
				"
				
				XPath: /wing-stats/device[mac=key1]/crm/critical_resources[via=key2]/mode"
			::= { wingStatsDevCrmCriticalResEntry 5 }

		
		-- 1.3.6.1.4.1.1916.2.131.50.1.4.2.32.3
		wingStatsDevCrmCriticalResResTable OBJECT-TYPE
			SYNTAX SEQUENCE OF WingStatsDevCrmCriticalResResEntry
			MAX-ACCESS not-accessible
			STATUS current
			DESCRIPTION
				"
				
				/wing-stats/device/crm/critical_resources/resources"
			::= { wingStatsDevCrm 3 }

		
		-- 1.3.6.1.4.1.1916.2.131.50.1.4.2.32.3.1
		wingStatsDevCrmCriticalResResEntry OBJECT-TYPE
			SYNTAX WingStatsDevCrmCriticalResResEntry
			MAX-ACCESS not-accessible
			STATUS current
			DESCRIPTION
				"An entry in the table."
			INDEX { wingStatsDevMac, wingStatsDevCrmCriticalResVia, wingStatsDevCrmCriticalResResAddr }
			::= { wingStatsDevCrmCriticalResResTable 1 }

		
		WingStatsDevCrmCriticalResResEntry ::=
			SEQUENCE { 
				wingStatsDevCrmCriticalResResAddr
					WingIdentifier,
				wingStatsDevCrmCriticalResResMonitorMode
					DisplayString,
				wingStatsDevCrmCriticalResResArpVlan
					Unsigned32,
				wingStatsDevCrmCriticalResResStatus
					DisplayString,
				wingStatsDevCrmCriticalResResArpPort
					DisplayString
			 }

		-- 1.3.6.1.4.1.1916.2.131.50.1.4.2.32.3.1.1
		wingStatsDevCrmCriticalResResAddr OBJECT-TYPE
			SYNTAX WingIdentifier
			MAX-ACCESS read-only
			STATUS current
			DESCRIPTION
				"
				
				XPath: /wing-stats/device[mac=key1]/crm/critical_resources[via=key2]/resources[addr=key3]/addr"
			::= { wingStatsDevCrmCriticalResResEntry 1 }

		
		-- 1.3.6.1.4.1.1916.2.131.50.1.4.2.32.3.1.3
		wingStatsDevCrmCriticalResResMonitorMode OBJECT-TYPE
			SYNTAX DisplayString
			MAX-ACCESS read-only
			STATUS current
			DESCRIPTION
				"
				
				Values:
				arp-only,
				arp-and-ping
				
				XPath: /wing-stats/device[mac=key1]/crm/critical_resources[via=key2]/resources[addr=key3]/monitor_mode"
			::= { wingStatsDevCrmCriticalResResEntry 3 }

		
		-- 1.3.6.1.4.1.1916.2.131.50.1.4.2.32.3.1.4
		wingStatsDevCrmCriticalResResArpVlan OBJECT-TYPE
			SYNTAX Unsigned32
			MAX-ACCESS read-only
			STATUS current
			DESCRIPTION
				"
				
				XPath: /wing-stats/device[mac=key1]/crm/critical_resources[via=key2]/resources[addr=key3]/arp_vlan"
			::= { wingStatsDevCrmCriticalResResEntry 4 }

		
		-- 1.3.6.1.4.1.1916.2.131.50.1.4.2.32.3.1.5
		wingStatsDevCrmCriticalResResStatus OBJECT-TYPE
			SYNTAX DisplayString
			MAX-ACCESS read-only
			STATUS current
			DESCRIPTION
				"
				
				Values:
				up,
				down,
				unresolved
				
				XPath: /wing-stats/device[mac=key1]/crm/critical_resources[via=key2]/resources[addr=key3]/status"
			::= { wingStatsDevCrmCriticalResResEntry 5 }

		
		-- 1.3.6.1.4.1.1916.2.131.50.1.4.2.32.3.1.6
		wingStatsDevCrmCriticalResResArpPort OBJECT-TYPE
			SYNTAX DisplayString
			MAX-ACCESS read-only
			STATUS current
			DESCRIPTION
				"
				
				XPath: /wing-stats/device[mac=key1]/crm/critical_resources[via=key2]/resources[addr=key3]/arp_port"
			::= { wingStatsDevCrmCriticalResResEntry 6 }

		
-- /wing-stats/device/pbr_stats
		-- 1.3.6.1.4.1.1916.2.131.50.1.4.2.33
		wingStatsDevPbr OBJECT IDENTIFIER ::= { wingStatsDev 33 }

		
		-- 1.3.6.1.4.1.1916.2.131.50.1.4.2.33.1
		wingStatsDevPbrTable OBJECT-TYPE
			SYNTAX SEQUENCE OF WingStatsDevPbrEntry
			MAX-ACCESS not-accessible
			STATUS current
			DESCRIPTION
				"
				
				/wing-stats/device/pbr_stats"
			::= { wingStatsDevPbr 1 }

		
		-- 1.3.6.1.4.1.1916.2.131.50.1.4.2.33.1.1
		wingStatsDevPbrEntry OBJECT-TYPE
			SYNTAX WingStatsDevPbrEntry
			MAX-ACCESS not-accessible
			STATUS current
			DESCRIPTION
				"An entry in the table."
			INDEX { wingStatsDevMac, wingStatsDevPbrRouteMapPrecedence }
			::= { wingStatsDevPbrTable 1 }

		
		WingStatsDevPbrEntry ::=
			SEQUENCE { 
				wingStatsDevPbrRouteMapPrecedence
					Unsigned32,
				wingStatsDevPbrPrimaryNextHopIfName
					DisplayString,
				wingStatsDevPbrPrimaryNextHopIpAddr
					DisplayString,
				wingStatsDevPbrPrimaryNextHopState
					DisplayString,
				wingStatsDevPbrPrimaryNextHopMonitorMode
					DisplayString,
				wingStatsDevPbrSecondaryNextHopIfName
					DisplayString,
				wingStatsDevPbrSecondaryNextHopIpAddr
					DisplayString,
				wingStatsDevPbrSecondaryNextHopState
					DisplayString,
				wingStatsDevPbrSecondaryNextHopMonitorMode
					DisplayString,
				wingStatsDevPbrDefaultNextHopIfName
					DisplayString,
				wingStatsDevPbrDefaultNextHopIpAddr
					DisplayString,
				wingStatsDevPbrDefaultNextHopState
					DisplayString,
				wingStatsDevPbrDefaultNextHopMonitorMode
					DisplayString,
				wingStatsDevPbrWlan
					DisplayString,
				wingStatsDevPbrWirelessClientRole
					DisplayString,
				wingStatsDevPbrInInterface
					DisplayString,
				wingStatsDevPbrIpDscp
					DisplayString
			 }

		-- 1.3.6.1.4.1.1916.2.131.50.1.4.2.33.1.1.1
		wingStatsDevPbrRouteMapPrecedence OBJECT-TYPE
			SYNTAX Unsigned32 (1..100)
			MAX-ACCESS read-only
			STATUS current
			DESCRIPTION
				"
				
				XPath: /wing-stats/device[mac=key1]/pbr_stats[route_map_precedence=key2]/route_map_precedence"
			::= { wingStatsDevPbrEntry 1 }

		
		-- 1.3.6.1.4.1.1916.2.131.50.1.4.2.33.1.1.3
		wingStatsDevPbrPrimaryNextHopIfName OBJECT-TYPE
			SYNTAX DisplayString
			MAX-ACCESS read-only
			STATUS current
			DESCRIPTION
				"
				
				XPath: /wing-stats/device[mac=key1]/pbr_stats[route_map_precedence=key2]/primary_next_hop/interface_name"
			::= { wingStatsDevPbrEntry 3 }

		
		-- 1.3.6.1.4.1.1916.2.131.50.1.4.2.33.1.1.4
		wingStatsDevPbrPrimaryNextHopIpAddr OBJECT-TYPE
			SYNTAX DisplayString
			MAX-ACCESS read-only
			STATUS current
			DESCRIPTION
				"
				
				XPath: /wing-stats/device[mac=key1]/pbr_stats[route_map_precedence=key2]/primary_next_hop/ip_address"
			::= { wingStatsDevPbrEntry 4 }

		
		-- 1.3.6.1.4.1.1916.2.131.50.1.4.2.33.1.1.5
		wingStatsDevPbrPrimaryNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /wing-stats/device[mac=key1]/pbr_stats[route_map_precedence=key2]/primary_next_hop/state"
			::= { wingStatsDevPbrEntry 5 }

		
		-- 1.3.6.1.4.1.1916.2.131.50.1.4.2.33.1.1.6
		wingStatsDevPbrPrimaryNextHopMonitorMode OBJECT-TYPE
			SYNTAX DisplayString
			MAX-ACCESS read-only
			STATUS current
			DESCRIPTION
				"
				
				XPath: /wing-stats/device[mac=key1]/pbr_stats[route_map_precedence=key2]/primary_next_hop/monitor_mode"
			::= { wingStatsDevPbrEntry 6 }

		
		-- 1.3.6.1.4.1.1916.2.131.50.1.4.2.33.1.1.7
		wingStatsDevPbrSecondaryNextHopIfName OBJECT-TYPE
			SYNTAX DisplayString
			MAX-ACCESS read-only
			STATUS current
			DESCRIPTION
				"
				
				XPath: /wing-stats/device[mac=key1]/pbr_stats[route_map_precedence=key2]/secondary_next_hop/interface_name"
			::= { wingStatsDevPbrEntry 7 }

		
		-- 1.3.6.1.4.1.1916.2.131.50.1.4.2.33.1.1.8
		wingStatsDevPbrSecondaryNextHopIpAddr OBJECT-TYPE
			SYNTAX DisplayString
			MAX-ACCESS read-only
			STATUS current
			DESCRIPTION
				"
				
				XPath: /wing-stats/device[mac=key1]/pbr_stats[route_map_precedence=key2]/secondary_next_hop/ip_address"
			::= { wingStatsDevPbrEntry 8 }

		
		-- 1.3.6.1.4.1.1916.2.131.50.1.4.2.33.1.1.9
		wingStatsDevPbrSecondaryNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /wing-stats/device[mac=key1]/pbr_stats[route_map_precedence=key2]/secondary_next_hop/state"
			::= { wingStatsDevPbrEntry 9 }

		
		-- 1.3.6.1.4.1.1916.2.131.50.1.4.2.33.1.1.10
		wingStatsDevPbrSecondaryNextHopMonitorMode OBJECT-TYPE
			SYNTAX DisplayString
			MAX-ACCESS read-only
			STATUS current
			DESCRIPTION
				"
				
				XPath: /wing-stats/device[mac=key1]/pbr_stats[route_map_precedence=key2]/secondary_next_hop/monitor_mode"
			::= { wingStatsDevPbrEntry 10 }

		
		-- 1.3.6.1.4.1.1916.2.131.50.1.4.2.33.1.1.11
		wingStatsDevPbrDefaultNextHopIfName OBJECT-TYPE
			SYNTAX DisplayString
			MAX-ACCESS read-only
			STATUS current
			DESCRIPTION
				"
				
				XPath: /wing-stats/device[mac=key1]/pbr_stats[route_map_precedence=key2]/default_next_hop/interface_name"
			::= { wingStatsDevPbrEntry 11 }

		
		-- 1.3.6.1.4.1.1916.2.131.50.1.4.2.33.1.1.12
		wingStatsDevPbrDefaultNextHopIpAddr OBJECT-TYPE
			SYNTAX DisplayString
			MAX-ACCESS read-only
			STATUS current
			DESCRIPTION
				"
				
				XPath: /wing-stats/device[mac=key1]/pbr_stats[route_map_precedence=key2]/default_next_hop/ip_address"
			::= { wingStatsDevPbrEntry 12 }

		
		-- 1.3.6.1.4.1.1916.2.131.50.1.4.2.33.1.1.13
		wingStatsDevPbrDefaultNextHopState OBJECT-TYPE
			SYNTAX DisplayString
			MAX-ACCESS read-only
			STATUS current
			DESCRIPTION
				"UP: next-hop is up and traffic is being routed through it, UNREACHABLE: next-hop has been reported down by critical-resource monitoring, UNKNOWN: an interface was configured as next-hop but the gateway has not been determined, INVALID: configured next-hop is not a neighbor
				
				XPath: /wing-stats/device[mac=key1]/pbr_stats[route_map_precedence=key2]/default_next_hop/state"
			::= { wingStatsDevPbrEntry 13 }

		
		-- 1.3.6.1.4.1.1916.2.131.50.1.4.2.33.1.1.14
		wingStatsDevPbrDefaultNextHopMonitorMode OBJECT-TYPE
			SYNTAX DisplayString
			MAX-ACCESS read-only
			STATUS current
			DESCRIPTION
				"
				
				XPath: /wing-stats/device[mac=key1]/pbr_stats[route_map_precedence=key2]/default_next_hop/monitor_mode"
			::= { wingStatsDevPbrEntry 14 }

		
		-- 1.3.6.1.4.1.1916.2.131.50.1.4.2.33.1.1.15
		wingStatsDevPbrWlan OBJECT-TYPE
			SYNTAX DisplayString
			MAX-ACCESS read-only
			STATUS current
			DESCRIPTION
				"
				
				XPath: /wing-stats/device[mac=key1]/pbr_stats[route_map_precedence=key2]/wlan"
			::= { wingStatsDevPbrEntry 15 }

		
		-- 1.3.6.1.4.1.1916.2.131.50.1.4.2.33.1.1.16
		wingStatsDevPbrWirelessClientRole OBJECT-TYPE
			SYNTAX DisplayString
			MAX-ACCESS read-only
			STATUS current
			DESCRIPTION
				"
				
				XPath: /wing-stats/device[mac=key1]/pbr_stats[route_map_precedence=key2]/wireless_client_role"
			::= { wingStatsDevPbrEntry 16 }

		
		-- 1.3.6.1.4.1.1916.2.131.50.1.4.2.33.1.1.17
		wingStatsDevPbrInInterface OBJECT-TYPE
			SYNTAX DisplayString
			MAX-ACCESS read-only
			STATUS current
			DESCRIPTION
				"
				
				XPath: /wing-stats/device[mac=key1]/pbr_stats[route_map_precedence=key2]/in_interface"
			::= { wingStatsDevPbrEntry 17 }

		
		-- 1.3.6.1.4.1.1916.2.131.50.1.4.2.33.1.1.18
		wingStatsDevPbrIpDscp OBJECT-TYPE
			SYNTAX DisplayString
			MAX-ACCESS read-only
			STATUS current
			DESCRIPTION
				"
				
				XPath: /wing-stats/device[mac=key1]/pbr_stats[route_map_precedence=key2]/ip_dscp"
			::= { wingStatsDevPbrEntry 18 }

		
		-- 1.3.6.1.4.1.1916.2.131.50.1.4.2.33.2
		wingStatsDevPbrRulesTable OBJECT-TYPE
			SYNTAX SEQUENCE OF WingStatsDevPbrRulesEntry
			MAX-ACCESS not-accessible
			STATUS current
			DESCRIPTION
				"
				
				/wing-stats/device/pbr_stats/rules"
			::= { wingStatsDevPbr 2 }

		
		-- 1.3.6.1.4.1.1916.2.131.50.1.4.2.33.2.1
		wingStatsDevPbrRulesEntry OBJECT-TYPE
			SYNTAX WingStatsDevPbrRulesEntry
			MAX-ACCESS not-accessible
			STATUS current
			DESCRIPTION
				"An entry in the table."
			INDEX { wingStatsDevMac, wingStatsDevPbrRouteMapPrecedence, wingStatsDevPbrRuleString }
			::= { wingStatsDevPbrRulesTable 1 }

		
		WingStatsDevPbrRulesEntry ::=
			SEQUENCE { 
				wingStatsDevPbrRuleString
					WingIdentifier,
				wingStatsDevPbrRulesHitcount
					Unsigned32
			 }

		-- 1.3.6.1.4.1.1916.2.131.50.1.4.2.33.2.1.1
		wingStatsDevPbrRuleString OBJECT-TYPE
			SYNTAX WingIdentifier
			MAX-ACCESS read-only
			STATUS current
			DESCRIPTION
				"
				
				XPath: /wing-stats/device[mac=key1]/pbr_stats[route_map_precedence=key2]/rules[rule_string=key3]/match_criteria/rule_string"
			::= { wingStatsDevPbrRulesEntry 1 }

		
		-- 1.3.6.1.4.1.1916.2.131.50.1.4.2.33.2.1.3
		wingStatsDevPbrRulesHitcount OBJECT-TYPE
			SYNTAX Unsigned32
			MAX-ACCESS read-only
			STATUS current
			DESCRIPTION
				"
				
				XPath: /wing-stats/device[mac=key1]/pbr_stats[route_map_precedence=key2]/rules[rule_string=key3]/match_criteria/hitcount"
			::= { wingStatsDevPbrRulesEntry 3 }

		
		-- 1.3.6.1.4.1.1916.2.131.50.1.4.2.34
		wingStatsDevDynRoute OBJECT IDENTIFIER ::= { wingStatsDev 34 }
-- Ospf Stats
		
		-- 1.3.6.1.4.1.1916.2.131.50.1.4.2.34.1
		wingStatsDevDynRouteIpOspfTable OBJECT-TYPE
			SYNTAX SEQUENCE OF WingStatsDevDynRouteIpOspfEntry
			MAX-ACCESS not-accessible
			STATUS current
			DESCRIPTION
				"Ip Ospf Stats."
			::= { wingStatsDevDynRoute 1 }

		
		-- 1.3.6.1.4.1.1916.2.131.50.1.4.2.34.1.1
		wingStatsDevDynRouteIpOspfEntry OBJECT-TYPE
			SYNTAX WingStatsDevDynRouteIpOspfEntry
			MAX-ACCESS not-accessible
			STATUS current
			DESCRIPTION
				"An entry in the table."
			INDEX { wingStatsDevMac }
			::= { wingStatsDevDynRouteIpOspfTable 1 }

		
		WingStatsDevDynRouteIpOspfEntry ::=
			SEQUENCE { 
				wingStatsDevDynRouteIpOspfRouterId
					WingIdentifier,
				wingStatsDevDynRouteIpOspfShutdownFlag
					TruthValue,
				wingStatsDevDynRouteIpOspfShutdownDueTime
					DisplayString,
				wingStatsDevDynRouteIpOspfTos
					Unsigned32,
				wingStatsDevDynRouteIpOspfRFC2328ConformanceFlag
					TruthValue,
				wingStatsDevDynRouteIpOspfRFC1583CompatFlag
					TruthValue,
				wingStatsDevDynRouteIpOspfOpaquelsaFlag
					TruthValue,
				wingStatsDevDynRouteIpOspfOpaquelsaOriginationBlockedFlag
					TruthValue,
				wingStatsDevDynRouteIpOspfStubRouterAdvFlag
					TruthValue,
				wingStatsDevDynRouteIpOspfStubRouterStartupTime
					Unsigned32,
				wingStatsDevDynRouteIpOspfStubRouterShutdownTime
					Unsigned32,
				wingStatsDevDynRouteIpOspfDelay
					Unsigned32,
				wingStatsDevDynRouteIpOspfHoldTime
					Unsigned32,
				wingStatsDevDynRouteIpOspfMaxHoldTime
					Unsigned32,
				wingStatsDevDynRouteIpOspfHoldMultiplier
					Unsigned32,
				wingStatsDevDynRouteIpOspfExecutedFlag
					TruthValue,
				wingStatsDevDynRouteIpOspfExecutedWhen
					DisplayString,
				wingStatsDevDynRouteIpOspfTimerDueFlag
					TruthValue,
				wingStatsDevDynRouteIpOspfDueIn
					DisplayString,
				wingStatsDevDynRouteIpOspflsaRefreshTimer
					Unsigned32,
				wingStatsDevDynRouteIpOspfAbrFlag
					TruthValue,
				wingStatsDevDynRouteIpOspfAbrType
					DisplayString,
				wingStatsDevDynRouteIpOspfAsbrFlag
					TruthValue,
				wingStatsDevDynRouteIpOspfExtLsdbCount
					Counter64,
				wingStatsDevDynRouteIpOspfExtLsdbCsum
					Unsigned32,
				wingStatsDevDynRouteIpOspfOpaqueLsdbCount
					Counter64,
				wingStatsDevDynRouteIpOspfOpaqueExtLsdbCsum
					Unsigned32,
				wingStatsDevDynRouteIpOspfNumAreasAttached
					Unsigned32,
				wingStatsDevDynRouteIpOspfMaxRoutes
					Unsigned32,
				wingStatsDevDynRouteIpOspfRoutesReceived
					Unsigned32,
				wingStatsDevDynRouteIpOspfMaxIgnoreStateCount
					Unsigned32,
				wingStatsDevDynRouteIpOspfIgnoreStateCount
					Unsigned32,
				wingStatsDevDynRouteIpOspfIgnoreStateTimeout
					Unsigned32,
				wingStatsDevDynRouteIpOspfIgnoreStateMonitorTimeout
					Unsigned32,
				wingStatsDevDynRouteIpOspfState
					DisplayString
			 }

		-- 1.3.6.1.4.1.1916.2.131.50.1.4.2.34.1.1.1
		wingStatsDevDynRouteIpOspfRouterId OBJECT-TYPE
			SYNTAX WingIdentifier
			MAX-ACCESS read-only
			STATUS current
			DESCRIPTION
				"Router-ID for this device.
				
				XPath: /wing-stats/device[mac=key1]/ospf_stats/ip_ospf_stats/router_id"
			::= { wingStatsDevDynRouteIpOspfEntry 1 }

		
		-- 1.3.6.1.4.1.1916.2.131.50.1.4.2.34.1.1.2
		wingStatsDevDynRouteIpOspfShutdownFlag OBJECT-TYPE
			SYNTAX TruthValue
			MAX-ACCESS read-only
			STATUS current
			DESCRIPTION
				"Whether gracefull shutdown is in progress.
				
				XPath: /wing-stats/device[mac=key1]/ospf_stats/ip_ospf_stats/gracefull_shutdown_flag"
			::= { wingStatsDevDynRouteIpOspfEntry 2 }

		
		-- 1.3.6.1.4.1.1916.2.131.50.1.4.2.34.1.1.3
		wingStatsDevDynRouteIpOspfShutdownDueTime OBJECT-TYPE
			SYNTAX DisplayString
			MAX-ACCESS read-only
			STATUS current
			DESCRIPTION
				"Last time SPF was executed in <HH>h<MM>m<SS>s format.
				
				XPath: /wing-stats/device[mac=key1]/ospf_stats/ip_ospf_stats/shutdown_due_time"
			::= { wingStatsDevDynRouteIpOspfEntry 3 }

		
		-- 1.3.6.1.4.1.1916.2.131.50.1.4.2.34.1.1.4
		wingStatsDevDynRouteIpOspfTos OBJECT-TYPE
			SYNTAX Unsigned32
			MAX-ACCESS read-only
			STATUS current
			DESCRIPTION
				"This implementaion of OSPF supports only single TOS(TOS0) routes.
				
				XPath: /wing-stats/device[mac=key1]/ospf_stats/ip_ospf_stats/tos
				"
			::= { wingStatsDevDynRouteIpOspfEntry 4 }

		
		-- 1.3.6.1.4.1.1916.2.131.50.1.4.2.34.1.1.5
		wingStatsDevDynRouteIpOspfRFC2328ConformanceFlag OBJECT-TYPE
			SYNTAX TruthValue
			MAX-ACCESS read-only
			STATUS current
			DESCRIPTION
				"Whether this implementation of OSPF is RFC 2328 compliant
				
				XPath: /wing-stats/device[mac=key1]/ospf_stats/ip_ospf_stats/rfc2328_conformance_flag"
			::= { wingStatsDevDynRouteIpOspfEntry 5 }

		
		-- 1.3.6.1.4.1.1916.2.131.50.1.4.2.34.1.1.6
		wingStatsDevDynRouteIpOspfRFC1583CompatFlag OBJECT-TYPE
			SYNTAX TruthValue
			MAX-ACCESS read-only
			STATUS current
			DESCRIPTION
				"Whether this implementation of OSPF is RFC 1583 compliant.
				
				XPath: /wing-stats/device[mac=key1]/ospf_stats/ip_ospf_stats/rfc1583_compat_flag"
			::= { wingStatsDevDynRouteIpOspfEntry 6 }

		
		-- 1.3.6.1.4.1.1916.2.131.50.1.4.2.34.1.1.7
		wingStatsDevDynRouteIpOspfOpaquelsaFlag OBJECT-TYPE
			SYNTAX TruthValue
			MAX-ACCESS read-only
			STATUS current
			DESCRIPTION
				"Whether opaque LSA is supported.
				
				XPath: /wing-stats/device[mac=key1]/ospf_stats/ip_ospf_stats/opaque_lsa_flag"
			::= { wingStatsDevDynRouteIpOspfEntry 7 }

		
		-- 1.3.6.1.4.1.1916.2.131.50.1.4.2.34.1.1.8
		wingStatsDevDynRouteIpOspfOpaquelsaOriginationBlockedFlag OBJECT-TYPE
			SYNTAX TruthValue
			MAX-ACCESS read-only
			STATUS current
			DESCRIPTION
				"Whether opaque LSA origination is blocked.
				
				XPath: /wing-stats/device[mac=key1]/ospf_stats/ip_ospf_stats/opaque_lsa_origination_blocked_flag"
			::= { wingStatsDevDynRouteIpOspfEntry 8 }

		
		-- 1.3.6.1.4.1.1916.2.131.50.1.4.2.34.1.1.9
		wingStatsDevDynRouteIpOspfStubRouterAdvFlag OBJECT-TYPE
			SYNTAX TruthValue
			MAX-ACCESS read-only
			STATUS current
			DESCRIPTION
				"Whether stub router advertisement is configured.
				
				XPath: /wing-stats/device[mac=key1]/ospf_stats/ip_ospf_stats/stub_router_adv_flag"
			::= { wingStatsDevDynRouteIpOspfEntry 9 }

		
		-- 1.3.6.1.4.1.1916.2.131.50.1.4.2.34.1.1.10
		wingStatsDevDynRouteIpOspfStubRouterStartupTime OBJECT-TYPE
			SYNTAX Unsigned32
			MAX-ACCESS read-only
			STATUS current
			DESCRIPTION
				"Stub router advertisement starts configured seconds after startup.
				
				XPath: /wing-stats/device[mac=key1]/ospf_stats/ip_ospf_stats/stub_router_startup_time"
			::= { wingStatsDevDynRouteIpOspfEntry 10 }

		
		-- 1.3.6.1.4.1.1916.2.131.50.1.4.2.34.1.1.11
		wingStatsDevDynRouteIpOspfStubRouterShutdownTime OBJECT-TYPE
			SYNTAX Unsigned32
			MAX-ACCESS read-only
			STATUS current
			DESCRIPTION
				"Stub router advertisement stops configured seconds prior to shutdown.
				
				XPath: /wing-stats/device[mac=key1]/ospf_stats/ip_ospf_stats/stub_router_shutdown_time"
			::= { wingStatsDevDynRouteIpOspfEntry 11 }

		
		-- 1.3.6.1.4.1.1916.2.131.50.1.4.2.34.1.1.12
		wingStatsDevDynRouteIpOspfDelay OBJECT-TYPE
			SYNTAX Unsigned32
			MAX-ACCESS read-only
			STATUS current
			DESCRIPTION
				"Initial SPF scheduling delay in milliseconds.
				
				XPath: /wing-stats/device[mac=key1]/ospf_stats/ip_ospf_stats/spf_delay"
			::= { wingStatsDevDynRouteIpOspfEntry 12 }

		
		-- 1.3.6.1.4.1.1916.2.131.50.1.4.2.34.1.1.13
		wingStatsDevDynRouteIpOspfHoldTime OBJECT-TYPE
			SYNTAX Unsigned32
			MAX-ACCESS read-only
			STATUS current
			DESCRIPTION
				"Minimum hold time between consecutive SPFs in milliseconds.
				
				XPath: /wing-stats/device[mac=key1]/ospf_stats/ip_ospf_stats/spf_holdtime"
			::= { wingStatsDevDynRouteIpOspfEntry 13 }

		
		-- 1.3.6.1.4.1.1916.2.131.50.1.4.2.34.1.1.14
		wingStatsDevDynRouteIpOspfMaxHoldTime OBJECT-TYPE
			SYNTAX Unsigned32
			MAX-ACCESS read-only
			STATUS current
			DESCRIPTION
				"Maximum hold time between consecutive SPFs in milliseconds.
				
				XPath: /wing-stats/device[mac=key1]/ospf_stats/ip_ospf_stats/spf_max_holdtime"
			::= { wingStatsDevDynRouteIpOspfEntry 14 }

		
		-- 1.3.6.1.4.1.1916.2.131.50.1.4.2.34.1.1.15
		wingStatsDevDynRouteIpOspfHoldMultiplier OBJECT-TYPE
			SYNTAX Unsigned32
			MAX-ACCESS read-only
			STATUS current
			DESCRIPTION
				"Holdtime multiplier factor.
				
				XPath: /wing-stats/device[mac=key1]/ospf_stats/ip_ospf_stats/spf_hold_multiplier"
			::= { wingStatsDevDynRouteIpOspfEntry 15 }

		
		-- 1.3.6.1.4.1.1916.2.131.50.1.4.2.34.1.1.16
		wingStatsDevDynRouteIpOspfExecutedFlag OBJECT-TYPE
			SYNTAX TruthValue
			MAX-ACCESS read-only
			STATUS current
			DESCRIPTION
				"Whether SPF algorithm has been executed.
				
				XPath: /wing-stats/device[mac=key1]/ospf_stats/ip_ospf_stats/spf_executed_flag
				"
			::= { wingStatsDevDynRouteIpOspfEntry 16 }

		
		-- 1.3.6.1.4.1.1916.2.131.50.1.4.2.34.1.1.17
		wingStatsDevDynRouteIpOspfExecutedWhen OBJECT-TYPE
			SYNTAX DisplayString
			MAX-ACCESS read-only
			STATUS current
			DESCRIPTION
				"Last time SPF was executed in <HH>h<MM>m<SS>s format.
				
				XPath: /wing-stats/device[mac=key1]/ospf_stats/ip_ospf_stats/spf_executed_when"
			::= { wingStatsDevDynRouteIpOspfEntry 17 }

		
		-- 1.3.6.1.4.1.1916.2.131.50.1.4.2.34.1.1.18
		wingStatsDevDynRouteIpOspfTimerDueFlag OBJECT-TYPE
			SYNTAX TruthValue
			MAX-ACCESS read-only
			STATUS current
			DESCRIPTION
				"Whether SPF timer is due or not.
				
				XPath: /wing-stats/device[mac=key1]/ospf_stats/ip_ospf_stats/spf_timer_due_flag
				"
			::= { wingStatsDevDynRouteIpOspfEntry 18 }

		
		-- 1.3.6.1.4.1.1916.2.131.50.1.4.2.34.1.1.19
		wingStatsDevDynRouteIpOspfDueIn OBJECT-TYPE
			SYNTAX DisplayString
			MAX-ACCESS read-only
			STATUS current
			DESCRIPTION
				"Time SPF algorithm is due in <HH>h<MM>m<SS>s format.
				
				XPath: /wing-stats/device[mac=key1]/ospf_stats/ip_ospf_stats/spf_due_in"
			::= { wingStatsDevDynRouteIpOspfEntry 19 }

		
		-- 1.3.6.1.4.1.1916.2.131.50.1.4.2.34.1.1.20
		wingStatsDevDynRouteIpOspflsaRefreshTimer OBJECT-TYPE
			SYNTAX Unsigned32
			MAX-ACCESS read-only
			STATUS current
			DESCRIPTION
				"LSA refresh timer in seconds.
				
				XPath: /wing-stats/device[mac=key1]/ospf_stats/ip_ospf_stats/lsa_refresh_timer"
			::= { wingStatsDevDynRouteIpOspfEntry 20 }

		
		-- 1.3.6.1.4.1.1916.2.131.50.1.4.2.34.1.1.21
		wingStatsDevDynRouteIpOspfAbrFlag OBJECT-TYPE
			SYNTAX TruthValue
			MAX-ACCESS read-only
			STATUS current
			DESCRIPTION
				"Whether this router is an ABR.
				
				XPath: /wing-stats/device[mac=key1]/ospf_stats/ip_ospf_stats/abr_flag"
			::= { wingStatsDevDynRouteIpOspfEntry 21 }

		
		-- 1.3.6.1.4.1.1916.2.131.50.1.4.2.34.1.1.22
		wingStatsDevDynRouteIpOspfAbrType OBJECT-TYPE
			SYNTAX DisplayString
			MAX-ACCESS read-only
			STATUS current
			DESCRIPTION
				"Type of ABR.
				
				enum Unknown
				enum Standard (RFC2328)
				enum Alternative IBM
				enum Alternative CISCO
				enum Alternative Shortcut.
				
				XPath: /wing-stats/device[mac=key1]/ospf_stats/ip_ospf_stats/abr_type"
			::= { wingStatsDevDynRouteIpOspfEntry 22 }

		
		-- 1.3.6.1.4.1.1916.2.131.50.1.4.2.34.1.1.23
		wingStatsDevDynRouteIpOspfAsbrFlag OBJECT-TYPE
			SYNTAX TruthValue
			MAX-ACCESS read-only
			STATUS current
			DESCRIPTION
				"Whetner this router is an ASBR.
				
				XPath: /wing-stats/device[mac=key1]/ospf_stats/ip_ospf_stats/asbr_flag"
			::= { wingStatsDevDynRouteIpOspfEntry 23 }

		
		-- 1.3.6.1.4.1.1916.2.131.50.1.4.2.34.1.1.24
		wingStatsDevDynRouteIpOspfExtLsdbCount OBJECT-TYPE
			SYNTAX Counter64
			MAX-ACCESS read-only
			STATUS current
			DESCRIPTION
				"Number of external LSAs.
				
				XPath: /wing-stats/device[mac=key1]/ospf_stats/ip_ospf_stats/ext_lsdb_count"
			::= { wingStatsDevDynRouteIpOspfEntry 24 }

		
		-- 1.3.6.1.4.1.1916.2.131.50.1.4.2.34.1.1.25
		wingStatsDevDynRouteIpOspfExtLsdbCsum OBJECT-TYPE
			SYNTAX Unsigned32
			MAX-ACCESS read-only
			STATUS current
			DESCRIPTION
				"External LSA checksum.
				
				XPath: /wing-stats/device[mac=key1]/ospf_stats/ip_ospf_stats/ext_lsdb_csum"
			::= { wingStatsDevDynRouteIpOspfEntry 25 }

		
		-- 1.3.6.1.4.1.1916.2.131.50.1.4.2.34.1.1.26
		wingStatsDevDynRouteIpOspfOpaqueLsdbCount OBJECT-TYPE
			SYNTAX Counter64
			MAX-ACCESS read-only
			STATUS current
			DESCRIPTION
				"Number of opaque AS LSAs.
				
				XPath: /wing-stats/device[mac=key1]/ospf_stats/ip_ospf_stats/opaque_lsdb_count"
			::= { wingStatsDevDynRouteIpOspfEntry 26 }

		
		-- 1.3.6.1.4.1.1916.2.131.50.1.4.2.34.1.1.27
		wingStatsDevDynRouteIpOspfOpaqueExtLsdbCsum OBJECT-TYPE
			SYNTAX Unsigned32
			MAX-ACCESS read-only
			STATUS current
			DESCRIPTION
				"Opaque AS LSA checksum.
				
				XPath: /wing-stats/device[mac=key1]/ospf_stats/ip_ospf_stats/opaque_ext_lsdb_csum"
			::= { wingStatsDevDynRouteIpOspfEntry 27 }

		
		-- 1.3.6.1.4.1.1916.2.131.50.1.4.2.34.1.1.28
		wingStatsDevDynRouteIpOspfNumAreasAttached OBJECT-TYPE
			SYNTAX Unsigned32
			MAX-ACCESS read-only
			STATUS current
			DESCRIPTION
				"Number of OSPF areas attached to this router.
				
				XPath: /wing-stats/device[mac=key1]/ospf_stats/ip_ospf_stats/num_areas_attached"
			::= { wingStatsDevDynRouteIpOspfEntry 28 }

		
		-- 1.3.6.1.4.1.1916.2.131.50.1.4.2.34.1.1.29
		wingStatsDevDynRouteIpOspfMaxRoutes OBJECT-TYPE
			SYNTAX Unsigned32
			MAX-ACCESS read-only
			STATUS current
			DESCRIPTION
				"Maximum number of OSPF routes allowed.
				
				XPath: /wing-stats/device[mac=key1]/ospf_stats/ip_ospf_state/ospf_max_routes"
			::= { wingStatsDevDynRouteIpOspfEntry 29 }

		
		-- 1.3.6.1.4.1.1916.2.131.50.1.4.2.34.1.1.30
		wingStatsDevDynRouteIpOspfRoutesReceived OBJECT-TYPE
			SYNTAX Unsigned32
			MAX-ACCESS read-only
			STATUS current
			DESCRIPTION
				"Number of OSPF routes received so far.
				
				XPath: /wing-stats/device[mac=key1]/ospf_stats/ip_ospf_state/ospf_routes_received"
			::= { wingStatsDevDynRouteIpOspfEntry 30 }

		
		-- 1.3.6.1.4.1.1916.2.131.50.1.4.2.34.1.1.31
		wingStatsDevDynRouteIpOspfMaxIgnoreStateCount OBJECT-TYPE
			SYNTAX Unsigned32
			MAX-ACCESS read-only
			STATUS current
			DESCRIPTION
				"Maximum number of times ospfd can be put in ignore state before entering permanent ignore state.
				
				XPath: /wing-stats/device[mac=key1]/ospf_stats/ip_ospf_state/ospf_max_ignore_state_count"
			::= { wingStatsDevDynRouteIpOspfEntry 31 }

		
		-- 1.3.6.1.4.1.1916.2.131.50.1.4.2.34.1.1.32
		wingStatsDevDynRouteIpOspfIgnoreStateCount OBJECT-TYPE
			SYNTAX Unsigned32
			MAX-ACCESS read-only
			STATUS current
			DESCRIPTION
				"Number of times ospfd has been put in ignore state.
				
				XPath: /wing-stats/device[mac=key1]/ospf_stats/ip_ospf_state/ospf_ignore_state_count"
			::= { wingStatsDevDynRouteIpOspfEntry 32 }

		
		-- 1.3.6.1.4.1.1916.2.131.50.1.4.2.34.1.1.33
		wingStatsDevDynRouteIpOspfIgnoreStateTimeout OBJECT-TYPE
			SYNTAX Unsigned32
			MAX-ACCESS read-only
			STATUS current
			DESCRIPTION
				"Time after which ospfd shall exit the ignore state.
				
				XPath: /wing-stats/device[mac=key1]/ospf_stats/ip_ospf_state/ospf_ignore_state_timeout"
			::= { wingStatsDevDynRouteIpOspfEntry 33 }

		
		-- 1.3.6.1.4.1.1916.2.131.50.1.4.2.34.1.1.34
		wingStatsDevDynRouteIpOspfIgnoreStateMonitorTimeout OBJECT-TYPE
			SYNTAX Unsigned32
			MAX-ACCESS read-only
			STATUS current
			DESCRIPTION
				"Time after which ignore state count is reset to zero and ospfd continues in the state it was.
				
				XPath: /wing-stats/device[mac=key1]/ospf_stats/ip_ospf_state/ospf_ignore_state_monitor_timeout"
			::= { wingStatsDevDynRouteIpOspfEntry 34 }

		
		-- 1.3.6.1.4.1.1916.2.131.50.1.4.2.34.1.1.35
		wingStatsDevDynRouteIpOspfState OBJECT-TYPE
			SYNTAX DisplayString
			MAX-ACCESS read-only
			STATUS current
			DESCRIPTION
				"current state of ospfd.
				Running,
				Temporary ignore,
				Permanent ignore
				
				XPath: /wing-stats/device[mac=key1]/ospf_stats/ip_ospf_state/ospf_state"
			::= { wingStatsDevDynRouteIpOspfEntry 35 }

		
		-- 1.3.6.1.4.1.1916.2.131.50.1.4.2.34.2
		wingStatsDevDynRouteOspfAreaTable OBJECT-TYPE
			SYNTAX SEQUENCE OF WingStatsDevDynRouteOspfAreaEntry
			MAX-ACCESS not-accessible
			STATUS current
			DESCRIPTION
				"Ospf Area Stats"
			::= { wingStatsDevDynRoute 2 }

		
		-- 1.3.6.1.4.1.1916.2.131.50.1.4.2.34.2.1
		wingStatsDevDynRouteOspfAreaEntry OBJECT-TYPE
			SYNTAX WingStatsDevDynRouteOspfAreaEntry
			MAX-ACCESS not-accessible
			STATUS current
			DESCRIPTION
				"An entry in the table."
			INDEX { wingStatsDevMac, wingStatsDevDynRouteOspfAreaId }
			::= { wingStatsDevDynRouteOspfAreaTable 1 }

		
		WingStatsDevDynRouteOspfAreaEntry ::=
			SEQUENCE { 
				wingStatsDevDynRouteOspfAreaId
					WingIdentifier,
				wingStatsDevDynRouteOspfAreaType
					DisplayString,
				wingStatsDevDynRouteOspfAreaBackboneFlag
					TruthValue,
				wingStatsDevDynRouteOspfAreaNoSummaryFlag
					TruthValue,
				wingStatsDevDynRouteOspfAreaShortcutType
					DisplayString,
				wingStatsDevDynRouteOspfAreaShortcutCapability
					TruthValue,
				wingStatsDevDynRouteOspfAreaInterfaceNum
					Unsigned32,
				wingStatsDevDynRouteOspfAreaActiveInterfaces
					Unsigned32,
				wingStatsDevDynRouteOspfAreaNssaFlag
					TruthValue,
				wingStatsDevDynRouteOspfAreaNssaTransType
					DisplayString,
				wingStatsDevDynRouteOspfAreaStubRouterStateFlag
					TruthValue,
				wingStatsDevDynRouteOspfAreaAdminStubRoutedFlag
					TruthValue,
				wingStatsDevDynRouteOspfAreaStartupTimeDue
					DisplayString,
				wingStatsDevDynRouteOspfAreaNumFullyAdjNbrs
					Unsigned32,
				wingStatsDevDynRouteOspfAreaAuthType
					DisplayString,
				wingStatsDevDynRouteOspfAreaNumFullVirtualAdj
					Unsigned32,
				wingStatsDevDynRouteOspfAreaNumSpfExecuted
					Unsigned32,
				wingStatsDevDynRouteOspfAreaNumTotalLsa
					Counter64,
				wingStatsDevDynRouteOspfAreaNumRouterLsa
					Counter64,
				wingStatsDevDynRouteOspfAreaRouterLsaCsum
					Unsigned32,
				wingStatsDevDynRouteOspfAreaNumNetworkLsa
					Counter64,
				wingStatsDevDynRouteOspfAreaNetworkLsaCsum
					Unsigned32,
				wingStatsDevDynRouteOspfAreaNumSummaryLsa
					Counter64,
				wingStatsDevDynRouteOspfAreaSummaryLsaCsum
					Unsigned32,
				wingStatsDevDynRouteOspfAreaNumAsbrSummaryLsa
					Counter64,
				wingStatsDevDynRouteOspfAreaAsbrSummaryLsaCsum
					Unsigned32,
				wingStatsDevDynRouteOspfAreaNumNssaLsa
					Counter64,
				wingStatsDevDynRouteOspfAreaNssaLsaCsum
					Unsigned32,
				wingStatsDevDynRouteOspfAreaNumOpaqueLinkLsa
					Counter64,
				wingStatsDevDynRouteOspfAreaOpaqueLinkLsaCsum
					Unsigned32,
				wingStatsDevDynRouteOspfAreaNumOpaqueAreaLsa
					Counter64,
				wingStatsDevDynRouteOspfAreaOpaqueAreaLsaCsum
					Unsigned32
			 }

		-- 1.3.6.1.4.1.1916.2.131.50.1.4.2.34.2.1.1
		wingStatsDevDynRouteOspfAreaId OBJECT-TYPE
			SYNTAX WingIdentifier
			MAX-ACCESS read-only
			STATUS current
			DESCRIPTION
				"OSPF area-id.
				
				XPath: /wing-stats/device[mac=key1]/ospf_stats/ip_ospf_stats/ospf_area_stats[ospf_area_id=key2]/ospf_area_id"
			::= { wingStatsDevDynRouteOspfAreaEntry 1 }

		
		-- 1.3.6.1.4.1.1916.2.131.50.1.4.2.34.2.1.2
		wingStatsDevDynRouteOspfAreaType OBJECT-TYPE
			SYNTAX DisplayString
			MAX-ACCESS read-only
			STATUS current
			DESCRIPTION
				"Type of this OSPF area.
				
				XPath: /wing-stats/device[mac=key1]/ospf_stats/ip_ospf_stats/ospf_area_stats[ospf_area_id=key2]/area_type"
			::= { wingStatsDevDynRouteOspfAreaEntry 2 }

		
		-- 1.3.6.1.4.1.1916.2.131.50.1.4.2.34.2.1.3
		wingStatsDevDynRouteOspfAreaBackboneFlag OBJECT-TYPE
			SYNTAX TruthValue
			MAX-ACCESS read-only
			STATUS current
			DESCRIPTION
				"Whether this area is backbone.
				
				XPath: /wing-stats/device[mac=key1]/ospf_stats/ip_ospf_stats/ospf_area_stats[ospf_area_id=key2]/backbone_flag"
			::= { wingStatsDevDynRouteOspfAreaEntry 3 }

		
		-- 1.3.6.1.4.1.1916.2.131.50.1.4.2.34.2.1.4
		wingStatsDevDynRouteOspfAreaNoSummaryFlag OBJECT-TYPE
			SYNTAX TruthValue
			MAX-ACCESS read-only
			STATUS current
			DESCRIPTION
				"Whether to inject inter-area routes into stub.
				
				XPath: /wing-stats/device[mac=key1]/ospf_stats/ip_ospf_stats/ospf_area_stats[ospf_area_id=key2]/no_summary_flag"
			::= { wingStatsDevDynRouteOspfAreaEntry 4 }

		
		-- 1.3.6.1.4.1.1916.2.131.50.1.4.2.34.2.1.5
		wingStatsDevDynRouteOspfAreaShortcutType OBJECT-TYPE
			SYNTAX DisplayString
			MAX-ACCESS read-only
			STATUS current
			DESCRIPTION
				"Shortcutting mode of this area.
				
				XPath: /wing-stats/device[mac=key1]/ospf_stats/ip_ospf_stats/ospf_area_stats[ospf_area_id=key2]/shortcut_type"
			::= { wingStatsDevDynRouteOspfAreaEntry 5 }

		
		-- 1.3.6.1.4.1.1916.2.131.50.1.4.2.34.2.1.6
		wingStatsDevDynRouteOspfAreaShortcutCapability OBJECT-TYPE
			SYNTAX TruthValue
			MAX-ACCESS read-only
			STATUS current
			DESCRIPTION
				"Whether other ABRs agree on S-bit.
				
				XPath: /wing-stats/device[mac=key1]/ospf_stats/ip_ospf_stats/ospf_area_stats[ospf_area_id=key2]/shortcut_capability"
			::= { wingStatsDevDynRouteOspfAreaEntry 6 }

		
		-- 1.3.6.1.4.1.1916.2.131.50.1.4.2.34.2.1.7
		wingStatsDevDynRouteOspfAreaInterfaceNum OBJECT-TYPE
			SYNTAX Unsigned32
			MAX-ACCESS read-only
			STATUS current
			DESCRIPTION
				"Total number of OSPF interfaces in this area.
				
				XPath: /wing-stats/device[mac=key1]/ospf_stats/ip_ospf_stats/ospf_area_stats[ospf_area_id=key2]/num_ospf_inf"
			::= { wingStatsDevDynRouteOspfAreaEntry 7 }

		
		-- 1.3.6.1.4.1.1916.2.131.50.1.4.2.34.2.1.8
		wingStatsDevDynRouteOspfAreaActiveInterfaces OBJECT-TYPE
			SYNTAX Unsigned32
			MAX-ACCESS read-only
			STATUS current
			DESCRIPTION
				"Total number of active OSPF interfaces in this area.
				
				XPath: /wing-stats/device[mac=key1]/ospf_stats/ip_ospf_stats/ospf_area_stats[ospf_area_id=key2]/num_active_ospf_inf"
			::= { wingStatsDevDynRouteOspfAreaEntry 8 }

		
		-- 1.3.6.1.4.1.1916.2.131.50.1.4.2.34.2.1.9
		wingStatsDevDynRouteOspfAreaNssaFlag OBJECT-TYPE
			SYNTAX TruthValue
			MAX-ACCESS read-only
			STATUS current
			DESCRIPTION
				"Whether this area is NSSA.
				
				XPath: /wing-stats/device[mac=key1]/ospf_stats/ip_ospf_stats/ospf_area_stats[ospf_area_id=key2]/nssa_area_flag"
			::= { wingStatsDevDynRouteOspfAreaEntry 9 }

		
		-- 1.3.6.1.4.1.1916.2.131.50.1.4.2.34.2.1.10
		wingStatsDevDynRouteOspfAreaNssaTransType OBJECT-TYPE
			SYNTAX DisplayString
			MAX-ACCESS read-only
			STATUS current
			DESCRIPTION
				"LSA type7 to LSA type5 translation in NSSA.
				
				XPath: /wing-stats/device[mac=key1]/ospf_stats/ip_ospf_stats/ospf_area_stats[ospf_area_id=key2]/nssa_translator_type"
			::= { wingStatsDevDynRouteOspfAreaEntry 10 }

		
		-- 1.3.6.1.4.1.1916.2.131.50.1.4.2.34.2.1.11
		wingStatsDevDynRouteOspfAreaStubRouterStateFlag OBJECT-TYPE
			SYNTAX TruthValue
			MAX-ACCESS read-only
			STATUS current
			DESCRIPTION
				"Whether the router is in STUB state for this area.
				
				XPath: /wing-stats/device[mac=key1]/ospf_stats/ip_ospf_stats/ospf_area_stats[ospf_area_id=key2]/stub_router_state_flag"
			::= { wingStatsDevDynRouteOspfAreaEntry 11 }

		
		-- 1.3.6.1.4.1.1916.2.131.50.1.4.2.34.2.1.12
		wingStatsDevDynRouteOspfAreaAdminStubRoutedFlag OBJECT-TYPE
			SYNTAX TruthValue
			MAX-ACCESS read-only
			STATUS current
			DESCRIPTION
				"Admin stub router state.
				
				XPath: /wing-stats/device[mac=key1]/ospf_stats/ip_ospf_stats/ospf_area_stats[ospf_area_id=key2]/admin_stub_routed_flag"
			::= { wingStatsDevDynRouteOspfAreaEntry 12 }

		
		-- 1.3.6.1.4.1.1916.2.131.50.1.4.2.34.2.1.13
		wingStatsDevDynRouteOspfAreaStartupTimeDue OBJECT-TYPE
			SYNTAX DisplayString
			MAX-ACCESS read-only
			STATUS current
			DESCRIPTION
				"Time remaining to enter STUB state in <HH>h<MM>m<SS>s format.
				
				XPath: /wing-stats/device[mac=key1]/ospf_stats/ip_ospf_stats/ospf_area_stats[ospf_area_id=key2]/startup_time_due"
			::= { wingStatsDevDynRouteOspfAreaEntry 13 }

		
		-- 1.3.6.1.4.1.1916.2.131.50.1.4.2.34.2.1.14
		wingStatsDevDynRouteOspfAreaNumFullyAdjNbrs OBJECT-TYPE
			SYNTAX Unsigned32
			MAX-ACCESS read-only
			STATUS current
			DESCRIPTION
				"Number of fully adjacent neighbors in this area.
				
				XPath: /wing-stats/device[mac=key1]/ospf_stats/ip_ospf_stats/ospf_area_stats[ospf_area_id=key2]/num_fully_adj_nbrs"
			::= { wingStatsDevDynRouteOspfAreaEntry 14 }

		
		-- 1.3.6.1.4.1.1916.2.131.50.1.4.2.34.2.1.15
		wingStatsDevDynRouteOspfAreaAuthType OBJECT-TYPE
			SYNTAX DisplayString
			MAX-ACCESS read-only
			STATUS current
			DESCRIPTION
				"Authentication type of OSPF area.
				
				XPath: /wing-stats/device[mac=key1]/ospf_stats/ip_ospf_stats/ospf_area_stats[ospf_area_id=key2]/auth_type"
			::= { wingStatsDevDynRouteOspfAreaEntry 15 }

		
		-- 1.3.6.1.4.1.1916.2.131.50.1.4.2.34.2.1.16
		wingStatsDevDynRouteOspfAreaNumFullVirtualAdj OBJECT-TYPE
			SYNTAX Unsigned32
			MAX-ACCESS read-only
			STATUS current
			DESCRIPTION
				"Number of full virtual adjacencies going through this area.
				
				XPath: /wing-stats/device[mac=key1]/ospf_stats/ip_ospf_stats/ospf_area_stats[ospf_area_id=key2]/num_full_virt_adj"
			::= { wingStatsDevDynRouteOspfAreaEntry 16 }

		
		-- 1.3.6.1.4.1.1916.2.131.50.1.4.2.34.2.1.17
		wingStatsDevDynRouteOspfAreaNumSpfExecuted OBJECT-TYPE
			SYNTAX Unsigned32
			MAX-ACCESS read-only
			STATUS current
			DESCRIPTION
				"Number of times SPF algorithm executed.
				
				XPath: /wing-stats/device[mac=key1]/ospf_stats/ip_ospf_stats/ospf_area_stats[ospf_area_id=key2]/num_spf_executed"
			::= { wingStatsDevDynRouteOspfAreaEntry 17 }

		
		-- 1.3.6.1.4.1.1916.2.131.50.1.4.2.34.2.1.18
		wingStatsDevDynRouteOspfAreaNumTotalLsa OBJECT-TYPE
			SYNTAX Counter64
			MAX-ACCESS read-only
			STATUS current
			DESCRIPTION
				"Total nimber of LSAs.
				
				XPath: /wing-stats/device[mac=key1]/ospf_stats/ip_ospf_stats/ospf_area_stats[ospf_area_id=key2]/num_total_lsa"
			::= { wingStatsDevDynRouteOspfAreaEntry 18 }

		
		-- 1.3.6.1.4.1.1916.2.131.50.1.4.2.34.2.1.19
		wingStatsDevDynRouteOspfAreaNumRouterLsa OBJECT-TYPE
			SYNTAX Counter64
			MAX-ACCESS read-only
			STATUS current
			DESCRIPTION
				"Number of router LSAs.
				
				XPath: /wing-stats/device[mac=key1]/ospf_stats/ip_ospf_stats/ospf_area_stats[ospf_area_id=key2]/num_router_lsa"
			::= { wingStatsDevDynRouteOspfAreaEntry 19 }

		
		-- 1.3.6.1.4.1.1916.2.131.50.1.4.2.34.2.1.20
		wingStatsDevDynRouteOspfAreaRouterLsaCsum OBJECT-TYPE
			SYNTAX Unsigned32
			MAX-ACCESS read-only
			STATUS current
			DESCRIPTION
				"Router LSA checksum
				
				XPath: /wing-stats/device[mac=key1]/ospf_stats/ip_ospf_stats/ospf_area_stats[ospf_area_id=key2]/router_lsa_csum"
			::= { wingStatsDevDynRouteOspfAreaEntry 20 }

		
		-- 1.3.6.1.4.1.1916.2.131.50.1.4.2.34.2.1.21
		wingStatsDevDynRouteOspfAreaNumNetworkLsa OBJECT-TYPE
			SYNTAX Counter64
			MAX-ACCESS read-only
			STATUS current
			DESCRIPTION
				"Number of network LSAs.
				
				XPath: /wing-stats/device[mac=key1]/ospf_stats/ip_ospf_stats/ospf_area_stats[ospf_area_id=key2]/num_network_lsa"
			::= { wingStatsDevDynRouteOspfAreaEntry 21 }

		
		-- 1.3.6.1.4.1.1916.2.131.50.1.4.2.34.2.1.22
		wingStatsDevDynRouteOspfAreaNetworkLsaCsum OBJECT-TYPE
			SYNTAX Unsigned32
			MAX-ACCESS read-only
			STATUS current
			DESCRIPTION
				"Network LSA checksum.
				
				XPath: /wing-stats/device[mac=key1]/ospf_stats/ip_ospf_stats/ospf_area_stats[ospf_area_id=key2]/network_lsa_csum"
			::= { wingStatsDevDynRouteOspfAreaEntry 22 }

		
		-- 1.3.6.1.4.1.1916.2.131.50.1.4.2.34.2.1.23
		wingStatsDevDynRouteOspfAreaNumSummaryLsa OBJECT-TYPE
			SYNTAX Counter64
			MAX-ACCESS read-only
			STATUS current
			DESCRIPTION
				"Number of summary LSAs.
				
				XPath: /wing-stats/device[mac=key1]/ospf_stats/ip_ospf_stats/ospf_area_stats[ospf_area_id=key2]/num_summary_lsa"
			::= { wingStatsDevDynRouteOspfAreaEntry 23 }

		
		-- 1.3.6.1.4.1.1916.2.131.50.1.4.2.34.2.1.24
		wingStatsDevDynRouteOspfAreaSummaryLsaCsum OBJECT-TYPE
			SYNTAX Unsigned32
			MAX-ACCESS read-only
			STATUS current
			DESCRIPTION
				"Summary LSA checksum.
				
				XPath: /wing-stats/device[mac=key1]/ospf_stats/ip_ospf_stats/ospf_area_stats[ospf_area_id=key2]/summary_lsa_csum"
			::= { wingStatsDevDynRouteOspfAreaEntry 24 }

		
		-- 1.3.6.1.4.1.1916.2.131.50.1.4.2.34.2.1.25
		wingStatsDevDynRouteOspfAreaNumAsbrSummaryLsa OBJECT-TYPE
			SYNTAX Counter64
			MAX-ACCESS read-only
			STATUS current
			DESCRIPTION
				"Number of ASBR LSAs.
				
				XPath: /wing-stats/device[mac=key1]/ospf_stats/ip_ospf_stats/ospf_area_stats[ospf_area_id=key2]/num_asbr_summary_lsa"
			::= { wingStatsDevDynRouteOspfAreaEntry 25 }

		
		-- 1.3.6.1.4.1.1916.2.131.50.1.4.2.34.2.1.26
		wingStatsDevDynRouteOspfAreaAsbrSummaryLsaCsum OBJECT-TYPE
			SYNTAX Unsigned32
			MAX-ACCESS read-only
			STATUS current
			DESCRIPTION
				"ASBR LSA checksum.
				
				XPath: /wing-stats/device[mac=key1]/ospf_stats/ip_ospf_stats/ospf_area_stats[ospf_area_id=key2]/asbr_summary_lsa_csum"
			::= { wingStatsDevDynRouteOspfAreaEntry 26 }

		
		-- 1.3.6.1.4.1.1916.2.131.50.1.4.2.34.2.1.27
		wingStatsDevDynRouteOspfAreaNumNssaLsa OBJECT-TYPE
			SYNTAX Counter64
			MAX-ACCESS read-only
			STATUS current
			DESCRIPTION
				"Number of NSSA LSAs.
				
				XPath: /wing-stats/device[mac=key1]/ospf_stats/ip_ospf_stats/ospf_area_stats[ospf_area_id=key2]/num_nssa_lsa"
			::= { wingStatsDevDynRouteOspfAreaEntry 27 }

		
		-- 1.3.6.1.4.1.1916.2.131.50.1.4.2.34.2.1.28
		wingStatsDevDynRouteOspfAreaNssaLsaCsum OBJECT-TYPE
			SYNTAX Unsigned32
			MAX-ACCESS read-only
			STATUS current
			DESCRIPTION
				"NSSA LSA checksum.
				
				XPath: /wing-stats/device[mac=key1]/ospf_stats/ip_ospf_stats/ospf_area_stats[ospf_area_id=key2]/nssa_lsa_csum"
			::= { wingStatsDevDynRouteOspfAreaEntry 28 }

		
		-- 1.3.6.1.4.1.1916.2.131.50.1.4.2.34.2.1.29
		wingStatsDevDynRouteOspfAreaNumOpaqueLinkLsa OBJECT-TYPE
			SYNTAX Counter64
			MAX-ACCESS read-only
			STATUS current
			DESCRIPTION
				"Number of opaque link LSAs.
				
				XPath: /wing-stats/device[mac=key1]/ospf_stats/ip_ospf_stats/ospf_area_stats[ospf_area_id=key2]/num_opaque_link_lsa"
			::= { wingStatsDevDynRouteOspfAreaEntry 29 }

		
		-- 1.3.6.1.4.1.1916.2.131.50.1.4.2.34.2.1.30
		wingStatsDevDynRouteOspfAreaOpaqueLinkLsaCsum OBJECT-TYPE
			SYNTAX Unsigned32
			MAX-ACCESS read-only
			STATUS current
			DESCRIPTION
				"Opaque link LSA checksum.
				
				XPath: /wing-stats/device[mac=key1]/ospf_stats/ip_ospf_stats/ospf_area_stats[ospf_area_id=key2]/opaque_link_lsa_csum"
			::= { wingStatsDevDynRouteOspfAreaEntry 30 }

		
		-- 1.3.6.1.4.1.1916.2.131.50.1.4.2.34.2.1.31
		wingStatsDevDynRouteOspfAreaNumOpaqueAreaLsa OBJECT-TYPE
			SYNTAX Counter64
			MAX-ACCESS read-only
			STATUS current
			DESCRIPTION
				"Number of opaque area LSAs.
				
				XPath: /wing-stats/device[mac=key1]/ospf_stats/ip_ospf_stats/ospf_area_stats[ospf_area_id=key2]/num_opaque_area_lsa"
			::= { wingStatsDevDynRouteOspfAreaEntry 31 }

		
		-- 1.3.6.1.4.1.1916.2.131.50.1.4.2.34.2.1.32
		wingStatsDevDynRouteOspfAreaOpaqueAreaLsaCsum OBJECT-TYPE
			SYNTAX Unsigned32
			MAX-ACCESS read-only
			STATUS current
			DESCRIPTION
				"Opaque area LSA checksum.
				
				XPath: /wing-stats/device[mac=key1]/ospf_stats/ip_ospf_stats/ospf_area_stats[ospf_area_id=key2]/opaque_area_lsa_csum"
			::= { wingStatsDevDynRouteOspfAreaEntry 32 }

		
		-- 1.3.6.1.4.1.1916.2.131.50.1.4.2.34.3
		wingStatsDevDynRouteIpOspfNetworkRoutesTable OBJECT-TYPE
			SYNTAX SEQUENCE OF WingStatsDevDynRouteIpOspfNetworkRoutesEntry
			MAX-ACCESS not-accessible
			STATUS current
			DESCRIPTION
				"Description."
			::= { wingStatsDevDynRoute 3 }

		
		-- 1.3.6.1.4.1.1916.2.131.50.1.4.2.34.3.1
		wingStatsDevDynRouteIpOspfNetworkRoutesEntry OBJECT-TYPE
			SYNTAX WingStatsDevDynRouteIpOspfNetworkRoutesEntry
			MAX-ACCESS not-accessible
			STATUS current
			DESCRIPTION
				"Description."
			INDEX { wingStatsDevMac, wingStatsDevDynRouteIpOspfNetworkRoute }
			::= { wingStatsDevDynRouteIpOspfNetworkRoutesTable 1 }

		
		WingStatsDevDynRouteIpOspfNetworkRoutesEntry ::=
			SEQUENCE { 
				wingStatsDevDynRouteIpOspfNetworkRoute
					WingIdentifier,
				wingStatsDevDynRouteIpOspfNetworkRoutesPathType
					DisplayString,
				wingStatsDevDynRouteIpOspfNetworkRoutesDestType
					DisplayString,
				wingStatsDevDynRouteIpOspfNetworkRoutesCost
					Unsigned32,
				wingStatsDevDynRouteIpOspfNetworkRoutesArea
					DisplayString
			 }

		-- 1.3.6.1.4.1.1916.2.131.50.1.4.2.34.3.1.1
		wingStatsDevDynRouteIpOspfNetworkRoute OBJECT-TYPE
			SYNTAX WingIdentifier
			MAX-ACCESS read-only
			STATUS current
			DESCRIPTION
				"Network represented in IP-Address/Mask format.
				
				XPath: /wing-stats/device[mac=key1]/ospf_stats/network_routes[network=key2]/network"
			::= { wingStatsDevDynRouteIpOspfNetworkRoutesEntry 1 }

		
		-- 1.3.6.1.4.1.1916.2.131.50.1.4.2.34.3.1.2
		wingStatsDevDynRouteIpOspfNetworkRoutesPathType OBJECT-TYPE
			SYNTAX DisplayString
			MAX-ACCESS read-only
			STATUS current
			DESCRIPTION
				"Type of this OSPF network.
				
				XPath: /wing-stats/device[mac=key1]/ospf_stats/network_routes[network=key2]/path_type"
			::= { wingStatsDevDynRouteIpOspfNetworkRoutesEntry 2 }

		
		-- 1.3.6.1.4.1.1916.2.131.50.1.4.2.34.3.1.3
		wingStatsDevDynRouteIpOspfNetworkRoutesDestType OBJECT-TYPE
			SYNTAX DisplayString
			MAX-ACCESS read-only
			STATUS current
			DESCRIPTION
				"Dest Type.
				
				XPath: /wing-stats/device[mac=key1]/ospf_stats/network_routes[network=key2]/dest_type"
			::= { wingStatsDevDynRouteIpOspfNetworkRoutesEntry 3 }

		
		-- 1.3.6.1.4.1.1916.2.131.50.1.4.2.34.3.1.4
		wingStatsDevDynRouteIpOspfNetworkRoutesCost OBJECT-TYPE
			SYNTAX Unsigned32
			MAX-ACCESS read-only
			STATUS current
			DESCRIPTION
				"Cost of this OSPF network.
				
				XPath: /wing-stats/device[mac=key1]/ospf_stats/network_routes[network=key2]/cost"
			::= { wingStatsDevDynRouteIpOspfNetworkRoutesEntry 4 }

		
		-- 1.3.6.1.4.1.1916.2.131.50.1.4.2.34.3.1.5
		wingStatsDevDynRouteIpOspfNetworkRoutesArea OBJECT-TYPE
			SYNTAX DisplayString
			MAX-ACCESS read-only
			STATUS current
			DESCRIPTION
				"Routes Area.
				
				XPath: /wing-stats/device[mac=key1]/ospf_stats/network_routes[network=key2]/area"
			::= { wingStatsDevDynRouteIpOspfNetworkRoutesEntry 5 }

		
		-- 1.3.6.1.4.1.1916.2.131.50.1.4.2.34.4
		wingStatsDevDynRouteIpOspfNetworkRoutesMPathsTable OBJECT-TYPE
			SYNTAX SEQUENCE OF WingStatsDevDynRouteIpOspfNetworkRoutesMPathsEntry
			MAX-ACCESS not-accessible
			STATUS current
			DESCRIPTION
				"Description."
			::= { wingStatsDevDynRoute 4 }

		
		-- 1.3.6.1.4.1.1916.2.131.50.1.4.2.34.4.1
		wingStatsDevDynRouteIpOspfNetworkRoutesMPathsEntry OBJECT-TYPE
			SYNTAX WingStatsDevDynRouteIpOspfNetworkRoutesMPathsEntry
			MAX-ACCESS not-accessible
			STATUS current
			DESCRIPTION
				"Description."
			INDEX { wingStatsDevMac, wingStatsDevDynRouteIpOspfNetworkRoute, wingStatsDevDynRouteIpOspfNetworkRoutesMPathsIndex }
			::= { wingStatsDevDynRouteIpOspfNetworkRoutesMPathsTable 1 }

		
		WingStatsDevDynRouteIpOspfNetworkRoutesMPathsEntry ::=
			SEQUENCE { 
				wingStatsDevDynRouteIpOspfNetworkRoutesMPathsIndex
					Unsigned32,
				wingStatsDevDynRouteIpOspfNetworkRoutesAttachedFlags
					TruthValue,
				wingStatsDevDynRouteIpOspfNetworkRoutesIfName
					DisplayString,
				wingStatsDevDynRouteIpOspfNetworkRoutesNextHop
					DisplayString
			 }

		-- 1.3.6.1.4.1.1916.2.131.50.1.4.2.34.4.1.1
		wingStatsDevDynRouteIpOspfNetworkRoutesMPathsIndex OBJECT-TYPE
			SYNTAX Unsigned32 (1..4294967295)
			MAX-ACCESS read-only
			STATUS current
			DESCRIPTION
				"Network routes multipath table index.
				
				XPath: /wing-stats/device[mac=key1]/ospf_stats/network_routes[network=key2]/multipaths[m_path_index=key3]/m_path_index"
			::= { wingStatsDevDynRouteIpOspfNetworkRoutesMPathsEntry 1 }

		
		-- 1.3.6.1.4.1.1916.2.131.50.1.4.2.34.4.1.2
		wingStatsDevDynRouteIpOspfNetworkRoutesAttachedFlags OBJECT-TYPE
			SYNTAX TruthValue
			MAX-ACCESS read-only
			STATUS current
			DESCRIPTION
				"Whether the network is directly connected or not
				
				XPath: /wing-stats/device[mac=key1]/ospf_stats/network_routes[network=key2]/multipaths[m_path_index=key3]/attached_flag"
			::= { wingStatsDevDynRouteIpOspfNetworkRoutesMPathsEntry 2 }

		
		-- 1.3.6.1.4.1.1916.2.131.50.1.4.2.34.4.1.3
		wingStatsDevDynRouteIpOspfNetworkRoutesIfName OBJECT-TYPE
			SYNTAX DisplayString
			MAX-ACCESS read-only
			STATUS current
			DESCRIPTION
				"Name of the interface to which the network is attached.
				
				XPath: /wing-stats/device[mac=key1]/ospf_stats/network_routes[network=key2]/multipaths[m_path_index=key3]/ifname"
			::= { wingStatsDevDynRouteIpOspfNetworkRoutesMPathsEntry 3 }

		
		-- 1.3.6.1.4.1.1916.2.131.50.1.4.2.34.4.1.4
		wingStatsDevDynRouteIpOspfNetworkRoutesNextHop OBJECT-TYPE
			SYNTAX DisplayString
			MAX-ACCESS read-only
			STATUS current
			DESCRIPTION
				"Next hop through which the network is reachable.
				
				XPath: /wing-stats/device[mac=key1]/ospf_stats/network_routes[network=key2]/multipaths[m_path_index=key3]/next_hop"
			::= { wingStatsDevDynRouteIpOspfNetworkRoutesMPathsEntry 4 }

		
		-- 1.3.6.1.4.1.1916.2.131.50.1.4.2.34.5
		wingStatsDevDynRouteIpOspfRouterRoutesTable OBJECT-TYPE
			SYNTAX SEQUENCE OF WingStatsDevDynRouteIpOspfRouterRoutesEntry
			MAX-ACCESS not-accessible
			STATUS current
			DESCRIPTION
				"Description."
			::= { wingStatsDevDynRoute 5 }

		
		-- 1.3.6.1.4.1.1916.2.131.50.1.4.2.34.5.1
		wingStatsDevDynRouteIpOspfRouterRoutesEntry OBJECT-TYPE
			SYNTAX WingStatsDevDynRouteIpOspfRouterRoutesEntry
			MAX-ACCESS not-accessible
			STATUS current
			DESCRIPTION
				"Description."
			INDEX { wingCfgDevMac, wingStatsDevDynRouteIpOspfRouterRoute }
			::= { wingStatsDevDynRouteIpOspfRouterRoutesTable 1 }

		
		WingStatsDevDynRouteIpOspfRouterRoutesEntry ::=
			SEQUENCE { 
				wingStatsDevDynRouteIpOspfRouterRoute
					WingIdentifier
			 }

		-- 1.3.6.1.4.1.1916.2.131.50.1.4.2.34.5.1.1
		wingStatsDevDynRouteIpOspfRouterRoute OBJECT-TYPE
			SYNTAX WingIdentifier
			MAX-ACCESS read-only
			STATUS current
			DESCRIPTION
				"Router IP address.
				
				XPath: /wing-stats/device[mac=key1]/ospf_stats/router_routes[router=key2]/router
				"
			::= { wingStatsDevDynRouteIpOspfRouterRoutesEntry 1 }

		
		-- 1.3.6.1.4.1.1916.2.131.50.1.4.2.34.6
		wingStatsDevDynRouteIpOspfRouterRoutesInfoTable OBJECT-TYPE
			SYNTAX SEQUENCE OF WingStatsDevDynRouteIpOspfRouterRoutesInfoEntry
			MAX-ACCESS not-accessible
			STATUS current
			DESCRIPTION
				"Description."
			::= { wingStatsDevDynRoute 6 }

		
		-- 1.3.6.1.4.1.1916.2.131.50.1.4.2.34.6.1
		wingStatsDevDynRouteIpOspfRouterRoutesInfoEntry OBJECT-TYPE
			SYNTAX WingStatsDevDynRouteIpOspfRouterRoutesInfoEntry
			MAX-ACCESS not-accessible
			STATUS current
			DESCRIPTION
				"Description."
			INDEX { wingStatsDevMac, wingStatsDevDynRouteIpOspfRouterRoute, wingStatsDevDynRouteIpOspfRouterRoutesInfoIndex }
			::= { wingStatsDevDynRouteIpOspfRouterRoutesInfoTable 1 }

		
		WingStatsDevDynRouteIpOspfRouterRoutesInfoEntry ::=
			SEQUENCE { 
				wingStatsDevDynRouteIpOspfRouterRoutesInfoIndex
					Unsigned32,
				wingStatsDevDynRouteIpOspfRouterRoutePathType
					DisplayString,
				wingStatsDevDynRouteIpOspfRouterRouteArea
					DisplayString,
				wingStatsDevDynRouteIpOspfRouterRouteCost
					Unsigned32,
				wingStatsDevDynRouteIpOspfRouterRouteFlags
					DisplayString,
				wingStatsDevDynRouteIpOspfRouterRouteAttachedFlag
					TruthValue,
				wingStatsDevDynRouteIpOspfRouterRouteIfName
					DisplayString,
				wingStatsDevDynRouteIpOspfRouterRouteNextHop
					DisplayString
			 }

		-- 1.3.6.1.4.1.1916.2.131.50.1.4.2.34.6.1.1
		wingStatsDevDynRouteIpOspfRouterRoutesInfoIndex OBJECT-TYPE
			SYNTAX Unsigned32 (1..4294967295)
			MAX-ACCESS read-only
			STATUS current
			DESCRIPTION
				"Router Information table index.
				
				XPath: /wing-stats/device[mac=key1]/ospf_stats/router_routes[router=key2]/route_info_nodes[route_node_index=key3]/route_node_index"
			::= { wingStatsDevDynRouteIpOspfRouterRoutesInfoEntry 1 }

		
		-- 1.3.6.1.4.1.1916.2.131.50.1.4.2.34.6.1.2
		wingStatsDevDynRouteIpOspfRouterRoutePathType OBJECT-TYPE
			SYNTAX DisplayString
			MAX-ACCESS read-only
			STATUS current
			DESCRIPTION
				"Type of this OSPF route.
				
				XPath: /wing-stats/device[mac=key1]/ospf_stats/router_routes[router=key2]/route_info_nodes[route_node_index=key3]/path_type"
			::= { wingStatsDevDynRouteIpOspfRouterRoutesInfoEntry 2 }

		
		-- 1.3.6.1.4.1.1916.2.131.50.1.4.2.34.6.1.3
		wingStatsDevDynRouteIpOspfRouterRouteArea OBJECT-TYPE
			SYNTAX DisplayString
			MAX-ACCESS read-only
			STATUS current
			DESCRIPTION
				"Area ID this OSPF router belongs to.
				
				XPath: /wing-stats/device[mac=key1]/ospf_stats/router_routes[router=key2]/route_info_nodes[route_node_index=key3]/area"
			::= { wingStatsDevDynRouteIpOspfRouterRoutesInfoEntry 3 }

		
		-- 1.3.6.1.4.1.1916.2.131.50.1.4.2.34.6.1.4
		wingStatsDevDynRouteIpOspfRouterRouteCost OBJECT-TYPE
			SYNTAX Unsigned32
			MAX-ACCESS read-only
			STATUS current
			DESCRIPTION
				"Cost of this OSPF route.
				
				XPath: /wing-stats/device[mac=key1]/ospf_stats/router_routes[router=key2]/route_info_nodes[route_node_index=key3]/cost"
			::= { wingStatsDevDynRouteIpOspfRouterRoutesInfoEntry 4 }

		
		-- 1.3.6.1.4.1.1916.2.131.50.1.4.2.34.6.1.5
		wingStatsDevDynRouteIpOspfRouterRouteFlags OBJECT-TYPE
			SYNTAX DisplayString
			MAX-ACCESS read-only
			STATUS current
			DESCRIPTION
				"OSPF Router LSA Flags.
				
				XPath: /wing-stats/device[mac=key1]/ospf_stats/router_routes[router=key2]/route_info_nodes[route_node_index=key3]/flags"
			::= { wingStatsDevDynRouteIpOspfRouterRoutesInfoEntry 5 }

		
		-- 1.3.6.1.4.1.1916.2.131.50.1.4.2.34.6.1.6
		wingStatsDevDynRouteIpOspfRouterRouteAttachedFlag OBJECT-TYPE
			SYNTAX TruthValue
			MAX-ACCESS read-only
			STATUS current
			DESCRIPTION
				"Whether the network is directly connected or not.
				
				XPath: /wing-stats/device[mac=key1]/ospf_stats/router_routes[router=key2]/route_info_nodes[route_node_index=key3]/attached_flag
				
				"
			::= { wingStatsDevDynRouteIpOspfRouterRoutesInfoEntry 6 }

		
		-- 1.3.6.1.4.1.1916.2.131.50.1.4.2.34.6.1.7
		wingStatsDevDynRouteIpOspfRouterRouteIfName OBJECT-TYPE
			SYNTAX DisplayString
			MAX-ACCESS read-only
			STATUS current
			DESCRIPTION
				"Name of the interface to which the network is attached.
				
				XPath: /wing-stats/device[mac=key1]/ospf_stats/router_routes[router=key2]/route_info_nodes[route_node_index=key3]/ifname"
			::= { wingStatsDevDynRouteIpOspfRouterRoutesInfoEntry 7 }

		
		-- 1.3.6.1.4.1.1916.2.131.50.1.4.2.34.6.1.8
		wingStatsDevDynRouteIpOspfRouterRouteNextHop OBJECT-TYPE
			SYNTAX DisplayString
			MAX-ACCESS read-only
			STATUS current
			DESCRIPTION
				"Next hop through which the network is reachable.
				
				XPath: /wing-stats/device[mac=key1]/ospf_stats/router_routes[router=key2]/route_info_nodes[route_node_index=key3]/next_hop"
			::= { wingStatsDevDynRouteIpOspfRouterRoutesInfoEntry 8 }

		
		-- 1.3.6.1.4.1.1916.2.131.50.1.4.2.34.7
		wingstatsDevDynRouteIpOspfExtRoutesTable OBJECT-TYPE
			SYNTAX SEQUENCE OF WingstatsDevDynRouteIpOspfExtRoutesEntry
			MAX-ACCESS not-accessible
			STATUS current
			DESCRIPTION
				"Description."
			::= { wingStatsDevDynRoute 7 }

		
		-- 1.3.6.1.4.1.1916.2.131.50.1.4.2.34.7.1
		wingstatsDevDynRouteIpOspfExtRoutesEntry OBJECT-TYPE
			SYNTAX WingstatsDevDynRouteIpOspfExtRoutesEntry
			MAX-ACCESS not-accessible
			STATUS current
			DESCRIPTION
				"Description."
			INDEX { wingStatsDevMac, wingstatsDevDynRouteIpOspfExtRoute }
			::= { wingstatsDevDynRouteIpOspfExtRoutesTable 1 }

		
		WingstatsDevDynRouteIpOspfExtRoutesEntry ::=
			SEQUENCE { 
				wingstatsDevDynRouteIpOspfExtRoute
					WingIdentifier,
				wingstatsDevDynRouteIpOspfExtRoutePathType
					DisplayString,
				wingstatsDevDynRouteIpOspfExtRouteArea
					DisplayString,
				wingstatsDevDynRouteIpOspfExtRouteCost
					Unsigned32,
				wingstatsDevDynRouteIpOspfExtRouteType2Cost
					Unsigned32,
				wingstatsDevDynRouteIpOspfExtRouteTag
					Unsigned32
			 }

		-- 1.3.6.1.4.1.1916.2.131.50.1.4.2.34.7.1.1
		wingstatsDevDynRouteIpOspfExtRoute OBJECT-TYPE
			SYNTAX WingIdentifier
			MAX-ACCESS read-only
			STATUS current
			DESCRIPTION
				"External OSPF route.
				
				XPath: /wing-stats/device[mac=key1]/ospf_stats/external_routes[ext_route=key2]/ext_route"
			::= { wingstatsDevDynRouteIpOspfExtRoutesEntry 1 }

		
		-- 1.3.6.1.4.1.1916.2.131.50.1.4.2.34.7.1.2
		wingstatsDevDynRouteIpOspfExtRoutePathType OBJECT-TYPE
			SYNTAX DisplayString
			MAX-ACCESS read-only
			STATUS current
			DESCRIPTION
				"Type of this OSPF network.
				
				XPath: /wing-stats/device[mac=key1]/ospf_stats/external_routes[ext_route=key2]/path_type"
			::= { wingstatsDevDynRouteIpOspfExtRoutesEntry 2 }

		
		-- 1.3.6.1.4.1.1916.2.131.50.1.4.2.34.7.1.3
		wingstatsDevDynRouteIpOspfExtRouteArea OBJECT-TYPE
			SYNTAX DisplayString
			MAX-ACCESS read-only
			STATUS current
			DESCRIPTION
				"Area ID this OSPF network belongs to.
				
				XPath: /wing-stats/device[mac=key1]/ospf_stats/external_routes[ext_route=key2]/area"
			::= { wingstatsDevDynRouteIpOspfExtRoutesEntry 3 }

		
		-- 1.3.6.1.4.1.1916.2.131.50.1.4.2.34.7.1.4
		wingstatsDevDynRouteIpOspfExtRouteCost OBJECT-TYPE
			SYNTAX Unsigned32
			MAX-ACCESS read-only
			STATUS current
			DESCRIPTION
				"Cost of this OSPF external route.
				
				XPath: /wing-stats/device[mac=key1]/ospf_stats/external_routes[ext_route=key2]/cost"
			::= { wingstatsDevDynRouteIpOspfExtRoutesEntry 4 }

		
		-- 1.3.6.1.4.1.1916.2.131.50.1.4.2.34.7.1.5
		wingstatsDevDynRouteIpOspfExtRouteType2Cost OBJECT-TYPE
			SYNTAX Unsigned32
			MAX-ACCESS read-only
			STATUS current
			DESCRIPTION
				"Cost of this type 2 OSPF route.
				
				XPath: /wing-stats/device[mac=key1]/ospf_stats/external_routes[ext_route=key2]/type_2_cost"
			::= { wingstatsDevDynRouteIpOspfExtRoutesEntry 5 }

		
		-- 1.3.6.1.4.1.1916.2.131.50.1.4.2.34.7.1.6
		wingstatsDevDynRouteIpOspfExtRouteTag OBJECT-TYPE
			SYNTAX Unsigned32
			MAX-ACCESS read-only
			STATUS current
			DESCRIPTION
				"Tag of external route.
				
				XPath: /wing-stats/device[mac=key1]/ospf_stats/external_routes[ext_route=key2]/tag"
			::= { wingstatsDevDynRouteIpOspfExtRoutesEntry 6 }

		
		-- 1.3.6.1.4.1.1916.2.131.50.1.4.2.34.8
		wingstatsDevDynRouteIpOspfExtRoutesMPathsTable OBJECT-TYPE
			SYNTAX SEQUENCE OF WingstatsDevDynRouteIpOspfExtRoutesMPathsEntry
			MAX-ACCESS not-accessible
			STATUS current
			DESCRIPTION
				"Description."
			::= { wingStatsDevDynRoute 8 }

		
		-- 1.3.6.1.4.1.1916.2.131.50.1.4.2.34.8.1
		wingstatsDevDynRouteIpOspfExtRoutesMPathsEntry OBJECT-TYPE
			SYNTAX WingstatsDevDynRouteIpOspfExtRoutesMPathsEntry
			MAX-ACCESS not-accessible
			STATUS current
			DESCRIPTION
				"Description."
			INDEX { wingStatsDevMac, wingstatsDevDynRouteIpOspfExtRoute, wingstatsDevDynRouteIpOspfExtRoutesMPathsIndex }
			::= { wingstatsDevDynRouteIpOspfExtRoutesMPathsTable 1 }

		
		WingstatsDevDynRouteIpOspfExtRoutesMPathsEntry ::=
			SEQUENCE { 
				wingstatsDevDynRouteIpOspfExtRoutesMPathsIndex
					Unsigned32,
				wingstatsDevDynRouteIpOspfExtRouteAttachedFlag
					TruthValue,
				wingstatsDevDynRouteIpOspfExtRouteIfName
					DisplayString,
				wingstatsDevDynRouteIpOspfExtRouteNextHop
					DisplayString
			 }

		-- 1.3.6.1.4.1.1916.2.131.50.1.4.2.34.8.1.1
		wingstatsDevDynRouteIpOspfExtRoutesMPathsIndex OBJECT-TYPE
			SYNTAX Unsigned32 (1..4294967295)
			MAX-ACCESS read-only
			STATUS current
			DESCRIPTION
				"External routes multipath table index.
				
				XPath: /wing-stats/device[mac=key1]/ospf_stats/external_routes[ext_route=key2]/multipaths[m_path_index=key3]/m_path_index
				"
			::= { wingstatsDevDynRouteIpOspfExtRoutesMPathsEntry 1 }

		
		-- 1.3.6.1.4.1.1916.2.131.50.1.4.2.34.8.1.2
		wingstatsDevDynRouteIpOspfExtRouteAttachedFlag OBJECT-TYPE
			SYNTAX TruthValue
			MAX-ACCESS read-only
			STATUS current
			DESCRIPTION
				"Whether the network is directly connected or not.
				
				XPath: /wing-stats/device[mac=key1]/ospf_stats/external_routes[ext_route=key2]/multipaths[m_path_index=key3]/attached_flag"
			::= { wingstatsDevDynRouteIpOspfExtRoutesMPathsEntry 2 }

		
		-- 1.3.6.1.4.1.1916.2.131.50.1.4.2.34.8.1.3
		wingstatsDevDynRouteIpOspfExtRouteIfName OBJECT-TYPE
			SYNTAX DisplayString
			MAX-ACCESS read-only
			STATUS current
			DESCRIPTION
				"Name of the interface to which the network is attached.
				
				XPath: /wing-stats/device[mac=key1]/ospf_stats/external_routes[ext_route=key2]/multipaths[m_path_index=key3]/ifname"
			::= { wingstatsDevDynRouteIpOspfExtRoutesMPathsEntry 3 }

		
		-- 1.3.6.1.4.1.1916.2.131.50.1.4.2.34.8.1.4
		wingstatsDevDynRouteIpOspfExtRouteNextHop OBJECT-TYPE
			SYNTAX DisplayString
			MAX-ACCESS read-only
			STATUS current
			DESCRIPTION
				"Next hop through which the network is reachable.
				
				XPath: /wing-stats/device[mac=key1]/ospf_stats/external_routes[ext_route=key2]/multipaths[m_path_index=key3]/next_hop"
			::= { wingstatsDevDynRouteIpOspfExtRoutesMPathsEntry 4 }

		
		-- 1.3.6.1.4.1.1916.2.131.50.1.4.2.34.9
		wingStatsDevDynRouteBorderRoutersTable OBJECT-TYPE
			SYNTAX SEQUENCE OF WingStatsDevDynRouteBorderRoutersEntry
			MAX-ACCESS not-accessible
			STATUS current
			DESCRIPTION
				"Description."
			::= { wingStatsDevDynRoute 9 }

		
		-- 1.3.6.1.4.1.1916.2.131.50.1.4.2.34.9.1
		wingStatsDevDynRouteBorderRoutersEntry OBJECT-TYPE
			SYNTAX WingStatsDevDynRouteBorderRoutersEntry
			MAX-ACCESS not-accessible
			STATUS current
			DESCRIPTION
				"Description."
			INDEX { wingStatsDevMac, wingStatsDevDynRouteBorderRouter }
			::= { wingStatsDevDynRouteBorderRoutersTable 1 }

		
		WingStatsDevDynRouteBorderRoutersEntry ::=
			SEQUENCE { 
				wingStatsDevDynRouteBorderRouter
					WingIdentifier
			 }

		-- 1.3.6.1.4.1.1916.2.131.50.1.4.2.34.9.1.1
		wingStatsDevDynRouteBorderRouter OBJECT-TYPE
			SYNTAX WingIdentifier
			MAX-ACCESS read-only
			STATUS current
			DESCRIPTION
				"Router IP address.
				
				XPath: /wing-stats/device[mac=key1]/ospf_stats/border_routers[router=key2]/router"
			::= { wingStatsDevDynRouteBorderRoutersEntry 1 }

		
		-- 1.3.6.1.4.1.1916.2.131.50.1.4.2.34.10
		wingStatsDevDynRouteBorderRoutersInfoTable OBJECT-TYPE
			SYNTAX SEQUENCE OF WingStatsDevDynRouteBorderRoutersInfoEntry
			MAX-ACCESS not-accessible
			STATUS current
			DESCRIPTION
				"Description."
			::= { wingStatsDevDynRoute 10 }

		
		-- 1.3.6.1.4.1.1916.2.131.50.1.4.2.34.10.1
		wingStatsDevDynRouteBorderRoutersInfoEntry OBJECT-TYPE
			SYNTAX WingStatsDevDynRouteBorderRoutersInfoEntry
			MAX-ACCESS not-accessible
			STATUS current
			DESCRIPTION
				"Description."
			INDEX { wingStatsDevMac, wingStatsDevDynRouteBorderRouter, wingStatsDevDynRouteBorderRoutersInfoIndex }
			::= { wingStatsDevDynRouteBorderRoutersInfoTable 1 }

		
		WingStatsDevDynRouteBorderRoutersInfoEntry ::=
			SEQUENCE { 
				wingStatsDevDynRouteBorderRoutersInfoIndex
					Unsigned32,
				wingStatsDevDynRouteBorderRouterPathType
					DisplayString,
				wingStatsDevDynRouteBorderRouterArea
					DisplayString,
				wingStatsDevDynRouteBorderRouterCost
					Unsigned32,
				wingStatsDevDynRouteBorderRouterFlags
					DisplayString,
				wingStatsDevDynRouteBorderRouterAttachedFlag
					TruthValue,
				wingStatsDevDynRouteBorderRouterIfName
					DisplayString,
				wingStatsDevDynRouteBorderRouterNextHop
					DisplayString
			 }

		-- 1.3.6.1.4.1.1916.2.131.50.1.4.2.34.10.1.1
		wingStatsDevDynRouteBorderRoutersInfoIndex OBJECT-TYPE
			SYNTAX Unsigned32 (1..4294967295)
			MAX-ACCESS read-only
			STATUS current
			DESCRIPTION
				"Router Information table index.
				
				XPath: /wing-stats/device[mac=key1]/ospf_stats/border_routers[router=key2]/route_info_nodes[route_node_index=key3]/route_node_index"
			::= { wingStatsDevDynRouteBorderRoutersInfoEntry 1 }

		
		-- 1.3.6.1.4.1.1916.2.131.50.1.4.2.34.10.1.2
		wingStatsDevDynRouteBorderRouterPathType OBJECT-TYPE
			SYNTAX DisplayString
			MAX-ACCESS read-only
			STATUS current
			DESCRIPTION
				"Type of this OSPF route
				
				XPath: /wing-stats/device[mac=key1]/ospf_stats/border_routers[router=key2]/route_info_nodes[route_node_index=key3]/path_type"
			::= { wingStatsDevDynRouteBorderRoutersInfoEntry 2 }

		
		-- 1.3.6.1.4.1.1916.2.131.50.1.4.2.34.10.1.3
		wingStatsDevDynRouteBorderRouterArea OBJECT-TYPE
			SYNTAX DisplayString
			MAX-ACCESS read-only
			STATUS current
			DESCRIPTION
				"Area ID this OSPF router belongs to.
				
				XPath: /wing-stats/device[mac=key1]/ospf_stats/border_routers[router=key2]/route_info_nodes[route_node_index=key3]/area"
			::= { wingStatsDevDynRouteBorderRoutersInfoEntry 3 }

		
		-- 1.3.6.1.4.1.1916.2.131.50.1.4.2.34.10.1.4
		wingStatsDevDynRouteBorderRouterCost OBJECT-TYPE
			SYNTAX Unsigned32
			MAX-ACCESS read-only
			STATUS current
			DESCRIPTION
				"Cost of this OSPF route.
				
				XPath: /wing-stats/device[mac=key1]/ospf_stats/border_routers[router=key2]/route_info_nodes[route_node_index=key3]/cost"
			::= { wingStatsDevDynRouteBorderRoutersInfoEntry 4 }

		
		-- 1.3.6.1.4.1.1916.2.131.50.1.4.2.34.10.1.5
		wingStatsDevDynRouteBorderRouterFlags OBJECT-TYPE
			SYNTAX DisplayString
			MAX-ACCESS read-only
			STATUS current
			DESCRIPTION
				"OSPF Router LSA Flags.
				
				XPath: /wing-stats/device[mac=key1]/ospf_stats/border_routers[router=key2]/route_info_nodes[route_node_index=key3]/flags"
			::= { wingStatsDevDynRouteBorderRoutersInfoEntry 5 }

		
		-- 1.3.6.1.4.1.1916.2.131.50.1.4.2.34.10.1.6
		wingStatsDevDynRouteBorderRouterAttachedFlag OBJECT-TYPE
			SYNTAX TruthValue
			MAX-ACCESS read-only
			STATUS current
			DESCRIPTION
				"Whether the network is directly connected or not.
				
				XPath: /wing-stats/device[mac=key1]/ospf_stats/border_routers[router=key2]/route_info_nodes[route_node_index=key3]/attached_flag"
			::= { wingStatsDevDynRouteBorderRoutersInfoEntry 6 }

		
		-- 1.3.6.1.4.1.1916.2.131.50.1.4.2.34.10.1.7
		wingStatsDevDynRouteBorderRouterIfName OBJECT-TYPE
			SYNTAX DisplayString
			MAX-ACCESS read-only
			STATUS current
			DESCRIPTION
				"Name of the interface to which the network is attached
				
				XPath: /wing-stats/device[mac=key1]/ospf_stats/border_routers[router=key2]/route_info_nodes[route_node_index=key3]/ifname"
			::= { wingStatsDevDynRouteBorderRoutersInfoEntry 7 }

		
		-- 1.3.6.1.4.1.1916.2.131.50.1.4.2.34.10.1.8
		wingStatsDevDynRouteBorderRouterNextHop OBJECT-TYPE
			SYNTAX DisplayString
			MAX-ACCESS read-only
			STATUS current
			DESCRIPTION
				"Next hop through which the network is reachable.
				
				XPath: /wing-stats/device[mac=key1]/ospf_stats/border_routers[router=key2]/route_info_nodes[route_node_index=key3]/next_hop"
			::= { wingStatsDevDynRouteBorderRoutersInfoEntry 8 }

		
		-- 1.3.6.1.4.1.1916.2.131.50.1.4.2.34.11
		wingStatsDevDynRouteOspfIfTable OBJECT-TYPE
			SYNTAX SEQUENCE OF WingStatsDevDynRouteOspfIfEntry
			MAX-ACCESS not-accessible
			STATUS current
			DESCRIPTION
				"Description."
			::= { wingStatsDevDynRoute 11 }

		
		-- 1.3.6.1.4.1.1916.2.131.50.1.4.2.34.11.1
		wingStatsDevDynRouteOspfIfEntry OBJECT-TYPE
			SYNTAX WingStatsDevDynRouteOspfIfEntry
			MAX-ACCESS not-accessible
			STATUS current
			DESCRIPTION
				"Description."
			INDEX { wingStatsDevMac, wingStatsDevDynRouteOspfIfName }
			::= { wingStatsDevDynRouteOspfIfTable 1 }

		
		WingStatsDevDynRouteOspfIfEntry ::=
			SEQUENCE { 
				wingStatsDevDynRouteOspfIfName
					WingIdentifier,
				wingStatsDevDynRouteOspfIfStatusFlag
					TruthValue,
				wingStatsDevDynRouteOspfIfIndex
					Unsigned32,
				wingStatsDevDynRouteOspfIfMtu
					Unsigned32,
				wingStatsDevDynRouteOspfIfBandwidth
					Unsigned32,
				wingStatsDevDynRouteOspfIfFlags
					Counter64,
				wingStatsDevDynRouteOspfIfEnabled
					TruthValue
			 }

		-- 1.3.6.1.4.1.1916.2.131.50.1.4.2.34.11.1.1
		wingStatsDevDynRouteOspfIfName OBJECT-TYPE
			SYNTAX WingIdentifier
			MAX-ACCESS read-only
			STATUS current
			DESCRIPTION
				"Interface Name.
				
				XPath: /wing-stats/device[mac=key1]/ospf_stats/ospf_if[ifname=key2]/ifname"
			::= { wingStatsDevDynRouteOspfIfEntry 1 }

		
		-- 1.3.6.1.4.1.1916.2.131.50.1.4.2.34.11.1.2
		wingStatsDevDynRouteOspfIfStatusFlag OBJECT-TYPE
			SYNTAX TruthValue
			MAX-ACCESS read-only
			STATUS current
			DESCRIPTION
				"Whether interface is up or down.
				
				XPath: /wing-stats/device[mac=key1]/ospf_stats/ospf_if[ifname=key2]/up_dn_flag"
			::= { wingStatsDevDynRouteOspfIfEntry 2 }

		
		-- 1.3.6.1.4.1.1916.2.131.50.1.4.2.34.11.1.3
		wingStatsDevDynRouteOspfIfIndex OBJECT-TYPE
			SYNTAX Unsigned32
			MAX-ACCESS read-only
			STATUS current
			DESCRIPTION
				"Interface index.
				
				XPath: /wing-stats/device[mac=key1]/ospf_stats/ospf_if[ifname=key2]/ifindex"
			::= { wingStatsDevDynRouteOspfIfEntry 3 }

		
		-- 1.3.6.1.4.1.1916.2.131.50.1.4.2.34.11.1.4
		wingStatsDevDynRouteOspfIfMtu OBJECT-TYPE
			SYNTAX Unsigned32
			MAX-ACCESS read-only
			STATUS current
			DESCRIPTION
				"Size of MTU of this interface in bytes.
				
				XPath: /wing-stats/device[mac=key1]/ospf_stats/ospf_if[ifname=key2]/mtu"
			::= { wingStatsDevDynRouteOspfIfEntry 4 }

		
		-- 1.3.6.1.4.1.1916.2.131.50.1.4.2.34.11.1.5
		wingStatsDevDynRouteOspfIfBandwidth OBJECT-TYPE
			SYNTAX Unsigned32
			MAX-ACCESS read-only
			STATUS current
			DESCRIPTION
				"Bandwidth of this interface in Kbits.
				
				XPath: /wing-stats/device[mac=key1]/ospf_stats/ospf_if[ifname=key2]/bw"
			::= { wingStatsDevDynRouteOspfIfEntry 5 }

		
		-- 1.3.6.1.4.1.1916.2.131.50.1.4.2.34.11.1.6
		wingStatsDevDynRouteOspfIfFlags OBJECT-TYPE
			SYNTAX Counter64
			MAX-ACCESS read-only
			STATUS current
			DESCRIPTION
				"Inteface flags.
				
				XPath: /wing-stats/device[mac=key1]/ospf_stats/ospf_if[ifname=key2]/flags"
			::= { wingStatsDevDynRouteOspfIfEntry 6 }

		
		-- 1.3.6.1.4.1.1916.2.131.50.1.4.2.34.11.1.7
		wingStatsDevDynRouteOspfIfEnabled OBJECT-TYPE
			SYNTAX TruthValue
			MAX-ACCESS read-only
			STATUS current
			DESCRIPTION
				"Whether OSPF is enabled on this interface or not.
				
				XPath: /wing-stats/device[mac=key1]/ospf_stats/ospf_if[ifname=key2]/ospf_enabled_flag"
			::= { wingStatsDevDynRouteOspfIfEntry 7 }

		
		-- 1.3.6.1.4.1.1916.2.131.50.1.4.2.34.12
		wingStatsDevDynRouteOspfIfInfoTable OBJECT-TYPE
			SYNTAX SEQUENCE OF WingStatsDevDynRouteOspfIfInfoEntry
			MAX-ACCESS not-accessible
			STATUS current
			DESCRIPTION
				"Description."
			::= { wingStatsDevDynRoute 12 }

		
		-- 1.3.6.1.4.1.1916.2.131.50.1.4.2.34.12.1
		wingStatsDevDynRouteOspfIfInfoEntry OBJECT-TYPE
			SYNTAX WingStatsDevDynRouteOspfIfInfoEntry
			MAX-ACCESS not-accessible
			STATUS current
			DESCRIPTION
				"Description."
			INDEX { wingStatsDevMac, wingStatsDevDynRouteOspfIfName, wingStatsDevDynRouteOspfIfInfoIndex }
			::= { wingStatsDevDynRouteOspfIfInfoTable 1 }

		
		WingStatsDevDynRouteOspfIfInfoEntry ::=
			SEQUENCE { 
				wingStatsDevDynRouteOspfIfInfoIndex
					Unsigned32,
				wingStatsDevDynRouteOspfIfIpAddr
					DisplayString,
				wingStatsDevDynRouteOspfIfMask
					Unsigned32,
				wingStatsDevDynRouteOspfIfBroadcastOrP2P
					DisplayString,
				wingStatsDevDynRouteOspfIfBroadcastOrP2PIpAddr
					DisplayString,
				wingStatsDevDynRouteOspfIfAreaId
					DisplayString,
				wingStatsDevDynRouteOspfIfMtuMismatchDetectFlag
					TruthValue,
				wingStatsDevDynRouteOspfIfRouterId
					DisplayString,
				wingStatsDevDynRouteOspfIfNetworkType
					DisplayString,
				wingStatsDevDynRouteOspfIfCost
					Unsigned32,
				wingStatsDevDynRouteOspfIfTransmitDelay
					Unsigned32,
				wingStatsDevDynRouteOspfIfIsmState
					DisplayString,
				wingStatsDevDynRouteOspfIfPriority
					Unsigned32,
				wingStatsDevDynRouteOspfIfDesgRouterId
					DisplayString,
				wingStatsDevDynRouteOspfIfDesgRouterAddr
					DisplayString,
				wingStatsDevDynRouteOspfIfBackupDesgRouterId
					DisplayString,
				wingStatsDevDynRouteOspfIfBackupDesgRouterAddr
					DisplayString,
				wingStatsDevDynRouteOspfIfMcastMembership
					DisplayString,
				wingStatsDevDynRouteOspfIfSubSecHelloFlag
					TruthValue,
				wingStatsDevDynRouteOspfIfHelloInterval
					Unsigned32,
				wingStatsDevDynRouteOspfIfDeadInterval
					Unsigned32,
				wingStatsDevDynRouteOspfIfWaitInterval
					Unsigned32,
				wingStatsDevDynRouteOspfIfRetransmitInterval
					Unsigned32,
				wingStatsDevDynRouteOspfIfPassiveFlag
					TruthValue,
				wingStatsDevDynRouteOspfIfHelloDueIn
					DisplayString,
				wingStatsDevDynRouteOspfIfNeighborCount
					Unsigned32,
				wingStatsDevDynRouteOspfIfAdjNeighborCount
					Unsigned32
			 }

		-- 1.3.6.1.4.1.1916.2.131.50.1.4.2.34.12.1.1
		wingStatsDevDynRouteOspfIfInfoIndex OBJECT-TYPE
			SYNTAX Unsigned32 (1..4294967295)
			MAX-ACCESS read-only
			STATUS current
			DESCRIPTION
				"OSPF interface information table index.
				
				XPath: /wing-stats/device[mac=key1]/ospf_stats/ospf_if[ifname=key2]/ospf_if_info[ospf_if_info_index=key3]/ospf_if_info_index"
			::= { wingStatsDevDynRouteOspfIfInfoEntry 1 }

		
		-- 1.3.6.1.4.1.1916.2.131.50.1.4.2.34.12.1.2
		wingStatsDevDynRouteOspfIfIpAddr OBJECT-TYPE
			SYNTAX DisplayString
			MAX-ACCESS read-only
			STATUS current
			DESCRIPTION
				"IP address of this interface.
				
				XPath: /wing-stats/device[mac=key1]/ospf_stats/ospf_if[ifname=key2]/ospf_if_info[ospf_if_info_index=key3]/intf_ip"
			::= { wingStatsDevDynRouteOspfIfInfoEntry 2 }

		
		-- 1.3.6.1.4.1.1916.2.131.50.1.4.2.34.12.1.3
		wingStatsDevDynRouteOspfIfMask OBJECT-TYPE
			SYNTAX Unsigned32
			MAX-ACCESS read-only
			STATUS current
			DESCRIPTION
				"Network mask for this interface.
				
				XPath: /wing-stats/device[mac=key1]/ospf_stats/ospf_if[ifname=key2]/ospf_if_info[ospf_if_info_index=key3]/mask"
			::= { wingStatsDevDynRouteOspfIfInfoEntry 3 }

		
		-- 1.3.6.1.4.1.1916.2.131.50.1.4.2.34.12.1.4
		wingStatsDevDynRouteOspfIfBroadcastOrP2P OBJECT-TYPE
			SYNTAX DisplayString
			MAX-ACCESS read-only
			STATUS current
			DESCRIPTION
				"Whether this interface is broadcast pr peer-to-peer.
				
				XPath: /wing-stats/device[mac=key1]/ospf_stats/ospf_if[ifname=key2]/ospf_if_info[ospf_if_info_index=key3]/dstr"
			::= { wingStatsDevDynRouteOspfIfInfoEntry 4 }

		
		-- 1.3.6.1.4.1.1916.2.131.50.1.4.2.34.12.1.5
		wingStatsDevDynRouteOspfIfBroadcastOrP2PIpAddr OBJECT-TYPE
			SYNTAX DisplayString
			MAX-ACCESS read-only
			STATUS current
			DESCRIPTION
				"Broadcast or peer IP address of this interface.
				
				XPath: /wing-stats/device[mac=key1]/ospf_stats/ospf_if[ifname=key2]/ospf_if_info[ospf_if_info_index=key3]/dest"
			::= { wingStatsDevDynRouteOspfIfInfoEntry 5 }

		
		-- 1.3.6.1.4.1.1916.2.131.50.1.4.2.34.12.1.6
		wingStatsDevDynRouteOspfIfAreaId OBJECT-TYPE
			SYNTAX DisplayString
			MAX-ACCESS read-only
			STATUS current
			DESCRIPTION
				"Area ID to which this interface belongs.
				
				XPath: /wing-stats/device[mac=key1]/ospf_stats/ospf_if[ifname=key2]/ospf_if_info[ospf_if_info_index=key3]/area_id"
			::= { wingStatsDevDynRouteOspfIfInfoEntry 6 }

		
		-- 1.3.6.1.4.1.1916.2.131.50.1.4.2.34.12.1.7
		wingStatsDevDynRouteOspfIfMtuMismatchDetectFlag OBJECT-TYPE
			SYNTAX TruthValue
			MAX-ACCESS read-only
			STATUS current
			DESCRIPTION
				"Wheter MTU mismatch detection is enabled or not.
				
				XPath: /wing-stats/device[mac=key1]/ospf_stats/ospf_if[ifname=key2]/ospf_if_info[ospf_if_info_index=key3]/mtu_mismatch_det_flag"
			::= { wingStatsDevDynRouteOspfIfInfoEntry 7 }

		
		-- 1.3.6.1.4.1.1916.2.131.50.1.4.2.34.12.1.8
		wingStatsDevDynRouteOspfIfRouterId OBJECT-TYPE
			SYNTAX DisplayString
			MAX-ACCESS read-only
			STATUS current
			DESCRIPTION
				"Router ID of this router.
				
				XPath: /wing-stats/device[mac=key1]/ospf_stats/ospf_if[ifname=key2]/ospf_if_info[ospf_if_info_index=key3]/router_id"
			::= { wingStatsDevDynRouteOspfIfInfoEntry 8 }

		
		-- 1.3.6.1.4.1.1916.2.131.50.1.4.2.34.12.1.9
		wingStatsDevDynRouteOspfIfNetworkType OBJECT-TYPE
			SYNTAX DisplayString
			MAX-ACCESS read-only
			STATUS current
			DESCRIPTION
				"Type of the network connected to this interface.
				
				XPath: /wing-stats/device[mac=key1]/ospf_stats/ospf_if[ifname=key2]/ospf_if_info[ospf_if_info_index=key3]/nw_type"
			::= { wingStatsDevDynRouteOspfIfInfoEntry 9 }

		
		-- 1.3.6.1.4.1.1916.2.131.50.1.4.2.34.12.1.10
		wingStatsDevDynRouteOspfIfCost OBJECT-TYPE
			SYNTAX Unsigned32
			MAX-ACCESS read-only
			STATUS current
			DESCRIPTION
				"Cost of this OSPF interface.
				
				XPath: /wing-stats/device[mac=key1]/ospf_stats/ospf_if[ifname=key2]/ospf_if_info[ospf_if_info_index=key3]/cost"
			::= { wingStatsDevDynRouteOspfIfInfoEntry 10 }

		
		-- 1.3.6.1.4.1.1916.2.131.50.1.4.2.34.12.1.11
		wingStatsDevDynRouteOspfIfTransmitDelay OBJECT-TYPE
			SYNTAX Unsigned32
			MAX-ACCESS read-only
			STATUS current
			DESCRIPTION
				"Link state transmit interval.
				
				XPath: /wing-stats/device[mac=key1]/ospf_stats/ospf_if[ifname=key2]/ospf_if_info[ospf_if_info_index=key3]/transmit_delay"
			::= { wingStatsDevDynRouteOspfIfInfoEntry 11 }

		
		-- 1.3.6.1.4.1.1916.2.131.50.1.4.2.34.12.1.12
		wingStatsDevDynRouteOspfIfIsmState OBJECT-TYPE
			SYNTAX DisplayString
			MAX-ACCESS read-only
			STATUS current
			DESCRIPTION
				"OSPF Interface State Machine state.
				
				XPath: /wing-stats/device[mac=key1]/ospf_stats/ospf_if[ifname=key2]/ospf_if_info[ospf_if_info_index=key3]/ism_state"
			::= { wingStatsDevDynRouteOspfIfInfoEntry 12 }

		
		-- 1.3.6.1.4.1.1916.2.131.50.1.4.2.34.12.1.13
		wingStatsDevDynRouteOspfIfPriority OBJECT-TYPE
			SYNTAX Unsigned32
			MAX-ACCESS read-only
			STATUS current
			DESCRIPTION
				"OSPF inteface priority.
				
				XPath: /wing-stats/device[mac=key1]/ospf_stats/ospf_if[ifname=key2]/ospf_if_info[ospf_if_info_index=key3]/priority"
			::= { wingStatsDevDynRouteOspfIfInfoEntry 13 }

		
		-- 1.3.6.1.4.1.1916.2.131.50.1.4.2.34.12.1.14
		wingStatsDevDynRouteOspfIfDesgRouterId OBJECT-TYPE
			SYNTAX DisplayString
			MAX-ACCESS read-only
			STATUS current
			DESCRIPTION
				"Designated Router ID.
				
				XPath: /wing-stats/device[mac=key1]/ospf_stats/ospf_if[ifname=key2]/ospf_if_info[ospf_if_info_index=key3]/dr_id"
			::= { wingStatsDevDynRouteOspfIfInfoEntry 14 }

		
		-- 1.3.6.1.4.1.1916.2.131.50.1.4.2.34.12.1.15
		wingStatsDevDynRouteOspfIfDesgRouterAddr OBJECT-TYPE
			SYNTAX DisplayString
			MAX-ACCESS read-only
			STATUS current
			DESCRIPTION
				"Interface through which DR is reachable.
				
				XPath: /wing-stats/device[mac=key1]/ospf_stats/ospf_if[ifname=key2]/ospf_if_info[ospf_if_info_index=key3]/dr_ifaddr"
			::= { wingStatsDevDynRouteOspfIfInfoEntry 15 }

		
		-- 1.3.6.1.4.1.1916.2.131.50.1.4.2.34.12.1.16
		wingStatsDevDynRouteOspfIfBackupDesgRouterId OBJECT-TYPE
			SYNTAX DisplayString
			MAX-ACCESS read-only
			STATUS current
			DESCRIPTION
				"Backup Designated Router ID.
				
				XPath: /wing-stats/device[mac=key1]/ospf_stats/ospf_if[ifname=key2]/ospf_if_info[ospf_if_info_index=key3]/bdr_id"
			::= { wingStatsDevDynRouteOspfIfInfoEntry 16 }

		
		-- 1.3.6.1.4.1.1916.2.131.50.1.4.2.34.12.1.17
		wingStatsDevDynRouteOspfIfBackupDesgRouterAddr OBJECT-TYPE
			SYNTAX DisplayString
			MAX-ACCESS read-only
			STATUS current
			DESCRIPTION
				"Interface through which BDR is reachable.
				
				XPath: /wing-stats/device[mac=key1]/ospf_stats/ospf_if[ifname=key2]/ospf_if_info[ospf_if_info_index=key3]/bdr_ifaddr"
			::= { wingStatsDevDynRouteOspfIfInfoEntry 17 }

		
		-- 1.3.6.1.4.1.1916.2.131.50.1.4.2.34.12.1.18
		wingStatsDevDynRouteOspfIfMcastMembership OBJECT-TYPE
			SYNTAX DisplayString
			MAX-ACCESS read-only
			STATUS current
			DESCRIPTION
				"What kind of multicast packets are acted upon by this interface.
				
				XPath: /wing-stats/device[mac=key1]/ospf_stats/ospf_if[ifname=key2]/ospf_if_info[ospf_if_info_index=key3]/mc_membership"
			::= { wingStatsDevDynRouteOspfIfInfoEntry 18 }

		
		-- 1.3.6.1.4.1.1916.2.131.50.1.4.2.34.12.1.19
		wingStatsDevDynRouteOspfIfSubSecHelloFlag OBJECT-TYPE
			SYNTAX TruthValue
			MAX-ACCESS read-only
			STATUS current
			DESCRIPTION
				"Whether fast hello is enabled.
				
				XPath: /wing-stats/device[mac=key1]/ospf_stats/ospf_if[ifname=key2]/ospf_if_info[ospf_if_info_index=key3]/sub_sec_hello_flag"
			::= { wingStatsDevDynRouteOspfIfInfoEntry 19 }

		
		-- 1.3.6.1.4.1.1916.2.131.50.1.4.2.34.12.1.20
		wingStatsDevDynRouteOspfIfHelloInterval OBJECT-TYPE
			SYNTAX Unsigned32
			MAX-ACCESS read-only
			STATUS current
			DESCRIPTION
				"Interval between OSPF Hello packets.
				
				XPath: /wing-stats/device[mac=key1]/ospf_stats/ospf_if[ifname=key2]/ospf_if_info[ospf_if_info_index=key3]/hello_interval"
			::= { wingStatsDevDynRouteOspfIfInfoEntry 20 }

		
		-- 1.3.6.1.4.1.1916.2.131.50.1.4.2.34.12.1.21
		wingStatsDevDynRouteOspfIfDeadInterval OBJECT-TYPE
			SYNTAX Unsigned32
			MAX-ACCESS read-only
			STATUS current
			DESCRIPTION
				"Interval after which a neighbor is declared dead.
				
				XPath: /wing-stats/device[mac=key1]/ospf_stats/ospf_if[ifname=key2]/ospf_if_info[ospf_if_info_index=key3]/dead_interval"
			::= { wingStatsDevDynRouteOspfIfInfoEntry 21 }

		
		-- 1.3.6.1.4.1.1916.2.131.50.1.4.2.34.12.1.22
		wingStatsDevDynRouteOspfIfWaitInterval OBJECT-TYPE
			SYNTAX Unsigned32
			MAX-ACCESS read-only
			STATUS current
			DESCRIPTION
				"Interval after which a neighbor is declared dead.
				
				XPath: /wing-stats/device[mac=key1]/ospf_stats/ospf_if[ifname=key2]/ospf_if_info[ospf_if_info_index=key3]/wait_interval"
			::= { wingStatsDevDynRouteOspfIfInfoEntry 22 }

		
		-- 1.3.6.1.4.1.1916.2.131.50.1.4.2.34.12.1.23
		wingStatsDevDynRouteOspfIfRetransmitInterval OBJECT-TYPE
			SYNTAX Unsigned32
			MAX-ACCESS read-only
			STATUS current
			DESCRIPTION
				"Time between retransmitting lost link state advertisements.
				
				XPath: /wing-stats/device[mac=key1]/ospf_stats/ospf_if[ifname=key2]/ospf_if_info[ospf_if_info_index=key3]/retransmit_interval"
			::= { wingStatsDevDynRouteOspfIfInfoEntry 23 }

		
		-- 1.3.6.1.4.1.1916.2.131.50.1.4.2.34.12.1.24
		wingStatsDevDynRouteOspfIfPassiveFlag OBJECT-TYPE
			SYNTAX TruthValue
			MAX-ACCESS read-only
			STATUS current
			DESCRIPTION
				"Whether this interface is passive or not.
				
				XPath: /wing-stats/device[mac=key1]/ospf_stats/ospf_if[ifname=key2]/ospf_if_info[ospf_if_info_index=key3]/passive_flag"
			::= { wingStatsDevDynRouteOspfIfInfoEntry 24 }

		
		-- 1.3.6.1.4.1.1916.2.131.50.1.4.2.34.12.1.25
		wingStatsDevDynRouteOspfIfHelloDueIn OBJECT-TYPE
			SYNTAX DisplayString
			MAX-ACCESS read-only
			STATUS current
			DESCRIPTION
				"Interval after which next HELLO will be sent.
				
				XPath: /wing-stats/device[mac=key1]/ospf_stats/ospf_if[ifname=key2]/ospf_if_info[ospf_if_info_index=key3]/hello_due_in"
			::= { wingStatsDevDynRouteOspfIfInfoEntry 25 }

		
		-- 1.3.6.1.4.1.1916.2.131.50.1.4.2.34.12.1.26
		wingStatsDevDynRouteOspfIfNeighborCount OBJECT-TYPE
			SYNTAX Unsigned32
			MAX-ACCESS read-only
			STATUS current
			DESCRIPTION
				"Number of OSPF neighbors.
				
				XPath: /wing-stats/device[mac=key1]/ospf_stats/ospf_if[ifname=key2]/ospf_if_info[ospf_if_info_index=key3]/ospf_nbr_count"
			::= { wingStatsDevDynRouteOspfIfInfoEntry 26 }

		
		-- 1.3.6.1.4.1.1916.2.131.50.1.4.2.34.12.1.27
		wingStatsDevDynRouteOspfIfAdjNeighborCount OBJECT-TYPE
			SYNTAX Unsigned32
			MAX-ACCESS read-only
			STATUS current
			DESCRIPTION
				"Number of adjacent OSPF neighbors.
				
				XPath: /wing-stats/device[mac=key1]/ospf_stats/ospf_if[ifname=key2]/ospf_if_info[ospf_if_info_index=key3]/ospf_adj_nbr_count"
			::= { wingStatsDevDynRouteOspfIfInfoEntry 27 }

		
		-- 1.3.6.1.4.1.1916.2.131.50.1.4.2.34.13
		wingStatsDevDynRouteNeighborTable OBJECT-TYPE
			SYNTAX SEQUENCE OF WingStatsDevDynRouteNeighborEntry
			MAX-ACCESS not-accessible
			STATUS current
			DESCRIPTION
				"Description."
			::= { wingStatsDevDynRoute 13 }

		
		-- 1.3.6.1.4.1.1916.2.131.50.1.4.2.34.13.1
		wingStatsDevDynRouteNeighborEntry OBJECT-TYPE
			SYNTAX WingStatsDevDynRouteNeighborEntry
			MAX-ACCESS not-accessible
			STATUS current
			DESCRIPTION
				"Description."
			INDEX { wingStatsDevMac, wingStatsDevDynRouteNeighborIndex }
			::= { wingStatsDevDynRouteNeighborTable 1 }

		
		WingStatsDevDynRouteNeighborEntry ::=
			SEQUENCE { 
				wingStatsDevDynRouteNeighborIndex
					Unsigned32,
				wingStatsDevDynRouteNeighborRouterId
					DisplayString,
				wingStatsDevDynRouteNeighborPriority
					Unsigned32,
				wingStatsDevDynRouteNeighborSelfState
					DisplayString,
				wingStatsDevDynRouteNeighborDeadTime
					Unsigned32,
				wingStatsDevDynRouteNeighborAddr
					DisplayString,
				wingStatsDevDynRouteNeighborIfName
					DisplayString,
				wingStatsDevDynRouteNeighborSrcAddr
					DisplayString,
				wingStatsDevDynRouteNeighborRetansmitCount
					Unsigned32,
				wingStatsDevDynRouteNeighborRequestCount
					Unsigned32,
				wingStatsDevDynRouteNeighborSummaryCount
					Unsigned32
			 }

		-- 1.3.6.1.4.1.1916.2.131.50.1.4.2.34.13.1.1
		wingStatsDevDynRouteNeighborIndex OBJECT-TYPE
			SYNTAX Unsigned32 (1..4294967295)
			MAX-ACCESS read-only
			STATUS current
			DESCRIPTION
				"Neighbor information table index.
				
				XPath: /wing-stats/device[mac=key1]/ospf_stats/neighbor_info[neighbor_index=key2]/neighbor_index"
			::= { wingStatsDevDynRouteNeighborEntry 1 }

		
		-- 1.3.6.1.4.1.1916.2.131.50.1.4.2.34.13.1.2
		wingStatsDevDynRouteNeighborRouterId OBJECT-TYPE
			SYNTAX DisplayString
			MAX-ACCESS read-only
			STATUS current
			DESCRIPTION
				"Router ID.
				
				XPath: /wing-stats/device[mac=key1]/ospf_stats/neighbor_info[neighbor_index=key2]/router_id"
			::= { wingStatsDevDynRouteNeighborEntry 2 }

		
		-- 1.3.6.1.4.1.1916.2.131.50.1.4.2.34.13.1.3
		wingStatsDevDynRouteNeighborPriority OBJECT-TYPE
			SYNTAX Unsigned32
			MAX-ACCESS read-only
			STATUS current
			DESCRIPTION
				"OSPF Priority of this neighbor.
				
				XPath: /wing-stats/device[mac=key1]/ospf_stats/neighbor_info[neighbor_index=key2]/nbr_priority"
			::= { wingStatsDevDynRouteNeighborEntry 3 }

		
		-- 1.3.6.1.4.1.1916.2.131.50.1.4.2.34.13.1.4
		wingStatsDevDynRouteNeighborSelfState OBJECT-TYPE
			SYNTAX DisplayString
			MAX-ACCESS read-only
			STATUS current
			DESCRIPTION
				"OSPF state of this router and neighbor router
				
				XPath: /wing-stats/device[mac=key1]/ospf_stats/neighbor_info[neighbor_index=key2]/self_nbr_state"
			::= { wingStatsDevDynRouteNeighborEntry 4 }

		
		-- 1.3.6.1.4.1.1916.2.131.50.1.4.2.34.13.1.5
		wingStatsDevDynRouteNeighborDeadTime OBJECT-TYPE
			SYNTAX Unsigned32
			MAX-ACCESS read-only
			STATUS current
			DESCRIPTION
				"Interval after which the will be declared dead.
				
				XPath: /wing-stats/device[mac=key1]/ospf_stats/neighbor_info[neighbor_index=key2]/dead_time"
			::= { wingStatsDevDynRouteNeighborEntry 5 }

		
		-- 1.3.6.1.4.1.1916.2.131.50.1.4.2.34.13.1.6
		wingStatsDevDynRouteNeighborAddr OBJECT-TYPE
			SYNTAX DisplayString
			MAX-ACCESS read-only
			STATUS current
			DESCRIPTION
				"IP Address of the neighbor router.
				
				XPath: /wing-stats/device[mac=key1]/ospf_stats/neighbor_info[neighbor_index=key2]/nbr_addr"
			::= { wingStatsDevDynRouteNeighborEntry 6 }

		
		-- 1.3.6.1.4.1.1916.2.131.50.1.4.2.34.13.1.7
		wingStatsDevDynRouteNeighborIfName OBJECT-TYPE
			SYNTAX DisplayString
			MAX-ACCESS read-only
			STATUS current
			DESCRIPTION
				"Interface Name.
				
				XPath: /wing-stats/device[mac=key1]/ospf_stats/neighbor_info[neighbor_index=key2]/ifname"
			::= { wingStatsDevDynRouteNeighborEntry 7 }

		
		-- 1.3.6.1.4.1.1916.2.131.50.1.4.2.34.13.1.8
		wingStatsDevDynRouteNeighborSrcAddr OBJECT-TYPE
			SYNTAX DisplayString
			MAX-ACCESS read-only
			STATUS current
			DESCRIPTION
				"IP Address of this router.
				
				XPath: /wing-stats/device[mac=key1]/ospf_stats/neighbor_info[neighbor_index=key2]/src_addr"
			::= { wingStatsDevDynRouteNeighborEntry 8 }

		
		-- 1.3.6.1.4.1.1916.2.131.50.1.4.2.34.13.1.9
		wingStatsDevDynRouteNeighborRetansmitCount OBJECT-TYPE
			SYNTAX Unsigned32
			MAX-ACCESS read-only
			STATUS current
			DESCRIPTION
				"Link state request message retransmit count.
				
				XPath: /wing-stats/device[mac=key1]/ospf_stats/neighbor_info[neighbor_index=key2]/retransmit_count"
			::= { wingStatsDevDynRouteNeighborEntry 9 }

		
		-- 1.3.6.1.4.1.1916.2.131.50.1.4.2.34.13.1.10
		wingStatsDevDynRouteNeighborRequestCount OBJECT-TYPE
			SYNTAX Unsigned32
			MAX-ACCESS read-only
			STATUS current
			DESCRIPTION
				"Link state request message request count
				
				XPath: /wing-stats/device[mac=key1]/ospf_stats/neighbor_info[neighbor_index=key2]/request_count"
			::= { wingStatsDevDynRouteNeighborEntry 10 }

		
		-- 1.3.6.1.4.1.1916.2.131.50.1.4.2.34.13.1.11
		wingStatsDevDynRouteNeighborSummaryCount OBJECT-TYPE
			SYNTAX Unsigned32
			MAX-ACCESS read-only
			STATUS current
			DESCRIPTION
				"Summary LSA count.
				
				XPath: /wing-stats/device[mac=key1]/ospf_stats/neighbor_info[neighbor_index=key2]/summary_count"
			::= { wingStatsDevDynRouteNeighborEntry 11 }

		
-- /wing-stats/device/pppoe
		-- 1.3.6.1.4.1.1916.2.131.50.1.4.2.35
		wingStatsDevPppoe OBJECT IDENTIFIER ::= { wingStatsDev 35 }

		
		-- 1.3.6.1.4.1.1916.2.131.50.1.4.2.35.1
		wingStatsDevPppoeStatusTable OBJECT-TYPE
			SYNTAX SEQUENCE OF WingStatsDevPppoeStatusEntry
			MAX-ACCESS not-accessible
			STATUS current
			DESCRIPTION
				"
				
				/wing-stats/device/pppoe/status"
			::= { wingStatsDevPppoe 1 }

		
		-- 1.3.6.1.4.1.1916.2.131.50.1.4.2.35.1.1
		wingStatsDevPppoeStatusEntry OBJECT-TYPE
			SYNTAX WingStatsDevPppoeStatusEntry
			MAX-ACCESS not-accessible
			STATUS current
			DESCRIPTION
				"An entry in the table."
			INDEX { wingStatsDevMac }
			::= { wingStatsDevPppoeStatusTable 1 }

		
		WingStatsDevPppoeStatusEntry ::=
			SEQUENCE { 
				wingStatsDevPppoeStatusPeer
					MacAddress,
				wingStatsDevPppoeStatusSid
					OCTET STRING,
				wingStatsDevPppoeStatusService
					DisplayString,
				wingStatsDevPppoeStatusStatus
					DisplayString,
				wingStatsDevPppoeStatusMtu
					Unsigned32,
				wingStatsDevPppoeStatusDns1
					DisplayString,
				wingStatsDevPppoeStatusDns2
					DisplayString
			 }

		-- 1.3.6.1.4.1.1916.2.131.50.1.4.2.35.1.1.1
		wingStatsDevPppoeStatusPeer OBJECT-TYPE
			SYNTAX MacAddress
			MAX-ACCESS read-only
			STATUS current
			DESCRIPTION
				"PPPoE peer MAC address.
				
				XPath: /wing-stats/device[mac=key1]/pppoe/status/peer"
			::= { wingStatsDevPppoeStatusEntry 1 }

		
		-- 1.3.6.1.4.1.1916.2.131.50.1.4.2.35.1.1.2
		wingStatsDevPppoeStatusSid OBJECT-TYPE
			SYNTAX OCTET STRING
			MAX-ACCESS read-only
			STATUS current
			DESCRIPTION
				"PPPoE session ID.
				
				XPath: /wing-stats/device[mac=key1]/pppoe/status/sid"
			::= { wingStatsDevPppoeStatusEntry 2 }

		
		-- 1.3.6.1.4.1.1916.2.131.50.1.4.2.35.1.1.3
		wingStatsDevPppoeStatusService OBJECT-TYPE
			SYNTAX DisplayString
			MAX-ACCESS read-only
			STATUS current
			DESCRIPTION
				"PPPoE service name.
				
				XPath: /wing-stats/device[mac=key1]/pppoe/status/service"
			::= { wingStatsDevPppoeStatusEntry 3 }

		
		-- 1.3.6.1.4.1.1916.2.131.50.1.4.2.35.1.1.4
		wingStatsDevPppoeStatusStatus OBJECT-TYPE
			SYNTAX DisplayString
			MAX-ACCESS read-only
			STATUS current
			DESCRIPTION
				"PPPoE client connection status.
				
				XPath: /wing-stats/device[mac=key1]/pppoe/status/status"
			::= { wingStatsDevPppoeStatusEntry 4 }

		
		-- 1.3.6.1.4.1.1916.2.131.50.1.4.2.35.1.1.5
		wingStatsDevPppoeStatusMtu OBJECT-TYPE
			SYNTAX Unsigned32
			MAX-ACCESS read-only
			STATUS current
			DESCRIPTION
				"PPPoE client negotiated MTU with peer.
				
				XPath: /wing-stats/device[mac=key1]/pppoe/status/mtu"
			::= { wingStatsDevPppoeStatusEntry 5 }

		
		-- 1.3.6.1.4.1.1916.2.131.50.1.4.2.35.1.1.6
		wingStatsDevPppoeStatusDns1 OBJECT-TYPE
			SYNTAX DisplayString
			MAX-ACCESS read-only
			STATUS current
			DESCRIPTION
				"PPPoE server supplied name server1.
				
				XPath: /wing-stats/device[mac=key1]/pppoe/status/dns1"
			::= { wingStatsDevPppoeStatusEntry 6 }

		
		-- 1.3.6.1.4.1.1916.2.131.50.1.4.2.35.1.1.7
		wingStatsDevPppoeStatusDns2 OBJECT-TYPE
			SYNTAX DisplayString
			MAX-ACCESS read-only
			STATUS current
			DESCRIPTION
				"PPPoE server supplied name server2.
				
				XPath: /wing-stats/device[mac=key1]/pppoe/status/dns2"
			::= { wingStatsDevPppoeStatusEntry 7 }

		
		-- 1.3.6.1.4.1.1916.2.131.50.1.4.2.35.2
		wingStatsDevPppoeCfgTable OBJECT-TYPE
			SYNTAX SEQUENCE OF WingStatsDevPppoeCfgEntry
			MAX-ACCESS not-accessible
			STATUS current
			DESCRIPTION
				"
				
				/wing-stats/device/pppoe/config"
			::= { wingStatsDevPppoe 2 }

		
		-- 1.3.6.1.4.1.1916.2.131.50.1.4.2.35.2.1
		wingStatsDevPppoeCfgEntry OBJECT-TYPE
			SYNTAX WingStatsDevPppoeCfgEntry
			MAX-ACCESS not-accessible
			STATUS current
			DESCRIPTION
				"An entry in the table."
			INDEX { wingStatsDevMac }
			::= { wingStatsDevPppoeCfgTable 1 }

		
		WingStatsDevPppoeCfgEntry ::=
			SEQUENCE { 
				wingStatsDevPppoeCfgAuthtype
					DisplayString,
				wingStatsDevPppoeCfgIdleTime
					Unsigned32,
				wingStatsDevPppoeCfgKalive
					TruthValue,
				wingStatsDevPppoeCfgMtu
					Unsigned32,
				wingStatsDevPppoeCfgNet
					DisplayString,
				wingStatsDevPppoeCfgService
					DisplayString,
				wingStatsDevPppoeCfgUsername
					DisplayString,
				wingStatsDevPppoeCfgPasswd
					DisplayString,
				wingStatsDevPppoeCfgShutdown
					TruthValue
			 }

		-- 1.3.6.1.4.1.1916.2.131.50.1.4.2.35.2.1.1
		wingStatsDevPppoeCfgAuthtype OBJECT-TYPE
			SYNTAX DisplayString
			MAX-ACCESS read-only
			STATUS current
			DESCRIPTION
				"PPPoE client authentication type.
				
				XPath: /wing-stats/device[mac=key1]/pppoe/config/authtype"
			::= { wingStatsDevPppoeCfgEntry 1 }

		
		-- 1.3.6.1.4.1.1916.2.131.50.1.4.2.35.2.1.2
		wingStatsDevPppoeCfgIdleTime OBJECT-TYPE
			SYNTAX Unsigned32
			MAX-ACCESS read-only
			STATUS current
			DESCRIPTION
				"PPPoE client idle time.
				
				XPath: /wing-stats/device[mac=key1]/pppoe/config/idle_time"
			::= { wingStatsDevPppoeCfgEntry 2 }

		
		-- 1.3.6.1.4.1.1916.2.131.50.1.4.2.35.2.1.3
		wingStatsDevPppoeCfgKalive OBJECT-TYPE
			SYNTAX TruthValue
			MAX-ACCESS read-only
			STATUS current
			DESCRIPTION
				"PPPoE client keepalive.
				
				XPath: /wing-stats/device[mac=key1]/pppoe/config/kalive"
			::= { wingStatsDevPppoeCfgEntry 3 }

		
		-- 1.3.6.1.4.1.1916.2.131.50.1.4.2.35.2.1.4
		wingStatsDevPppoeCfgMtu OBJECT-TYPE
			SYNTAX Unsigned32
			MAX-ACCESS read-only
			STATUS current
			DESCRIPTION
				"PPPoE client MTU.
				
				XPath: /wing-stats/device[mac=key1]/pppoe/config/mtu"
			::= { wingStatsDevPppoeCfgEntry 4 }

		
		-- 1.3.6.1.4.1.1916.2.131.50.1.4.2.35.2.1.5
		wingStatsDevPppoeCfgNet OBJECT-TYPE
			SYNTAX DisplayString
			MAX-ACCESS read-only
			STATUS current
			DESCRIPTION
				"PPPoE client network in which DSL modem is connected.
				
				XPath: /wing-stats/device[mac=key1]/pppoe/config/net"
			::= { wingStatsDevPppoeCfgEntry 5 }

		
		-- 1.3.6.1.4.1.1916.2.131.50.1.4.2.35.2.1.6
		wingStatsDevPppoeCfgService OBJECT-TYPE
			SYNTAX DisplayString
			MAX-ACCESS read-only
			STATUS current
			DESCRIPTION
				"PPPoE service name.
				
				XPath: /wing-stats/device[mac=key1]/pppoe/config/service"
			::= { wingStatsDevPppoeCfgEntry 6 }

		
		-- 1.3.6.1.4.1.1916.2.131.50.1.4.2.35.2.1.7
		wingStatsDevPppoeCfgUsername OBJECT-TYPE
			SYNTAX DisplayString
			MAX-ACCESS read-only
			STATUS current
			DESCRIPTION
				"PPPoE client authentication username.
				
				XPath: /wing-stats/device[mac=key1]/pppoe/config/username"
			::= { wingStatsDevPppoeCfgEntry 7 }

		
		-- 1.3.6.1.4.1.1916.2.131.50.1.4.2.35.2.1.8
		wingStatsDevPppoeCfgPasswd OBJECT-TYPE
			SYNTAX DisplayString
			MAX-ACCESS read-only
			STATUS current
			DESCRIPTION
				"PPPoE client authentication password.
				
				XPath: /wing-stats/device[mac=key1]/pppoe/config/passwd"
			::= { wingStatsDevPppoeCfgEntry 8 }

		
		-- 1.3.6.1.4.1.1916.2.131.50.1.4.2.35.2.1.9
		wingStatsDevPppoeCfgShutdown OBJECT-TYPE
			SYNTAX TruthValue
			MAX-ACCESS read-only
			STATUS current
			DESCRIPTION
				"PPPoE client mode of operation.
				
				XPath: /wing-stats/device[mac=key1]/pppoe/config/shutdown"
			::= { wingStatsDevPppoeCfgEntry 9 }

		
-- /wing-stats/device/l2tpv3_stats
		-- 1.3.6.1.4.1.1916.2.131.50.1.4.2.36
		wingStatsDevl2tpv3 OBJECT IDENTIFIER ::= { wingStatsDev 36 }

		
		-- 1.3.6.1.4.1.1916.2.131.50.1.4.2.36.1
		wingStatsDevl2tpv3TunnelTable OBJECT-TYPE
			SYNTAX SEQUENCE OF WingStatsDevl2tpv3TunnelEntry
			MAX-ACCESS not-accessible
			STATUS current
			DESCRIPTION
				"/wing-stats/device/l2tpv3_stats/l2tpv3_tunnels"
			::= { wingStatsDevl2tpv3 1 }

		
		-- 1.3.6.1.4.1.1916.2.131.50.1.4.2.36.1.1
		wingStatsDevl2tpv3TunnelEntry OBJECT-TYPE
			SYNTAX WingStatsDevl2tpv3TunnelEntry
			MAX-ACCESS not-accessible
			STATUS current
			DESCRIPTION
				"An entry in the table."
			INDEX { wingStatsDevMac, wingStatsDevl2tpv3TunnelName }
			::= { wingStatsDevl2tpv3TunnelTable 1 }

		
		WingStatsDevl2tpv3TunnelEntry ::=
			SEQUENCE { 
				wingStatsDevl2tpv3TunnelName
					WingIdentifier,
				wingStatsDevl2tpv3TunnelCtrlConnId
					Unsigned32,
				wingStatsDevl2tpv3TunnelUpTime
					Integer32,
				wingStatsDevl2tpv3TunnelPeerAddr
					DisplayString,
				wingStatsDevl2tpv3TunnelLocalAddr
					DisplayString,
				wingStatsDevl2tpv3TunnelMtu
					Unsigned32,
				wingStatsDevl2tpv3TunnelPeerHostName
					DisplayString,
				wingStatsDevl2tpv3TunnelPeerCtrlConnId
					Unsigned32,
				wingStatsDevl2tpv3TunnelPeerVendorName
					DisplayString,
				wingStatsDevl2tpv3TunnelState
					DisplayString,
				wingStatsDevl2tpv3TunnelEncapsulationProtocol
					DisplayString,
				wingStatsDevl2tpv3TunnelNextTxSeqNum
					Unsigned32,
				wingStatsDevl2tpv3TunnelNextRxSeqNum
					Unsigned32,
				wingStatsDevl2tpv3TunnelRxAckSeqNum
					Unsigned32,
				wingStatsDevl2tpv3TunnelRetransmitCount
					Unsigned32,
				wingStatsDevl2tpv3TunnelReconnectCount
					Unsigned32
			 }

		-- 1.3.6.1.4.1.1916.2.131.50.1.4.2.36.1.1.1
		wingStatsDevl2tpv3TunnelName OBJECT-TYPE
			SYNTAX WingIdentifier
			MAX-ACCESS read-only
			STATUS current
			DESCRIPTION
				"Name of the L2TP-v3 tunnel.
				
				XPath: /wing-stats/device[mac=key1]/l2tpv3_stats/l2tpv3_tunnels[tunnel_name=key2]/tunnel_name"
			::= { wingStatsDevl2tpv3TunnelEntry 1 }

		
		-- 1.3.6.1.4.1.1916.2.131.50.1.4.2.36.1.1.2
		wingStatsDevl2tpv3TunnelCtrlConnId OBJECT-TYPE
			SYNTAX Unsigned32
			MAX-ACCESS read-only
			STATUS current
			DESCRIPTION
				"Control connection ID.
				
				XPath: /wing-stats/device[mac=key1]/l2tpv3_stats/l2tpv3_tunnels[tunnel_name=key2]/ctrl_conn_id"
			::= { wingStatsDevl2tpv3TunnelEntry 2 }

		
		-- 1.3.6.1.4.1.1916.2.131.50.1.4.2.36.1.1.3
		wingStatsDevl2tpv3TunnelUpTime OBJECT-TYPE
			SYNTAX Integer32
			MAX-ACCESS read-only
			STATUS current
			DESCRIPTION
				"Tunnel uptime in seconds.
				
				XPath: /wing-stats/device[mac=key1]/l2tpv3_stats/l2tpv3_tunnels[tunnel_name=key2]/uptime"
			::= { wingStatsDevl2tpv3TunnelEntry 3 }

		
		-- 1.3.6.1.4.1.1916.2.131.50.1.4.2.36.1.1.4
		wingStatsDevl2tpv3TunnelPeerAddr OBJECT-TYPE
			SYNTAX DisplayString
			MAX-ACCESS read-only
			STATUS current
			DESCRIPTION
				"L2TPv3 Peer.
				
				XPath: /wing-stats/device[mac=key1]/l2tpv3_stats/l2tpv3_tunnels[tunnel_name=key2]/peer_addr"
			::= { wingStatsDevl2tpv3TunnelEntry 4 }

		
		-- 1.3.6.1.4.1.1916.2.131.50.1.4.2.36.1.1.5
		wingStatsDevl2tpv3TunnelLocalAddr OBJECT-TYPE
			SYNTAX DisplayString
			MAX-ACCESS read-only
			STATUS current
			DESCRIPTION
				"IP address of local end-point of the L2TPv3 tunnel.
				
				XPath: /wing-stats/device[mac=key1]/l2tpv3_stats/l2tpv3_tunnels[tunnel_name=key2]/local_addr"
			::= { wingStatsDevl2tpv3TunnelEntry 5 }

		
		-- 1.3.6.1.4.1.1916.2.131.50.1.4.2.36.1.1.6
		wingStatsDevl2tpv3TunnelMtu OBJECT-TYPE
			SYNTAX Unsigned32
			MAX-ACCESS read-write
			STATUS current
			DESCRIPTION
				"MTU size for this tunnel.
				
				XPath: /wing-stats/device[mac=key1]/l2tpv3_stats/l2tpv3_tunnels[tunnel_name=key2]/mtu"
			::= { wingStatsDevl2tpv3TunnelEntry 6 }

		
		-- 1.3.6.1.4.1.1916.2.131.50.1.4.2.36.1.1.7
		wingStatsDevl2tpv3TunnelPeerHostName OBJECT-TYPE
			SYNTAX DisplayString
			MAX-ACCESS read-only
			STATUS current
			DESCRIPTION
				"Peer's hostname.
				
				XPath: /wing-stats/device[mac=key1]/l2tpv3_stats/l2tpv3_tunnels[tunnel_name=key2]/peer_host_name"
			::= { wingStatsDevl2tpv3TunnelEntry 7 }

		
		-- 1.3.6.1.4.1.1916.2.131.50.1.4.2.36.1.1.8
		wingStatsDevl2tpv3TunnelPeerCtrlConnId OBJECT-TYPE
			SYNTAX Unsigned32
			MAX-ACCESS read-only
			STATUS current
			DESCRIPTION
				"Peer's control connection ID.
				
				XPath: /wing-stats/device[mac=key1]/l2tpv3_stats/l2tpv3_tunnels[tunnel_name=key2]/peer_ctrl_conn_id"
			::= { wingStatsDevl2tpv3TunnelEntry 8 }

		
		-- 1.3.6.1.4.1.1916.2.131.50.1.4.2.36.1.1.9
		wingStatsDevl2tpv3TunnelPeerVendorName OBJECT-TYPE
			SYNTAX DisplayString
			MAX-ACCESS read-only
			STATUS current
			DESCRIPTION
				"Peer's vendor name.
				
				XPath: /wing-stats/device[mac=key1]/l2tpv3_stats/l2tpv3_tunnels[tunnel_name=key2]/peer_vendor_name"
			::= { wingStatsDevl2tpv3TunnelEntry 9 }

		
		-- 1.3.6.1.4.1.1916.2.131.50.1.4.2.36.1.1.10
		wingStatsDevl2tpv3TunnelState OBJECT-TYPE
			SYNTAX DisplayString
			MAX-ACCESS read-only
			STATUS current
			DESCRIPTION
				"Tunnel state
				Idle
				WaitForSCCRP
				WaitForSCCCN
				Established
				Closing
				
				XPath: /wing-stats/device[mac=key1]/l2tpv3_stats/l2tpv3_tunnels[tunnel_name=key2]/tunnel_state"
			::= { wingStatsDevl2tpv3TunnelEntry 10 }

		
		-- 1.3.6.1.4.1.1916.2.131.50.1.4.2.36.1.1.11
		wingStatsDevl2tpv3TunnelEncapsulationProtocol OBJECT-TYPE
			SYNTAX DisplayString
			MAX-ACCESS read-write
			STATUS current
			DESCRIPTION
				"EncapsulationProtocol
				IP
				UDP
				
				XPath: /wing-stats/device[mac=key1]/l2tpv3_stats/l2tpv3_tunnels[tunnel_name=key2]/encapsulation_protocol"
			::= { wingStatsDevl2tpv3TunnelEntry 11 }

		
		-- 1.3.6.1.4.1.1916.2.131.50.1.4.2.36.1.1.12
		wingStatsDevl2tpv3TunnelNextTxSeqNum OBJECT-TYPE
			SYNTAX Unsigned32
			MAX-ACCESS read-only
			STATUS current
			DESCRIPTION
				"Sequence number of the next msg to the peer.
				
				XPath: /wing-stats/device[mac=key1]/l2tpv3_stats/l2tpv3_tunnels[tunnel_name=key2]/next_tx_seq_num"
			::= { wingStatsDevl2tpv3TunnelEntry 12 }

		
		-- 1.3.6.1.4.1.1916.2.131.50.1.4.2.36.1.1.13
		wingStatsDevl2tpv3TunnelNextRxSeqNum OBJECT-TYPE
			SYNTAX Unsigned32
			MAX-ACCESS read-only
			STATUS current
			DESCRIPTION
				"Expected sequence number of the next msg from the peer.
				
				XPath: /wing-stats/device[mac=key1]/l2tpv3_stats/l2tpv3_tunnels[tunnel_name=key2]/next_rx_seq_num"
			::= { wingStatsDevl2tpv3TunnelEntry 13 }

		
		-- 1.3.6.1.4.1.1916.2.131.50.1.4.2.36.1.1.14
		wingStatsDevl2tpv3TunnelRxAckSeqNum OBJECT-TYPE
			SYNTAX Unsigned32
			MAX-ACCESS read-only
			STATUS current
			DESCRIPTION
				"Seuence number of the next msg expected by the peer.
				
				XPath: /wing-stats/device[mac=key1]/l2tpv3_stats/l2tpv3_tunnels[tunnel_name=key2]/rx_ack_seq_num"
			::= { wingStatsDevl2tpv3TunnelEntry 14 }

		
		-- 1.3.6.1.4.1.1916.2.131.50.1.4.2.36.1.1.15
		wingStatsDevl2tpv3TunnelRetransmitCount OBJECT-TYPE
			SYNTAX Unsigned32
			MAX-ACCESS read-only
			STATUS current
			DESCRIPTION
				"Retransmission count.
				
				XPath: /wing-stats/device[mac=key1]/l2tpv3_stats/l2tpv3_tunnels[tunnel_name=key2]/retransmit_count"
			::= { wingStatsDevl2tpv3TunnelEntry 15 }

		
		-- 1.3.6.1.4.1.1916.2.131.50.1.4.2.36.1.1.16
		wingStatsDevl2tpv3TunnelReconnectCount OBJECT-TYPE
			SYNTAX Unsigned32
			MAX-ACCESS read-only
			STATUS current
			DESCRIPTION
				"Reconnection count.
				
				XPath: /wing-stats/device[mac=key1]/l2tpv3_stats/l2tpv3_tunnels[tunnel_name=key2]/reconnect_count"
			::= { wingStatsDevl2tpv3TunnelEntry 16 }

		
-- /wing-stats/device/l2tpv3_stats/l2tpv3_tunnels/l2tpv3_sessions
		-- 1.3.6.1.4.1.1916.2.131.50.1.4.2.36.2
		wingStatsDevl2tpv3Sessions OBJECT IDENTIFIER ::= { wingStatsDevl2tpv3 2 }

		
		-- 1.3.6.1.4.1.1916.2.131.50.1.4.2.36.2.1
		wingStatsDevl2tpv3SessionsVlansTable OBJECT-TYPE
			SYNTAX SEQUENCE OF WingStatsDevl2tpv3SessionsVlansEntry
			MAX-ACCESS not-accessible
			STATUS current
			DESCRIPTION
				"/wing-stats/device/l2tpv3_stats/l2tpv3_tunnels/l2tpv3_sessions/vlans"
			::= { wingStatsDevl2tpv3Sessions 1 }

		
		-- 1.3.6.1.4.1.1916.2.131.50.1.4.2.36.2.1.1
		wingStatsDevl2tpv3SessionsVlansEntry OBJECT-TYPE
			SYNTAX WingStatsDevl2tpv3SessionsVlansEntry
			MAX-ACCESS not-accessible
			STATUS current
			DESCRIPTION
				"An entry in the table."
			INDEX { wingStatsDevMac, wingStatsDevl2tpv3SessionsName, wingStatsDevl2tpv3SessionsVlanId }
			::= { wingStatsDevl2tpv3SessionsVlansTable 1 }

		
		WingStatsDevl2tpv3SessionsVlansEntry ::=
			SEQUENCE { 
				wingStatsDevl2tpv3SessionsVlanId
					Unsigned32
			 }

		-- 1.3.6.1.4.1.1916.2.131.50.1.4.2.36.2.1.1.1
		wingStatsDevl2tpv3SessionsVlanId OBJECT-TYPE
			SYNTAX Unsigned32 (1..65535)
			MAX-ACCESS read-only
			STATUS current
			DESCRIPTION
				"Extended VLAN ID.
				
				XPath: /wing-stats/device[mac=key1]/l2tpv3_stats/l2tpv3_tunnels[tunnel_name=key2]/l2tpv3_sessions[session_name=key3]/vlans[vlan_id=key4]/vlan_id"
			::= { wingStatsDevl2tpv3SessionsVlansEntry 1 }

		
		-- 1.3.6.1.4.1.1916.2.131.50.1.4.2.36.2.2
		wingStatsDevl2tpv3SessionsTable OBJECT-TYPE
			SYNTAX SEQUENCE OF WingStatsDevl2tpv3SessionsEntry
			MAX-ACCESS not-accessible
			STATUS current
			DESCRIPTION
				"/wing-stats/device/l2tpv3_stats/l2tpv3_tunnels/l2tpv3_sessions"
			::= { wingStatsDevl2tpv3Sessions 2 }

		
		-- 1.3.6.1.4.1.1916.2.131.50.1.4.2.36.2.2.1
		wingStatsDevl2tpv3SessionsEntry OBJECT-TYPE
			SYNTAX WingStatsDevl2tpv3SessionsEntry
			MAX-ACCESS not-accessible
			STATUS current
			DESCRIPTION
				"An entry in the table."
			INDEX { wingStatsDevMac, wingStatsDevl2tpv3TunnelName, wingStatsDevl2tpv3SessionsName }
			::= { wingStatsDevl2tpv3SessionsTable 1 }

		
		WingStatsDevl2tpv3SessionsEntry ::=
			SEQUENCE { 
				wingStatsDevl2tpv3SessionsName
					WingIdentifier,
				wingStatsDevl2tpv3TunnelNativeVlanId
					Unsigned32,
				wingStatsDevl2tpv3TunnelTrunkSession
					TruthValue,
				wingStatsDevl2tpv3TunnelNativeVlanTagged
					TruthValue,
				wingStatsDevl2tpv3SessionsPseudoWireType
					DisplayString,
				wingStatsDevl2tpv3SessionsCallSerialNumber
					Unsigned32,
				wingStatsDevl2tpv3SessionsLocalSessionId
					Unsigned32,
				wingStatsDevl2tpv3SessionsRemoteSessionId
					Unsigned32,
				wingStatsDevl2tpv3SessionsLocalCookieSize
					Unsigned32,
				wingStatsDevl2tpv3SessionsLocalcookieWord1
					Unsigned32,
				wingStatsDevl2tpv3SessionsLocalCookieWord2
					Unsigned32,
				wingStatsDevl2tpv3SessionsRemoteCookieSize
					Unsigned32,
				wingStatsDevl2tpv3SessionsRemoteCookieWord1
					Unsigned32,
				wingStatsDevl2tpv3SessionsRemoteCookieWord2
					Unsigned32,
				wingStatsDevl2tpv3SessionsState
					DisplayString,
				wingStatsDevl2tpv3SessionsRemoteEndId
					DisplayString,
				wingStatsDevl2tpv3SessionsRxPktCounter
					Unsigned32,
				wingStatsDevl2tpv3SessionsRxBytesCounter
					Unsigned32,
				wingStatsDevl2tpv3SessionsTxPktCounter
					Unsigned32,
				wingStatsDevl2tpv3SessionsTxBytesCounter
					Unsigned32,
				wingStatsDevl2tpv3SessionsNumDroppedPkts
					Unsigned32
			 }

		-- 1.3.6.1.4.1.1916.2.131.50.1.4.2.36.2.2.1.1
		wingStatsDevl2tpv3SessionsName OBJECT-TYPE
			SYNTAX WingIdentifier
			MAX-ACCESS read-only
			STATUS current
			DESCRIPTION
				"Name of the L2TPv3 session
				
				XPath: /wing-stats/device[mac=key1]/l2tpv3_stats/l2tpv3_tunnels[tunnel_name=key2]/l2tpv3_sessions[session_name=key3]/session_name"
			::= { wingStatsDevl2tpv3SessionsEntry 1 }

		
		-- 1.3.6.1.4.1.1916.2.131.50.1.4.2.36.2.2.1.2
		wingStatsDevl2tpv3TunnelNativeVlanId OBJECT-TYPE
			SYNTAX Unsigned32
			MAX-ACCESS read-only
			STATUS current
			DESCRIPTION
				"Native VLAN ID.
				
				XPath: /wing-stats/device[mac=key1]/l2tpv3_stats/l2tpv3_tunnels[tunnel_name=key2]/l2tpv3_sessions[session_name=key3]/native_vlan_id"
			::= { wingStatsDevl2tpv3SessionsEntry 2 }

		
		-- 1.3.6.1.4.1.1916.2.131.50.1.4.2.36.2.2.1.3
		wingStatsDevl2tpv3TunnelTrunkSession OBJECT-TYPE
			SYNTAX TruthValue
			MAX-ACCESS read-only
			STATUS current
			DESCRIPTION
				"Whether session carries traffic from/to multiple vlans.
				
				XPath: /wing-stats/device[mac=key1]/l2tpv3_stats/l2tpv3_tunnels[tunnel_name=key2]/l2tpv3_sessions[session_name=key3]/trunk_session"
			::= { wingStatsDevl2tpv3SessionsEntry 3 }

		
		-- 1.3.6.1.4.1.1916.2.131.50.1.4.2.36.2.2.1.4
		wingStatsDevl2tpv3TunnelNativeVlanTagged OBJECT-TYPE
			SYNTAX TruthValue
			MAX-ACCESS read-only
			STATUS current
			DESCRIPTION
				"Whether native VLAN packets are tagged.
				
				XPath: /wing-stats/device[mac=key1]/l2tpv3_stats/l2tpv3_tunnels[tunnel_name=key2]/l2tpv3_sessions[session_name=key3]/native_vlan_tagged"
			::= { wingStatsDevl2tpv3SessionsEntry 4 }

		
		-- 1.3.6.1.4.1.1916.2.131.50.1.4.2.36.2.2.1.5
		wingStatsDevl2tpv3SessionsPseudoWireType OBJECT-TYPE
			SYNTAX DisplayString
			MAX-ACCESS read-only
			STATUS current
			DESCRIPTION
				"L2TPv3 pseudo wire type.
				Ethernet
				Ethernet_VLAN
				
				XPath: /wing-stats/device[mac=key1]/l2tpv3_stats/l2tpv3_tunnels[tunnel_name=key2]/l2tpv3_sessions[session_name=key3]/pseudo_wire_type"
			::= { wingStatsDevl2tpv3SessionsEntry 5 }

		
		-- 1.3.6.1.4.1.1916.2.131.50.1.4.2.36.2.2.1.6
		wingStatsDevl2tpv3SessionsCallSerialNumber OBJECT-TYPE
			SYNTAX Unsigned32
			MAX-ACCESS read-only
			STATUS current
			DESCRIPTION
				"Serial number for the session.
				
				XPath: /wing-stats/device[mac=key1]/l2tpv3_stats/l2tpv3_tunnels[tunnel_name=key2]/l2tpv3_sessions[session_name=key3]/call_serial_number"
			::= { wingStatsDevl2tpv3SessionsEntry 6 }

		
		-- 1.3.6.1.4.1.1916.2.131.50.1.4.2.36.2.2.1.7
		wingStatsDevl2tpv3SessionsLocalSessionId OBJECT-TYPE
			SYNTAX Unsigned32
			MAX-ACCESS read-only
			STATUS current
			DESCRIPTION
				"Local Session ID.
				
				XPath: /wing-stats/device[mac=key1]/l2tpv3_stats/l2tpv3_tunnels[tunnel_name=key2]/l2tpv3_sessions[session_name=key3]/local_session_id"
			::= { wingStatsDevl2tpv3SessionsEntry 7 }

		
		-- 1.3.6.1.4.1.1916.2.131.50.1.4.2.36.2.2.1.8
		wingStatsDevl2tpv3SessionsRemoteSessionId OBJECT-TYPE
			SYNTAX Unsigned32
			MAX-ACCESS read-only
			STATUS current
			DESCRIPTION
				"Remote Session ID.
				
				XPath: /wing-stats/device[mac=key1]/l2tpv3_stats/l2tpv3_tunnels[tunnel_name=key2]/l2tpv3_sessions[session_name=key3]/remote_session_id"
			::= { wingStatsDevl2tpv3SessionsEntry 8 }

		
		-- 1.3.6.1.4.1.1916.2.131.50.1.4.2.36.2.2.1.9
		wingStatsDevl2tpv3SessionsLocalCookieSize OBJECT-TYPE
			SYNTAX Unsigned32
			MAX-ACCESS read-only
			STATUS current
			DESCRIPTION
				"Size of local cookie: 0, 4 or 8 bytes.
				
				XPath: /wing-stats/device[mac=key1]/l2tpv3_stats/l2tpv3_tunnels[tunnel_name=key2]/l2tpv3_sessions[session_name=key3]/local_cookie_size"
			::= { wingStatsDevl2tpv3SessionsEntry 9 }

		
		-- 1.3.6.1.4.1.1916.2.131.50.1.4.2.36.2.2.1.10
		wingStatsDevl2tpv3SessionsLocalcookieWord1 OBJECT-TYPE
			SYNTAX Unsigned32
			MAX-ACCESS read-only
			STATUS current
			DESCRIPTION
				"First word of local cookie.
				
				XPath: /wing-stats/device[mac=key1]/l2tpv3_stats/l2tpv3_tunnels[tunnel_name=key2]/l2tpv3_sessions[session_name=key3]/local_cookie_word1"
			::= { wingStatsDevl2tpv3SessionsEntry 10 }

		
		-- 1.3.6.1.4.1.1916.2.131.50.1.4.2.36.2.2.1.11
		wingStatsDevl2tpv3SessionsLocalCookieWord2 OBJECT-TYPE
			SYNTAX Unsigned32
			MAX-ACCESS read-only
			STATUS current
			DESCRIPTION
				"Second word of local cookie.
				
				XPath: /wing-stats/device[mac=key1]/l2tpv3_stats/l2tpv3_tunnels[tunnel_name=key2]/l2tpv3_sessions[session_name=key3]/local_cookie_word2"
			::= { wingStatsDevl2tpv3SessionsEntry 11 }

		
		-- 1.3.6.1.4.1.1916.2.131.50.1.4.2.36.2.2.1.12
		wingStatsDevl2tpv3SessionsRemoteCookieSize OBJECT-TYPE
			SYNTAX Unsigned32
			MAX-ACCESS read-only
			STATUS current
			DESCRIPTION
				"Size of remote cookie: 0, 4 or 8 bytes.
				
				XPath: /wing-stats/device[mac=key1]/l2tpv3_stats/l2tpv3_tunnels[tunnel_name=key2]/l2tpv3_sessions[session_name=key3]/remote_cookie_size"
			::= { wingStatsDevl2tpv3SessionsEntry 12 }

		
		-- 1.3.6.1.4.1.1916.2.131.50.1.4.2.36.2.2.1.13
		wingStatsDevl2tpv3SessionsRemoteCookieWord1 OBJECT-TYPE
			SYNTAX Unsigned32
			MAX-ACCESS read-only
			STATUS current
			DESCRIPTION
				"First word of remote cookie.
				
				XPath: /wing-stats/device[mac=key1]/l2tpv3_stats/l2tpv3_tunnels[tunnel_name=key2]/l2tpv3_sessions[session_name=key3]/remote_cookie_word1"
			::= { wingStatsDevl2tpv3SessionsEntry 13 }

		
		-- 1.3.6.1.4.1.1916.2.131.50.1.4.2.36.2.2.1.14
		wingStatsDevl2tpv3SessionsRemoteCookieWord2 OBJECT-TYPE
			SYNTAX Unsigned32
			MAX-ACCESS read-only
			STATUS current
			DESCRIPTION
				"Second word of remote cookie.
				
				XPath: /wing-stats/device[mac=key1]/l2tpv3_stats/l2tpv3_tunnels[tunnel_name=key2]/l2tpv3_sessions[session_name=key3]/remote_cookie_word2"
			::= { wingStatsDevl2tpv3SessionsEntry 14 }

		
		-- 1.3.6.1.4.1.1916.2.131.50.1.4.2.36.2.2.1.15
		wingStatsDevl2tpv3SessionsState OBJECT-TYPE
			SYNTAX DisplayString
			MAX-ACCESS read-only
			STATUS current
			DESCRIPTION
				"Session state.
				Idle
				WaitForICRP
				Established
				WaitForICCN
				LostTie
				
				XPath: /wing-stats/device[mac=key1]/l2tpv3_stats/l2tpv3_tunnels[tunnel_name=key2]/l2tpv3_sessions[session_name=key3]/session_state"
			::= { wingStatsDevl2tpv3SessionsEntry 15 }

		
		-- 1.3.6.1.4.1.1916.2.131.50.1.4.2.36.2.2.1.16
		wingStatsDevl2tpv3SessionsRemoteEndId OBJECT-TYPE
			SYNTAX DisplayString
			MAX-ACCESS read-only
			STATUS current
			DESCRIPTION
				"Remote End ID.
				
				XPath: /wing-stats/device[mac=key1]/l2tpv3_stats/l2tpv3_tunnels[tunnel_name=key2]/l2tpv3_sessions[session_name=key3]/remote_end_id"
			::= { wingStatsDevl2tpv3SessionsEntry 16 }

		
		-- 1.3.6.1.4.1.1916.2.131.50.1.4.2.36.2.2.1.17
		wingStatsDevl2tpv3SessionsRxPktCounter OBJECT-TYPE
			SYNTAX Unsigned32
			MAX-ACCESS read-only
			STATUS current
			DESCRIPTION
				"Number of packets received.
				
				XPath: /wing-stats/device[mac=key1]/l2tpv3_stats/l2tpv3_tunnels[tunnel_name=key2]/l2tpv3_sessions[session_name=key3]/rx_pkt_counter"
			::= { wingStatsDevl2tpv3SessionsEntry 17 }

		
		-- 1.3.6.1.4.1.1916.2.131.50.1.4.2.36.2.2.1.18
		wingStatsDevl2tpv3SessionsRxBytesCounter OBJECT-TYPE
			SYNTAX Unsigned32
			MAX-ACCESS read-only
			STATUS current
			DESCRIPTION
				"Number of bytes received.
				
				XPath: /wing-stats/device[mac=key1]/l2tpv3_stats/l2tpv3_tunnels[tunnel_name=key2]/l2tpv3_sessions[session_name=key3]/rx_bytes_counter"
			::= { wingStatsDevl2tpv3SessionsEntry 18 }

		
		-- 1.3.6.1.4.1.1916.2.131.50.1.4.2.36.2.2.1.19
		wingStatsDevl2tpv3SessionsTxPktCounter OBJECT-TYPE
			SYNTAX Unsigned32
			MAX-ACCESS read-only
			STATUS current
			DESCRIPTION
				"Number of packets sent.
				
				XPath: /wing-stats/device[mac=key1]/l2tpv3_stats/l2tpv3_tunnels[tunnel_name=key2]/l2tpv3_sessions[session_name=key3]/tx_pkt_counter"
			::= { wingStatsDevl2tpv3SessionsEntry 19 }

		
		-- 1.3.6.1.4.1.1916.2.131.50.1.4.2.36.2.2.1.20
		wingStatsDevl2tpv3SessionsTxBytesCounter OBJECT-TYPE
			SYNTAX Unsigned32
			MAX-ACCESS read-only
			STATUS current
			DESCRIPTION
				"Number of bytes sent.
				
				XPath: /wing-stats/device[mac=key1]/l2tpv3_stats/l2tpv3_tunnels[tunnel_name=key2]/l2tpv3_sessions[session_name=key3]/tx_bytes_counter"
			::= { wingStatsDevl2tpv3SessionsEntry 20 }

		
		-- 1.3.6.1.4.1.1916.2.131.50.1.4.2.36.2.2.1.21
		wingStatsDevl2tpv3SessionsNumDroppedPkts OBJECT-TYPE
			SYNTAX Unsigned32
			MAX-ACCESS read-only
			STATUS current
			DESCRIPTION
				"Number of packets dropped.
				
				XPath: /wing-stats/device[mac=key1]/l2tpv3_stats/l2tpv3_tunnels[tunnel_name=key2]/l2tpv3_sessions[session_name=key3]/num_dropped_pkts"
			::= { wingStatsDevl2tpv3SessionsEntry 21 }

		
-- Statistics on RF Domain
-- /wing-stats/rf_domain
		-- 1.3.6.1.4.1.1916.2.131.50.1.4.3
		wingStatsRfd OBJECT IDENTIFIER ::= { wingStats 3 }

		
		-- 1.3.6.1.4.1.1916.2.131.50.1.4.3.1
		wingStatsRfdTable OBJECT-TYPE
			SYNTAX SEQUENCE OF WingStatsRfdEntry
			MAX-ACCESS not-accessible
			STATUS current
			DESCRIPTION
				"Status of RF Domains
				
				/wing-stats/rf_domain"
			::= { wingStatsRfd 1 }

		
		-- 1.3.6.1.4.1.1916.2.131.50.1.4.3.1.1
		wingStatsRfdEntry OBJECT-TYPE
			SYNTAX WingStatsRfdEntry
			MAX-ACCESS not-accessible
			STATUS current
			DESCRIPTION
				"An entry in the table."
			INDEX { wingStatsRfdName }
			::= { wingStatsRfdTable 1 }

		
		WingStatsRfdEntry ::=
			SEQUENCE { 
				wingStatsRfdName
					WingIdentifier,
				wingStatsRfdManager
					MacAddress
			 }

		-- 1.3.6.1.4.1.1916.2.131.50.1.4.3.1.1.1
		wingStatsRfdName OBJECT-TYPE
			SYNTAX WingIdentifier
			MAX-ACCESS read-only
			STATUS current
			DESCRIPTION
				"RF Domain name
				
				XPath: /wing-stats/rf_domain[name=key1]/name"
			::= { wingStatsRfdEntry 1 }

		
		-- 1.3.6.1.4.1.1916.2.131.50.1.4.3.1.1.2
		wingStatsRfdManager OBJECT-TYPE
			SYNTAX MacAddress
			MAX-ACCESS read-only
			STATUS current
			DESCRIPTION
				"MAC address of RF Domain manager
				
				XPath: /wing-stats/rf_domain[name=key1]/manager"
			::= { wingStatsRfdEntry 2 }

		
-- /wing-stats/rf_domain/wireless
		-- 1.3.6.1.4.1.1916.2.131.50.1.4.3.2
		wingStatsRfdWl OBJECT IDENTIFIER ::= { wingStatsRfd 2 }

		
-- /wing-stats/rf_domain/wireless/ap-info
		-- 1.3.6.1.4.1.1916.2.131.50.1.4.3.2.1
		wingStatsRfdWlApInfo OBJECT IDENTIFIER ::= { wingStatsRfdWl 1 }

		
		-- 1.3.6.1.4.1.1916.2.131.50.1.4.3.2.1.1
		wingStatsRfdWlApInfoTable OBJECT-TYPE
			SYNTAX SEQUENCE OF WingStatsRfdWlApInfoEntry
			MAX-ACCESS not-accessible
			STATUS current
			DESCRIPTION
				"Status of managed Access Points on RF Domain
				
				/wing-stats/rf_domain/wireless/ap-info"
			::= { wingStatsRfdWlApInfo 1 }

		
		-- 1.3.6.1.4.1.1916.2.131.50.1.4.3.2.1.1.1
		wingStatsRfdWlApInfoEntry OBJECT-TYPE
			SYNTAX WingStatsRfdWlApInfoEntry
			MAX-ACCESS not-accessible
			STATUS current
			DESCRIPTION
				"An entry in the table."
			INDEX { wingStatsRfdName, wingStatsRfdWlApInfoMac }
			::= { wingStatsRfdWlApInfoTable 1 }

		
		WingStatsRfdWlApInfoEntry ::=
			SEQUENCE { 
				wingStatsRfdWlApInfoMac
					MacAddress,
				wingStatsRfdWlApInfoFaultDetected
					TruthValue,
				wingStatsRfdWlApInfoNumRadios
					Unsigned32,
				wingStatsRfdWlApInfoNumClients
					Unsigned32,
				wingStatsRfdWlApInfoLastCalTime
					DisplayString,
				wingStatsRfdWlApInfoType
					DisplayString,
				wingStatsRfdWlApInfoStatsMode
					DisplayString,
				wingStatsRfdWlApInfoStatsInterval
					Unsigned32,
				wingStatsRfdWlApInfoHostname
					DisplayString,
				wingStatsRfdWlApInfoRfDomainName
					DisplayString,
				wingStatsRfdWlApInfoLocation
					DisplayString,
				wingStatsRfdWlApInfoAdoptedTo
					MacAddress,
				wingStatsRfdWlApInfoIp
					DisplayString
			 }

		-- 1.3.6.1.4.1.1916.2.131.50.1.4.3.2.1.1.1.1
		wingStatsRfdWlApInfoMac OBJECT-TYPE
			SYNTAX MacAddress
			MAX-ACCESS read-only
			STATUS current
			DESCRIPTION
				"AP MAC
				
				XPath: /wing-stats/rf_domain[name=key1]/wireless/ap-info[mac=key2]/mac"
			::= { wingStatsRfdWlApInfoEntry 1 }

		
		-- 1.3.6.1.4.1.1916.2.131.50.1.4.3.2.1.1.1.2
		wingStatsRfdWlApInfoFaultDetected OBJECT-TYPE
			SYNTAX TruthValue
			MAX-ACCESS read-only
			STATUS current
			DESCRIPTION
				"Whether any fault has been detected on the AP
				
				XPath: /wing-stats/rf_domain[name=key1]/wireless/ap-info[mac=key2]/fault_detected"
			::= { wingStatsRfdWlApInfoEntry 2 }

		
		-- 1.3.6.1.4.1.1916.2.131.50.1.4.3.2.1.1.1.3
		wingStatsRfdWlApInfoNumRadios OBJECT-TYPE
			SYNTAX Unsigned32
			MAX-ACCESS read-only
			STATUS current
			DESCRIPTION
				"Number of radios on the AP
				
				XPath: /wing-stats/rf_domain[name=key1]/wireless/ap-info[mac=key2]/num_radios"
			::= { wingStatsRfdWlApInfoEntry 3 }

		
		-- 1.3.6.1.4.1.1916.2.131.50.1.4.3.2.1.1.1.4
		wingStatsRfdWlApInfoNumClients OBJECT-TYPE
			SYNTAX Unsigned32
			MAX-ACCESS read-only
			STATUS current
			DESCRIPTION
				"Number of wireless clients on the AP
				
				XPath: /wing-stats/rf_domain[name=key1]/wireless/ap-info[mac=key2]/num_clients"
			::= { wingStatsRfdWlApInfoEntry 4 }

		
		-- 1.3.6.1.4.1.1916.2.131.50.1.4.3.2.1.1.1.5
		wingStatsRfdWlApInfoLastCalTime OBJECT-TYPE
			SYNTAX DisplayString
			MAX-ACCESS read-only
			STATUS current
			DESCRIPTION
				"Last Smart-RF Calibration time on the AP
				
				XPath: /wing-stats/rf_domain[name=key1]/wireless/ap-info[mac=key2]/last_cal_time"
			::= { wingStatsRfdWlApInfoEntry 5 }

		
		-- 1.3.6.1.4.1.1916.2.131.50.1.4.3.2.1.1.1.6
		wingStatsRfdWlApInfoType OBJECT-TYPE
			SYNTAX DisplayString
			MAX-ACCESS read-only
			STATUS current
			DESCRIPTION
				"AP device type
				
				XPath: /wing-stats/rf_domain[name=key1]/wireless/ap-info[mac=key2]/type"
			::= { wingStatsRfdWlApInfoEntry 6 }

		
		-- 1.3.6.1.4.1.1916.2.131.50.1.4.3.2.1.1.1.7
		wingStatsRfdWlApInfoStatsMode OBJECT-TYPE
			SYNTAX DisplayString
			MAX-ACCESS read-only
			STATUS current
			DESCRIPTION
				"Statistics update mode
				
				XPath: /wing-stats/rf_domain[name=key1]/wireless/ap-info[mac=key2]/stats_mode"
			::= { wingStatsRfdWlApInfoEntry 7 }

		
		-- 1.3.6.1.4.1.1916.2.131.50.1.4.3.2.1.1.1.8
		wingStatsRfdWlApInfoStatsInterval OBJECT-TYPE
			SYNTAX Unsigned32
			MAX-ACCESS read-only
			STATUS current
			DESCRIPTION
				"The current statistics update interval in seconds
				
				XPath: /wing-stats/rf_domain[name=key1]/wireless/ap-info[mac=key2]/stats_interval"
			::= { wingStatsRfdWlApInfoEntry 8 }

		
		-- 1.3.6.1.4.1.1916.2.131.50.1.4.3.2.1.1.1.9
		wingStatsRfdWlApInfoHostname OBJECT-TYPE
			SYNTAX DisplayString
			MAX-ACCESS read-only
			STATUS current
			DESCRIPTION
				"Hostname of the AP
				
				XPath: /wing-stats/rf_domain[name=key1]/wireless/ap-info[mac=key2]/hostname"
			::= { wingStatsRfdWlApInfoEntry 9 }

		
		-- 1.3.6.1.4.1.1916.2.131.50.1.4.3.2.1.1.1.10
		wingStatsRfdWlApInfoRfDomainName OBJECT-TYPE
			SYNTAX DisplayString
			MAX-ACCESS read-only
			STATUS current
			DESCRIPTION
				"RF Domain name of the AP
				
				XPath: /wing-stats/rf_domain[name=key1]/wireless/ap-info[mac=key2]/rf_domain_name"
			::= { wingStatsRfdWlApInfoEntry 10 }

		
		-- 1.3.6.1.4.1.1916.2.131.50.1.4.3.2.1.1.1.11
		wingStatsRfdWlApInfoLocation OBJECT-TYPE
			SYNTAX DisplayString
			MAX-ACCESS read-only
			STATUS current
			DESCRIPTION
				"Location description of the AP
				
				XPath: /wing-stats/rf_domain[name=key1]/wireless/ap-info[mac=key2]/location"
			::= { wingStatsRfdWlApInfoEntry 11 }

		
		-- 1.3.6.1.4.1.1916.2.131.50.1.4.3.2.1.1.1.12
		wingStatsRfdWlApInfoAdoptedTo OBJECT-TYPE
			SYNTAX MacAddress
			MAX-ACCESS read-only
			STATUS current
			DESCRIPTION
				"MAC address of the parent wireless controller that the AP
				is adopted to.
				
				XPath: /wing-stats/rf_domain[name=key1]/wireless/ap-info[mac=key2]/adopted_to"
			::= { wingStatsRfdWlApInfoEntry 12 }

		
		-- 1.3.6.1.4.1.1916.2.131.50.1.4.3.2.1.1.1.13
		wingStatsRfdWlApInfoIp OBJECT-TYPE
			SYNTAX DisplayString
			MAX-ACCESS read-only
			STATUS current
			DESCRIPTION
				"Adopted AP IP address.
								
				XPath: /wing-stats/rf_domain[name=key1]/wireless/ap-info[mac=key2]/ip"
			::= { wingStatsRfdWlApInfoEntry 13 }

		
-- /wing-stats/rf_domain/wireless/client
		-- 1.3.6.1.4.1.1916.2.131.50.1.4.3.2.3
		wingStatsRfdWlClient OBJECT IDENTIFIER ::= { wingStatsRfdWl 3 }

		
		-- 1.3.6.1.4.1.1916.2.131.50.1.4.3.2.3.1
		wingStatsRfdWlClientTable OBJECT-TYPE
			SYNTAX SEQUENCE OF WingStatsRfdWlClientEntry
			MAX-ACCESS not-accessible
			STATUS current
			DESCRIPTION
				"Status of wireless clients associated currently on RF Domain.
				
				/wing-stats/rf_domain/wireless/client"
			::= { wingStatsRfdWlClient 1 }

		
		-- 1.3.6.1.4.1.1916.2.131.50.1.4.3.2.3.1.1
		wingStatsRfdWlClientEntry OBJECT-TYPE
			SYNTAX WingStatsRfdWlClientEntry
			MAX-ACCESS not-accessible
			STATUS current
			DESCRIPTION
				"An entry in the table"
			INDEX { wingStatsRfdName, wingStatsRfdWlClientMac }
			::= { wingStatsRfdWlClientTable 1 }

		
		WingStatsRfdWlClientEntry ::=
			SEQUENCE { 
				wingStatsRfdWlClientMac
					MacAddress,
				wingStatsRfdWlClientMacName
					DisplayString,
				wingStatsRfdWlClientVendor
					DisplayString,
				wingStatsRfdWlClientBss
					MacAddress,
				wingStatsRfdWlClientAp
					MacAddress,
				wingStatsRfdWlClientRadioNum
					Unsigned32,
				wingStatsRfdWlClientRadioType
					DisplayString,
				wingStatsRfdWlClientRadioEnc
					DisplayString,
				wingStatsRfdWlClientRadioAuth
					DisplayString,
				wingStatsRfdWlClientWlan
					DisplayString,
				wingStatsRfdWlClientState
					DisplayString,
				wingStatsRfdWlClientHotspotAuthed
					TruthValue,
				wingStatsRfdWlClientVlan
					Unsigned32,
				wingStatsRfdWlClientUserName
					DisplayString,
				wingStatsRfdWlClientIp
					DisplayString,
				wingStatsRfdWlClientRfdName
					DisplayString,
				wingStatsRfdWlClientHostname
					DisplayString,
				wingStatsRfdWlClientLocation
					DisplayString,
				wingStatsRfdWlClientRadioId
					DisplayString,
				wingStatsRfdWlClientRadioAlias
					DisplayString
			 }

		-- 1.3.6.1.4.1.1916.2.131.50.1.4.3.2.3.1.1.1
		wingStatsRfdWlClientMac OBJECT-TYPE
			SYNTAX MacAddress
			MAX-ACCESS read-only
			STATUS current
			DESCRIPTION
				"Client MAC
				
				XPath: /wing-stats/rf_domain[name=key1]/wireless/client[mac=key2]/mac"
			::= { wingStatsRfdWlClientEntry 1 }

		
		-- 1.3.6.1.4.1.1916.2.131.50.1.4.3.2.3.1.1.2
		wingStatsRfdWlClientMacName OBJECT-TYPE
			SYNTAX DisplayString
			MAX-ACCESS read-only
			STATUS current
			DESCRIPTION
				"Hostname of the client which could be obtained from
				packet sniffing or by manually configured via
				mac-name configuration.
				
				XPath: /wing-stats/rf_domain[name=key1]/wireless/client[mac=key2]/hostname"
			::= { wingStatsRfdWlClientEntry 2 }

		
		-- 1.3.6.1.4.1.1916.2.131.50.1.4.3.2.3.1.1.3
		wingStatsRfdWlClientVendor OBJECT-TYPE
			SYNTAX DisplayString
			MAX-ACCESS read-only
			STATUS current
			DESCRIPTION
				"Client vendor name based on the MAC OUI lookup
				
				XPath: /wing-stats/rf_domain[name=key1]/wireless/client[mac=key2]/vendor"
			::= { wingStatsRfdWlClientEntry 3 }

		
		-- 1.3.6.1.4.1.1916.2.131.50.1.4.3.2.3.1.1.4
		wingStatsRfdWlClientBss OBJECT-TYPE
			SYNTAX MacAddress
			MAX-ACCESS read-only
			STATUS current
			DESCRIPTION
				"BSSID where the client is associated
				
				XPath: /wing-stats/rf_domain[name=key1]/wireless/client[mac=key2]/bss"
			::= { wingStatsRfdWlClientEntry 4 }

		
		-- 1.3.6.1.4.1.1916.2.131.50.1.4.3.2.3.1.1.5
		wingStatsRfdWlClientAp OBJECT-TYPE
			SYNTAX MacAddress
			MAX-ACCESS read-only
			STATUS current
			DESCRIPTION
				"MAC address of the AP where the client is associated
				
				XPath: /wing-stats/rf_domain[name=key1]/wireless/client[mac=key2]/ap"
			::= { wingStatsRfdWlClientEntry 5 }

		
		-- 1.3.6.1.4.1.1916.2.131.50.1.4.3.2.3.1.1.6
		wingStatsRfdWlClientRadioNum OBJECT-TYPE
			SYNTAX Unsigned32
			MAX-ACCESS read-only
			STATUS current
			DESCRIPTION
				"Radio number on AP where the client is associated
				
				XPath: /wing-stats/rf_domain[name=key1]/wireless/client[mac=key2]/radio_num"
			::= { wingStatsRfdWlClientEntry 6 }

		
		-- 1.3.6.1.4.1.1916.2.131.50.1.4.3.2.3.1.1.7
		wingStatsRfdWlClientRadioType OBJECT-TYPE
			SYNTAX DisplayString
			MAX-ACCESS read-only
			STATUS current
			DESCRIPTION
				"802.11 radio-type of the client
				
				XPath: /wing-stats/rf_domain[name=key1]/wireless/client[mac=key2]/radio_type"
			::= { wingStatsRfdWlClientEntry 7 }

		
		-- 1.3.6.1.4.1.1916.2.131.50.1.4.3.2.3.1.1.8
		wingStatsRfdWlClientRadioEnc OBJECT-TYPE
			SYNTAX DisplayString
			MAX-ACCESS read-only
			STATUS current
			DESCRIPTION
				"Encryption type
				
				XPath: /wing-stats/rf_domain[name=key1]/wireless/client[mac=key2]/enc"
			::= { wingStatsRfdWlClientEntry 8 }

		
		-- 1.3.6.1.4.1.1916.2.131.50.1.4.3.2.3.1.1.9
		wingStatsRfdWlClientRadioAuth OBJECT-TYPE
			SYNTAX DisplayString
			MAX-ACCESS read-only
			STATUS current
			DESCRIPTION
				"Authentication type
				
				XPath: /wing-stats/rf_domain[name=key1]/wireless/client[mac=key2]/auth"
			::= { wingStatsRfdWlClientEntry 9 }

		
		-- 1.3.6.1.4.1.1916.2.131.50.1.4.3.2.3.1.1.10
		wingStatsRfdWlClientWlan OBJECT-TYPE
			SYNTAX DisplayString
			MAX-ACCESS read-only
			STATUS current
			DESCRIPTION
				"WLAN where the client is associated
				
				XPath: /wing-stats/rf_domain[name=key1]/wireless/client[mac=key2]/wlan"
			::= { wingStatsRfdWlClientEntry 10 }

		
		-- 1.3.6.1.4.1.1916.2.131.50.1.4.3.2.3.1.1.11
		wingStatsRfdWlClientState OBJECT-TYPE
			SYNTAX DisplayString
			MAX-ACCESS read-only
			STATUS current
			DESCRIPTION
				"Current state of the client
				
				XPath: /wing-stats/rf_domain[name=key1]/wireless/client[mac=key2]/state"
			::= { wingStatsRfdWlClientEntry 11 }

		
		-- 1.3.6.1.4.1.1916.2.131.50.1.4.3.2.3.1.1.12
		wingStatsRfdWlClientHotspotAuthed OBJECT-TYPE
			SYNTAX TruthValue
			MAX-ACCESS read-only
			STATUS current
			DESCRIPTION
				"Whether the client has succeeded in guest access
				authentication.
				
				XPath: /wing-stats/rf_domain[name=key1]/wireless/client[mac=key2]/hotspot_authed"
			::= { wingStatsRfdWlClientEntry 12 }

		
		-- 1.3.6.1.4.1.1916.2.131.50.1.4.3.2.3.1.1.13
		wingStatsRfdWlClientVlan OBJECT-TYPE
			SYNTAX Unsigned32
			MAX-ACCESS read-only
			STATUS current
			DESCRIPTION
				"The VLAN assigned to the client
				
				XPath: /wing-stats/rf_domain[name=key1]/wireless/client[mac=key2]/vlan"
			::= { wingStatsRfdWlClientEntry 13 }

		
		-- 1.3.6.1.4.1.1916.2.131.50.1.4.3.2.3.1.1.14
		wingStatsRfdWlClientUserName OBJECT-TYPE
			SYNTAX DisplayString
			MAX-ACCESS read-only
			STATUS current
			DESCRIPTION
				"Username of the client, if available
				
				XPath: /wing-stats/rf_domain[name=key1]/wireless/client[mac=key2]/username"
			::= { wingStatsRfdWlClientEntry 14 }

		
		-- 1.3.6.1.4.1.1916.2.131.50.1.4.3.2.3.1.1.15
		wingStatsRfdWlClientIp OBJECT-TYPE
			SYNTAX DisplayString
			MAX-ACCESS read-only
			STATUS current
			DESCRIPTION
				"IP address of the client (if known)
				
				XPath: /wing-stats/rf_domain[name=key1]/wireless/client[mac=key2]/ip"
			::= { wingStatsRfdWlClientEntry 15 }

		
		-- 1.3.6.1.4.1.1916.2.131.50.1.4.3.2.3.1.1.16
		wingStatsRfdWlClientRfdName OBJECT-TYPE
			SYNTAX DisplayString
			MAX-ACCESS read-only
			STATUS current
			DESCRIPTION
				"RF Domain that the client is in
				
				XPath: /wing-stats/rf_domain[name=key1]/wireless/client[mac=key2]/rf_domain_name"
			::= { wingStatsRfdWlClientEntry 16 }

		
		-- 1.3.6.1.4.1.1916.2.131.50.1.4.3.2.3.1.1.17
		wingStatsRfdWlClientHostname OBJECT-TYPE
			SYNTAX DisplayString
			MAX-ACCESS read-only
			STATUS current
			DESCRIPTION
				"Hostname of the AP the client is associated to
				
				XPath: /wing-stats/rf_domain[name=key1]/wireless/client[mac=key2]/ap_hostname"
			::= { wingStatsRfdWlClientEntry 17 }

		
		-- 1.3.6.1.4.1.1916.2.131.50.1.4.3.2.3.1.1.18
		wingStatsRfdWlClientLocation OBJECT-TYPE
			SYNTAX DisplayString
			MAX-ACCESS read-only
			STATUS current
			DESCRIPTION
				"Location of the AP the client is associated to.
				
				XPath: /wing-stats/rf_domain[name=key1]/wireless/client[mac=key2]/location"
			::= { wingStatsRfdWlClientEntry 18 }

		
		-- 1.3.6.1.4.1.1916.2.131.50.1.4.3.2.3.1.1.19
		wingStatsRfdWlClientRadioId OBJECT-TYPE
			SYNTAX DisplayString
			MAX-ACCESS read-only
			STATUS current
			DESCRIPTION
				"Unique ID for its associated radio in the form of
				AP-MAC:R%d. E.g., 00-A0-F8-00-00-00:R1
				
				XPath: /wing-stats/rf_domain[name=key1]/wireless/client[mac=key2]/radio_id"
			::= { wingStatsRfdWlClientEntry 19 }

		
		-- 1.3.6.1.4.1.1916.2.131.50.1.4.3.2.3.1.1.20
		wingStatsRfdWlClientRadioAlias OBJECT-TYPE
			SYNTAX DisplayString
			MAX-ACCESS read-only
			STATUS current
			DESCRIPTION
				"A radio ID alias of its associated radio in the form of
				hostname:R%d. E.g., wm3400-22A24E:R1
				
				XPath: /wing-stats/rf_domain[name=key1]/wireless/client[mac=key2]/radio_alias"
			::= { wingStatsRfdWlClientEntry 20 }

		
-- /wing-stats/rf_domain/wireless/client-details
		-- 1.3.6.1.4.1.1916.2.131.50.1.4.3.2.4
		wingStatsRfdWlClientDetail OBJECT IDENTIFIER ::= { wingStatsRfdWl 4 }

		
		-- 1.3.6.1.4.1.1916.2.131.50.1.4.3.2.4.1
		wingStatsRfdWlClientDetailTable OBJECT-TYPE
			SYNTAX SEQUENCE OF WingStatsRfdWlClientDetailEntry
			MAX-ACCESS not-accessible
			STATUS current
			DESCRIPTION
				"Detailed status of wireless clients associated currently
				on RF Domain.
				
				/wing-stats/rf_domain/wireless/client-details"
			::= { wingStatsRfdWlClientDetail 1 }

		
		-- 1.3.6.1.4.1.1916.2.131.50.1.4.3.2.4.1.1
		wingStatsRfdWlClientDetailEntry OBJECT-TYPE
			SYNTAX WingStatsRfdWlClientDetailEntry
			MAX-ACCESS not-accessible
			STATUS current
			DESCRIPTION
				"An entry in the table"
			INDEX { wingStatsRfdName, wingStatsRfdWlClientDetailMac }
			::= { wingStatsRfdWlClientDetailTable 1 }

		
		WingStatsRfdWlClientDetailEntry ::=
			SEQUENCE { 
				wingStatsRfdWlClientDetailMac
					MacAddress,
				wingStatsRfdWlClientDetailMacName
					DisplayString,
				wingStatsRfdWlClientDetailVendor
					DisplayString,
				wingStatsRfdWlClientDetailBss
					MacAddress,
				wingStatsRfdWlClientDetailAp
					MacAddress,
				wingStatsRfdWlClientDetailRadioNum
					Unsigned32,
				wingStatsRfdWlClientDetailRadioType
					DisplayString,
				wingStatsRfdWlClientDetailEnc
					DisplayString,
				wingStatsRfdWlClientDetailAuth
					DisplayString,
				wingStatsRfdWlClientDetailWlan
					DisplayString,
				wingStatsRfdWlClientDetailState
					DisplayString,
				wingStatsRfdWlClientDetailHotspotAuthed
					TruthValue,
				wingStatsRfdWlClientDetailVlan
					Unsigned32,
				wingStatsRfdWlClientDetailUsername
					DisplayString,
				wingStatsRfdWlClientDetailIp
					DisplayString,
				wingStatsRfdWlClientDetailRfDomainName
					DisplayString,
				wingStatsRfdWlClientDetailMc2ucStreams
					DisplayString,
				wingStatsRfdWlClientDetailHostname
					DisplayString,
				wingStatsRfdWlClientDetailLocation
					DisplayString,
				wingStatsRfdWlClientDetailRadioId
					DisplayString,
				wingStatsRfdWlClientDetailRadioAlias
					DisplayString,
				wingStatsRfdWlClientDetailSsid
					DisplayString,
				wingStatsRfdWlClientDetailAid
					Unsigned32,
				wingStatsRfdWlClientDetailRates
					DisplayString,
				wingStatsRfdWlClientDetailInPsp
					TruthValue,
				wingStatsRfdWlClientDetailIsWmm
					TruthValue,
				wingStatsRfdWlClientDetailUapsd
					DisplayString,
				wingStatsRfdWlClientDetailSmPowersave
					DisplayString,
				wingStatsRfdWlClientDetailHtCapable
					TruthValue,
				wingStatsRfdWlClientDetailShortGi
					TruthValue,
				wingStatsRfdWlClientDetailCurWidth40
					TruthValue,
				wingStatsRfdWlClientDetailAmsduSize
					Unsigned32,
				wingStatsRfdWlClientDetailAmpduSize
					Unsigned32,
				wingStatsRfdWlClientDetailAmpduSpacing
					Unsigned32,
				wingStatsRfdWlClientDetailRifs
					TruthValue,
				wingStatsRfdWlClientDetailLastActive
					Unsigned32,
				wingStatsRfdWlClientDetailLastAssoc
					Unsigned32,
				wingStatsRfdWlClientDetailSessTime
					Unsigned32,
				wingStatsRfdWlClientDetailIdleTime
					Unsigned32,
				wingStatsRfdWlClientDetailMaxPhyRate
					Unsigned32,
				wingStatsRfdWlClientDetailMaxUserRate
					Unsigned32,
				wingStatsRfdWlClientDetailIsVoice
					TruthValue,
				wingStatsRfdWlClientDetailIsCallActive
					TruthValue
			 }

		-- 1.3.6.1.4.1.1916.2.131.50.1.4.3.2.4.1.1.1
		wingStatsRfdWlClientDetailMac OBJECT-TYPE
			SYNTAX MacAddress
			MAX-ACCESS read-only
			STATUS current
			DESCRIPTION
				"Client MAC
				
				XPath: /wing-stats/rf_domain[name=key1]/wireless/client-details[mac=key2]/mac"
			::= { wingStatsRfdWlClientDetailEntry 1 }

		
		-- 1.3.6.1.4.1.1916.2.131.50.1.4.3.2.4.1.1.2
		wingStatsRfdWlClientDetailMacName OBJECT-TYPE
			SYNTAX DisplayString
			MAX-ACCESS read-only
			STATUS current
			DESCRIPTION
				"Hostname of the client which could be obtained from
				packet sniffing or by manually configured via
				mac-name configuration.
				
				XPath: /wing-stats/rf_domain[name=key1]/wireless/client-details[mac=key2]/hostname"
			::= { wingStatsRfdWlClientDetailEntry 2 }

		
		-- 1.3.6.1.4.1.1916.2.131.50.1.4.3.2.4.1.1.3
		wingStatsRfdWlClientDetailVendor OBJECT-TYPE
			SYNTAX DisplayString
			MAX-ACCESS read-only
			STATUS current
			DESCRIPTION
				"Client vendor name based on the MAC OUI lookup
				
				XPath: /wing-stats/rf_domain[name=key1]/wireless/client-details[mac=key2]/vendor"
			::= { wingStatsRfdWlClientDetailEntry 3 }

		
		-- 1.3.6.1.4.1.1916.2.131.50.1.4.3.2.4.1.1.4
		wingStatsRfdWlClientDetailBss OBJECT-TYPE
			SYNTAX MacAddress
			MAX-ACCESS read-only
			STATUS current
			DESCRIPTION
				"BSSID where the client is associated
				
				XPath: /wing-stats/rf_domain[name=key1]/wireless/client-details[mac=key2]/bss"
			::= { wingStatsRfdWlClientDetailEntry 4 }

		
		-- 1.3.6.1.4.1.1916.2.131.50.1.4.3.2.4.1.1.5
		wingStatsRfdWlClientDetailAp OBJECT-TYPE
			SYNTAX MacAddress
			MAX-ACCESS read-only
			STATUS current
			DESCRIPTION
				"MAC address of the AP where the client is associated
				
				XPath: /wing-stats/rf_domain[name=key1]/wireless/client-details[mac=key2]/ap"
			::= { wingStatsRfdWlClientDetailEntry 5 }

		
		-- 1.3.6.1.4.1.1916.2.131.50.1.4.3.2.4.1.1.6
		wingStatsRfdWlClientDetailRadioNum OBJECT-TYPE
			SYNTAX Unsigned32
			MAX-ACCESS read-only
			STATUS current
			DESCRIPTION
				"Radio number on AP where the client is associated
				
				XPath: /wing-stats/rf_domain[name=key1]/wireless/client-details[mac=key2]/radio_num"
			::= { wingStatsRfdWlClientDetailEntry 6 }

		
		-- 1.3.6.1.4.1.1916.2.131.50.1.4.3.2.4.1.1.7
		wingStatsRfdWlClientDetailRadioType OBJECT-TYPE
			SYNTAX DisplayString
			MAX-ACCESS read-only
			STATUS current
			DESCRIPTION
				"802.11 radio-type of the client
				
				XPath: /wing-stats/rf_domain[name=key1]/wireless/client-details[mac=key2]/radio_type"
			::= { wingStatsRfdWlClientDetailEntry 7 }

		
		-- 1.3.6.1.4.1.1916.2.131.50.1.4.3.2.4.1.1.8
		wingStatsRfdWlClientDetailEnc OBJECT-TYPE
			SYNTAX DisplayString
			MAX-ACCESS read-only
			STATUS current
			DESCRIPTION
				"Encryption type
				
				XPath: /wing-stats/rf_domain[name=key1]/wireless/client-details[mac=key2]/enc"
			::= { wingStatsRfdWlClientDetailEntry 8 }

		
		-- 1.3.6.1.4.1.1916.2.131.50.1.4.3.2.4.1.1.9
		wingStatsRfdWlClientDetailAuth OBJECT-TYPE
			SYNTAX DisplayString
			MAX-ACCESS read-only
			STATUS current
			DESCRIPTION
				"Authentication type
				
				XPath: /wing-stats/rf_domain[name=key1]/wireless/client-details[mac=key2]/auth"
			::= { wingStatsRfdWlClientDetailEntry 9 }

		
		-- 1.3.6.1.4.1.1916.2.131.50.1.4.3.2.4.1.1.10
		wingStatsRfdWlClientDetailWlan OBJECT-TYPE
			SYNTAX DisplayString
			MAX-ACCESS read-only
			STATUS current
			DESCRIPTION
				"WLAN where the client is associated
				
				XPath: /wing-stats/rf_domain[name=key1]/wireless/client-details[mac=key2]/wlan"
			::= { wingStatsRfdWlClientDetailEntry 10 }

		
		-- 1.3.6.1.4.1.1916.2.131.50.1.4.3.2.4.1.1.11
		wingStatsRfdWlClientDetailState OBJECT-TYPE
			SYNTAX DisplayString
			MAX-ACCESS read-only
			STATUS current
			DESCRIPTION
				"Current state of the client
				
				XPath: /wing-stats/rf_domain[name=key1]/wireless/client-details[mac=key2]/state"
			::= { wingStatsRfdWlClientDetailEntry 11 }

		
		-- 1.3.6.1.4.1.1916.2.131.50.1.4.3.2.4.1.1.12
		wingStatsRfdWlClientDetailHotspotAuthed OBJECT-TYPE
			SYNTAX TruthValue
			MAX-ACCESS read-only
			STATUS current
			DESCRIPTION
				"Whether the client has succeeded in guest access
				authentication.
				
				XPath: /wing-stats/rf_domain[name=key1]/wireless/client-details[mac=key2]/hotspot_authed"
			::= { wingStatsRfdWlClientDetailEntry 12 }

		
		-- 1.3.6.1.4.1.1916.2.131.50.1.4.3.2.4.1.1.13
		wingStatsRfdWlClientDetailVlan OBJECT-TYPE
			SYNTAX Unsigned32
			MAX-ACCESS read-only
			STATUS current
			DESCRIPTION
				"The VLAN assigned to the client
				
				XPath: /wing-stats/rf_domain[name=key1]/wireless/client-details[mac=key2]/vlan"
			::= { wingStatsRfdWlClientDetailEntry 13 }

		
		-- 1.3.6.1.4.1.1916.2.131.50.1.4.3.2.4.1.1.14
		wingStatsRfdWlClientDetailUsername OBJECT-TYPE
			SYNTAX DisplayString
			MAX-ACCESS read-only
			STATUS current
			DESCRIPTION
				"Username of the client, if available
				
				XPath: /wing-stats/rf_domain[name=key1]/wireless/client-details[mac=key2]/username"
			::= { wingStatsRfdWlClientDetailEntry 14 }

		
		-- 1.3.6.1.4.1.1916.2.131.50.1.4.3.2.4.1.1.15
		wingStatsRfdWlClientDetailIp OBJECT-TYPE
			SYNTAX DisplayString
			MAX-ACCESS read-only
			STATUS current
			DESCRIPTION
				"IP address of the client (if known)
				
				XPath: /wing-stats/rf_domain[name=key1]/wireless/client-details[mac=key2]/ip"
			::= { wingStatsRfdWlClientDetailEntry 15 }

		
		-- 1.3.6.1.4.1.1916.2.131.50.1.4.3.2.4.1.1.16
		wingStatsRfdWlClientDetailRfDomainName OBJECT-TYPE
			SYNTAX DisplayString
			MAX-ACCESS read-only
			STATUS current
			DESCRIPTION
				"RF Domain that the client is in
				
				XPath: /wing-stats/rf_domain[name=key1]/wireless/client-details[mac=key2]/rf_domain_name"
			::= { wingStatsRfdWlClientDetailEntry 16 }

		
		-- 1.3.6.1.4.1.1916.2.131.50.1.4.3.2.4.1.1.17
		wingStatsRfdWlClientDetailMc2ucStreams OBJECT-TYPE
			SYNTAX DisplayString
			MAX-ACCESS read-only
			STATUS current
			DESCRIPTION
				"Accelerated multicast streams the client is registered for.
				
				XPath: /wing-stats/rf_domain[name=key1]/wireless/client-details[mac=key2]/mc2uc_streams"
			::= { wingStatsRfdWlClientDetailEntry 17 }

		
		-- 1.3.6.1.4.1.1916.2.131.50.1.4.3.2.4.1.1.18
		wingStatsRfdWlClientDetailHostname OBJECT-TYPE
			SYNTAX DisplayString
			MAX-ACCESS read-only
			STATUS current
			DESCRIPTION
				"Hostname of the AP the client is associated to
				
				XPath: /wing-stats/rf_domain[name=key1]/wireless/client-details[mac=key2]/ap_hostname"
			::= { wingStatsRfdWlClientDetailEntry 18 }

		
		-- 1.3.6.1.4.1.1916.2.131.50.1.4.3.2.4.1.1.19
		wingStatsRfdWlClientDetailLocation OBJECT-TYPE
			SYNTAX DisplayString
			MAX-ACCESS read-only
			STATUS current
			DESCRIPTION
				"Location of the AP the client is associated to
				
				XPath: /wing-stats/rf_domain[name=key1]/wireless/client-details[mac=key2]/location"
			::= { wingStatsRfdWlClientDetailEntry 19 }

		
		-- 1.3.6.1.4.1.1916.2.131.50.1.4.3.2.4.1.1.20
		wingStatsRfdWlClientDetailRadioId OBJECT-TYPE
			SYNTAX DisplayString
			MAX-ACCESS read-only
			STATUS current
			DESCRIPTION
				"Unique ID for its associated radio in the form of
				AP-MAC:R%d. E.g., 00-A0-F8-00-00-00:R1
				
				XPath: /wing-stats/rf_domain[name=key1]/wireless/client-details[mac=key2]/radio_id"
			::= { wingStatsRfdWlClientDetailEntry 20 }

		
		-- 1.3.6.1.4.1.1916.2.131.50.1.4.3.2.4.1.1.21
		wingStatsRfdWlClientDetailRadioAlias OBJECT-TYPE
			SYNTAX DisplayString
			MAX-ACCESS read-only
			STATUS current
			DESCRIPTION
				"A radio ID alias of its associated radio in the form of
				hostname:R%d. E.g., wm3400-22A24E:R1
				
				XPath: /wing-stats/rf_domain[name=key1]/wireless/client-details[mac=key2]/radio_alias"
			::= { wingStatsRfdWlClientDetailEntry 21 }

		
		-- 1.3.6.1.4.1.1916.2.131.50.1.4.3.2.4.1.1.22
		wingStatsRfdWlClientDetailSsid OBJECT-TYPE
			SYNTAX DisplayString
			MAX-ACCESS read-only
			STATUS current
			DESCRIPTION
				"SSID of the WLAN where the client is associated
				
				XPath: /wing-stats/rf_domain[name=key1]/wireless/client-details[mac=key2]/ssid"
			::= { wingStatsRfdWlClientDetailEntry 22 }

		
		-- 1.3.6.1.4.1.1916.2.131.50.1.4.3.2.4.1.1.23
		wingStatsRfdWlClientDetailAid OBJECT-TYPE
			SYNTAX Unsigned32
			MAX-ACCESS read-only
			STATUS current
			DESCRIPTION
				"802.11 association index of the client
				
				XPath: /wing-stats/rf_domain[name=key1]/wireless/client-details[mac=key2]/aid"
			::= { wingStatsRfdWlClientDetailEntry 23 }

		
		-- 1.3.6.1.4.1.1916.2.131.50.1.4.3.2.4.1.1.24
		wingStatsRfdWlClientDetailRates OBJECT-TYPE
			SYNTAX DisplayString
			MAX-ACCESS read-only
			STATUS current
			DESCRIPTION
				"Data rates supported by the client
				
				XPath: /wing-stats/rf_domain[name=key1]/wireless/client-details[mac=key2]/rates"
			::= { wingStatsRfdWlClientDetailEntry 24 }

		
		-- 1.3.6.1.4.1.1916.2.131.50.1.4.3.2.4.1.1.25
		wingStatsRfdWlClientDetailInPsp OBJECT-TYPE
			SYNTAX TruthValue
			MAX-ACCESS read-only
			STATUS current
			DESCRIPTION
				"Whether the client is currently in a power save mode
				
				XPath: /wing-stats/rf_domain[name=key1]/wireless/client-details[mac=key2]/in_psp"
			::= { wingStatsRfdWlClientDetailEntry 25 }

		
		-- 1.3.6.1.4.1.1916.2.131.50.1.4.3.2.4.1.1.26
		wingStatsRfdWlClientDetailIsWmm OBJECT-TYPE
			SYNTAX TruthValue
			MAX-ACCESS read-only
			STATUS current
			DESCRIPTION
				"Whether the client is associated with support for WMM
				
				XPath: /wing-stats/rf_domain[name=key1]/wireless/client-details[mac=key2]/is_wmm"
			::= { wingStatsRfdWlClientDetailEntry 26 }

		
		-- 1.3.6.1.4.1.1916.2.131.50.1.4.3.2.4.1.1.27
		wingStatsRfdWlClientDetailUapsd OBJECT-TYPE
			SYNTAX DisplayString
			MAX-ACCESS read-only
			STATUS current
			DESCRIPTION
				"Unscheduled APSD support by the client
				
				XPath: /wing-stats/rf_domain[name=key1]/wireless/client-details[mac=key2]/uapsd"
			::= { wingStatsRfdWlClientDetailEntry 27 }

		
		-- 1.3.6.1.4.1.1916.2.131.50.1.4.3.2.4.1.1.28
		wingStatsRfdWlClientDetailSmPowersave OBJECT-TYPE
			SYNTAX DisplayString
			MAX-ACCESS read-only
			STATUS current
			DESCRIPTION
				"SM Powersave mode of this client (static|dynamic|off)
				
				XPath: /wing-stats/rf_domain[name=key1]/wireless/client-details[mac=key2]/sm_powersave"
			::= { wingStatsRfdWlClientDetailEntry 28 }

		
		-- 1.3.6.1.4.1.1916.2.131.50.1.4.3.2.4.1.1.29
		wingStatsRfdWlClientDetailHtCapable OBJECT-TYPE
			SYNTAX TruthValue
			MAX-ACCESS read-only
			STATUS current
			DESCRIPTION
				"Whether this client supports 802.11n High-Throughput
				data-rates.
				
				XPath: /wing-stats/rf_domain[name=key1]/wireless/client-details[mac=key2]/ht_capable"
			::= { wingStatsRfdWlClientDetailEntry 29 }

		
		-- 1.3.6.1.4.1.1916.2.131.50.1.4.3.2.4.1.1.30
		wingStatsRfdWlClientDetailShortGi OBJECT-TYPE
			SYNTAX TruthValue
			MAX-ACCESS read-only
			STATUS current
			DESCRIPTION
				"Whether short-guard interval is supported by the client.
				
				XPath: /wing-stats/rf_domain[name=key1]/wireless/client-details[mac=key2]/short_gi"
			::= { wingStatsRfdWlClientDetailEntry 30 }

		
		-- 1.3.6.1.4.1.1916.2.131.50.1.4.3.2.4.1.1.31
		wingStatsRfdWlClientDetailCurWidth40 OBJECT-TYPE
			SYNTAX TruthValue
			MAX-ACCESS read-only
			STATUS current
			DESCRIPTION
				"Whether the client is 40MHz capable, or 20-only
				
				XPath: /wing-stats/rf_domain[name=key1]/wireless/client-details[mac=key2]/current_width_40"
			::= { wingStatsRfdWlClientDetailEntry 31 }

		
		-- 1.3.6.1.4.1.1916.2.131.50.1.4.3.2.4.1.1.32
		wingStatsRfdWlClientDetailAmsduSize OBJECT-TYPE
			SYNTAX Unsigned32
			MAX-ACCESS read-only
			STATUS current
			DESCRIPTION
				"Maximum size of amsdu supported by the client
				
				XPath: /wing-stats/rf_domain[name=key1]/wireless/client-details[mac=key2]/amsdu_size"
			::= { wingStatsRfdWlClientDetailEntry 32 }

		
		-- 1.3.6.1.4.1.1916.2.131.50.1.4.3.2.4.1.1.33
		wingStatsRfdWlClientDetailAmpduSize OBJECT-TYPE
			SYNTAX Unsigned32
			MAX-ACCESS read-only
			STATUS current
			DESCRIPTION
				"Maximum size of ampdu supported by the client
				
				XPath: /wing-stats/rf_domain[name=key1]/wireless/client-details[mac=key2]/ampdu_size"
			::= { wingStatsRfdWlClientDetailEntry 33 }

		
		-- 1.3.6.1.4.1.1916.2.131.50.1.4.3.2.4.1.1.34
		wingStatsRfdWlClientDetailAmpduSpacing OBJECT-TYPE
			SYNTAX Unsigned32
			UNITS "microSeconds"
			MAX-ACCESS read-only
			STATUS current
			DESCRIPTION
				"Interframe spacing of 802.11n aggregate MPDUs
				
				XPath: /wing-stats/rf_domain[name=key1]/wireless/client-details[mac=key2]/ampdu_spacing"
			::= { wingStatsRfdWlClientDetailEntry 34 }

		
		-- 1.3.6.1.4.1.1916.2.131.50.1.4.3.2.4.1.1.35
		wingStatsRfdWlClientDetailRifs OBJECT-TYPE
			SYNTAX TruthValue
			MAX-ACCESS read-only
			STATUS current
			DESCRIPTION
				"Whether RIFS (Reduced InterFrame Spacing) supported
				by the client.
				
				XPath: /wing-stats/rf_domain[name=key1]/wireless/client-details[mac=key2]/rifs"
			::= { wingStatsRfdWlClientDetailEntry 35 }

		
		-- 1.3.6.1.4.1.1916.2.131.50.1.4.3.2.4.1.1.36
		wingStatsRfdWlClientDetailLastActive OBJECT-TYPE
			SYNTAX Unsigned32
			MAX-ACCESS read-only
			STATUS current
			DESCRIPTION
				"The seconds ago the last packet was received from the client.
				
				XPath: /wing-stats/rf_domain[name=key1]/wireless/client-details[mac=key2]/last_active"
			::= { wingStatsRfdWlClientDetailEntry 36 }

		
		-- 1.3.6.1.4.1.1916.2.131.50.1.4.3.2.4.1.1.37
		wingStatsRfdWlClientDetailLastAssoc OBJECT-TYPE
			SYNTAX Unsigned32
			MAX-ACCESS read-only
			STATUS current
			DESCRIPTION
				"The seconds ago the last association of the client to AP.
				
				XPath: /wing-stats/rf_domain[name=key1]/wireless/client-details[mac=key2]/last_assoc"
			::= { wingStatsRfdWlClientDetailEntry 37 }

		
		-- 1.3.6.1.4.1.1916.2.131.50.1.4.3.2.4.1.1.38
		wingStatsRfdWlClientDetailSessTime OBJECT-TYPE
			SYNTAX Unsigned32
			MAX-ACCESS read-only
			STATUS current
			DESCRIPTION
				"The time in seconds for which this session was made active
				
				XPath: /wing-stats/rf_domain[name=key1]/wireless/client-details[mac=key2]/sess_time"
			::= { wingStatsRfdWlClientDetailEntry 38 }

		
		-- 1.3.6.1.4.1.1916.2.131.50.1.4.3.2.4.1.1.39
		wingStatsRfdWlClientDetailIdleTime OBJECT-TYPE
			SYNTAX Unsigned32
			MAX-ACCESS read-only
			STATUS current
			DESCRIPTION
				"The number of seconds of inactivity after which the client
				will be disassociated.
				
				XPath: /wing-stats/rf_domain[name=key1]/wireless/client-details[mac=key2]/idle_time"
			::= { wingStatsRfdWlClientDetailEntry 39 }

		
		-- 1.3.6.1.4.1.1916.2.131.50.1.4.3.2.4.1.1.40
		wingStatsRfdWlClientDetailMaxPhyRate OBJECT-TYPE
			SYNTAX Unsigned32
			UNITS "kbps"
			MAX-ACCESS read-only
			STATUS current
			DESCRIPTION
				"Maximum physical data rate
				
				XPath: /wing-stats/rf_domain[name=key1]/wireless/client-details[mac=key2]/max_phy_rate"
			::= { wingStatsRfdWlClientDetailEntry 40 }

		
		-- 1.3.6.1.4.1.1916.2.131.50.1.4.3.2.4.1.1.41
		wingStatsRfdWlClientDetailMaxUserRate OBJECT-TYPE
			SYNTAX Unsigned32
			UNITS "kbps"
			MAX-ACCESS read-only
			STATUS current
			DESCRIPTION
				"Theoretic maximum user-level data rate
				
				XPath: /wing-stats/rf_domain[name=key1]/wireless/client-details[mac=key2]/max_user_rate"
			::= { wingStatsRfdWlClientDetailEntry 41 }

		
		-- 1.3.6.1.4.1.1916.2.131.50.1.4.3.2.4.1.1.42
		wingStatsRfdWlClientDetailIsVoice OBJECT-TYPE
			SYNTAX TruthValue
			MAX-ACCESS read-only
			STATUS current
			DESCRIPTION
				"Whether client is classified as voice device or not
				
				XPath: /wing-stats/rf_domain[name=key1]/wireless/client-details[mac=key2]/is_voice"
			::= { wingStatsRfdWlClientDetailEntry 42 }

		
		-- 1.3.6.1.4.1.1916.2.131.50.1.4.3.2.4.1.1.43
		wingStatsRfdWlClientDetailIsCallActive OBJECT-TYPE
			SYNTAX TruthValue
			MAX-ACCESS read-only
			STATUS current
			DESCRIPTION
				"Whether the client is currently on active voice call,
				applicable to voice client only.
				
				XPath: /wing-stats/rf_domain[name=key1]/wireless/client-details[mac=key2]/is_call_active"
			::= { wingStatsRfdWlClientDetailEntry 43 }

		
-- /wing-stats/rf_domain/wireless/client-stats
		-- 1.3.6.1.4.1.1916.2.131.50.1.4.3.2.5
		wingStatsRfdWlClientStat OBJECT IDENTIFIER ::= { wingStatsRfdWl 5 }

		
		-- 1.3.6.1.4.1.1916.2.131.50.1.4.3.2.5.1
		wingStatsRfdWlClientStatTable OBJECT-TYPE
			SYNTAX SEQUENCE OF WingStatsRfdWlClientStatEntry
			MAX-ACCESS not-accessible
			STATUS current
			DESCRIPTION
				"Statistical information of wireless clients associated
				currently on RF Domain
				
				/wing-stats/rf_domain/wireless/client-stats"
			::= { wingStatsRfdWlClientStat 1 }

		
		-- 1.3.6.1.4.1.1916.2.131.50.1.4.3.2.5.1.1
		wingStatsRfdWlClientStatEntry OBJECT-TYPE
			SYNTAX WingStatsRfdWlClientStatEntry
			MAX-ACCESS not-accessible
			STATUS current
			DESCRIPTION
				"An entry in the table"
			INDEX { wingStatsRfdName, wingStatsRfdWlClientStatMac }
			::= { wingStatsRfdWlClientStatTable 1 }

		
		WingStatsRfdWlClientStatEntry ::=
			SEQUENCE { 
				wingStatsRfdWlClientStatMac
					MacAddress,
				wingStatsRfdWlClientStatMacName
					DisplayString,
				wingStatsRfdWlClientStatVendor
					DisplayString,
				wingStatsRfdWlClientStatAp
					MacAddress,
				wingStatsRfdWlClientStatTxBytes
					Counter64,
				wingStatsRfdWlClientStatRxBytes
					Counter64,
				wingStatsRfdWlClientStatTxPkts
					Counter32,
				wingStatsRfdWlClientStatRxPkts
					Counter32,
				wingStatsRfdWlClientStatTxDropped
					Counter32,
				wingStatsRfdWlClientStatRxErrors
					Counter32,
				wingStatsRfdWlClientStatTIndex
					Integer32,
				wingStatsRfdWlClientStatTxBps
					Unsigned32,
				wingStatsRfdWlClientStatRxBps
					Unsigned32,
				wingStatsRfdWlClientStatSignal
					Integer32,
				wingStatsRfdWlClientStatNoise
					Integer32,
				wingStatsRfdWlClientStatSnr
					Integer32,
				wingStatsRfdWlClientStatTxRate
					Unsigned32,
				wingStatsRfdWlClientStatRxRate
					Unsigned32,
				wingStatsRfdWlClientStatErrorRate
					Unsigned32,
				wingStatsRfdWlClientStatQIndex
					Integer32
			 }

		-- 1.3.6.1.4.1.1916.2.131.50.1.4.3.2.5.1.1.1
		wingStatsRfdWlClientStatMac OBJECT-TYPE
			SYNTAX MacAddress
			MAX-ACCESS read-only
			STATUS current
			DESCRIPTION
				"Client MAC
				
				XPath: /wing-stats/rf_domain[name=key1]/wireless/client-stats[mac=key2]/mac"
			::= { wingStatsRfdWlClientStatEntry 1 }

		
		-- 1.3.6.1.4.1.1916.2.131.50.1.4.3.2.5.1.1.2
		wingStatsRfdWlClientStatMacName OBJECT-TYPE
			SYNTAX DisplayString
			MAX-ACCESS read-only
			STATUS current
			DESCRIPTION
				"Hostname of the client which could be obtained from
				packet sniffing or by manually configured via
				mac-name configuration.
				
				XPath: /wing-stats/rf_domain[name=key1]/wireless/client-stats[mac=key2]/hostname"
			::= { wingStatsRfdWlClientStatEntry 2 }

		
		-- 1.3.6.1.4.1.1916.2.131.50.1.4.3.2.5.1.1.3
		wingStatsRfdWlClientStatVendor OBJECT-TYPE
			SYNTAX DisplayString
			MAX-ACCESS read-only
			STATUS current
			DESCRIPTION
				"Client vendor name based on the MAC OUI lookup
				
				XPath: /wing-stats/rf_domain[name=key1]/wireless/client-stats[mac=key2]/vendor"
			::= { wingStatsRfdWlClientStatEntry 3 }

		
		-- 1.3.6.1.4.1.1916.2.131.50.1.4.3.2.5.1.1.4
		wingStatsRfdWlClientStatAp OBJECT-TYPE
			SYNTAX MacAddress
			MAX-ACCESS read-only
			STATUS current
			DESCRIPTION
				"MAC address of AP where the client is associated.
				
				XPath: /wing-stats/rf_domain[name=key1]/wireless/client-stats[mac=key2]/ap"
			::= { wingStatsRfdWlClientStatEntry 4 }

		
		-- 1.3.6.1.4.1.1916.2.131.50.1.4.3.2.5.1.1.5
		wingStatsRfdWlClientStatTxBytes OBJECT-TYPE
			SYNTAX Counter64
			MAX-ACCESS read-only
			STATUS current
			DESCRIPTION
				"Number of data bytes transmitted from AP to client
				
				XPath: /wing-stats/rf_domain[name=key1]/wireless/client-stats[mac=key2]/tx_bytes"
			::= { wingStatsRfdWlClientStatEntry 5 }

		
		-- 1.3.6.1.4.1.1916.2.131.50.1.4.3.2.5.1.1.6
		wingStatsRfdWlClientStatRxBytes OBJECT-TYPE
			SYNTAX Counter64
			MAX-ACCESS read-only
			STATUS current
			DESCRIPTION
				"Number of data bytes received from client to AP
				
				XPath: /wing-stats/rf_domain[name=key1]/wireless/client-stats[mac=key2]/rx_bytes"
			::= { wingStatsRfdWlClientStatEntry 6 }

		
		-- 1.3.6.1.4.1.1916.2.131.50.1.4.3.2.5.1.1.7
		wingStatsRfdWlClientStatTxPkts OBJECT-TYPE
			SYNTAX Counter32
			MAX-ACCESS read-only
			STATUS current
			DESCRIPTION
				"Number of packets of data transmitted from AP to client
				
				XPath: /wing-stats/rf_domain[name=key1]/wireless/client-stats[mac=key2]/tx_pkts"
			::= { wingStatsRfdWlClientStatEntry 7 }

		
		-- 1.3.6.1.4.1.1916.2.131.50.1.4.3.2.5.1.1.8
		wingStatsRfdWlClientStatRxPkts OBJECT-TYPE
			SYNTAX Counter32
			MAX-ACCESS read-only
			STATUS current
			DESCRIPTION
				"Number of packets of data received from client to AP
				
				XPath: /wing-stats/rf_domain[name=key1]/wireless/client-stats[mac=key2]/rx_pkts"
			::= { wingStatsRfdWlClientStatEntry 8 }

		
		-- 1.3.6.1.4.1.1916.2.131.50.1.4.3.2.5.1.1.9
		wingStatsRfdWlClientStatTxDropped OBJECT-TYPE
			SYNTAX Counter32
			MAX-ACCESS read-only
			STATUS current
			DESCRIPTION
				"Number of packets of data dropped on transmission
				
				XPath: /wing-stats/rf_domain[name=key1]/wireless/client-stats[mac=key2]/tx_dropped"
			::= { wingStatsRfdWlClientStatEntry 9 }

		
		-- 1.3.6.1.4.1.1916.2.131.50.1.4.3.2.5.1.1.10
		wingStatsRfdWlClientStatRxErrors OBJECT-TYPE
			SYNTAX Counter32
			MAX-ACCESS read-only
			STATUS current
			DESCRIPTION
				"Number of packets of data received with errors
				
				XPath: /wing-stats/rf_domain[name=key1]/wireless/client-stats[mac=key2]/rx_errors"
			::= { wingStatsRfdWlClientStatEntry 10 }

		
		-- 1.3.6.1.4.1.1916.2.131.50.1.4.3.2.5.1.1.11
		wingStatsRfdWlClientStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/rf_domain[name=key1]/wireless/client-stats[mac=key2]/t_index"
			::= { wingStatsRfdWlClientStatEntry 11 }

		
		-- 1.3.6.1.4.1.1916.2.131.50.1.4.3.2.5.1.1.12
		wingStatsRfdWlClientStatTxBps OBJECT-TYPE
			SYNTAX Unsigned32
			UNITS "kbps"
			MAX-ACCESS read-only
			STATUS current
			DESCRIPTION
				"User data transmit rate
				
				XPath: /wing-stats/rf_domain[name=key1]/wireless/client-stats[mac=key2]/tx_bps"
			::= { wingStatsRfdWlClientStatEntry 12 }

		
		-- 1.3.6.1.4.1.1916.2.131.50.1.4.3.2.5.1.1.13
		wingStatsRfdWlClientStatRxBps OBJECT-TYPE
			SYNTAX Unsigned32
			UNITS "kbps"
			MAX-ACCESS read-only
			STATUS current
			DESCRIPTION
				"User data receive rate
				
				XPath: /wing-stats/rf_domain[name=key1]/wireless/client-stats[mac=key2]/rx_bps"
			::= { wingStatsRfdWlClientStatEntry 13 }

		
		-- 1.3.6.1.4.1.1916.2.131.50.1.4.3.2.5.1.1.14
		wingStatsRfdWlClientStatSignal OBJECT-TYPE
			SYNTAX Integer32
			UNITS "dbm"
			MAX-ACCESS read-only
			STATUS current
			DESCRIPTION
				"Signal strength
				
				XPath: /wing-stats/rf_domain[name=key1]/wireless/client-stats[mac=key2]/signal"
			::= { wingStatsRfdWlClientStatEntry 14 }

		
		-- 1.3.6.1.4.1.1916.2.131.50.1.4.3.2.5.1.1.15
		wingStatsRfdWlClientStatNoise OBJECT-TYPE
			SYNTAX Integer32
			UNITS "dbm"
			MAX-ACCESS read-only
			STATUS current
			DESCRIPTION
				"Noise level in units of dbm
				
				XPath: /wing-stats/rf_domain[name=key1]/wireless/client-stats[mac=key2]/noise"
			::= { wingStatsRfdWlClientStatEntry 15 }

		
		-- 1.3.6.1.4.1.1916.2.131.50.1.4.3.2.5.1.1.16
		wingStatsRfdWlClientStatSnr OBJECT-TYPE
			SYNTAX Integer32
			UNITS "db"
			MAX-ACCESS read-only
			STATUS current
			DESCRIPTION
				"Signal to noise ratio in units of db
				
				XPath: /wing-stats/rf_domain[name=key1]/wireless/client-stats[mac=key2]/snr"
			::= { wingStatsRfdWlClientStatEntry 16 }

		
		-- 1.3.6.1.4.1.1916.2.131.50.1.4.3.2.5.1.1.17
		wingStatsRfdWlClientStatTxRate OBJECT-TYPE
			SYNTAX Unsigned32
			UNITS "Mbps"
			MAX-ACCESS read-only
			STATUS current
			DESCRIPTION
				"The effective phy-layer transmit rate
				
				XPath: /wing-stats/rf_domain[name=key1]/wireless/client-stats[mac=key2]/tx_rate"
			::= { wingStatsRfdWlClientStatEntry 17 }

		
		-- 1.3.6.1.4.1.1916.2.131.50.1.4.3.2.5.1.1.18
		wingStatsRfdWlClientStatRxRate OBJECT-TYPE
			SYNTAX Unsigned32
			UNITS "Mbps"
			MAX-ACCESS read-only
			STATUS current
			DESCRIPTION
				"The effective phy-layer receive rate
				
				XPath: /wing-stats/rf_domain[name=key1]/wireless/client-stats[mac=key2]/rx_rate"
			::= { wingStatsRfdWlClientStatEntry 18 }

		
		-- 1.3.6.1.4.1.1916.2.131.50.1.4.3.2.5.1.1.19
		wingStatsRfdWlClientStatErrorRate OBJECT-TYPE
			SYNTAX Unsigned32
			MAX-ACCESS read-only
			STATUS current
			DESCRIPTION
				"Ratio of errors to rx-packets in percentage
				
				XPath: /wing-stats/rf_domain[name=key1]/wireless/client-stats[mac=key2]/error_rate"
			::= { wingStatsRfdWlClientStatEntry 19 }

		
		-- 1.3.6.1.4.1.1916.2.131.50.1.4.3.2.5.1.1.20
		wingStatsRfdWlClientStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/rf_domain[name=key1]/wireless/client-stats[mac=key2]/q_index"
			::= { wingStatsRfdWlClientStatEntry 20 }

		
-- /wing-stats/rf_domain/wireless/client-stats-details
		-- 1.3.6.1.4.1.1916.2.131.50.1.4.3.2.6
		wingStatsRfdWlClientStatDetail OBJECT IDENTIFIER ::= { wingStatsRfdWl 6 }

		
		-- 1.3.6.1.4.1.1916.2.131.50.1.4.3.2.6.1
		wingStatsRfdWlClientStatDetailTable OBJECT-TYPE
			SYNTAX SEQUENCE OF WingStatsRfdWlClientStatDetailEntry
			MAX-ACCESS not-accessible
			STATUS current
			DESCRIPTION
				"Detailed statistical information of wireless clients
				associated currently on RF Domain
				
				/wing-stats/rf_domain/wireless/client-stats-details"
			::= { wingStatsRfdWlClientStatDetail 1 }

		
		-- 1.3.6.1.4.1.1916.2.131.50.1.4.3.2.6.1.1
		wingStatsRfdWlClientStatDetailEntry OBJECT-TYPE
			SYNTAX WingStatsRfdWlClientStatDetailEntry
			MAX-ACCESS not-accessible
			STATUS current
			DESCRIPTION
				"An entry in the table."
			INDEX { wingStatsRfdName, wingStatsRfdWlClientStatDetailMac }
			::= { wingStatsRfdWlClientStatDetailTable 1 }

		
		WingStatsRfdWlClientStatDetailEntry ::=
			SEQUENCE { 
				wingStatsRfdWlClientStatDetailMac
					MacAddress,
				wingStatsRfdWlClientStatDetailMacName
					DisplayString,
				wingStatsRfdWlClientStatDetailVendor
					DisplayString,
				wingStatsRfdWlClientStatDetailTxBytes
					Counter64,
				wingStatsRfdWlClientStatDetailRxBytes
					Counter64,
				wingStatsRfdWlClientStatDetailTxPkts
					Counter32,
				wingStatsRfdWlClientStatDetailRxPkts
					Counter32,
				wingStatsRfdWlClientStatDetailTxDropped
					Counter32,
				wingStatsRfdWlClientStatDetailRxErrors
					Counter32,
				wingStatsRfdWlClientStatDetailTIndex
					Integer32,
				wingStatsRfdWlClientStatDetailTxBps
					Unsigned32,
				wingStatsRfdWlClientStatDetailRxBps
					Unsigned32,
				wingStatsRfdWlClientStatDetailSignal
					Integer32,
				wingStatsRfdWlClientStatDetailNoise
					Integer32,
				wingStatsRfdWlClientStatDetailSnr
					Integer32,
				wingStatsRfdWlClientStatDetailTxRate
					Unsigned32,
				wingStatsRfdWlClientStatDetailRxRate
					Unsigned32,
				wingStatsRfdWlClientStatDetailErrorRate
					Unsigned32,
				wingStatsRfdWlClientStatDetailQIndex
					Integer32,
				wingStatsRfdWlClientStatDetailRawTxBytes
					Counter64,
				wingStatsRfdWlClientStatDetailRawRxBytes
					Counter64,
				wingStatsRfdWlClientStatDetailRawTotalBytes
					Counter64,
				wingStatsRfdWlClientStatDetailRawTxPkts
					Counter32,
				wingStatsRfdWlClientStatDetailRawRxPkts
					Counter32,
				wingStatsRfdWlClientStatDetailRawTotalPkts
					Counter32,
				wingStatsRfdWlClientStatDetailRawTxBps
					Unsigned32,
				wingStatsRfdWlClientStatDetailRawRxBps
					Unsigned32,
				wingStatsRfdWlClientStatDetailRawTotalBps
					Unsigned32,
				wingStatsRfdWlClientStatDetailRawTxPps
					Unsigned32,
				wingStatsRfdWlClientStatDetailRawRxPps
					Unsigned32,
				wingStatsRfdWlClientStatDetailRawTotalPps
					Unsigned32,
				wingStatsRfdWlClientStatDetailRawTxRate
					Unsigned32,
				wingStatsRfdWlClientStatDetailRawRxRate
					Unsigned32,
				wingStatsRfdWlClientStatDetailRawOverallRate
					Unsigned32,
				wingStatsRfdWlClientStatDetailTxBcmcPkts
					Counter64,
				wingStatsRfdWlClientStatDetailRxBcmcPkts
					Counter64,
				wingStatsRfdWlClientStatDetailTotalBcmcPkts
					Counter64,
				wingStatsRfdWlClientStatDetailTxPps
					Unsigned32,
				wingStatsRfdWlClientStatDetailRxPps
					Unsigned32,
				wingStatsRfdWlClientStatDetailTotalPps
					Unsigned32,
				wingStatsRfdWlClientStatDetailTxMgmtPkts
					Counter64,
				wingStatsRfdWlClientStatDetailRxMgmtPkts
					Counter64,
				wingStatsRfdWlClientStatDetailTotalMgmtPkts
					Counter64,
				wingStatsRfdWlClientStatDetailTxRetries
					Counter64,
				wingStatsRfdWlClientStatDetailRxProbes
					Counter32,
				wingStatsRfdWlClientStatDetailRxActions
					Counter32,
				wingStatsRfdWlClientStatDetailRxPsPoll
					Counter32,
				wingStatsRfdWlClientStatDetailLastCallStatus
					DisplayString,
				wingStatsRfdWlClientStatDetailCallTotal
					Unsigned32,
				wingStatsRfdWlClientStatDetailCallStatOk
					Unsigned32,
				wingStatsRfdWlClientStatDetailCallStatBusy
					Unsigned32,
				wingStatsRfdWlClientStatDetailCallStatNoAnswer
					Unsigned32,
				wingStatsRfdWlClientStatDetailCallStatUnknownDest
					Unsigned32,
				wingStatsRfdWlClientStatDetailCallStatAdmDenied
					Unsigned32,
				wingStatsRfdWlClientStatDetailCallStatDeclined
					Unsigned32,
				wingStatsRfdWlClientStatDetailCallStatUnauth
					Unsigned32,
				wingStatsRfdWlClientStatDetailCallStatUnsuppMedia
					Unsigned32,
				wingStatsRfdWlClientStatDetailCallStatTempUnavail
					Unsigned32,
				wingStatsRfdWlClientStatDetailCallStatNoForkAllowed
					Unsigned32,
				wingStatsRfdWlClientStatDetailCallStatSessInactive
					Unsigned32,
				wingStatsRfdWlClientStatDetailCallStatOther
					Unsigned32,
				wingStatsRfdWlClientStatDetailTotalBytes
					Counter64,
				wingStatsRfdWlClientStatDetailTotalPkts
					Counter32,
				wingStatsRfdWlClientStatDetailTxRetriedBytes
					Counter64
			 }

		-- 1.3.6.1.4.1.1916.2.131.50.1.4.3.2.6.1.1.1
		wingStatsRfdWlClientStatDetailMac OBJECT-TYPE
			SYNTAX MacAddress
			MAX-ACCESS read-only
			STATUS current
			DESCRIPTION
				"Client MAC
				
				XPath: /wing-stats/rf_domain[name=key1]/wireless/client-stats-details[mac=key2]/mac"
			::= { wingStatsRfdWlClientStatDetailEntry 1 }

		
		-- 1.3.6.1.4.1.1916.2.131.50.1.4.3.2.6.1.1.2
		wingStatsRfdWlClientStatDetailMacName OBJECT-TYPE
			SYNTAX DisplayString
			MAX-ACCESS read-only
			STATUS current
			DESCRIPTION
				"Hostname of the client which could be obtained from
				packet sniffing or by manually configured via
				mac-name configuration.
				
				XPath: /wing-stats/rf_domain[name=key1]/wireless/client-stats-details[mac=key2]/hostname"
			::= { wingStatsRfdWlClientStatDetailEntry 2 }

		
		-- 1.3.6.1.4.1.1916.2.131.50.1.4.3.2.6.1.1.3
		wingStatsRfdWlClientStatDetailVendor OBJECT-TYPE
			SYNTAX DisplayString
			MAX-ACCESS read-only
			STATUS current
			DESCRIPTION
				"Client vendor name based on the MAC OUI lookup
				
				XPath: /wing-stats/rf_domain[name=key1]/wireless/client-stats-details[mac=key2]/vendor"
			::= { wingStatsRfdWlClientStatDetailEntry 3 }

		
		-- 1.3.6.1.4.1.1916.2.131.50.1.4.3.2.6.1.1.4
		wingStatsRfdWlClientStatDetailTxBytes OBJECT-TYPE
			SYNTAX Counter64
			MAX-ACCESS read-only
			STATUS current
			DESCRIPTION
				"Number of data bytes transmitted from AP to client
				
				XPath: /wing-stats/rf_domain[name=key1]/wireless/client-stats-details[mac=key2]/tx_bytes"
			::= { wingStatsRfdWlClientStatDetailEntry 4 }

		
		-- 1.3.6.1.4.1.1916.2.131.50.1.4.3.2.6.1.1.5
		wingStatsRfdWlClientStatDetailRxBytes OBJECT-TYPE
			SYNTAX Counter64
			MAX-ACCESS read-only
			STATUS current
			DESCRIPTION
				"Number of data bytes received from client to AP
				
				XPath: /wing-stats/rf_domain[name=key1]/wireless/client-stats-details[mac=key2]/rx_bytes"
			::= { wingStatsRfdWlClientStatDetailEntry 5 }

		
		-- 1.3.6.1.4.1.1916.2.131.50.1.4.3.2.6.1.1.6
		wingStatsRfdWlClientStatDetailTxPkts OBJECT-TYPE
			SYNTAX Counter32
			MAX-ACCESS read-only
			STATUS current
			DESCRIPTION
				"Number of packets of data transmitted from AP to client
				
				XPath: /wing-stats/rf_domain[name=key1]/wireless/client-stats-details[mac=key2]/tx_pkts"
			::= { wingStatsRfdWlClientStatDetailEntry 6 }

		
		-- 1.3.6.1.4.1.1916.2.131.50.1.4.3.2.6.1.1.7
		wingStatsRfdWlClientStatDetailRxPkts OBJECT-TYPE
			SYNTAX Counter32
			MAX-ACCESS read-only
			STATUS current
			DESCRIPTION
				"Number of packets of data received from client to AP
				
				XPath: /wing-stats/rf_domain[name=key1]/wireless/client-stats-details[mac=key2]/rx_pkts"
			::= { wingStatsRfdWlClientStatDetailEntry 7 }

		
		-- 1.3.6.1.4.1.1916.2.131.50.1.4.3.2.6.1.1.8
		wingStatsRfdWlClientStatDetailTxDropped OBJECT-TYPE
			SYNTAX Counter32
			MAX-ACCESS read-only
			STATUS current
			DESCRIPTION
				"Number of packets of data dropped on transmission
				
				XPath: /wing-stats/rf_domain[name=key1]/wireless/client-stats-details[mac=key2]/tx_dropped"
			::= { wingStatsRfdWlClientStatDetailEntry 8 }

		
		-- 1.3.6.1.4.1.1916.2.131.50.1.4.3.2.6.1.1.9
		wingStatsRfdWlClientStatDetailRxErrors OBJECT-TYPE
			SYNTAX Counter32
			MAX-ACCESS read-only
			STATUS current
			DESCRIPTION
				"Number of packets of data received with errors
				
				XPath: /wing-stats/rf_domain[name=key1]/wireless/client-stats-details[mac=key2]/rx_errors"
			::= { wingStatsRfdWlClientStatDetailEntry 9 }

		
		-- 1.3.6.1.4.1.1916.2.131.50.1.4.3.2.6.1.1.10
		wingStatsRfdWlClientStatDetailTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/rf_domain[name=key1]/wireless/client-stats-details[mac=key2]/t_index"
			::= { wingStatsRfdWlClientStatDetailEntry 10 }

		
		-- 1.3.6.1.4.1.1916.2.131.50.1.4.3.2.6.1.1.11
		wingStatsRfdWlClientStatDetailTxBps OBJECT-TYPE
			SYNTAX Unsigned32
			UNITS "kbps"
			MAX-ACCESS read-only
			STATUS current
			DESCRIPTION
				"User data transmit rate
				
				XPath: /wing-stats/rf_domain[name=key1]/wireless/client-stats-details[mac=key2]/tx_bps"
			::= { wingStatsRfdWlClientStatDetailEntry 11 }

		
		-- 1.3.6.1.4.1.1916.2.131.50.1.4.3.2.6.1.1.12
		wingStatsRfdWlClientStatDetailRxBps OBJECT-TYPE
			SYNTAX Unsigned32
			UNITS "kbps"
			MAX-ACCESS read-only
			STATUS current
			DESCRIPTION
				"User data receive rate
				
				XPath: /wing-stats/rf_domain[name=key1]/wireless/client-stats-details[mac=key2]/rx_bps"
			::= { wingStatsRfdWlClientStatDetailEntry 12 }

		
		-- 1.3.6.1.4.1.1916.2.131.50.1.4.3.2.6.1.1.13
		wingStatsRfdWlClientStatDetailSignal OBJECT-TYPE
			SYNTAX Integer32
			UNITS "dbm"
			MAX-ACCESS read-only
			STATUS current
			DESCRIPTION
				"Signal strength in units of dbm
				
				XPath: /wing-stats/rf_domain[name=key1]/wireless/client-stats-details[mac=key2]/signal"
			::= { wingStatsRfdWlClientStatDetailEntry 13 }

		
		-- 1.3.6.1.4.1.1916.2.131.50.1.4.3.2.6.1.1.14
		wingStatsRfdWlClientStatDetailNoise OBJECT-TYPE
			SYNTAX Integer32
			UNITS "dbm"
			MAX-ACCESS read-only
			STATUS current
			DESCRIPTION
				"Noise level in units of dbm
				
				XPath: /wing-stats/rf_domain[name=key1]/wireless/client-stats-details[mac=key2]/noise"
			::= { wingStatsRfdWlClientStatDetailEntry 14 }

		
		-- 1.3.6.1.4.1.1916.2.131.50.1.4.3.2.6.1.1.15
		wingStatsRfdWlClientStatDetailSnr OBJECT-TYPE
			SYNTAX Integer32
			UNITS "db"
			MAX-ACCESS read-only
			STATUS current
			DESCRIPTION
				"Signal to noise ratio in units of db
				
				XPath: /wing-stats/rf_domain[name=key1]/wireless/client-stats-details[mac=key2]/snr"
			::= { wingStatsRfdWlClientStatDetailEntry 15 }

		
		-- 1.3.6.1.4.1.1916.2.131.50.1.4.3.2.6.1.1.16
		wingStatsRfdWlClientStatDetailTxRate OBJECT-TYPE
			SYNTAX Unsigned32
			UNITS "Mbps"
			MAX-ACCESS read-only
			STATUS current
			DESCRIPTION
				"The effective phy-layer transmit rate
				
				XPath: /wing-stats/rf_domain[name=key1]/wireless/client-stats-details[mac=key2]/tx_rate"
			::= { wingStatsRfdWlClientStatDetailEntry 16 }

		
		-- 1.3.6.1.4.1.1916.2.131.50.1.4.3.2.6.1.1.17
		wingStatsRfdWlClientStatDetailRxRate OBJECT-TYPE
			SYNTAX Unsigned32
			UNITS "Mbps"
			MAX-ACCESS read-only
			STATUS current
			DESCRIPTION
				"The effective phy-layer receive rate
				
				XPath: /wing-stats/rf_domain[name=key1]/wireless/client-stats-details[mac=key2]/rx_rate"
			::= { wingStatsRfdWlClientStatDetailEntry 17 }

		
		-- 1.3.6.1.4.1.1916.2.131.50.1.4.3.2.6.1.1.18
		wingStatsRfdWlClientStatDetailErrorRate OBJECT-TYPE
			SYNTAX Unsigned32
			MAX-ACCESS read-only
			STATUS current
			DESCRIPTION
				"Ratio of errors to rx-packets in percentage
				
				XPath: /wing-stats/rf_domain[name=key1]/wireless/client-stats-details[mac=key2]/error_rate"
			::= { wingStatsRfdWlClientStatDetailEntry 18 }

		
		-- 1.3.6.1.4.1.1916.2.131.50.1.4.3.2.6.1.1.19
		wingStatsRfdWlClientStatDetailQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/rf_domain[name=key1]/wireless/client-stats-details[mac=key2]/q_index"
			::= { wingStatsRfdWlClientStatDetailEntry 19 }

		
		-- 1.3.6.1.4.1.1916.2.131.50.1.4.3.2.6.1.1.20
		wingStatsRfdWlClientStatDetailRawTxBytes OBJECT-TYPE
			SYNTAX Counter64
			MAX-ACCESS read-only
			STATUS current
			DESCRIPTION
				"Number of raw (data + management) bytes transmitted
				from AP to client
				
				XPath: /wing-stats/rf_domain[name=key1]/wireless/client-stats-details[mac=key2]/raw_tx_bytes"
			::= { wingStatsRfdWlClientStatDetailEntry 20 }

		
		-- 1.3.6.1.4.1.1916.2.131.50.1.4.3.2.6.1.1.21
		wingStatsRfdWlClientStatDetailRawRxBytes OBJECT-TYPE
			SYNTAX Counter64
			MAX-ACCESS read-only
			STATUS current
			DESCRIPTION
				"Number of raw (data + management) bytes received
				from client to AP
				
				XPath: /wing-stats/rf_domain[name=key1]/wireless/client-stats-details[mac=key2]/raw_rx_bytes"
			::= { wingStatsRfdWlClientStatDetailEntry 21 }

		
		-- 1.3.6.1.4.1.1916.2.131.50.1.4.3.2.6.1.1.22
		wingStatsRfdWlClientStatDetailRawTotalBytes OBJECT-TYPE
			SYNTAX Counter64
			MAX-ACCESS read-only
			STATUS current
			DESCRIPTION
				"Total mumber of raw (data + management) bytes
				through the AP to/from the client
				
				XPath: /wing-stats/rf_domain[name=key1]/wireless/client-stats-details[mac=key2]/raw_total_bytes"
			::= { wingStatsRfdWlClientStatDetailEntry 22 }

		
		-- 1.3.6.1.4.1.1916.2.131.50.1.4.3.2.6.1.1.23
		wingStatsRfdWlClientStatDetailRawTxPkts OBJECT-TYPE
			SYNTAX Counter32
			MAX-ACCESS read-only
			STATUS current
			DESCRIPTION
				"Number of packets of raw (data + management) transmitted
				from AP to client
				
				XPath: /wing-stats/rf_domain[name=key1]/wireless/client-stats-details[mac=key2]/raw_tx_pkts"
			::= { wingStatsRfdWlClientStatDetailEntry 23 }

		
		-- 1.3.6.1.4.1.1916.2.131.50.1.4.3.2.6.1.1.24
		wingStatsRfdWlClientStatDetailRawRxPkts OBJECT-TYPE
			SYNTAX Counter32
			MAX-ACCESS read-only
			STATUS current
			DESCRIPTION
				"Number of packets of raw (data + management) received
				from client to AP
				
				XPath: /wing-stats/rf_domain[name=key1]/wireless/client-stats-details[mac=key2]/raw_rx_pkts"
			::= { wingStatsRfdWlClientStatDetailEntry 24 }

		
		-- 1.3.6.1.4.1.1916.2.131.50.1.4.3.2.6.1.1.25
		wingStatsRfdWlClientStatDetailRawTotalPkts OBJECT-TYPE
			SYNTAX Counter32
			MAX-ACCESS read-only
			STATUS current
			DESCRIPTION
				"Total number of raw packets through the AP for the client
				
				XPath: /wing-stats/rf_domain[name=key1]/wireless/client-stats-details[mac=key2]/raw_total_pkts"
			::= { wingStatsRfdWlClientStatDetailEntry 25 }

		
		-- 1.3.6.1.4.1.1916.2.131.50.1.4.3.2.6.1.1.26
		wingStatsRfdWlClientStatDetailRawTxBps OBJECT-TYPE
			SYNTAX Unsigned32
			UNITS "kbps"
			MAX-ACCESS read-only
			STATUS current
			DESCRIPTION
				"User raw (data + management) transmit rate
				
				XPath: /wing-stats/rf_domain[name=key1]/wireless/client-stats-details[mac=key2]/raw_tx_bps"
			::= { wingStatsRfdWlClientStatDetailEntry 26 }

		
		-- 1.3.6.1.4.1.1916.2.131.50.1.4.3.2.6.1.1.27
		wingStatsRfdWlClientStatDetailRawRxBps OBJECT-TYPE
			SYNTAX Unsigned32
			UNITS "kbps"
			MAX-ACCESS read-only
			STATUS current
			DESCRIPTION
				"User raw (data + management) receive rate
				
				XPath: /wing-stats/rf_domain[name=key1]/wireless/client-stats-details[mac=key2]/raw_rx_bps"
			::= { wingStatsRfdWlClientStatDetailEntry 27 }

		
		-- 1.3.6.1.4.1.1916.2.131.50.1.4.3.2.6.1.1.28
		wingStatsRfdWlClientStatDetailRawTotalBps OBJECT-TYPE
			SYNTAX Unsigned32
			UNITS "kbps"
			MAX-ACCESS read-only
			STATUS current
			DESCRIPTION
				"Total user raw (data + management) rate
				
				XPath: /wing-stats/rf_domain[name=key1]/wireless/client-stats-details[mac=key2]/raw_total_bps"
			::= { wingStatsRfdWlClientStatDetailEntry 28 }

		
		-- 1.3.6.1.4.1.1916.2.131.50.1.4.3.2.6.1.1.29
		wingStatsRfdWlClientStatDetailRawTxPps OBJECT-TYPE
			SYNTAX Unsigned32
			MAX-ACCESS read-only
			STATUS current
			DESCRIPTION
				"Raw packet rate per second transmitted by AP to client
				
				XPath: /wing-stats/rf_domain[name=key1]/wireless/client-stats-details[mac=key2]/raw_tx_pps"
			::= { wingStatsRfdWlClientStatDetailEntry 29 }

		
		-- 1.3.6.1.4.1.1916.2.131.50.1.4.3.2.6.1.1.30
		wingStatsRfdWlClientStatDetailRawRxPps OBJECT-TYPE
			SYNTAX Unsigned32
			MAX-ACCESS read-only
			STATUS current
			DESCRIPTION
				"Raw packet rate per second received by AP from client
				
				XPath: /wing-stats/rf_domain[name=key1]/wireless/client-stats-details[mac=key2]/raw_rx_pps"
			::= { wingStatsRfdWlClientStatDetailEntry 30 }

		
		-- 1.3.6.1.4.1.1916.2.131.50.1.4.3.2.6.1.1.31
		wingStatsRfdWlClientStatDetailRawTotalPps OBJECT-TYPE
			SYNTAX Unsigned32
			MAX-ACCESS read-only
			STATUS current
			DESCRIPTION
				"Raw packet rate per second through the AP for the client
				
				XPath: /wing-stats/rf_domain[name=key1]/wireless/client-stats-details[mac=key2]/raw_total_pps"
			::= { wingStatsRfdWlClientStatDetailEntry 31 }

		
		-- 1.3.6.1.4.1.1916.2.131.50.1.4.3.2.6.1.1.32
		wingStatsRfdWlClientStatDetailRawTxRate OBJECT-TYPE
			SYNTAX Unsigned32
			UNITS "Mbps"
			MAX-ACCESS read-only
			STATUS current
			DESCRIPTION
				"The effective phy-layer transmit rate for raw data
				
				XPath: /wing-stats/rf_domain[name=key1]/wireless/client-stats-details[mac=key2]/raw_tx_rate"
			::= { wingStatsRfdWlClientStatDetailEntry 32 }

		
		-- 1.3.6.1.4.1.1916.2.131.50.1.4.3.2.6.1.1.33
		wingStatsRfdWlClientStatDetailRawRxRate OBJECT-TYPE
			SYNTAX Unsigned32
			UNITS "Mbps"
			MAX-ACCESS read-only
			STATUS current
			DESCRIPTION
				"The effective phy-layer receive rate for raw data
				
				XPath: /wing-stats/rf_domain[name=key1]/wireless/client-stats-details[mac=key2]/raw_rx_rate"
			::= { wingStatsRfdWlClientStatDetailEntry 33 }

		
		-- 1.3.6.1.4.1.1916.2.131.50.1.4.3.2.6.1.1.34
		wingStatsRfdWlClientStatDetailRawOverallRate OBJECT-TYPE
			SYNTAX Unsigned32
			UNITS "Mbps"
			MAX-ACCESS read-only
			STATUS current
			DESCRIPTION
				"The effective phy-layer overall rate, averaged on transmit and
				receive for raw data
				
				XPath: /wing-stats/rf_domain[name=key1]/wireless/client-stats-details[mac=key2]/raw_overall_rate"
			::= { wingStatsRfdWlClientStatDetailEntry 34 }

		
		-- 1.3.6.1.4.1.1916.2.131.50.1.4.3.2.6.1.1.35
		wingStatsRfdWlClientStatDetailTxBcmcPkts OBJECT-TYPE
			SYNTAX Counter64
			MAX-ACCESS read-only
			STATUS current
			DESCRIPTION
				"Number of broadcast packets transmitted from AP to client
				
				XPath: /wing-stats/rf_domain[name=key1]/wireless/client-stats-details[mac=key2]/tx_bcmc_pkts"
			::= { wingStatsRfdWlClientStatDetailEntry 35 }

		
		-- 1.3.6.1.4.1.1916.2.131.50.1.4.3.2.6.1.1.36
		wingStatsRfdWlClientStatDetailRxBcmcPkts OBJECT-TYPE
			SYNTAX Counter64
			MAX-ACCESS read-only
			STATUS current
			DESCRIPTION
				"Number of broadcast packets received by the AP from client
				
				XPath: /wing-stats/rf_domain[name=key1]/wireless/client-stats-details[mac=key2]/rx_bcmc_pkts"
			::= { wingStatsRfdWlClientStatDetailEntry 36 }

		
		-- 1.3.6.1.4.1.1916.2.131.50.1.4.3.2.6.1.1.37
		wingStatsRfdWlClientStatDetailTotalBcmcPkts OBJECT-TYPE
			SYNTAX Counter64
			MAX-ACCESS read-only
			STATUS current
			DESCRIPTION
				"Total Number of broadcast packets through the AP
				for the client
				
				XPath: /wing-stats/rf_domain[name=key1]/wireless/client-stats-details[mac=key2]/total_bcmc_pkts"
			::= { wingStatsRfdWlClientStatDetailEntry 37 }

		
		-- 1.3.6.1.4.1.1916.2.131.50.1.4.3.2.6.1.1.38
		wingStatsRfdWlClientStatDetailTxPps OBJECT-TYPE
			SYNTAX Unsigned32
			MAX-ACCESS read-only
			STATUS current
			DESCRIPTION
				"Packet rate per second transmitted by the AP to client
				
				XPath: /wing-stats/rf_domain[name=key1]/wireless/client-stats-details[mac=key2]/tx_pps"
			::= { wingStatsRfdWlClientStatDetailEntry 38 }

		
		-- 1.3.6.1.4.1.1916.2.131.50.1.4.3.2.6.1.1.39
		wingStatsRfdWlClientStatDetailRxPps OBJECT-TYPE
			SYNTAX Unsigned32
			MAX-ACCESS read-only
			STATUS current
			DESCRIPTION
				"Packet rate per second received by the AP from client
				
				XPath: /wing-stats/rf_domain[name=key1]/wireless/client-stats-details[mac=key2]/rx_pps"
			::= { wingStatsRfdWlClientStatDetailEntry 39 }

		
		-- 1.3.6.1.4.1.1916.2.131.50.1.4.3.2.6.1.1.40
		wingStatsRfdWlClientStatDetailTotalPps OBJECT-TYPE
			SYNTAX Unsigned32
			MAX-ACCESS read-only
			STATUS current
			DESCRIPTION
				"Packet rate per second through the AP for the client
				
				XPath: /wing-stats/rf_domain[name=key1]/wireless/client-stats-details[mac=key2]/total_pps"
			::= { wingStatsRfdWlClientStatDetailEntry 40 }

		
		-- 1.3.6.1.4.1.1916.2.131.50.1.4.3.2.6.1.1.41
		wingStatsRfdWlClientStatDetailTxMgmtPkts OBJECT-TYPE
			SYNTAX Counter64
			MAX-ACCESS read-only
			STATUS current
			DESCRIPTION
				"Number of management packets of transmitted
				by the AP to client
				
				XPath: /wing-stats/rf_domain[name=key1]/wireless/client-stats-details[mac=key2]/tx_mgmt_pkts"
			::= { wingStatsRfdWlClientStatDetailEntry 41 }

		
		-- 1.3.6.1.4.1.1916.2.131.50.1.4.3.2.6.1.1.42
		wingStatsRfdWlClientStatDetailRxMgmtPkts OBJECT-TYPE
			SYNTAX Counter64
			MAX-ACCESS read-only
			STATUS current
			DESCRIPTION
				"Number of management packets received by the AP from client
				
				XPath: /wing-stats/rf_domain[name=key1]/wireless/client-stats-details[mac=key2]/rx_mgmt_pkts"
			::= { wingStatsRfdWlClientStatDetailEntry 42 }

		
		-- 1.3.6.1.4.1.1916.2.131.50.1.4.3.2.6.1.1.43
		wingStatsRfdWlClientStatDetailTotalMgmtPkts OBJECT-TYPE
			SYNTAX Counter64
			MAX-ACCESS read-only
			STATUS current
			DESCRIPTION
				"Number of management packets through the AP for the client
				
				XPath: /wing-stats/rf_domain[name=key1]/wireless/client-stats-details[mac=key2]/total_mgmt_pkts"
			::= { wingStatsRfdWlClientStatDetailEntry 43 }

		
		-- 1.3.6.1.4.1.1916.2.131.50.1.4.3.2.6.1.1.44
		wingStatsRfdWlClientStatDetailTxRetries OBJECT-TYPE
			SYNTAX Counter64
			MAX-ACCESS read-only
			STATUS current
			DESCRIPTION
				"Total number of retries
				
				XPath: /wing-stats/rf_domain[name=key1]/wireless/client-stats-details[mac=key2]/tx_retries"
			::= { wingStatsRfdWlClientStatDetailEntry 44 }

		
		-- 1.3.6.1.4.1.1916.2.131.50.1.4.3.2.6.1.1.45
		wingStatsRfdWlClientStatDetailRxProbes OBJECT-TYPE
			SYNTAX Counter32
			MAX-ACCESS read-only
			STATUS current
			DESCRIPTION
				"Total number of probe-request packets received
				
				XPath: /wing-stats/rf_domain[name=key1]/wireless/client-stats-details[mac=key2]/rx_probes"
			::= { wingStatsRfdWlClientStatDetailEntry 45 }

		
		-- 1.3.6.1.4.1.1916.2.131.50.1.4.3.2.6.1.1.46
		wingStatsRfdWlClientStatDetailRxActions OBJECT-TYPE
			SYNTAX Counter32
			MAX-ACCESS read-only
			STATUS current
			DESCRIPTION
				"Total number of action packets received
				
				XPath: /wing-stats/rf_domain[name=key1]/wireless/client-stats-details[mac=key2]/rx_actions"
			::= { wingStatsRfdWlClientStatDetailEntry 46 }

		
		-- 1.3.6.1.4.1.1916.2.131.50.1.4.3.2.6.1.1.47
		wingStatsRfdWlClientStatDetailRxPsPoll OBJECT-TYPE
			SYNTAX Counter32
			MAX-ACCESS read-only
			STATUS current
			DESCRIPTION
				"Total number of PS-Poll packets received
				
				XPath: /wing-stats/rf_domain[name=key1]/wireless/client-stats-details[mac=key2]/rx_ps_poll"
			::= { wingStatsRfdWlClientStatDetailEntry 47 }

		
		-- 1.3.6.1.4.1.1916.2.131.50.1.4.3.2.6.1.1.48
		wingStatsRfdWlClientStatDetailLastCallStatus OBJECT-TYPE
			SYNTAX DisplayString
			MAX-ACCESS read-only
			STATUS current
			DESCRIPTION
				"Last voice call status
				
				XPath: /wing-stats/rf_domain[name=key1]/wireless/client-stats-details[mac=key2]/last_call_status"
			::= { wingStatsRfdWlClientStatDetailEntry 48 }

		
		-- 1.3.6.1.4.1.1916.2.131.50.1.4.3.2.6.1.1.49
		wingStatsRfdWlClientStatDetailCallTotal OBJECT-TYPE
			SYNTAX Unsigned32
			MAX-ACCESS read-only
			STATUS current
			DESCRIPTION
				"Total number of voice calls attempted
				
				XPath: /wing-stats/rf_domain[name=key1]/wireless/client-stats-details[mac=key2]/call_total"
			::= { wingStatsRfdWlClientStatDetailEntry 49 }

		
		-- 1.3.6.1.4.1.1916.2.131.50.1.4.3.2.6.1.1.50
		wingStatsRfdWlClientStatDetailCallStatOk OBJECT-TYPE
			SYNTAX Unsigned32
			MAX-ACCESS read-only
			STATUS current
			DESCRIPTION
				"Voice calls successfully made
				
				XPath: /wing-stats/rf_domain[name=key1]/wireless/client-stats-details[mac=key2]/call_status_ok"
			::= { wingStatsRfdWlClientStatDetailEntry 50 }

		
		-- 1.3.6.1.4.1.1916.2.131.50.1.4.3.2.6.1.1.51
		wingStatsRfdWlClientStatDetailCallStatBusy OBJECT-TYPE
			SYNTAX Unsigned32
			MAX-ACCESS read-only
			STATUS current
			DESCRIPTION
				"Voice calls failed because of busy
				
				XPath: /wing-stats/rf_domain[name=key1]/wireless/client-stats-details[mac=key2]/call_status_busy"
			::= { wingStatsRfdWlClientStatDetailEntry 51 }

		
		-- 1.3.6.1.4.1.1916.2.131.50.1.4.3.2.6.1.1.52
		wingStatsRfdWlClientStatDetailCallStatNoAnswer OBJECT-TYPE
			SYNTAX Unsigned32
			MAX-ACCESS read-only
			STATUS current
			DESCRIPTION
				"Voice calls failed because of no-answer
				
				XPath: /wing-stats/rf_domain[name=key1]/wireless/client-stats-details[mac=key2]/call_status_no_answer"
			::= { wingStatsRfdWlClientStatDetailEntry 52 }

		
		-- 1.3.6.1.4.1.1916.2.131.50.1.4.3.2.6.1.1.53
		wingStatsRfdWlClientStatDetailCallStatUnknownDest OBJECT-TYPE
			SYNTAX Unsigned32
			MAX-ACCESS read-only
			STATUS current
			DESCRIPTION
				"Voice calls failed because of unknown destination
				
				XPath: /wing-stats/rf_domain[name=key1]/wireless/client-stats-details[mac=key2]/call_status_unknown_dest"
			::= { wingStatsRfdWlClientStatDetailEntry 53 }

		
		-- 1.3.6.1.4.1.1916.2.131.50.1.4.3.2.6.1.1.54
		wingStatsRfdWlClientStatDetailCallStatAdmDenied OBJECT-TYPE
			SYNTAX Unsigned32
			MAX-ACCESS read-only
			STATUS current
			DESCRIPTION
				"Voice calls failed because of admission denied
				
				XPath: /wing-stats/rf_domain[name=key1]/wireless/client-stats-details[mac=key2]/call_status_admission_denied"
			::= { wingStatsRfdWlClientStatDetailEntry 54 }

		
		-- 1.3.6.1.4.1.1916.2.131.50.1.4.3.2.6.1.1.55
		wingStatsRfdWlClientStatDetailCallStatDeclined OBJECT-TYPE
			SYNTAX Unsigned32
			MAX-ACCESS read-only
			STATUS current
			DESCRIPTION
				"Voice calls failed because of being declined
				
				XPath: /wing-stats/rf_domain[name=key1]/wireless/client-stats-details[mac=key2]/call_status_declined"
			::= { wingStatsRfdWlClientStatDetailEntry 55 }

		
		-- 1.3.6.1.4.1.1916.2.131.50.1.4.3.2.6.1.1.56
		wingStatsRfdWlClientStatDetailCallStatUnauth OBJECT-TYPE
			SYNTAX Unsigned32
			MAX-ACCESS read-only
			STATUS current
			DESCRIPTION
				"Voice calls failed because of being unauthorized
				
				XPath: /wing-stats/rf_domain[name=key1]/wireless/client-stats-details[mac=key2]/call_status_unauthorized"
			::= { wingStatsRfdWlClientStatDetailEntry 56 }

		
		-- 1.3.6.1.4.1.1916.2.131.50.1.4.3.2.6.1.1.57
		wingStatsRfdWlClientStatDetailCallStatUnsuppMedia OBJECT-TYPE
			SYNTAX Unsigned32
			MAX-ACCESS read-only
			STATUS current
			DESCRIPTION
				"Voice calls failed because of unsupported media
				
				XPath: /wing-stats/rf_domain[name=key1]/wireless/client-stats-details[mac=key2]/call_status_unsupported_media"
			::= { wingStatsRfdWlClientStatDetailEntry 57 }

		
		-- 1.3.6.1.4.1.1916.2.131.50.1.4.3.2.6.1.1.58
		wingStatsRfdWlClientStatDetailCallStatTempUnavail OBJECT-TYPE
			SYNTAX Unsigned32
			MAX-ACCESS read-only
			STATUS current
			DESCRIPTION
				"Voice calls failed because of temporarily unavailable
				resources
				
				XPath: /wing-stats/rf_domain[name=key1]/wireless/client-stats-details[mac=key2]/call_status_temporarily_unavailable"
			::= { wingStatsRfdWlClientStatDetailEntry 58 }

		
		-- 1.3.6.1.4.1.1916.2.131.50.1.4.3.2.6.1.1.59
		wingStatsRfdWlClientStatDetailCallStatNoForkAllowed OBJECT-TYPE
			SYNTAX Unsigned32
			MAX-ACCESS read-only
			STATUS current
			DESCRIPTION
				"Voice calls failed because of no-fork-allowed
				
				XPath: /wing-stats/rf_domain[name=key1]/wireless/client-stats-details[mac=key2]/call_status_no_fork_allowed"
			::= { wingStatsRfdWlClientStatDetailEntry 59 }

		
		-- 1.3.6.1.4.1.1916.2.131.50.1.4.3.2.6.1.1.60
		wingStatsRfdWlClientStatDetailCallStatSessInactive OBJECT-TYPE
			SYNTAX Unsigned32
			MAX-ACCESS read-only
			STATUS current
			DESCRIPTION
				"Voice calls ended because of session-inactive
				
				XPath: /wing-stats/rf_domain[name=key1]/wireless/client-stats-details[mac=key2]/call_status_session_inactive"
			::= { wingStatsRfdWlClientStatDetailEntry 60 }

		
		-- 1.3.6.1.4.1.1916.2.131.50.1.4.3.2.6.1.1.61
		wingStatsRfdWlClientStatDetailCallStatOther OBJECT-TYPE
			SYNTAX Unsigned32
			MAX-ACCESS read-only
			STATUS current
			DESCRIPTION
				"Voice calls ended for unknown reason
				
				XPath: /wing-stats/rf_domain[name=key1]/wireless/client-stats-details[mac=key2]/call_status_other"
			::= { wingStatsRfdWlClientStatDetailEntry 61 }

		
		-- 1.3.6.1.4.1.1916.2.131.50.1.4.3.2.6.1.1.62
		wingStatsRfdWlClientStatDetailTotalBytes OBJECT-TYPE
			SYNTAX Counter64
			MAX-ACCESS read-only
			STATUS current
			DESCRIPTION
				"Total mumber of data bytes through the AP for the client
				
				XPath: /wing-stats/rf_domain[name=key1]/wireless/client-stats-details[mac=key2]/total_bytes"
			::= { wingStatsRfdWlClientStatDetailEntry 62 }

		
		-- 1.3.6.1.4.1.1916.2.131.50.1.4.3.2.6.1.1.63
		wingStatsRfdWlClientStatDetailTotalPkts OBJECT-TYPE
			SYNTAX Counter32
			MAX-ACCESS read-only
			STATUS current
			DESCRIPTION
				"Total number of packets through the AP for the client
				
				XPath: /wing-stats/rf_domain[name=key1]/wireless/client-stats-details[mac=key2]/total_pkts"
			::= { wingStatsRfdWlClientStatDetailEntry 63 }

		
		-- 1.3.6.1.4.1.1916.2.131.50.1.4.3.2.6.1.1.64
		wingStatsRfdWlClientStatDetailTxRetriedBytes OBJECT-TYPE
			SYNTAX Counter64
			MAX-ACCESS read-only
			STATUS current
			DESCRIPTION
				"Total retried bytes excluding bytes sent.								 	
				XPath: /wing-stats/rf_domain[name=key1]/wireless/client-stats-details[mac=key2]/tx_retried_bytes."
			::= { wingStatsRfdWlClientStatDetailEntry 64 }

		
-- /wing-stats/rf_domain/wireless/radio
		-- 1.3.6.1.4.1.1916.2.131.50.1.4.3.2.8
		wingStatsRfdWlRadio OBJECT IDENTIFIER ::= { wingStatsRfdWl 8 }

		
		-- 1.3.6.1.4.1.1916.2.131.50.1.4.3.2.8.1
		wingStatsRfdWlRadioTable OBJECT-TYPE
			SYNTAX SEQUENCE OF WingStatsRfdWlRadioEntry
			MAX-ACCESS not-accessible
			STATUS current
			DESCRIPTION
				"Status of radios on RF Domain
				
				/wing-stats/rf_domain/wireless/radio"
			::= { wingStatsRfdWlRadio 1 }

		
		-- 1.3.6.1.4.1.1916.2.131.50.1.4.3.2.8.1.1
		wingStatsRfdWlRadioEntry OBJECT-TYPE
			SYNTAX WingStatsRfdWlRadioEntry
			MAX-ACCESS not-accessible
			STATUS current
			DESCRIPTION
				"An entry in the table."
			INDEX { wingStatsRfdName, wingStatsRfdWlRadioId }
			::= { wingStatsRfdWlRadioTable 1 }

		
		WingStatsRfdWlRadioEntry ::=
			SEQUENCE { 
				wingStatsRfdWlRadioId
					WingIdentifier,
				wingStatsRfdWlRadioDeviceMac
					MacAddress,
				wingStatsRfdWlRadioAlias
					DisplayString,
				wingStatsRfdWlRadioMac
					MacAddress,
				wingStatsRfdWlRadioType
					DisplayString,
				wingStatsRfdWlRadioHostname
					DisplayString,
				wingStatsRfdWlRadioRfdName
					DisplayString,
				wingStatsRfdWlRadioLocation
					DisplayString,
				wingStatsRfdWlRadioState
					DisplayString,
				wingStatsRfdWlRadioCurChannel
					DisplayString,
				wingStatsRfdWlRadioConfigChannel
					DisplayString,
				wingStatsRfdWlRadioCurPower
					Unsigned32,
				wingStatsRfdWlRadioConfigPower
					DisplayString,
				wingStatsRfdWlRadioMaxUserRate
					Unsigned32,
				wingStatsRfdWlRadioNumClient
					Unsigned32,
				wingStatsRfdWlRadioProtocol
					Unsigned32
			 }

		-- 1.3.6.1.4.1.1916.2.131.50.1.4.3.2.8.1.1.1
		wingStatsRfdWlRadioId OBJECT-TYPE
			SYNTAX WingIdentifier
			MAX-ACCESS read-only
			STATUS current
			DESCRIPTION
				"Unique ID for each radio interface in the form of
				AP-MAC:R%d. E.g., 00-A0-F8-00-00-00:R1
				
				XPath: /wing-stats/rf_domain[name=key1]/wireless/radio[radio_id=key2]/radio_id"
			::= { wingStatsRfdWlRadioEntry 1 }

		
		-- 1.3.6.1.4.1.1916.2.131.50.1.4.3.2.8.1.1.2
		wingStatsRfdWlRadioDeviceMac OBJECT-TYPE
			SYNTAX MacAddress
			MAX-ACCESS read-only
			STATUS current
			DESCRIPTION
				"MAC address of the AP the radio belongs to.
				
				XPath: /wing-stats/rf_domain[name=key1]/wireless/radio[radio_id=key2]/device_mac"
			::= { wingStatsRfdWlRadioEntry 2 }

		
		-- 1.3.6.1.4.1.1916.2.131.50.1.4.3.2.8.1.1.3
		wingStatsRfdWlRadioAlias OBJECT-TYPE
			SYNTAX DisplayString
			MAX-ACCESS read-only
			STATUS current
			DESCRIPTION
				"An alias to radio id in the form of hostname:R%d.
				E.g., wm3400-22A24E:R1
				
				XPath: /wing-stats/rf_domain[name=key1]/wireless/radio[radio_id=key2]/radio_alias"
			::= { wingStatsRfdWlRadioEntry 3 }

		
		-- 1.3.6.1.4.1.1916.2.131.50.1.4.3.2.8.1.1.4
		wingStatsRfdWlRadioMac OBJECT-TYPE
			SYNTAX MacAddress
			MAX-ACCESS read-only
			STATUS current
			DESCRIPTION
				"MAC address of the radio interface
				
				XPath: /wing-stats/rf_domain[name=key1]/wireless/radio[radio_id=key2]/radio_mac"
			::= { wingStatsRfdWlRadioEntry 4 }

		
		-- 1.3.6.1.4.1.1916.2.131.50.1.4.3.2.8.1.1.5
		wingStatsRfdWlRadioType OBJECT-TYPE
			SYNTAX DisplayString
			MAX-ACCESS read-only
			STATUS current
			DESCRIPTION
				"802.11 radio-type
				
				XPath: /wing-stats/rf_domain[name=key1]/wireless/radio[radio_id=key2]/radio_type"
			::= { wingStatsRfdWlRadioEntry 5 }

		
		-- 1.3.6.1.4.1.1916.2.131.50.1.4.3.2.8.1.1.6
		wingStatsRfdWlRadioHostname OBJECT-TYPE
			SYNTAX DisplayString
			MAX-ACCESS read-only
			STATUS current
			DESCRIPTION
				"Hostname of the AP device
				
				XPath: /wing-stats/rf_domain[name=key1]/wireless/radio[radio_id=key2]/hostname"
			::= { wingStatsRfdWlRadioEntry 6 }

		
		-- 1.3.6.1.4.1.1916.2.131.50.1.4.3.2.8.1.1.7
		wingStatsRfdWlRadioRfdName OBJECT-TYPE
			SYNTAX DisplayString
			MAX-ACCESS read-only
			STATUS current
			DESCRIPTION
				"RF Domain name of the AP device
				
				XPath: /wing-stats/rf_domain[name=key1]/wireless/radio[radio_id=key2]/rf_domain_name"
			::= { wingStatsRfdWlRadioEntry 7 }

		
		-- 1.3.6.1.4.1.1916.2.131.50.1.4.3.2.8.1.1.8
		wingStatsRfdWlRadioLocation OBJECT-TYPE
			SYNTAX DisplayString
			MAX-ACCESS read-only
			STATUS current
			DESCRIPTION
				"Location description of the AP device
				
				XPath: /wing-stats/rf_domain[name=key1]/wireless/radio[radio_id=key2]/location"
			::= { wingStatsRfdWlRadioEntry 8 }

		
		-- 1.3.6.1.4.1.1916.2.131.50.1.4.3.2.8.1.1.9
		wingStatsRfdWlRadioState OBJECT-TYPE
			SYNTAX DisplayString
			MAX-ACCESS read-only
			STATUS current
			DESCRIPTION
				"Radio state
				
				XPath: /wing-stats/rf_domain[name=key1]/wireless/radio[radio_id=key2]/state"
			::= { wingStatsRfdWlRadioEntry 9 }

		
		-- 1.3.6.1.4.1.1916.2.131.50.1.4.3.2.8.1.1.10
		wingStatsRfdWlRadioCurChannel OBJECT-TYPE
			SYNTAX DisplayString
			MAX-ACCESS read-only
			STATUS current
			DESCRIPTION
				"Current channel the radio is operating at
				
				XPath: /wing-stats/rf_domain[name=key1]/wireless/radio[radio_id=key2]/current_channel"
			::= { wingStatsRfdWlRadioEntry 10 }

		
		-- 1.3.6.1.4.1.1916.2.131.50.1.4.3.2.8.1.1.11
		wingStatsRfdWlRadioConfigChannel OBJECT-TYPE
			SYNTAX DisplayString
			MAX-ACCESS read-only
			STATUS current
			DESCRIPTION
				"Configured channel for the radio
				
				XPath: /wing-stats/rf_domain[name=key1]/wireless/radio[radio_id=key2]/config_channel"
			::= { wingStatsRfdWlRadioEntry 11 }

		
		-- 1.3.6.1.4.1.1916.2.131.50.1.4.3.2.8.1.1.12
		wingStatsRfdWlRadioCurPower OBJECT-TYPE
			SYNTAX Unsigned32
			UNITS "dBm"
			MAX-ACCESS read-only
			STATUS current
			DESCRIPTION
				"Current power the radio is operating at
				
				XPath: /wing-stats/rf_domain[name=key1]/wireless/radio[radio_id=key2]/current_power"
			::= { wingStatsRfdWlRadioEntry 12 }

		
		-- 1.3.6.1.4.1.1916.2.131.50.1.4.3.2.8.1.1.13
		wingStatsRfdWlRadioConfigPower OBJECT-TYPE
			SYNTAX DisplayString
			MAX-ACCESS read-only
			STATUS current
			DESCRIPTION
				"Configured power for the radio
				
				XPath: /wing-stats/rf_domain[name=key1]/wireless/radio[radio_id=key2]/config_power"
			::= { wingStatsRfdWlRadioEntry 13 }

		
		-- 1.3.6.1.4.1.1916.2.131.50.1.4.3.2.8.1.1.14
		wingStatsRfdWlRadioMaxUserRate OBJECT-TYPE
			SYNTAX Unsigned32
			UNITS "kbps"
			MAX-ACCESS read-only
			STATUS current
			DESCRIPTION
				"Theoretic maximum user-level data rate
				
				XPath: /wing-stats/rf_domain[name=key1]/wireless/radio[radio_id=key2]/max_user_rate"
			::= { wingStatsRfdWlRadioEntry 14 }

		
		-- 1.3.6.1.4.1.1916.2.131.50.1.4.3.2.8.1.1.15
		wingStatsRfdWlRadioNumClient OBJECT-TYPE
			SYNTAX Unsigned32
			MAX-ACCESS read-only
			STATUS current
			DESCRIPTION
				"Number of clients associated to the radio
				
				XPath: /wing-stats/rf_domain[name=key1]/wireless/radio[radio_id=key2]/num_clients"
			::= { wingStatsRfdWlRadioEntry 15 }

		
		-- 1.3.6.1.4.1.1916.2.131.50.1.4.3.2.8.1.1.16
		wingStatsRfdWlRadioProtocol OBJECT-TYPE
			SYNTAX Unsigned32
			MAX-ACCESS read-only
			STATUS current
			DESCRIPTION
				"Bit map of protocols currently enabled on the radio.
				
				Bit position:
				The Least Significant Bit corresponds to the first bit
				in the map. The next bit corresponds to the second bit
				and so on. Unused bits are ignored.
				
				bit position  meaning
				============  =======
				0             dot11a
				1             dot11b
				2             dot11g
				3             dot11an
				4             dot11gn
				
				Bit values:
				1 - enabled
				0 - disabled
				
				XPath: /wing-stats/rf_domain[name=key1]/wireless/radio[radio_id=key2]/protocol"
			::= { wingStatsRfdWlRadioEntry 16 }

		
-- /wing-stats/rf_domain/wireless/radio-stats
		-- 1.3.6.1.4.1.1916.2.131.50.1.4.3.2.9
		wingStatsRfdWlRadioStat OBJECT IDENTIFIER ::= { wingStatsRfdWl 9 }

		
		-- 1.3.6.1.4.1.1916.2.131.50.1.4.3.2.9.1
		wingStatsRfdWlRadioStatTable OBJECT-TYPE
			SYNTAX SEQUENCE OF WingStatsRfdWlRadioStatEntry
			MAX-ACCESS not-accessible
			STATUS current
			DESCRIPTION
				"Traffic and RF statistics of radios on RF Domain
				
				/wing-stats/rf_domain/wireless/radio-stats"
			::= { wingStatsRfdWlRadioStat 1 }

		
		-- 1.3.6.1.4.1.1916.2.131.50.1.4.3.2.9.1.1
		wingStatsRfdWlRadioStatEntry OBJECT-TYPE
			SYNTAX WingStatsRfdWlRadioStatEntry
			MAX-ACCESS not-accessible
			STATUS current
			DESCRIPTION
				"An entry in the table."
			INDEX { wingStatsRfdName, wingStatsRfdWlRadioStatId }
			::= { wingStatsRfdWlRadioStatTable 1 }

		
		WingStatsRfdWlRadioStatEntry ::=
			SEQUENCE { 
				wingStatsRfdWlRadioStatId
					WingIdentifier,
				wingStatsRfdWlRadioStatDeviceMac
					MacAddress,
				wingStatsRfdWlRadioStatAlias
					DisplayString,
				wingStatsRfdWlRadioStatMac
					MacAddress,
				wingStatsRfdWlRadioStatType
					DisplayString,
				wingStatsRfdWlRadioStatTxBytes
					Counter64,
				wingStatsRfdWlRadioStatRxBytes
					Counter64,
				wingStatsRfdWlRadioStatTxPkts
					Counter32,
				wingStatsRfdWlRadioStatRxPkts
					Counter32,
				wingStatsRfdWlRadioStatTxDropped
					Counter32,
				wingStatsRfdWlRadioStatRxErrors
					Counter32,
				wingStatsRfdWlRadioStatTIndex
					Integer32,
				wingStatsRfdWlRadioStatTxBps
					Unsigned32,
				wingStatsRfdWlRadioStatRxBps
					Unsigned32,
				wingStatsRfdWlRadioStatSignal
					Integer32,
				wingStatsRfdWlRadioStatNoise
					Integer32,
				wingStatsRfdWlRadioStatSnr
					Integer32,
				wingStatsRfdWlRadioStatTxRate
					Unsigned32,
				wingStatsRfdWlRadioStatRxRate
					Unsigned32,
				wingStatsRfdWlRadioStatErrorRate
					Unsigned32,
				wingStatsRfdWlRadioStatQIndex
					Integer32,
				wingStatsRfdWlRadioStatNumClients
					Unsigned32,
				wingStatsRfdWlRadioStatNumBClients
					Unsigned32,
				wingStatsRfdWlRadioStatNumBgClients
					Unsigned32,
				wingStatsRfdWlRadioStatNumBgnClients
					Unsigned32,
				wingStatsRfdWlRadioStatNumAClients
					Unsigned32,
				wingStatsRfdWlRadioStatNumAnClients
					Unsigned32,
				wingStatsRfdWlRadioStatMediumErrorRate
					Unsigned32,
				wingStatsRfdWlRadioStatTxRetries
					Counter64,
				wingStatsRfdWlRadioStatTxRetriedBytes
					Counter64
			 }

		-- 1.3.6.1.4.1.1916.2.131.50.1.4.3.2.9.1.1.1
		wingStatsRfdWlRadioStatId OBJECT-TYPE
			SYNTAX WingIdentifier
			MAX-ACCESS read-only
			STATUS current
			DESCRIPTION
				"Unique ID for each radio interface in the form of
				AP-MAC:R%d. E.g., 00-A0-F8-00-00-00:R1
				
				XPath: /wing-stats/rf_domain[name=key1]/wireless/radio-stats[radio_id=key2]/radio_id"
			::= { wingStatsRfdWlRadioStatEntry 1 }

		
		-- 1.3.6.1.4.1.1916.2.131.50.1.4.3.2.9.1.1.2
		wingStatsRfdWlRadioStatDeviceMac OBJECT-TYPE
			SYNTAX MacAddress
			MAX-ACCESS read-only
			STATUS current
			DESCRIPTION
				"MAC address of AP the radio belongs to
				
				XPath: /wing-stats/rf_domain[name=key1]/wireless/radio-stats[radio_id=key2]/device_mac"
			::= { wingStatsRfdWlRadioStatEntry 2 }

		
		-- 1.3.6.1.4.1.1916.2.131.50.1.4.3.2.9.1.1.3
		wingStatsRfdWlRadioStatAlias OBJECT-TYPE
			SYNTAX DisplayString
			MAX-ACCESS read-only
			STATUS current
			DESCRIPTION
				"An alias to radio id in the form of hostname:R%d.
				E.g., wm3400-22A24E:R1
				
				XPath: /wing-stats/rf_domain[name=key1]/wireless/radio-stats[radio_id=key2]/radio_alias"
			::= { wingStatsRfdWlRadioStatEntry 3 }

		
		-- 1.3.6.1.4.1.1916.2.131.50.1.4.3.2.9.1.1.4
		wingStatsRfdWlRadioStatMac OBJECT-TYPE
			SYNTAX MacAddress
			MAX-ACCESS read-only
			STATUS current
			DESCRIPTION
				"MAC address of the radio
				
				XPath: /wing-stats/rf_domain[name=key1]/wireless/radio-stats[radio_id=key2]/radio_mac"
			::= { wingStatsRfdWlRadioStatEntry 4 }

		
		-- 1.3.6.1.4.1.1916.2.131.50.1.4.3.2.9.1.1.5
		wingStatsRfdWlRadioStatType OBJECT-TYPE
			SYNTAX DisplayString
			MAX-ACCESS read-only
			STATUS current
			DESCRIPTION
				"802.11 radio-type
				
				XPath: /wing-stats/rf_domain[name=key1]/wireless/radio-stats[radio_id=key2]/radio_type"
			::= { wingStatsRfdWlRadioStatEntry 5 }

		
		-- 1.3.6.1.4.1.1916.2.131.50.1.4.3.2.9.1.1.6
		wingStatsRfdWlRadioStatTxBytes OBJECT-TYPE
			SYNTAX Counter64
			MAX-ACCESS read-only
			STATUS current
			DESCRIPTION
				"Number of data bytes transmitted from radio to clients
				
				XPath: /wing-stats/rf_domain[name=key1]/wireless/radio-stats[radio_id=key2]/tx_bytes"
			::= { wingStatsRfdWlRadioStatEntry 6 }

		
		-- 1.3.6.1.4.1.1916.2.131.50.1.4.3.2.9.1.1.7
		wingStatsRfdWlRadioStatRxBytes OBJECT-TYPE
			SYNTAX Counter64
			MAX-ACCESS read-only
			STATUS current
			DESCRIPTION
				"Number of data bytes received from clients to radio
				
				XPath: /wing-stats/rf_domain[name=key1]/wireless/radio-stats[radio_id=key2]/rx_bytes"
			::= { wingStatsRfdWlRadioStatEntry 7 }

		
		-- 1.3.6.1.4.1.1916.2.131.50.1.4.3.2.9.1.1.8
		wingStatsRfdWlRadioStatTxPkts OBJECT-TYPE
			SYNTAX Counter32
			MAX-ACCESS read-only
			STATUS current
			DESCRIPTION
				"Number of packets of data transmitted from radio to clients
				
				XPath: /wing-stats/rf_domain[name=key1]/wireless/radio-stats[radio_id=key2]/tx_pkts"
			::= { wingStatsRfdWlRadioStatEntry 8 }

		
		-- 1.3.6.1.4.1.1916.2.131.50.1.4.3.2.9.1.1.9
		wingStatsRfdWlRadioStatRxPkts OBJECT-TYPE
			SYNTAX Counter32
			MAX-ACCESS read-only
			STATUS current
			DESCRIPTION
				"Number of packets of data received from clients to radio
				
				XPath: /wing-stats/rf_domain[name=key1]/wireless/radio-stats[radio_id=key2]/rx_pkts"
			::= { wingStatsRfdWlRadioStatEntry 9 }

		
		-- 1.3.6.1.4.1.1916.2.131.50.1.4.3.2.9.1.1.10
		wingStatsRfdWlRadioStatTxDropped OBJECT-TYPE
			SYNTAX Counter32
			MAX-ACCESS read-only
			STATUS current
			DESCRIPTION
				"Number of packets of data dropped on transmission
				
				XPath: /wing-stats/rf_domain[name=key1]/wireless/radio-stats[radio_id=key2]/tx_dropped"
			::= { wingStatsRfdWlRadioStatEntry 10 }

		
		-- 1.3.6.1.4.1.1916.2.131.50.1.4.3.2.9.1.1.11
		wingStatsRfdWlRadioStatRxErrors OBJECT-TYPE
			SYNTAX Counter32
			MAX-ACCESS read-only
			STATUS current
			DESCRIPTION
				"Number of packets of data received with errors
				
				XPath: /wing-stats/rf_domain[name=key1]/wireless/radio-stats[radio_id=key2]/rx_errors"
			::= { wingStatsRfdWlRadioStatEntry 11 }

		
		-- 1.3.6.1.4.1.1916.2.131.50.1.4.3.2.9.1.1.12
		wingStatsRfdWlRadioStatTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/rf_domain[name=key1]/wireless/radio-stats[radio_id=key2]/t_index"
			::= { wingStatsRfdWlRadioStatEntry 12 }

		
		-- 1.3.6.1.4.1.1916.2.131.50.1.4.3.2.9.1.1.13
		wingStatsRfdWlRadioStatTxBps OBJECT-TYPE
			SYNTAX Unsigned32
			UNITS "kbps"
			MAX-ACCESS read-only
			STATUS current
			DESCRIPTION
				"User data transmit rate
				
				XPath: /wing-stats/rf_domain[name=key1]/wireless/radio-stats[radio_id=key2]/tx_bps"
			::= { wingStatsRfdWlRadioStatEntry 13 }

		
		-- 1.3.6.1.4.1.1916.2.131.50.1.4.3.2.9.1.1.14
		wingStatsRfdWlRadioStatRxBps OBJECT-TYPE
			SYNTAX Unsigned32
			UNITS "kbps"
			MAX-ACCESS read-only
			STATUS current
			DESCRIPTION
				"User data receive rate
				
				XPath: /wing-stats/rf_domain[name=key1]/wireless/radio-stats[radio_id=key2]/rx_bps"
			::= { wingStatsRfdWlRadioStatEntry 14 }

		
		-- 1.3.6.1.4.1.1916.2.131.50.1.4.3.2.9.1.1.15
		wingStatsRfdWlRadioStatSignal OBJECT-TYPE
			SYNTAX Integer32
			UNITS "dbm"
			MAX-ACCESS read-only
			STATUS current
			DESCRIPTION
				"Signal strength in units of dbm
				
				XPath: /wing-stats/rf_domain[name=key1]/wireless/radio-stats[radio_id=key2]/signal"
			::= { wingStatsRfdWlRadioStatEntry 15 }

		
		-- 1.3.6.1.4.1.1916.2.131.50.1.4.3.2.9.1.1.16
		wingStatsRfdWlRadioStatNoise OBJECT-TYPE
			SYNTAX Integer32
			UNITS "dbm"
			MAX-ACCESS read-only
			STATUS current
			DESCRIPTION
				"Noise level in units of dbm
				
				XPath: /wing-stats/rf_domain[name=key1]/wireless/radio-stats[radio_id=key2]/noise"
			::= { wingStatsRfdWlRadioStatEntry 16 }

		
		-- 1.3.6.1.4.1.1916.2.131.50.1.4.3.2.9.1.1.17
		wingStatsRfdWlRadioStatSnr OBJECT-TYPE
			SYNTAX Integer32
			UNITS "db"
			MAX-ACCESS read-only
			STATUS current
			DESCRIPTION
				"Signal to noise ratio in units of db
				
				XPath: /wing-stats/rf_domain[name=key1]/wireless/radio-stats[radio_id=key2]/snr"
			::= { wingStatsRfdWlRadioStatEntry 17 }

		
		-- 1.3.6.1.4.1.1916.2.131.50.1.4.3.2.9.1.1.18
		wingStatsRfdWlRadioStatTxRate OBJECT-TYPE
			SYNTAX Unsigned32
			UNITS "Mbps"
			MAX-ACCESS read-only
			STATUS current
			DESCRIPTION
				"The effective phy-layer transmit rate
				
				XPath: /wing-stats/rf_domain[name=key1]/wireless/radio-stats[radio_id=key2]/tx_rate"
			::= { wingStatsRfdWlRadioStatEntry 18 }

		
		-- 1.3.6.1.4.1.1916.2.131.50.1.4.3.2.9.1.1.19
		wingStatsRfdWlRadioStatRxRate OBJECT-TYPE
			SYNTAX Unsigned32
			UNITS "Mbps"
			MAX-ACCESS read-only
			STATUS current
			DESCRIPTION
				"The effective phy-layer receive rate
				
				XPath: /wing-stats/rf_domain[name=key1]/wireless/radio-stats[radio_id=key2]/rx_rate"
			::= { wingStatsRfdWlRadioStatEntry 19 }

		
		-- 1.3.6.1.4.1.1916.2.131.50.1.4.3.2.9.1.1.20
		wingStatsRfdWlRadioStatErrorRate OBJECT-TYPE
			SYNTAX Unsigned32
			MAX-ACCESS read-only
			STATUS current
			DESCRIPTION
				"Ratio of errors to rx-packets in percentage
				
				XPath: /wing-stats/rf_domain[name=key1]/wireless/radio-stats[radio_id=key2]/error_rate"
			::= { wingStatsRfdWlRadioStatEntry 20 }

		
		-- 1.3.6.1.4.1.1916.2.131.50.1.4.3.2.9.1.1.21
		wingStatsRfdWlRadioStatQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/rf_domain[name=key1]/wireless/radio-stats[radio_id=key2]/q_index"
			::= { wingStatsRfdWlRadioStatEntry 21 }

		
		-- 1.3.6.1.4.1.1916.2.131.50.1.4.3.2.9.1.1.22
		wingStatsRfdWlRadioStatNumClients OBJECT-TYPE
			SYNTAX Unsigned32
			MAX-ACCESS read-only
			STATUS current
			DESCRIPTION
				"Total number of clients
				
				XPath: /wing-stats/rf_domain[name=key1]/wireless/radio-stats[radio_id=key2]/num_clients"
			::= { wingStatsRfdWlRadioStatEntry 22 }

		
		-- 1.3.6.1.4.1.1916.2.131.50.1.4.3.2.9.1.1.23
		wingStatsRfdWlRadioStatNumBClients OBJECT-TYPE
			SYNTAX Unsigned32
			MAX-ACCESS read-only
			STATUS current
			DESCRIPTION
				"Number of 11b clients
				
				XPath: /wing-stats/rf_domain[name=key1]/wireless/radio-stats[radio_id=key2]/num_b_clients"
			::= { wingStatsRfdWlRadioStatEntry 23 }

		
		-- 1.3.6.1.4.1.1916.2.131.50.1.4.3.2.9.1.1.24
		wingStatsRfdWlRadioStatNumBgClients OBJECT-TYPE
			SYNTAX Unsigned32
			MAX-ACCESS read-only
			STATUS current
			DESCRIPTION
				"Number of 11bg clients
				
				XPath: /wing-stats/rf_domain[name=key1]/wireless/radio-stats[radio_id=key2]/num_bg_clients"
			::= { wingStatsRfdWlRadioStatEntry 24 }

		
		-- 1.3.6.1.4.1.1916.2.131.50.1.4.3.2.9.1.1.25
		wingStatsRfdWlRadioStatNumBgnClients OBJECT-TYPE
			SYNTAX Unsigned32
			MAX-ACCESS read-only
			STATUS current
			DESCRIPTION
				"Number of 11bgn clients
				
				XPath: /wing-stats/rf_domain[name=key1]/wireless/radio-stats[radio_id=key2]/num_bgn_clients"
			::= { wingStatsRfdWlRadioStatEntry 25 }

		
		-- 1.3.6.1.4.1.1916.2.131.50.1.4.3.2.9.1.1.26
		wingStatsRfdWlRadioStatNumAClients OBJECT-TYPE
			SYNTAX Unsigned32
			MAX-ACCESS read-only
			STATUS current
			DESCRIPTION
				"Number of 11a clients
				
				XPath: /wing-stats/rf_domain[name=key1]/wireless/radio-stats[radio_id=key2]/num_a_clients"
			::= { wingStatsRfdWlRadioStatEntry 26 }

		
		-- 1.3.6.1.4.1.1916.2.131.50.1.4.3.2.9.1.1.27
		wingStatsRfdWlRadioStatNumAnClients OBJECT-TYPE
			SYNTAX Unsigned32
			MAX-ACCESS read-only
			STATUS current
			DESCRIPTION
				"Number of 11an clients
				
				XPath: /wing-stats/rf_domain[name=key1]/wireless/radio-stats[radio_id=key2]/num_an_clients"
			::= { wingStatsRfdWlRadioStatEntry 27 }

		
		-- 1.3.6.1.4.1.1916.2.131.50.1.4.3.2.9.1.1.28
		wingStatsRfdWlRadioStatMediumErrorRate OBJECT-TYPE
			SYNTAX Unsigned32
			MAX-ACCESS read-only
			STATUS current
			DESCRIPTION
				"Ratio of medium errors and rx-retries to rx-packets
				in percentage
				
				XPath: /wing-stats/rf_domain[name=key1]/wireless/radio-stats[radio_id=key2]/medium_error_rate"
			::= { wingStatsRfdWlRadioStatEntry 28 }

		
		-- 1.3.6.1.4.1.1916.2.131.50.1.4.3.2.9.1.1.29
		wingStatsRfdWlRadioStatTxRetries OBJECT-TYPE
			SYNTAX Counter64
			MAX-ACCESS read-only
			STATUS current
			DESCRIPTION
				"Total number of retries
				
				XPath: /wing-stats/rf_domain[name=key1]/wireless/radio-stats[radio_id=key2]/tx_retries"
			::= { wingStatsRfdWlRadioStatEntry 29 }

		
		-- 1.3.6.1.4.1.1916.2.131.50.1.4.3.2.9.1.1.30
		wingStatsRfdWlRadioStatTxRetriedBytes OBJECT-TYPE
			SYNTAX Counter64
			MAX-ACCESS read-only
			STATUS current
			DESCRIPTION
				"Total retried bytes excluding bytes sent.				    
				
				XPath: /wing-stats/rf_domain[name=key1]/wireless/radio-stats[radio_id=key2]/tx_retried_bytes."
			::= { wingStatsRfdWlRadioStatEntry 30 }

		
-- /wing-stats/rf_domain/wireless/radio-details
		-- 1.3.6.1.4.1.1916.2.131.50.1.4.3.2.10
		wingStatsRfdWlRadioDetail OBJECT IDENTIFIER ::= { wingStatsRfdWl 10 }

		
		-- 1.3.6.1.4.1.1916.2.131.50.1.4.3.2.10.1
		wingStatsRfdWlRadioDetailTable OBJECT-TYPE
			SYNTAX SEQUENCE OF WingStatsRfdWlRadioDetailEntry
			MAX-ACCESS not-accessible
			STATUS current
			DESCRIPTION
				"Detailed status of radios on RF Domain
				
				/wing-stats/rf_domain/wireless/radio-details"
			::= { wingStatsRfdWlRadioDetail 1 }

		
		-- 1.3.6.1.4.1.1916.2.131.50.1.4.3.2.10.1.1
		wingStatsRfdWlRadioDetailEntry OBJECT-TYPE
			SYNTAX WingStatsRfdWlRadioDetailEntry
			MAX-ACCESS not-accessible
			STATUS current
			DESCRIPTION
				"An entry in the table."
			INDEX { wingStatsRfdName, wingStatsRfdWlRadioDetailId }
			::= { wingStatsRfdWlRadioDetailTable 1 }

		
		WingStatsRfdWlRadioDetailEntry ::=
			SEQUENCE { 
				wingStatsRfdWlRadioDetailId
					WingIdentifier,
				wingStatsRfdWlRadioDetailDeviceMac
					MacAddress,
				wingStatsRfdWlRadioDetailAlias
					DisplayString,
				wingStatsRfdWlRadioDetailMac
					MacAddress,
				wingStatsRfdWlRadioDetailType
					DisplayString,
				wingStatsRfdWlRadioDetailHostname
					DisplayString,
				wingStatsRfdWlRadioDetailRfdName
					DisplayString,
				wingStatsRfdWlRadioDetailLocation
					DisplayString,
				wingStatsRfdWlRadioDetailState
					DisplayString,
				wingStatsRfdWlRadioDetailCurChannel
					DisplayString,
				wingStatsRfdWlRadioDetailConfigChannel
					DisplayString,
				wingStatsRfdWlRadioDetailCurPower
					Unsigned32,
				wingStatsRfdWlRadioDetailConfigPower
					DisplayString,
				wingStatsRfdWlRadioDetailMaxUserRate
					Unsigned32,
				wingStatsRfdWlRadioDetailNumClient
					Unsigned32,
				wingStatsRfdWlRadioDetailSpectrumMgmt
					TruthValue,
				wingStatsRfdWlRadioDetailShortPreamble
					TruthValue,
				wingStatsRfdWlRadioDetailNonErpPresent
					TruthValue,
				wingStatsRfdWlRadioDetailErpProtectionOn
					TruthValue,
				wingStatsRfdWlRadioDetailNonErpDetected
					TruthValue,
				wingStatsRfdWlRadioDetailHtProtectionOn
					TruthValue,
				wingStatsRfdWlRadioDetailHt20Present
					TruthValue,
				wingStatsRfdWlRadioDetailNonHtDetected
					TruthValue,
				wingStatsRfdWlRadioDetailDualChannelOn
					TruthValue,
				wingStatsRfdWlRadioDetailTxAntennaUsed
					Unsigned32,
				wingStatsRfdWlRadioDetailRxAntennaUsed
					Unsigned32,
				wingStatsRfdWlRadioDetailMaxPhyRate
					Unsigned32,
				wingStatsRfdWlRadioDetailCurMcastStreams
					Unsigned32,
				wingStatsRfdWlRadioDetailMaxMcastStreams
					Unsigned32,
				wingStatsRfdWlRadioDetailMcastStreams
					DisplayString,
				wingStatsRfdWlRadioDetailLastError
					DisplayString
			 }

		-- 1.3.6.1.4.1.1916.2.131.50.1.4.3.2.10.1.1.1
		wingStatsRfdWlRadioDetailId OBJECT-TYPE
			SYNTAX WingIdentifier
			MAX-ACCESS read-only
			STATUS current
			DESCRIPTION
				"Unique ID for each radio interface in the form of
				AP-MAC:R%d. E.g., 00-A0-F8-00-00-00:R1
				
				XPath: /wing-stats/rf_domain[name=key1]/wireless/radio-details[radio_id=key2]/radio_id"
			::= { wingStatsRfdWlRadioDetailEntry 1 }

		
		-- 1.3.6.1.4.1.1916.2.131.50.1.4.3.2.10.1.1.2
		wingStatsRfdWlRadioDetailDeviceMac OBJECT-TYPE
			SYNTAX MacAddress
			MAX-ACCESS read-only
			STATUS current
			DESCRIPTION
				"MAC address of AP the radio belongs to
				
				XPath: /wing-stats/rf_domain[name=key1]/wireless/radio-details[radio_id=key2]/device_mac"
			::= { wingStatsRfdWlRadioDetailEntry 2 }

		
		-- 1.3.6.1.4.1.1916.2.131.50.1.4.3.2.10.1.1.3
		wingStatsRfdWlRadioDetailAlias OBJECT-TYPE
			SYNTAX DisplayString
			MAX-ACCESS read-only
			STATUS current
			DESCRIPTION
				"An alias to radio id in the form of hostname:R%d.
				E.g., wm3400-22A24E:R1
				
				XPath: /wing-stats/rf_domain[name=key1]/wireless/radio-details[radio_id=key2]/radio_alias"
			::= { wingStatsRfdWlRadioDetailEntry 3 }

		
		-- 1.3.6.1.4.1.1916.2.131.50.1.4.3.2.10.1.1.4
		wingStatsRfdWlRadioDetailMac OBJECT-TYPE
			SYNTAX MacAddress
			MAX-ACCESS read-only
			STATUS current
			DESCRIPTION
				"MAC address of the radio interface
				
				XPath: /wing-stats/rf_domain[name=key1]/wireless/radio-details[radio_id=key2]/radio_mac"
			::= { wingStatsRfdWlRadioDetailEntry 4 }

		
		-- 1.3.6.1.4.1.1916.2.131.50.1.4.3.2.10.1.1.5
		wingStatsRfdWlRadioDetailType OBJECT-TYPE
			SYNTAX DisplayString
			MAX-ACCESS read-only
			STATUS current
			DESCRIPTION
				"802.11 radio-type
				
				XPath: /wing-stats/rf_domain[name=key1]/wireless/radio-details[radio_id=key2]/radio_type"
			::= { wingStatsRfdWlRadioDetailEntry 5 }

		
		-- 1.3.6.1.4.1.1916.2.131.50.1.4.3.2.10.1.1.6
		wingStatsRfdWlRadioDetailHostname OBJECT-TYPE
			SYNTAX DisplayString
			MAX-ACCESS read-only
			STATUS current
			DESCRIPTION
				"Hostname of the AP device
				
				XPath: /wing-stats/rf_domain[name=key1]/wireless/radio-details[radio_id=key2]/hostname"
			::= { wingStatsRfdWlRadioDetailEntry 6 }

		
		-- 1.3.6.1.4.1.1916.2.131.50.1.4.3.2.10.1.1.7
		wingStatsRfdWlRadioDetailRfdName OBJECT-TYPE
			SYNTAX DisplayString
			MAX-ACCESS read-only
			STATUS current
			DESCRIPTION
				"RF Domain name of the AP device
				
				XPath: /wing-stats/rf_domain[name=key1]/wireless/radio-details[radio_id=key2]/rf_domain_name"
			::= { wingStatsRfdWlRadioDetailEntry 7 }

		
		-- 1.3.6.1.4.1.1916.2.131.50.1.4.3.2.10.1.1.8
		wingStatsRfdWlRadioDetailLocation OBJECT-TYPE
			SYNTAX DisplayString
			MAX-ACCESS read-only
			STATUS current
			DESCRIPTION
				"Location description of the AP device
				
				XPath: /wing-stats/rf_domain[name=key1]/wireless/radio-details[radio_id=key2]/location"
			::= { wingStatsRfdWlRadioDetailEntry 8 }

		
		-- 1.3.6.1.4.1.1916.2.131.50.1.4.3.2.10.1.1.9
		wingStatsRfdWlRadioDetailState OBJECT-TYPE
			SYNTAX DisplayString
			MAX-ACCESS read-only
			STATUS current
			DESCRIPTION
				"Radio state
				
				XPath: /wing-stats/rf_domain[name=key1]/wireless/radio-details[radio_id=key2]/state"
			::= { wingStatsRfdWlRadioDetailEntry 9 }

		
		-- 1.3.6.1.4.1.1916.2.131.50.1.4.3.2.10.1.1.10
		wingStatsRfdWlRadioDetailCurChannel OBJECT-TYPE
			SYNTAX DisplayString
			MAX-ACCESS read-only
			STATUS current
			DESCRIPTION
				"Current channel the radio is operating at
				
				XPath: /wing-stats/rf_domain[name=key1]/wireless/radio-details[radio_id=key2]/current_channel"
			::= { wingStatsRfdWlRadioDetailEntry 10 }

		
		-- 1.3.6.1.4.1.1916.2.131.50.1.4.3.2.10.1.1.11
		wingStatsRfdWlRadioDetailConfigChannel OBJECT-TYPE
			SYNTAX DisplayString
			MAX-ACCESS read-only
			STATUS current
			DESCRIPTION
				"Configured channel for the radio
				
				XPath: /wing-stats/rf_domain[name=key1]/wireless/radio-details[radio_id=key2]/config_channel"
			::= { wingStatsRfdWlRadioDetailEntry 11 }

		
		-- 1.3.6.1.4.1.1916.2.131.50.1.4.3.2.10.1.1.12
		wingStatsRfdWlRadioDetailCurPower OBJECT-TYPE
			SYNTAX Unsigned32
			UNITS "dBm"
			MAX-ACCESS read-only
			STATUS current
			DESCRIPTION
				"Current power the radio is operating at
				
				XPath: /wing-stats/rf_domain[name=key1]/wireless/radio-details[radio_id=key2]/current_power"
			::= { wingStatsRfdWlRadioDetailEntry 12 }

		
		-- 1.3.6.1.4.1.1916.2.131.50.1.4.3.2.10.1.1.13
		wingStatsRfdWlRadioDetailConfigPower OBJECT-TYPE
			SYNTAX DisplayString
			MAX-ACCESS read-only
			STATUS current
			DESCRIPTION
				"Configured power for the radio
				
				XPath: /wing-stats/rf_domain[name=key1]/wireless/radio-details[radio_id=key2]/config_power"
			::= { wingStatsRfdWlRadioDetailEntry 13 }

		
		-- 1.3.6.1.4.1.1916.2.131.50.1.4.3.2.10.1.1.14
		wingStatsRfdWlRadioDetailMaxUserRate OBJECT-TYPE
			SYNTAX Unsigned32
			UNITS "kbps"
			MAX-ACCESS read-only
			STATUS current
			DESCRIPTION
				"Theoretic maximum user-level data rate
				
				XPath: /wing-stats/rf_domain[name=key1]/wireless/radio-details[radio_id=key2]/max_user_rate"
			::= { wingStatsRfdWlRadioDetailEntry 14 }

		
		-- 1.3.6.1.4.1.1916.2.131.50.1.4.3.2.10.1.1.15
		wingStatsRfdWlRadioDetailNumClient OBJECT-TYPE
			SYNTAX Unsigned32
			MAX-ACCESS read-only
			STATUS current
			DESCRIPTION
				"Number of clients associated to the radio
				
				XPath: /wing-stats/rf_domain[name=key1]/wireless/radio-details[radio_id=key2]/num_clients"
			::= { wingStatsRfdWlRadioDetailEntry 15 }

		
		-- 1.3.6.1.4.1.1916.2.131.50.1.4.3.2.10.1.1.16
		wingStatsRfdWlRadioDetailSpectrumMgmt OBJECT-TYPE
			SYNTAX TruthValue
			MAX-ACCESS read-only
			STATUS current
			DESCRIPTION
				"Whether spectrum management is enabled
				
				XPath: /wing-stats/rf_domain[name=key1]/wireless/radio-details[radio_id=key2]/spectrum_mgmt"
			::= { wingStatsRfdWlRadioDetailEntry 16 }

		
		-- 1.3.6.1.4.1.1916.2.131.50.1.4.3.2.10.1.1.17
		wingStatsRfdWlRadioDetailShortPreamble OBJECT-TYPE
			SYNTAX TruthValue
			MAX-ACCESS read-only
			STATUS current
			DESCRIPTION
				"Whether short preamble mode is enabled
				
				XPath: /wing-stats/rf_domain[name=key1]/wireless/radio-details[radio_id=key2]/short_preamble"
			::= { wingStatsRfdWlRadioDetailEntry 17 }

		
		-- 1.3.6.1.4.1.1916.2.131.50.1.4.3.2.10.1.1.18
		wingStatsRfdWlRadioDetailNonErpPresent OBJECT-TYPE
			SYNTAX TruthValue
			MAX-ACCESS read-only
			STATUS current
			DESCRIPTION
				"Whether non-ERP (Extended Rate PHY) clients are present
				
				XPath: /wing-stats/rf_domain[name=key1]/wireless/radio-details[radio_id=key2]/non_erp_present"
			::= { wingStatsRfdWlRadioDetailEntry 18 }

		
		-- 1.3.6.1.4.1.1916.2.131.50.1.4.3.2.10.1.1.19
		wingStatsRfdWlRadioDetailErpProtectionOn OBJECT-TYPE
			SYNTAX TruthValue
			MAX-ACCESS read-only
			STATUS current
			DESCRIPTION
				"Whether ERP Protection is on
				
				XPath: /wing-stats/rf_domain[name=key1]/wireless/radio-details[radio_id=key2]/erp_protection_on"
			::= { wingStatsRfdWlRadioDetailEntry 19 }

		
		-- 1.3.6.1.4.1.1916.2.131.50.1.4.3.2.10.1.1.20
		wingStatsRfdWlRadioDetailNonErpDetected OBJECT-TYPE
			SYNTAX TruthValue
			MAX-ACCESS read-only
			STATUS current
			DESCRIPTION
				"Whether non-ERP (Extended Rate PHY, 11g) clients
				are detected
				
				XPath: /wing-stats/rf_domain[name=key1]/wireless/radio-details[radio_id=key2]/non_erp_detected"
			::= { wingStatsRfdWlRadioDetailEntry 20 }

		
		-- 1.3.6.1.4.1.1916.2.131.50.1.4.3.2.10.1.1.21
		wingStatsRfdWlRadioDetailHtProtectionOn OBJECT-TYPE
			SYNTAX TruthValue
			MAX-ACCESS read-only
			STATUS current
			DESCRIPTION
				"Whether HT (High Throughput, i.e. 11n) Protection is on
				
				XPath: /wing-stats/rf_domain[name=key1]/wireless/radio-details[radio_id=key2]/ht_protection_on"
			::= { wingStatsRfdWlRadioDetailEntry 21 }

		
		-- 1.3.6.1.4.1.1916.2.131.50.1.4.3.2.10.1.1.22
		wingStatsRfdWlRadioDetailHt20Present OBJECT-TYPE
			SYNTAX TruthValue
			MAX-ACCESS read-only
			STATUS current
			DESCRIPTION
				"Whether HT single channel (20Mhz) clients are present
				
				XPath: /wing-stats/rf_domain[name=key1]/wireless/radio-details[radio_id=key2]/ht_20_present"
			::= { wingStatsRfdWlRadioDetailEntry 22 }

		
		-- 1.3.6.1.4.1.1916.2.131.50.1.4.3.2.10.1.1.23
		wingStatsRfdWlRadioDetailNonHtDetected OBJECT-TYPE
			SYNTAX TruthValue
			MAX-ACCESS read-only
			STATUS current
			DESCRIPTION
				"Whether non-HT devices are present
				
				XPath: /wing-stats/rf_domain[name=key1]/wireless/radio-details[radio_id=key2]/non_ht_detected"
			::= { wingStatsRfdWlRadioDetailEntry 23 }

		
		-- 1.3.6.1.4.1.1916.2.131.50.1.4.3.2.10.1.1.24
		wingStatsRfdWlRadioDetailDualChannelOn OBJECT-TYPE
			SYNTAX TruthValue
			MAX-ACCESS read-only
			STATUS current
			DESCRIPTION
				"Whether dual channel mode is on
				
				XPath: /wing-stats/rf_domain[name=key1]/wireless/radio-details[radio_id=key2]/dual_channel_on"
			::= { wingStatsRfdWlRadioDetailEntry 24 }

		
		-- 1.3.6.1.4.1.1916.2.131.50.1.4.3.2.10.1.1.25
		wingStatsRfdWlRadioDetailTxAntennaUsed OBJECT-TYPE
			SYNTAX Unsigned32
			MAX-ACCESS read-only
			STATUS current
			DESCRIPTION
				"Number of antennas used in transmit chain
				
				XPath: /wing-stats/rf_domain[name=key1]/wireless/radio-details[radio_id=key2]/tx_antenna_used"
			::= { wingStatsRfdWlRadioDetailEntry 25 }

		
		-- 1.3.6.1.4.1.1916.2.131.50.1.4.3.2.10.1.1.26
		wingStatsRfdWlRadioDetailRxAntennaUsed OBJECT-TYPE
			SYNTAX Unsigned32
			MAX-ACCESS read-only
			STATUS current
			DESCRIPTION
				"Number of antennas used in receive chain
				
				XPath: /wing-stats/rf_domain[name=key1]/wireless/radio-details[radio_id=key2]/rx_antenna_used"
			::= { wingStatsRfdWlRadioDetailEntry 26 }

		
		-- 1.3.6.1.4.1.1916.2.131.50.1.4.3.2.10.1.1.27
		wingStatsRfdWlRadioDetailMaxPhyRate OBJECT-TYPE
			SYNTAX Unsigned32
			UNITS "kbps"
			MAX-ACCESS read-only
			STATUS current
			DESCRIPTION
				"Maximum physical data rate
				
				XPath: /wing-stats/rf_domain[name=key1]/wireless/radio-details[radio_id=key2]/max_phy_rate"
			::= { wingStatsRfdWlRadioDetailEntry 27 }

		
		-- 1.3.6.1.4.1.1916.2.131.50.1.4.3.2.10.1.1.28
		wingStatsRfdWlRadioDetailCurMcastStreams OBJECT-TYPE
			SYNTAX Unsigned32
			MAX-ACCESS read-only
			STATUS current
			DESCRIPTION
				"Number of active accelerated multicast streams
				
				XPath: /wing-stats/rf_domain[name=key1]/wireless/radio-details[radio_id=key2]/cur_mcast_streams"
			::= { wingStatsRfdWlRadioDetailEntry 28 }

		
		-- 1.3.6.1.4.1.1916.2.131.50.1.4.3.2.10.1.1.29
		wingStatsRfdWlRadioDetailMaxMcastStreams OBJECT-TYPE
			SYNTAX Unsigned32
			MAX-ACCESS read-only
			STATUS current
			DESCRIPTION
				"Maximum number of accelerated multicast streams
				
				XPath: /wing-stats/rf_domain[name=key1]/wireless/radio-details[radio_id=key2]/max_mcast_streams"
			::= { wingStatsRfdWlRadioDetailEntry 29 }

		
		-- 1.3.6.1.4.1.1916.2.131.50.1.4.3.2.10.1.1.30
		wingStatsRfdWlRadioDetailMcastStreams OBJECT-TYPE
			SYNTAX DisplayString
			MAX-ACCESS read-only
			STATUS current
			DESCRIPTION
				"IP addresses and number of registered clients for
				accelerated multicast streams
				
				XPath: /wing-stats/rf_domain[name=key1]/wireless/radio-details[radio_id=key2]/mcast_streams"
			::= { wingStatsRfdWlRadioDetailEntry 30 }

		
		-- 1.3.6.1.4.1.1916.2.131.50.1.4.3.2.10.1.1.31
		wingStatsRfdWlRadioDetailLastError OBJECT-TYPE
			SYNTAX DisplayString
			MAX-ACCESS read-only
			STATUS current
			DESCRIPTION
				"The last run-time error encountered when applying a
				configuration to this radio or its AP
				
				XPath: /wing-stats/rf_domain[name=key1]/wireless/radio-details[radio_id=key2]/last_error"
			::= { wingStatsRfdWlRadioDetailEntry 31 }

		
		-- 1.3.6.1.4.1.1916.2.131.50.1.4.3.2.10.2
		wingStatsRfdWlRadioDetailWlanMapTable OBJECT-TYPE
			SYNTAX SEQUENCE OF WingStatsRfdWlRadioDetailWlanMapEntry
			MAX-ACCESS not-accessible
			STATUS current
			DESCRIPTION
				"Wireless LANs mapped on this radio interface.
				
				/wing-stats/rf_domain/wireless/radio-details/wlan_map"
			::= { wingStatsRfdWlRadioDetail 2 }

		
		-- 1.3.6.1.4.1.1916.2.131.50.1.4.3.2.10.2.1
		wingStatsRfdWlRadioDetailWlanMapEntry OBJECT-TYPE
			SYNTAX WingStatsRfdWlRadioDetailWlanMapEntry
			MAX-ACCESS not-accessible
			STATUS current
			DESCRIPTION
				"An entry in the table."
			INDEX { wingStatsRfdName, wingStatsRfdWlRadioDetailId, wingStatsRfdWlRadioDetailWlanMapWlanName }
			::= { wingStatsRfdWlRadioDetailWlanMapTable 1 }

		
		WingStatsRfdWlRadioDetailWlanMapEntry ::=
			SEQUENCE { 
				wingStatsRfdWlRadioDetailWlanMapWlanName
					WingIdentifier,
				wingStatsRfdWlRadioDetailWlanMapBssIndex
					Unsigned32,
				wingStatsRfdWlRadioDetailWlanMapIsPrimary
					TruthValue
			 }

		-- 1.3.6.1.4.1.1916.2.131.50.1.4.3.2.10.2.1.1
		wingStatsRfdWlRadioDetailWlanMapWlanName OBJECT-TYPE
			SYNTAX WingIdentifier
			MAX-ACCESS read-only
			STATUS current
			DESCRIPTION
				"The name of the WLAN.
				
				XPath: /wing-stats/rf_domain[name=key1]/wireless/radio-details[radio_id=key2]/wlan_map[wlan_name=key3]/wlan_name"
			::= { wingStatsRfdWlRadioDetailWlanMapEntry 1 }

		
		-- 1.3.6.1.4.1.1916.2.131.50.1.4.3.2.10.2.1.2
		wingStatsRfdWlRadioDetailWlanMapBssIndex OBJECT-TYPE
			SYNTAX Unsigned32
			MAX-ACCESS read-only
			STATUS current
			DESCRIPTION
				"The BSS Index on the radio that this WLAN is mapped upon.
				
				XPath: /wing-stats/rf_domain[name=key1]/wireless/radio-details[radio_id=key2]/wlan_map[wlan_name=key3]/bss_index"
			::= { wingStatsRfdWlRadioDetailWlanMapEntry 2 }

		
		-- 1.3.6.1.4.1.1916.2.131.50.1.4.3.2.10.2.1.3
		wingStatsRfdWlRadioDetailWlanMapIsPrimary OBJECT-TYPE
			SYNTAX TruthValue
			MAX-ACCESS read-only
			STATUS current
			DESCRIPTION
				"Whether this WLAN is the primary WLAN on the bss_index.
				Only the primary WLAN on a bss_index would have
				beacons advertised.
				
				XPath: /wing-stats/rf_domain[name=key1]/wireless/radio-details[radio_id=key2]/wlan_map[wlan_name=key3]/is_primary"
			::= { wingStatsRfdWlRadioDetailWlanMapEntry 3 }

		
		-- 1.3.6.1.4.1.1916.2.131.50.1.4.3.2.10.3
		wingStatsRfdWlRadioDetailBssMapTable OBJECT-TYPE
			SYNTAX SEQUENCE OF WingStatsRfdWlRadioDetailBssMapEntry
			MAX-ACCESS not-accessible
			STATUS current
			DESCRIPTION
				"BSS radio details.
				
				/wing-stats/rf_domain/wireless/radio-details/bss_map"
			::= { wingStatsRfdWlRadioDetail 3 }

		
		-- 1.3.6.1.4.1.1916.2.131.50.1.4.3.2.10.3.1
		wingStatsRfdWlRadioDetailBssMapEntry OBJECT-TYPE
			SYNTAX WingStatsRfdWlRadioDetailBssMapEntry
			MAX-ACCESS not-accessible
			STATUS current
			DESCRIPTION
				"An entry in the table."
			INDEX { wingStatsRfdName, wingStatsRfdWlRadioDetailId, wingStatsRfdWlRadioDetailBssMapBssIndex }
			::= { wingStatsRfdWlRadioDetailBssMapTable 1 }

		
		WingStatsRfdWlRadioDetailBssMapEntry ::=
			SEQUENCE { 
				wingStatsRfdWlRadioDetailBssMapBssIndex
					WingIdentifier,
				wingStatsRfdWlRadioDetailBssMapBasicRates
					DisplayString,
				wingStatsRfdWlRadioDetailBssMapSupportedRates
					DisplayString
			 }

		-- 1.3.6.1.4.1.1916.2.131.50.1.4.3.2.10.3.1.1
		wingStatsRfdWlRadioDetailBssMapBssIndex OBJECT-TYPE
			SYNTAX WingIdentifier
			MAX-ACCESS read-only
			STATUS current
			DESCRIPTION
				"The BSS index
				
				Values:
				1
				2
				3
				4
				5
				6
				7
				8
				
				XPath: /wing-stats/rf_domain[name=key1]/wireless/radio-details[radio_id=key2]/bss_map[bss_index=key3]/bss_index"
			::= { wingStatsRfdWlRadioDetailBssMapEntry 1 }

		
		-- 1.3.6.1.4.1.1916.2.131.50.1.4.3.2.10.3.1.2
		wingStatsRfdWlRadioDetailBssMapBasicRates OBJECT-TYPE
			SYNTAX DisplayString
			MAX-ACCESS read-only
			STATUS current
			DESCRIPTION
				"Basic rate set on this BSS.
				
				XPath: /wing-stats/rf_domain[name=key1]/wireless/radio-details[radio_id=key2]/bss_map[bss_index=key3]/basic_rates"
			::= { wingStatsRfdWlRadioDetailBssMapEntry 2 }

		
		-- 1.3.6.1.4.1.1916.2.131.50.1.4.3.2.10.3.1.3
		wingStatsRfdWlRadioDetailBssMapSupportedRates OBJECT-TYPE
			SYNTAX DisplayString
			MAX-ACCESS read-only
			STATUS current
			DESCRIPTION
				"Supported rate set on this BSS.
				
				XPath: /wing-stats/rf_domain[name=key1]/wireless/radio-details[radio_id=key2]/bss_map[bss_index=key3]/supported_rates"
			::= { wingStatsRfdWlRadioDetailBssMapEntry 3 }

		
-- /wing-stats/rf_domain/wireless/radio-stats-details
		-- 1.3.6.1.4.1.1916.2.131.50.1.4.3.2.11
		wingStatsRfdWlRadioStatDetail OBJECT IDENTIFIER ::= { wingStatsRfdWl 11 }

		
		-- 1.3.6.1.4.1.1916.2.131.50.1.4.3.2.11.1
		wingStatsRfdWlRadioStatDetailTable OBJECT-TYPE
			SYNTAX SEQUENCE OF WingStatsRfdWlRadioStatDetailEntry
			MAX-ACCESS not-accessible
			STATUS current
			DESCRIPTION
				"Detailed Traffic and RF statistics of radios on RF Domain
				
				/wing-stats/rf_domain/wireless/radio-stats-details"
			::= { wingStatsRfdWlRadioStatDetail 1 }

		
		-- 1.3.6.1.4.1.1916.2.131.50.1.4.3.2.11.1.1
		wingStatsRfdWlRadioStatDetailEntry OBJECT-TYPE
			SYNTAX WingStatsRfdWlRadioStatDetailEntry
			MAX-ACCESS not-accessible
			STATUS current
			DESCRIPTION
				"An entry in the table."
			INDEX { wingStatsRfdName, wingStatsRfdWlRadioStatDetailId }
			::= { wingStatsRfdWlRadioStatDetailTable 1 }

		
		WingStatsRfdWlRadioStatDetailEntry ::=
			SEQUENCE { 
				wingStatsRfdWlRadioStatDetailId
					WingIdentifier,
				wingStatsRfdWlRadioStatDetailDeviceMac
					MacAddress,
				wingStatsRfdWlRadioStatDetailAlias
					DisplayString,
				wingStatsRfdWlRadioStatDetailMac
					MacAddress,
				wingStatsRfdWlRadioStatDetailType
					DisplayString,
				wingStatsRfdWlRadioStatDetailTxBytes
					Counter64,
				wingStatsRfdWlRadioStatDetailRxBytes
					Counter64,
				wingStatsRfdWlRadioStatDetailTxPkts
					Counter32,
				wingStatsRfdWlRadioStatDetailRxPkts
					Counter32,
				wingStatsRfdWlRadioStatDetailTxDropped
					Counter32,
				wingStatsRfdWlRadioStatDetailRxErrors
					Counter32,
				wingStatsRfdWlRadioStatDetailTIndex
					Integer32,
				wingStatsRfdWlRadioStatDetailTxBps
					Unsigned32,
				wingStatsRfdWlRadioStatDetailRxBps
					Unsigned32,
				wingStatsRfdWlRadioStatDetailSignal
					Integer32,
				wingStatsRfdWlRadioStatDetailNoise
					Integer32,
				wingStatsRfdWlRadioStatDetailSnr
					Integer32,
				wingStatsRfdWlRadioStatDetailTxRate
					Unsigned32,
				wingStatsRfdWlRadioStatDetailRxRate
					Unsigned32,
				wingStatsRfdWlRadioStatDetailErrorRate
					Unsigned32,
				wingStatsRfdWlRadioStatDetailQIndex
					Integer32,
				wingStatsRfdWlRadioStatDetailNumClients
					Unsigned32,
				wingStatsRfdWlRadioStatDetailNumBClients
					Unsigned32,
				wingStatsRfdWlRadioStatDetailNumBgClients
					Unsigned32,
				wingStatsRfdWlRadioStatDetailNumBgnClients
					Unsigned32,
				wingStatsRfdWlRadioStatDetailNumAClients
					Unsigned32,
				wingStatsRfdWlRadioStatDetailNumAnClients
					Unsigned32,
				wingStatsRfdWlRadioStatDetailMediumErrorRate
					Unsigned32,
				wingStatsRfdWlRadioStatDetailRawTxBytes
					Counter64,
				wingStatsRfdWlRadioStatDetailRawRxBytes
					Counter64,
				wingStatsRfdWlRadioStatDetailRawTotalBytes
					Counter64,
				wingStatsRfdWlRadioStatDetailRawTxPkts
					Counter32,
				wingStatsRfdWlRadioStatDetailRawRxPkts
					Counter32,
				wingStatsRfdWlRadioStatDetailRawTotalPkts
					Counter32,
				wingStatsRfdWlRadioStatDetailRawTxBps
					Unsigned32,
				wingStatsRfdWlRadioStatDetailRawRxBps
					Unsigned32,
				wingStatsRfdWlRadioStatDetailRawTotalBps
					Unsigned32,
				wingStatsRfdWlRadioStatDetailRawTxPps
					Unsigned32,
				wingStatsRfdWlRadioStatDetailRawRxPps
					Unsigned32,
				wingStatsRfdWlRadioStatDetailRawTotalPps
					Unsigned32,
				wingStatsRfdWlRadioStatDetailRawTxRate
					Unsigned32,
				wingStatsRfdWlRadioStatDetailRawRxRate
					Unsigned32,
				wingStatsRfdWlRadioStatDetailRawOverallRate
					Unsigned32,
				wingStatsRfdWlRadioStatDetailTxBcmcPkts
					Counter64,
				wingStatsRfdWlRadioStatDetailRxBcmcPkts
					Counter64,
				wingStatsRfdWlRadioStatDetailTotalBcmcPkts
					Counter64,
				wingStatsRfdWlRadioStatDetailTxPps
					Unsigned32,
				wingStatsRfdWlRadioStatDetailRxPps
					Unsigned32,
				wingStatsRfdWlRadioStatDetailTotalPps
					Unsigned32,
				wingStatsRfdWlRadioStatDetailTxMgmtPkts
					Counter64,
				wingStatsRfdWlRadioStatDetailRxMgmtPkts
					Counter64,
				wingStatsRfdWlRadioStatDetailTotalMgmtPkts
					Counter64,
				wingStatsRfdWlRadioStatDetailTxRetries
					Counter64,
				wingStatsRfdWlRadioStatDetailRxProbes
					Counter32,
				wingStatsRfdWlRadioStatDetailRxActions
					Counter32,
				wingStatsRfdWlRadioStatDetailRxPsPoll
					Counter32,
				wingStatsRfdWlRadioStatDetailLastCallStatus
					DisplayString,
				wingStatsRfdWlRadioStatDetailCallTotal
					Counter32,
				wingStatsRfdWlRadioStatDetailCallStatOk
					Counter32,
				wingStatsRfdWlRadioStatDetailCallStatBusy
					Counter32,
				wingStatsRfdWlRadioStatDetailCallStatNoAnswer
					Counter32,
				wingStatsRfdWlRadioStatDetailCallStatUnknownDest
					Counter32,
				wingStatsRfdWlRadioStatDetailCallStatAdmDenied
					Counter32,
				wingStatsRfdWlRadioStatDetailCallStatDeclined
					Counter32,
				wingStatsRfdWlRadioStatDetailCallStatUnauth
					Counter32,
				wingStatsRfdWlRadioStatDetailCallStatUnsuppMedia
					Counter32,
				wingStatsRfdWlRadioStatDetailCallStatTempUnavail
					Counter32,
				wingStatsRfdWlRadioStatDetailCallStatNoForkAllowed
					Counter32,
				wingStatsRfdWlRadioStatDetailCallStatSessInactive
					Counter32,
				wingStatsRfdWlRadioStatDetailCallStatOther
					Counter32,
				wingStatsRfdWlRadioStatDetailTotalBytes
					Counter64,
				wingStatsRfdWlRadioStatDetailTotalPkts
					Counter32,
				wingStatsRfdWlRadioStatDetailRxRetries
					Counter64,
				wingStatsRfdWlRadioStatDetailRxCrcErrors
					Counter32,
				wingStatsRfdWlRadioStatDetailRxUndecryptable
					Counter32,
				wingStatsRfdWlRadioStatDetailRxIncomplete
					Counter32,
				wingStatsRfdWlRadioStatDetailRxLengthErrors
					Counter32,
				wingStatsRfdWlRadioStatDetailRxOtherErrors
					Counter32,
				wingStatsRfdWlRadioStatDetailLongPreambleClients
					Unsigned32,
				wingStatsRfdWlRadioStatDetailLtClients
					Unsigned32,
				wingStatsRfdWlRadioStatDetailHt20Clients
					Unsigned32,
				wingStatsRfdWlRadioStatDetailLongSlotClients
					Unsigned32,
				wingStatsRfdWlRadioStatDetailTxRetriedBytes
					Counter64
			 }

		-- 1.3.6.1.4.1.1916.2.131.50.1.4.3.2.11.1.1.1
		wingStatsRfdWlRadioStatDetailId OBJECT-TYPE
			SYNTAX WingIdentifier
			MAX-ACCESS read-only
			STATUS current
			DESCRIPTION
				"Unique ID for each radio interface in the form of
				AP-MAC:R%d. E.g., 00-A0-F8-00-00-00:R1
				
				XPath: /wing-stats/rf_domain[name=key1]/wireless/radio-stats-details[radio_id=key2]/radio_id"
			::= { wingStatsRfdWlRadioStatDetailEntry 1 }

		
		-- 1.3.6.1.4.1.1916.2.131.50.1.4.3.2.11.1.1.2
		wingStatsRfdWlRadioStatDetailDeviceMac OBJECT-TYPE
			SYNTAX MacAddress
			MAX-ACCESS read-only
			STATUS current
			DESCRIPTION
				"MAC address of AP the radio belongs to
				
				XPath: /wing-stats/rf_domain[name=key1]/wireless/radio-stats-details[radio_id=key2]/device_mac"
			::= { wingStatsRfdWlRadioStatDetailEntry 2 }

		
		-- 1.3.6.1.4.1.1916.2.131.50.1.4.3.2.11.1.1.3
		wingStatsRfdWlRadioStatDetailAlias OBJECT-TYPE
			SYNTAX DisplayString
			MAX-ACCESS read-only
			STATUS current
			DESCRIPTION
				"An alias to radio id in the form of hostname:R%d.
				E.g., wm3400-22A24E:R1
				
				XPath: /wing-stats/rf_domain[name=key1]/wireless/radio-stats-details[radio_id=key2]/radio_alias"
			::= { wingStatsRfdWlRadioStatDetailEntry 3 }

		
		-- 1.3.6.1.4.1.1916.2.131.50.1.4.3.2.11.1.1.4
		wingStatsRfdWlRadioStatDetailMac OBJECT-TYPE
			SYNTAX MacAddress
			MAX-ACCESS read-only
			STATUS current
			DESCRIPTION
				"MAC address of the radio
				
				XPath: /wing-stats/rf_domain[name=key1]/wireless/radio-stats-details[radio_id=key2]/radio_mac"
			::= { wingStatsRfdWlRadioStatDetailEntry 4 }

		
		-- 1.3.6.1.4.1.1916.2.131.50.1.4.3.2.11.1.1.5
		wingStatsRfdWlRadioStatDetailType OBJECT-TYPE
			SYNTAX DisplayString
			MAX-ACCESS read-only
			STATUS current
			DESCRIPTION
				"802.11 radio-type
				
				XPath: /wing-stats/rf_domain[name=key1]/wireless/radio-stats-details[radio_id=key2]/radio_type"
			::= { wingStatsRfdWlRadioStatDetailEntry 5 }

		
		-- 1.3.6.1.4.1.1916.2.131.50.1.4.3.2.11.1.1.6
		wingStatsRfdWlRadioStatDetailTxBytes OBJECT-TYPE
			SYNTAX Counter64
			MAX-ACCESS read-only
			STATUS current
			DESCRIPTION
				"Number of data bytes transmitted from radio to clients
				
				XPath: /wing-stats/rf_domain[name=key1]/wireless/radio-stats-details[radio_id=key2]/tx_bytes"
			::= { wingStatsRfdWlRadioStatDetailEntry 6 }

		
		-- 1.3.6.1.4.1.1916.2.131.50.1.4.3.2.11.1.1.7
		wingStatsRfdWlRadioStatDetailRxBytes OBJECT-TYPE
			SYNTAX Counter64
			MAX-ACCESS read-only
			STATUS current
			DESCRIPTION
				"Number of data bytes received from clients to radio
				
				XPath: /wing-stats/rf_domain[name=key1]/wireless/radio-stats-details[radio_id=key2]/rx_bytes"
			::= { wingStatsRfdWlRadioStatDetailEntry 7 }

		
		-- 1.3.6.1.4.1.1916.2.131.50.1.4.3.2.11.1.1.8
		wingStatsRfdWlRadioStatDetailTxPkts OBJECT-TYPE
			SYNTAX Counter32
			MAX-ACCESS read-only
			STATUS current
			DESCRIPTION
				"Number of packets of data transmitted from radio to clients
				
				XPath: /wing-stats/rf_domain[name=key1]/wireless/radio-stats-details[radio_id=key2]/tx_pkts"
			::= { wingStatsRfdWlRadioStatDetailEntry 8 }

		
		-- 1.3.6.1.4.1.1916.2.131.50.1.4.3.2.11.1.1.9
		wingStatsRfdWlRadioStatDetailRxPkts OBJECT-TYPE
			SYNTAX Counter32
			MAX-ACCESS read-only
			STATUS current
			DESCRIPTION
				"Number of packets of data received from clients to radio
				
				XPath: /wing-stats/rf_domain[name=key1]/wireless/radio-stats-details[radio_id=key2]/rx_pkts"
			::= { wingStatsRfdWlRadioStatDetailEntry 9 }

		
		-- 1.3.6.1.4.1.1916.2.131.50.1.4.3.2.11.1.1.10
		wingStatsRfdWlRadioStatDetailTxDropped OBJECT-TYPE
			SYNTAX Counter32
			MAX-ACCESS read-only
			STATUS current
			DESCRIPTION
				"Number of packets of data dropped on transmission
				
				XPath: /wing-stats/rf_domain[name=key1]/wireless/radio-stats-details[radio_id=key2]/tx_dropped"
			::= { wingStatsRfdWlRadioStatDetailEntry 10 }

		
		-- 1.3.6.1.4.1.1916.2.131.50.1.4.3.2.11.1.1.11
		wingStatsRfdWlRadioStatDetailRxErrors OBJECT-TYPE
			SYNTAX Counter32
			MAX-ACCESS read-only
			STATUS current
			DESCRIPTION
				"Number of packets of data received with errors
				
				XPath: /wing-stats/rf_domain[name=key1]/wireless/radio-stats-details[radio_id=key2]/rx_errors"
			::= { wingStatsRfdWlRadioStatDetailEntry 11 }

		
		-- 1.3.6.1.4.1.1916.2.131.50.1.4.3.2.11.1.1.12
		wingStatsRfdWlRadioStatDetailTIndex OBJECT-TYPE
			SYNTAX Integer32
			MAX-ACCESS read-only
			STATUS current
			DESCRIPTION
				"Traffic Utilization Index
				
				Measures the efficiency the medium under consideration
				is used. It is the percentage of the current data throughput
				over the theoretical data rate limit, which is derived
				the current maximum physical rate configured over the medium
				based on past empirical data. This index could assist end user
				in site planning and expansion. The numerical value might be
				further classified as:
				  -1: no data available ( e.g. radio is not in wlan operation
				                          mode )
				  0-20 : very low utilization
				  20-40: low utilization
				  40-60: moderate utilization
				  60 and above: high utilization
				
				XPath: /wing-stats/rf_domain[name=key1]/wireless/radio-stats-details[radio_id=key2]/t_index"
			::= { wingStatsRfdWlRadioStatDetailEntry 12 }

		
		-- 1.3.6.1.4.1.1916.2.131.50.1.4.3.2.11.1.1.13
		wingStatsRfdWlRadioStatDetailTxBps OBJECT-TYPE
			SYNTAX Unsigned32
			UNITS "kbps"
			MAX-ACCESS read-only
			STATUS current
			DESCRIPTION
				"User data transmit rate
				
				XPath: /wing-stats/rf_domain[name=key1]/wireless/radio-stats-details[radio_id=key2]/tx_bps"
			::= { wingStatsRfdWlRadioStatDetailEntry 13 }

		
		-- 1.3.6.1.4.1.1916.2.131.50.1.4.3.2.11.1.1.14
		wingStatsRfdWlRadioStatDetailRxBps OBJECT-TYPE
			SYNTAX Unsigned32
			UNITS "kbps"
			MAX-ACCESS read-only
			STATUS current
			DESCRIPTION
				"User data receive rate
				
				XPath: /wing-stats/rf_domain[name=key1]/wireless/radio-stats-details[radio_id=key2]/rx_bps"
			::= { wingStatsRfdWlRadioStatDetailEntry 14 }

		
		-- 1.3.6.1.4.1.1916.2.131.50.1.4.3.2.11.1.1.15
		wingStatsRfdWlRadioStatDetailSignal OBJECT-TYPE
			SYNTAX Integer32
			UNITS "dbm"
			MAX-ACCESS read-only
			STATUS current
			DESCRIPTION
				"Signal strength in units of dbm
				
				XPath: /wing-stats/rf_domain[name=key1]/wireless/radio-stats-details[radio_id=key2]/signal"
			::= { wingStatsRfdWlRadioStatDetailEntry 15 }

		
		-- 1.3.6.1.4.1.1916.2.131.50.1.4.3.2.11.1.1.16
		wingStatsRfdWlRadioStatDetailNoise OBJECT-TYPE
			SYNTAX Integer32
			UNITS "dbm"
			MAX-ACCESS read-only
			STATUS current
			DESCRIPTION
				"Noise level in units of dbm
				
				XPath: /wing-stats/rf_domain[name=key1]/wireless/radio-stats-details[radio_id=key2]/noise"
			::= { wingStatsRfdWlRadioStatDetailEntry 16 }

		
		-- 1.3.6.1.4.1.1916.2.131.50.1.4.3.2.11.1.1.17
		wingStatsRfdWlRadioStatDetailSnr OBJECT-TYPE
			SYNTAX Integer32
			UNITS "db"
			MAX-ACCESS read-only
			STATUS current
			DESCRIPTION
				"Signal to noise ratio in units of db
				
				XPath: /wing-stats/rf_domain[name=key1]/wireless/radio-stats-details[radio_id=key2]/snr"
			::= { wingStatsRfdWlRadioStatDetailEntry 17 }

		
		-- 1.3.6.1.4.1.1916.2.131.50.1.4.3.2.11.1.1.18
		wingStatsRfdWlRadioStatDetailTxRate OBJECT-TYPE
			SYNTAX Unsigned32
			UNITS "Mbps"
			MAX-ACCESS read-only
			STATUS current
			DESCRIPTION
				"The effective phy-layer transmit rate
				
				XPath: /wing-stats/rf_domain[name=key1]/wireless/radio-stats-details[radio_id=key2]/tx_rate"
			::= { wingStatsRfdWlRadioStatDetailEntry 18 }

		
		-- 1.3.6.1.4.1.1916.2.131.50.1.4.3.2.11.1.1.19
		wingStatsRfdWlRadioStatDetailRxRate OBJECT-TYPE
			SYNTAX Unsigned32
			UNITS "Mbps"
			MAX-ACCESS read-only
			STATUS current
			DESCRIPTION
				"The effective phy-layer receive rate
				
				XPath: /wing-stats/rf_domain[name=key1]/wireless/radio-stats-details[radio_id=key2]/rx_rate"
			::= { wingStatsRfdWlRadioStatDetailEntry 19 }

		
		-- 1.3.6.1.4.1.1916.2.131.50.1.4.3.2.11.1.1.20
		wingStatsRfdWlRadioStatDetailErrorRate OBJECT-TYPE
			SYNTAX Unsigned32
			MAX-ACCESS read-only
			STATUS current
			DESCRIPTION
				"Ratio of errors to rx-packets in percentage
				
				XPath: /wing-stats/rf_domain[name=key1]/wireless/radio-stats-details[radio_id=key2]/error_rate"
			::= { wingStatsRfdWlRadioStatDetailEntry 20 }

		
		-- 1.3.6.1.4.1.1916.2.131.50.1.4.3.2.11.1.1.21
		wingStatsRfdWlRadioStatDetailQIndex OBJECT-TYPE
			SYNTAX Integer32
			MAX-ACCESS read-only
			STATUS current
			DESCRIPTION
				"RF quality Index
				
				Measure the quality of the medium in percentage. It is a
				function of average retries and error rate. Its range is from
				0-100. Typically:
				  -1: no data available ( e.g. radio is not in wlan operation
				                          mode )
				  0-20: very poor quality
				  20-40: poor quality
				  40-60: average quality
				  60-100: good quality
				
				XPath: /wing-stats/rf_domain[name=key1]/wireless/radio-stats-details[radio_id=key2]/q_index"
			::= { wingStatsRfdWlRadioStatDetailEntry 21 }

		
		-- 1.3.6.1.4.1.1916.2.131.50.1.4.3.2.11.1.1.22
		wingStatsRfdWlRadioStatDetailNumClients OBJECT-TYPE
			SYNTAX Unsigned32
			MAX-ACCESS read-only
			STATUS current
			DESCRIPTION
				"Total number of clients
				
				XPath: /wing-stats/rf_domain[name=key1]/wireless/radio-stats-details[radio_id=key2]/num_clients"
			::= { wingStatsRfdWlRadioStatDetailEntry 22 }

		
		-- 1.3.6.1.4.1.1916.2.131.50.1.4.3.2.11.1.1.23
		wingStatsRfdWlRadioStatDetailNumBClients OBJECT-TYPE
			SYNTAX Unsigned32
			MAX-ACCESS read-only
			STATUS current
			DESCRIPTION
				"Number of 11b clients
				
				XPath: /wing-stats/rf_domain[name=key1]/wireless/radio-stats-details[radio_id=key2]/num_b_clients"
			::= { wingStatsRfdWlRadioStatDetailEntry 23 }

		
		-- 1.3.6.1.4.1.1916.2.131.50.1.4.3.2.11.1.1.24
		wingStatsRfdWlRadioStatDetailNumBgClients OBJECT-TYPE
			SYNTAX Unsigned32
			MAX-ACCESS read-only
			STATUS current
			DESCRIPTION
				"Number of 11bg clients
				
				XPath: /wing-stats/rf_domain[name=key1]/wireless/radio-stats-details[radio_id=key2]/num_bg_clients"
			::= { wingStatsRfdWlRadioStatDetailEntry 24 }

		
		-- 1.3.6.1.4.1.1916.2.131.50.1.4.3.2.11.1.1.25
		wingStatsRfdWlRadioStatDetailNumBgnClients OBJECT-TYPE
			SYNTAX Unsigned32
			MAX-ACCESS read-only
			STATUS current
			DESCRIPTION
				"Number of 11bgn clients
				
				XPath: /wing-stats/rf_domain[name=key1]/wireless/radio-stats-details[radio_id=key2]/num_bgn_clients"
			::= { wingStatsRfdWlRadioStatDetailEntry 25 }

		
		-- 1.3.6.1.4.1.1916.2.131.50.1.4.3.2.11.1.1.26
		wingStatsRfdWlRadioStatDetailNumAClients OBJECT-TYPE
			SYNTAX Unsigned32
			MAX-ACCESS read-only
			STATUS current
			DESCRIPTION
				"Number of 11a clients
				
				XPath: /wing-stats/rf_domain[name=key1]/wireless/radio-stats-details[radio_id=key2]/num_a_clients"
			::= { wingStatsRfdWlRadioStatDetailEntry 26 }

		
		-- 1.3.6.1.4.1.1916.2.131.50.1.4.3.2.11.1.1.27
		wingStatsRfdWlRadioStatDetailNumAnClients OBJECT-TYPE
			SYNTAX Unsigned32
			MAX-ACCESS read-only
			STATUS current
			DESCRIPTION
				"Number of 11an clients
				
				XPath: /wing-stats/rf_domain[name=key1]/wireless/radio-stats-details[radio_id=key2]/num_an_clients"
			::= { wingStatsRfdWlRadioStatDetailEntry 27 }

		
		-- 1.3.6.1.4.1.1916.2.131.50.1.4.3.2.11.1.1.28
		wingStatsRfdWlRadioStatDetailMediumErrorRate OBJECT-TYPE
			SYNTAX Unsigned32
			MAX-ACCESS read-only
			STATUS current
			DESCRIPTION
				"Ratio of medium errors and rx-retries to rx-packets
				in percentage
				
				XPath: /wing-stats/rf_domain[name=key1]/wireless/radio-stats-details[radio_id=key2]/medium_error_rate"
			::= { wingStatsRfdWlRadioStatDetailEntry 28 }

		
		-- 1.3.6.1.4.1.1916.2.131.50.1.4.3.2.11.1.1.29
		wingStatsRfdWlRadioStatDetailRawTxBytes OBJECT-TYPE
			SYNTAX Counter64
			MAX-ACCESS read-only
			STATUS current
			DESCRIPTION
				"Number of raw (data + management) bytes transmitted
				from radio to clients
				
				XPath: /wing-stats/rf_domain[name=key1]/wireless/radio-stats-details[radio_id=key2]/raw_tx_bytes"
			::= { wingStatsRfdWlRadioStatDetailEntry 29 }

		
		-- 1.3.6.1.4.1.1916.2.131.50.1.4.3.2.11.1.1.30
		wingStatsRfdWlRadioStatDetailRawRxBytes OBJECT-TYPE
			SYNTAX Counter64
			MAX-ACCESS read-only
			STATUS current
			DESCRIPTION
				"Number of raw (data + management) bytes received
				from clients to radio
				
				XPath: /wing-stats/rf_domain[name=key1]/wireless/radio-stats-details[radio_id=key2]/raw_rx_bytes"
			::= { wingStatsRfdWlRadioStatDetailEntry 30 }

		
		-- 1.3.6.1.4.1.1916.2.131.50.1.4.3.2.11.1.1.31
		wingStatsRfdWlRadioStatDetailRawTotalBytes OBJECT-TYPE
			SYNTAX Counter64
			MAX-ACCESS read-only
			STATUS current
			DESCRIPTION
				"Total mumber of raw (data + management) bytes through
				the radio for clients
				
				XPath: /wing-stats/rf_domain[name=key1]/wireless/radio-stats-details[radio_id=key2]/raw_total_bytes"
			::= { wingStatsRfdWlRadioStatDetailEntry 31 }

		
		-- 1.3.6.1.4.1.1916.2.131.50.1.4.3.2.11.1.1.32
		wingStatsRfdWlRadioStatDetailRawTxPkts OBJECT-TYPE
			SYNTAX Counter32
			MAX-ACCESS read-only
			STATUS current
			DESCRIPTION
				"Number of packets of raw (data + management) transmitted
				from radio to clients
				
				XPath: /wing-stats/rf_domain[name=key1]/wireless/radio-stats-details[radio_id=key2]/raw_tx_pkts"
			::= { wingStatsRfdWlRadioStatDetailEntry 32 }

		
		-- 1.3.6.1.4.1.1916.2.131.50.1.4.3.2.11.1.1.33
		wingStatsRfdWlRadioStatDetailRawRxPkts OBJECT-TYPE
			SYNTAX Counter32
			MAX-ACCESS read-only
			STATUS current
			DESCRIPTION
				"Number of packets of raw (data + management) received
				from clients to radio
				
				XPath: /wing-stats/rf_domain[name=key1]/wireless/radio-stats-details[radio_id=key2]/raw_rx_pkts"
			::= { wingStatsRfdWlRadioStatDetailEntry 33 }

		
		-- 1.3.6.1.4.1.1916.2.131.50.1.4.3.2.11.1.1.34
		wingStatsRfdWlRadioStatDetailRawTotalPkts OBJECT-TYPE
			SYNTAX Counter32
			MAX-ACCESS read-only
			STATUS current
			DESCRIPTION
				"Total number of raw packets through the radio
				
				XPath: /wing-stats/rf_domain[name=key1]/wireless/radio-stats-details[radio_id=key2]/raw_total_pkts"
			::= { wingStatsRfdWlRadioStatDetailEntry 34 }

		
		-- 1.3.6.1.4.1.1916.2.131.50.1.4.3.2.11.1.1.35
		wingStatsRfdWlRadioStatDetailRawTxBps OBJECT-TYPE
			SYNTAX Unsigned32
			UNITS "kbps"
			MAX-ACCESS read-only
			STATUS current
			DESCRIPTION
				"User raw (data + management) transmit rate
				
				XPath: /wing-stats/rf_domain[name=key1]/wireless/radio-stats-details[radio_id=key2]/raw_tx_bps"
			::= { wingStatsRfdWlRadioStatDetailEntry 35 }

		
		-- 1.3.6.1.4.1.1916.2.131.50.1.4.3.2.11.1.1.36
		wingStatsRfdWlRadioStatDetailRawRxBps OBJECT-TYPE
			SYNTAX Unsigned32
			UNITS "kbps"
			MAX-ACCESS read-only
			STATUS current
			DESCRIPTION
				"User raw (data + management) receive rate
				
				XPath: /wing-stats/rf_domain[name=key1]/wireless/radio-stats-details[radio_id=key2]/raw_rx_bps"
			::= { wingStatsRfdWlRadioStatDetailEntry 36 }

		
		-- 1.3.6.1.4.1.1916.2.131.50.1.4.3.2.11.1.1.37
		wingStatsRfdWlRadioStatDetailRawTotalBps OBJECT-TYPE
			SYNTAX Unsigned32
			UNITS "kbps"
			MAX-ACCESS read-only
			STATUS current
			DESCRIPTION
				"Total user raw (data + management) rate
				
				XPath: /wing-stats/rf_domain[name=key1]/wireless/radio-stats-details[radio_id=key2]/raw_total_bps"
			::= { wingStatsRfdWlRadioStatDetailEntry 37 }

		
		-- 1.3.6.1.4.1.1916.2.131.50.1.4.3.2.11.1.1.38
		wingStatsRfdWlRadioStatDetailRawTxPps OBJECT-TYPE
			SYNTAX Unsigned32
			MAX-ACCESS read-only
			STATUS current
			DESCRIPTION
				"Raw packet rate per second transmitted by the radio
				
				XPath: /wing-stats/rf_domain[name=key1]/wireless/radio-stats-details[radio_id=key2]/raw_tx_pps"
			::= { wingStatsRfdWlRadioStatDetailEntry 38 }

		
		-- 1.3.6.1.4.1.1916.2.131.50.1.4.3.2.11.1.1.39
		wingStatsRfdWlRadioStatDetailRawRxPps OBJECT-TYPE
			SYNTAX Unsigned32
			MAX-ACCESS read-only
			STATUS current
			DESCRIPTION
				"Raw packet rate per second received by the radio
				
				XPath: /wing-stats/rf_domain[name=key1]/wireless/radio-stats-details[radio_id=key2]/raw_rx_pps"
			::= { wingStatsRfdWlRadioStatDetailEntry 39 }

		
		-- 1.3.6.1.4.1.1916.2.131.50.1.4.3.2.11.1.1.40
		wingStatsRfdWlRadioStatDetailRawTotalPps OBJECT-TYPE
			SYNTAX Unsigned32
			MAX-ACCESS read-only
			STATUS current
			DESCRIPTION
				"Raw packet rate per second through the radio
				
				XPath: /wing-stats/rf_domain[name=key1]/wireless/radio-stats-details[radio_id=key2]/raw_total_pps"
			::= { wingStatsRfdWlRadioStatDetailEntry 40 }

		
		-- 1.3.6.1.4.1.1916.2.131.50.1.4.3.2.11.1.1.41
		wingStatsRfdWlRadioStatDetailRawTxRate OBJECT-TYPE
			SYNTAX Unsigned32
			UNITS "Mbps"
			MAX-ACCESS read-only
			STATUS current
			DESCRIPTION
				"The effective phy-layer transmit rate for raw data
				
				XPath: /wing-stats/rf_domain[name=key1]/wireless/radio-stats-details[radio_id=key2]/raw_tx_rate"
			::= { wingStatsRfdWlRadioStatDetailEntry 41 }

		
		-- 1.3.6.1.4.1.1916.2.131.50.1.4.3.2.11.1.1.42
		wingStatsRfdWlRadioStatDetailRawRxRate OBJECT-TYPE
			SYNTAX Unsigned32
			UNITS "Mbps"
			MAX-ACCESS read-only
			STATUS current
			DESCRIPTION
				"The effective phy-layer receive rate for raw data
				
				XPath: /wing-stats/rf_domain[name=key1]/wireless/radio-stats-details[radio_id=key2]/raw_rx_rate"
			::= { wingStatsRfdWlRadioStatDetailEntry 42 }

		
		-- 1.3.6.1.4.1.1916.2.131.50.1.4.3.2.11.1.1.43
		wingStatsRfdWlRadioStatDetailRawOverallRate OBJECT-TYPE
			SYNTAX Unsigned32
			UNITS "Mbps"
			MAX-ACCESS read-only
			STATUS current
			DESCRIPTION
				"The effective phy-layer overall rate, averaged on transmit
				and receive for raw data
				
				XPath: /wing-stats/rf_domain[name=key1]/wireless/radio-stats-details[radio_id=key2]/raw_overall_rate"
			::= { wingStatsRfdWlRadioStatDetailEntry 43 }

		
		-- 1.3.6.1.4.1.1916.2.131.50.1.4.3.2.11.1.1.44
		wingStatsRfdWlRadioStatDetailTxBcmcPkts OBJECT-TYPE
			SYNTAX Counter64
			MAX-ACCESS read-only
			STATUS current
			DESCRIPTION
				"Number of broadcast packets transmitted by the radio
				
				XPath: /wing-stats/rf_domain[name=key1]/wireless/radio-stats-details[radio_id=key2]/tx_bcmc_pkts"
			::= { wingStatsRfdWlRadioStatDetailEntry 44 }

		
		-- 1.3.6.1.4.1.1916.2.131.50.1.4.3.2.11.1.1.45
		wingStatsRfdWlRadioStatDetailRxBcmcPkts OBJECT-TYPE
			SYNTAX Counter64
			MAX-ACCESS read-only
			STATUS current
			DESCRIPTION
				"Number of broadcast packets of received by the radio
				
				XPath: /wing-stats/rf_domain[name=key1]/wireless/radio-stats-details[radio_id=key2]/rx_bcmc_pkts"
			::= { wingStatsRfdWlRadioStatDetailEntry 45 }

		
		-- 1.3.6.1.4.1.1916.2.131.50.1.4.3.2.11.1.1.46
		wingStatsRfdWlRadioStatDetailTotalBcmcPkts OBJECT-TYPE
			SYNTAX Counter64
			MAX-ACCESS read-only
			STATUS current
			DESCRIPTION
				"Total Number of broadcast packets through the radio
				
				XPath: /wing-stats/rf_domain[name=key1]/wireless/radio-stats-details[radio_id=key2]/total_bcmc_pkts"
			::= { wingStatsRfdWlRadioStatDetailEntry 46 }

		
		-- 1.3.6.1.4.1.1916.2.131.50.1.4.3.2.11.1.1.47
		wingStatsRfdWlRadioStatDetailTxPps OBJECT-TYPE
			SYNTAX Unsigned32
			MAX-ACCESS read-only
			STATUS current
			DESCRIPTION
				"Packet rate per second transmitted by the radio
				
				XPath: /wing-stats/rf_domain[name=key1]/wireless/radio-stats-details[radio_id=key2]/tx_pps"
			::= { wingStatsRfdWlRadioStatDetailEntry 47 }

		
		-- 1.3.6.1.4.1.1916.2.131.50.1.4.3.2.11.1.1.48
		wingStatsRfdWlRadioStatDetailRxPps OBJECT-TYPE
			SYNTAX Unsigned32
			MAX-ACCESS read-only
			STATUS current
			DESCRIPTION
				"Packet rate per second received by the radio
				
				XPath: /wing-stats/rf_domain[name=key1]/wireless/radio-stats-details[radio_id=key2]/rx_pps"
			::= { wingStatsRfdWlRadioStatDetailEntry 48 }

		
		-- 1.3.6.1.4.1.1916.2.131.50.1.4.3.2.11.1.1.49
		wingStatsRfdWlRadioStatDetailTotalPps OBJECT-TYPE
			SYNTAX Unsigned32
			MAX-ACCESS read-only
			STATUS current
			DESCRIPTION
				"Packet rate per second through the radio
				
				XPath: /wing-stats/rf_domain[name=key1]/wireless/radio-stats-details[radio_id=key2]/total_pps"
			::= { wingStatsRfdWlRadioStatDetailEntry 49 }

		
		-- 1.3.6.1.4.1.1916.2.131.50.1.4.3.2.11.1.1.50
		wingStatsRfdWlRadioStatDetailTxMgmtPkts OBJECT-TYPE
			SYNTAX Counter64
			MAX-ACCESS read-only
			STATUS current
			DESCRIPTION
				"Number of management packets of transmitted by the radio
				
				XPath: /wing-stats/rf_domain[name=key1]/wireless/radio-stats-details[radio_id=key2]/tx_mgmt_pkts"
			::= { wingStatsRfdWlRadioStatDetailEntry 50 }

		
		-- 1.3.6.1.4.1.1916.2.131.50.1.4.3.2.11.1.1.51
		wingStatsRfdWlRadioStatDetailRxMgmtPkts OBJECT-TYPE
			SYNTAX Counter64
			MAX-ACCESS read-only
			STATUS current
			DESCRIPTION
				"Number of management packets of received by the radio
				
				XPath: /wing-stats/rf_domain[name=key1]/wireless/radio-stats-details[radio_id=key2]/rx_mgmt_pkts"
			::= { wingStatsRfdWlRadioStatDetailEntry 51 }

		
		-- 1.3.6.1.4.1.1916.2.131.50.1.4.3.2.11.1.1.52
		wingStatsRfdWlRadioStatDetailTotalMgmtPkts OBJECT-TYPE
			SYNTAX Counter64
			MAX-ACCESS read-only
			STATUS current
			DESCRIPTION
				"Number of management packets through the radio
				
				XPath: /wing-stats/rf_domain[name=key1]/wireless/radio-stats-details[radio_id=key2]/total_mgmt_pkts"
			::= { wingStatsRfdWlRadioStatDetailEntry 52 }

		
		-- 1.3.6.1.4.1.1916.2.131.50.1.4.3.2.11.1.1.53
		wingStatsRfdWlRadioStatDetailTxRetries OBJECT-TYPE
			SYNTAX Counter64
			MAX-ACCESS read-only
			STATUS current
			DESCRIPTION
				"Total number of retries
				
				XPath: /wing-stats/rf_domain[name=key1]/wireless/radio-stats-details[radio_id=key2]/tx_retries"
			::= { wingStatsRfdWlRadioStatDetailEntry 53 }

		
		-- 1.3.6.1.4.1.1916.2.131.50.1.4.3.2.11.1.1.54
		wingStatsRfdWlRadioStatDetailRxProbes OBJECT-TYPE
			SYNTAX Counter32
			MAX-ACCESS read-only
			STATUS current
			DESCRIPTION
				"Total number of probe-request packets received
				
				XPath: /wing-stats/rf_domain[name=key1]/wireless/radio-stats-details[radio_id=key2]/rx_probes"
			::= { wingStatsRfdWlRadioStatDetailEntry 54 }

		
		-- 1.3.6.1.4.1.1916.2.131.50.1.4.3.2.11.1.1.55
		wingStatsRfdWlRadioStatDetailRxActions OBJECT-TYPE
			SYNTAX Counter32
			MAX-ACCESS read-only
			STATUS current
			DESCRIPTION
				"Total number of action packets received
				
				XPath: /wing-stats/rf_domain[name=key1]/wireless/radio-stats-details[radio_id=key2]/rx_actions"
			::= { wingStatsRfdWlRadioStatDetailEntry 55 }

		
		-- 1.3.6.1.4.1.1916.2.131.50.1.4.3.2.11.1.1.56
		wingStatsRfdWlRadioStatDetailRxPsPoll OBJECT-TYPE
			SYNTAX Counter32
			MAX-ACCESS read-only
			STATUS current
			DESCRIPTION
				"Total number of PS-Poll packets received
				
				XPath: /wing-stats/rf_domain[name=key1]/wireless/radio-stats-details[radio_id=key2]/rx_ps_poll"
			::= { wingStatsRfdWlRadioStatDetailEntry 56 }

		
		-- 1.3.6.1.4.1.1916.2.131.50.1.4.3.2.11.1.1.57
		wingStatsRfdWlRadioStatDetailLastCallStatus OBJECT-TYPE
			SYNTAX DisplayString
			MAX-ACCESS read-only
			STATUS current
			DESCRIPTION
				"Last voice call status
				
				XPath: /wing-stats/rf_domain[name=key1]/wireless/radio-stats-details[radio_id=key2]/last_call_status"
			::= { wingStatsRfdWlRadioStatDetailEntry 57 }

		
		-- 1.3.6.1.4.1.1916.2.131.50.1.4.3.2.11.1.1.58
		wingStatsRfdWlRadioStatDetailCallTotal OBJECT-TYPE
			SYNTAX Counter32
			MAX-ACCESS read-only
			STATUS current
			DESCRIPTION
				"Total number of voice calls attempted
				
				XPath: /wing-stats/rf_domain[name=key1]/wireless/radio-stats-details[radio_id=key2]/call_total"
			::= { wingStatsRfdWlRadioStatDetailEntry 58 }

		
		-- 1.3.6.1.4.1.1916.2.131.50.1.4.3.2.11.1.1.59
		wingStatsRfdWlRadioStatDetailCallStatOk OBJECT-TYPE
			SYNTAX Counter32
			MAX-ACCESS read-only
			STATUS current
			DESCRIPTION
				"Voice calls successfully made
				
				XPath: /wing-stats/rf_domain[name=key1]/wireless/radio-stats-details[radio_id=key2]/call_status_ok"
			::= { wingStatsRfdWlRadioStatDetailEntry 59 }

		
		-- 1.3.6.1.4.1.1916.2.131.50.1.4.3.2.11.1.1.60
		wingStatsRfdWlRadioStatDetailCallStatBusy OBJECT-TYPE
			SYNTAX Counter32
			MAX-ACCESS read-only
			STATUS current
			DESCRIPTION
				"Voice calls failed because of busy
				
				XPath: /wing-stats/rf_domain[name=key1]/wireless/radio-stats-details[radio_id=key2]/call_status_busy"
			::= { wingStatsRfdWlRadioStatDetailEntry 60 }

		
		-- 1.3.6.1.4.1.1916.2.131.50.1.4.3.2.11.1.1.61
		wingStatsRfdWlRadioStatDetailCallStatNoAnswer OBJECT-TYPE
			SYNTAX Counter32
			MAX-ACCESS read-only
			STATUS current
			DESCRIPTION
				"Voice calls failed because of no-answer
				
				XPath: /wing-stats/rf_domain[name=key1]/wireless/radio-stats-details[radio_id=key2]/call_status_no_answer"
			::= { wingStatsRfdWlRadioStatDetailEntry 61 }

		
		-- 1.3.6.1.4.1.1916.2.131.50.1.4.3.2.11.1.1.62
		wingStatsRfdWlRadioStatDetailCallStatUnknownDest OBJECT-TYPE
			SYNTAX Counter32
			MAX-ACCESS read-only
			STATUS current
			DESCRIPTION
				"Voice calls failed because of unknown destination
				
				XPath: /wing-stats/rf_domain[name=key1]/wireless/radio-stats-details[radio_id=key2]/call_status_unknown_dest"
			::= { wingStatsRfdWlRadioStatDetailEntry 62 }

		
		-- 1.3.6.1.4.1.1916.2.131.50.1.4.3.2.11.1.1.63
		wingStatsRfdWlRadioStatDetailCallStatAdmDenied OBJECT-TYPE
			SYNTAX Counter32
			MAX-ACCESS read-only
			STATUS current
			DESCRIPTION
				"Voice calls failed because of admission denied
				
				XPath: /wing-stats/rf_domain[name=key1]/wireless/radio-stats-details[radio_id=key2]/call_status_admission_denied"
			::= { wingStatsRfdWlRadioStatDetailEntry 63 }

		
		-- 1.3.6.1.4.1.1916.2.131.50.1.4.3.2.11.1.1.64
		wingStatsRfdWlRadioStatDetailCallStatDeclined OBJECT-TYPE
			SYNTAX Counter32
			MAX-ACCESS read-only
			STATUS current
			DESCRIPTION
				"Voice calls failed because of being declined
				
				XPath: /wing-stats/rf_domain[name=key1]/wireless/radio-stats-details[radio_id=key2]/call_status_declined"
			::= { wingStatsRfdWlRadioStatDetailEntry 64 }

		
		-- 1.3.6.1.4.1.1916.2.131.50.1.4.3.2.11.1.1.65
		wingStatsRfdWlRadioStatDetailCallStatUnauth OBJECT-TYPE
			SYNTAX Counter32
			MAX-ACCESS read-only
			STATUS current
			DESCRIPTION
				"Voice calls failed because of being unauthorized
				
				XPath: /wing-stats/rf_domain[name=key1]/wireless/radio-stats-details[radio_id=key2]/call_status_unauthorized"
			::= { wingStatsRfdWlRadioStatDetailEntry 65 }

		
		-- 1.3.6.1.4.1.1916.2.131.50.1.4.3.2.11.1.1.66
		wingStatsRfdWlRadioStatDetailCallStatUnsuppMedia OBJECT-TYPE
			SYNTAX Counter32
			MAX-ACCESS read-only
			STATUS current
			DESCRIPTION
				"Voice calls failed because of unsupported media
				
				XPath: /wing-stats/rf_domain[name=key1]/wireless/radio-stats-details[radio_id=key2]/call_status_unsupported_media"
			::= { wingStatsRfdWlRadioStatDetailEntry 66 }

		
		-- 1.3.6.1.4.1.1916.2.131.50.1.4.3.2.11.1.1.67
		wingStatsRfdWlRadioStatDetailCallStatTempUnavail OBJECT-TYPE
			SYNTAX Counter32
			MAX-ACCESS read-only
			STATUS current
			DESCRIPTION
				"Voice calls failed because of temporarily
				unavailable resources
				
				XPath: /wing-stats/rf_domain[name=key1]/wireless/radio-stats-details[radio_id=key2]/call_status_temporarily_unavailable"
			::= { wingStatsRfdWlRadioStatDetailEntry 67 }

		
		-- 1.3.6.1.4.1.1916.2.131.50.1.4.3.2.11.1.1.68
		wingStatsRfdWlRadioStatDetailCallStatNoForkAllowed OBJECT-TYPE
			SYNTAX Counter32
			MAX-ACCESS read-only
			STATUS current
			DESCRIPTION
				"Voice calls failed because of no-fork-allowed
				
				XPath: /wing-stats/rf_domain[name=key1]/wireless/radio-stats-details[radio_id=key2]/call_status_no_fork_allowed"
			::= { wingStatsRfdWlRadioStatDetailEntry 68 }

		
		-- 1.3.6.1.4.1.1916.2.131.50.1.4.3.2.11.1.1.69
		wingStatsRfdWlRadioStatDetailCallStatSessInactive OBJECT-TYPE
			SYNTAX Counter32
			MAX-ACCESS read-only
			STATUS current
			DESCRIPTION
				"Voice calls ended because of session-inactive
				
				XPath: /wing-stats/rf_domain[name=key1]/wireless/radio-stats-details[radio_id=key2]/call_status_session_inactive"
			::= { wingStatsRfdWlRadioStatDetailEntry 69 }

		
		-- 1.3.6.1.4.1.1916.2.131.50.1.4.3.2.11.1.1.70
		wingStatsRfdWlRadioStatDetailCallStatOther OBJECT-TYPE
			SYNTAX Counter32
			MAX-ACCESS read-only
			STATUS current
			DESCRIPTION
				"Voice calls ended for unknown reason
				
				XPath: /wing-stats/rf_domain[name=key1]/wireless/radio-stats-details[radio_id=key2]/call_status_other"
			::= { wingStatsRfdWlRadioStatDetailEntry 70 }

		
		-- 1.3.6.1.4.1.1916.2.131.50.1.4.3.2.11.1.1.71
		wingStatsRfdWlRadioStatDetailTotalBytes OBJECT-TYPE
			SYNTAX Counter64
			MAX-ACCESS read-only
			STATUS current
			DESCRIPTION
				"Total mumber of data bytes through the radio
				
				XPath: /wing-stats/rf_domain[name=key1]/wireless/radio-stats-details[radio_id=key2]/total_bytes"
			::= { wingStatsRfdWlRadioStatDetailEntry 71 }

		
		-- 1.3.6.1.4.1.1916.2.131.50.1.4.3.2.11.1.1.72
		wingStatsRfdWlRadioStatDetailTotalPkts OBJECT-TYPE
			SYNTAX Counter32
			MAX-ACCESS read-only
			STATUS current
			DESCRIPTION
				"Total number of packets through the radio
				
				XPath: /wing-stats/rf_domain[name=key1]/wireless/radio-stats-details[radio_id=key2]/total_pkts"
			::= { wingStatsRfdWlRadioStatDetailEntry 72 }

		
		-- 1.3.6.1.4.1.1916.2.131.50.1.4.3.2.11.1.1.73
		wingStatsRfdWlRadioStatDetailRxRetries OBJECT-TYPE
			SYNTAX Counter64
			MAX-ACCESS read-only
			STATUS current
			DESCRIPTION
				"Received packets with retries
				
				XPath: /wing-stats/rf_domain[name=key1]/wireless/radio-stats-details[radio_id=key2]/rx_retries"
			::= { wingStatsRfdWlRadioStatDetailEntry 73 }

		
		-- 1.3.6.1.4.1.1916.2.131.50.1.4.3.2.11.1.1.74
		wingStatsRfdWlRadioStatDetailRxCrcErrors OBJECT-TYPE
			SYNTAX Counter32
			MAX-ACCESS read-only
			STATUS current
			DESCRIPTION
				"Received packets with CRC errors
				
				XPath: /wing-stats/rf_domain[name=key1]/wireless/radio-stats-details[radio_id=key2]/rx_crc_errors"
			::= { wingStatsRfdWlRadioStatDetailEntry 74 }

		
		-- 1.3.6.1.4.1.1916.2.131.50.1.4.3.2.11.1.1.75
		wingStatsRfdWlRadioStatDetailRxUndecryptable OBJECT-TYPE
			SYNTAX Counter32
			MAX-ACCESS read-only
			STATUS current
			DESCRIPTION
				"Received undecryptable packets
				
				XPath: /wing-stats/rf_domain[name=key1]/wireless/radio-stats-details[radio_id=key2]/rx_undecryptable"
			::= { wingStatsRfdWlRadioStatDetailEntry 75 }

		
		-- 1.3.6.1.4.1.1916.2.131.50.1.4.3.2.11.1.1.76
		wingStatsRfdWlRadioStatDetailRxIncomplete OBJECT-TYPE
			SYNTAX Counter32
			MAX-ACCESS read-only
			STATUS current
			DESCRIPTION
				"Received incomplete packets
				
				XPath: /wing-stats/rf_domain[name=key1]/wireless/radio-stats-details[radio_id=key2]/rx_incomplete"
			::= { wingStatsRfdWlRadioStatDetailEntry 76 }

		
		-- 1.3.6.1.4.1.1916.2.131.50.1.4.3.2.11.1.1.77
		wingStatsRfdWlRadioStatDetailRxLengthErrors OBJECT-TYPE
			SYNTAX Counter32
			MAX-ACCESS read-only
			STATUS current
			DESCRIPTION
				"Received packets with length errors
				
				XPath: /wing-stats/rf_domain[name=key1]/wireless/radio-stats-details[radio_id=key2]/rx_length_errors"
			::= { wingStatsRfdWlRadioStatDetailEntry 77 }

		
		-- 1.3.6.1.4.1.1916.2.131.50.1.4.3.2.11.1.1.78
		wingStatsRfdWlRadioStatDetailRxOtherErrors OBJECT-TYPE
			SYNTAX Counter32
			MAX-ACCESS read-only
			STATUS current
			DESCRIPTION
				"Received packets with other errors
				
				XPath: /wing-stats/rf_domain[name=key1]/wireless/radio-stats-details[radio_id=key2]/rx_other_errors"
			::= { wingStatsRfdWlRadioStatDetailEntry 78 }

		
		-- 1.3.6.1.4.1.1916.2.131.50.1.4.3.2.11.1.1.79
		wingStatsRfdWlRadioStatDetailLongPreambleClients OBJECT-TYPE
			SYNTAX Unsigned32
			MAX-ACCESS read-only
			STATUS current
			DESCRIPTION
				"Long-preamble-only only clients
				
				XPath: /wing-stats/rf_domain[name=key1]/wireless/radio-stats-details[radio_id=key2]/long_preamble_clients"
			::= { wingStatsRfdWlRadioStatDetailEntry 79 }

		
		-- 1.3.6.1.4.1.1916.2.131.50.1.4.3.2.11.1.1.80
		wingStatsRfdWlRadioStatDetailLtClients OBJECT-TYPE
			SYNTAX Unsigned32
			MAX-ACCESS read-only
			STATUS current
			DESCRIPTION
				"Low throughput clients in contrast to HT client
				
				XPath: /wing-stats/rf_domain[name=key1]/wireless/radio-stats-details[radio_id=key2]/lt_clients"
			::= { wingStatsRfdWlRadioStatDetailEntry 80 }

		
		-- 1.3.6.1.4.1.1916.2.131.50.1.4.3.2.11.1.1.81
		wingStatsRfdWlRadioStatDetailHt20Clients OBJECT-TYPE
			SYNTAX Unsigned32
			MAX-ACCESS read-only
			STATUS current
			DESCRIPTION
				"HT client single channel only
				
				XPath: /wing-stats/rf_domain[name=key1]/wireless/radio-stats-details[radio_id=key2]/ht_20_clients"
			::= { wingStatsRfdWlRadioStatDetailEntry 81 }

		
		-- 1.3.6.1.4.1.1916.2.131.50.1.4.3.2.11.1.1.82
		wingStatsRfdWlRadioStatDetailLongSlotClients OBJECT-TYPE
			SYNTAX Unsigned32
			MAX-ACCESS read-only
			STATUS current
			DESCRIPTION
				"Long slot clients
				
				XPath: /wing-stats/rf_domain[name=key1]/wireless/radio-stats-details[radio_id=key2]/long_slot_clients"
			::= { wingStatsRfdWlRadioStatDetailEntry 82 }

		
		-- 1.3.6.1.4.1.1916.2.131.50.1.4.3.2.11.1.1.83
		wingStatsRfdWlRadioStatDetailTxRetriedBytes OBJECT-TYPE
			SYNTAX Counter64
			MAX-ACCESS read-only
			STATUS current
			DESCRIPTION
				"Total retried bytes excluding bytes sent.				    
				XPath: /wing-stats/rf_domain[name=key1]/wireless/radio-stats-details[radio_id=key2]/tx_retried_bytes."
			::= { wingStatsRfdWlRadioStatDetailEntry 83 }

		
		-- 1.3.6.1.4.1.1916.2.131.50.1.4.3.5
		wingStatsRfdSmartRf OBJECT IDENTIFIER ::= { wingStatsRfd 5 }

		
		-- 1.3.6.1.4.1.1916.2.131.50.1.4.3.5.1
		wingStatsRfdSmartRfRadioInfoTable OBJECT-TYPE
			SYNTAX SEQUENCE OF WingStatsRfdSmartRfRadioInfoEntry
			MAX-ACCESS not-accessible
			STATUS current
			DESCRIPTION
				"
				
				/wing-stats/rf_domain/smart-rf/radio_info"
			::= { wingStatsRfdSmartRf 1 }

		
		-- 1.3.6.1.4.1.1916.2.131.50.1.4.3.5.1.1
		wingStatsRfdSmartRfRadioInfoEntry OBJECT-TYPE
			SYNTAX WingStatsRfdSmartRfRadioInfoEntry
			MAX-ACCESS not-accessible
			STATUS current
			DESCRIPTION
				"An entry in the table."
			INDEX { wingStatsRfdName, wingStatsRfdSmartRfRadioInfoMac }
			::= { wingStatsRfdSmartRfRadioInfoTable 1 }

		
		WingStatsRfdSmartRfRadioInfoEntry ::=
			SEQUENCE { 
				wingStatsRfdSmartRfRadioInfoMac
					WingIdentifier,
				wingStatsRfdSmartRfRadioInfoApMac
					DisplayString,
				wingStatsRfdSmartRfRadioInfoHostname
					DisplayString,
				wingStatsRfdSmartRfRadioInfoChannel
					DisplayString,
				wingStatsRfdSmartRfRadioInfoPower
					Unsigned32,
				wingStatsRfdSmartRfRadioInfoRadioIdx
					Unsigned32,
				wingStatsRfdSmartRfRadioInfoState
					DisplayString,
				wingStatsRfdSmartRfRadioInfoType
					DisplayString
			 }

		-- 1.3.6.1.4.1.1916.2.131.50.1.4.3.5.1.1.1
		wingStatsRfdSmartRfRadioInfoMac OBJECT-TYPE
			SYNTAX WingIdentifier
			MAX-ACCESS read-only
			STATUS current
			DESCRIPTION
				"Radio MAC address
				
				XPath: /wing-stats/rf_domain[name=key1]/smart-rf/radio_info[mac=key2]/mac"
			::= { wingStatsRfdSmartRfRadioInfoEntry 1 }

		
		-- 1.3.6.1.4.1.1916.2.131.50.1.4.3.5.1.1.3
		wingStatsRfdSmartRfRadioInfoApMac OBJECT-TYPE
			SYNTAX DisplayString
			MAX-ACCESS read-only
			STATUS current
			DESCRIPTION
				"Access point MAC address in which this radio is present
				
				XPath: /wing-stats/rf_domain[name=key1]/smart-rf/radio_info[mac=key2]/ap_mac"
			::= { wingStatsRfdSmartRfRadioInfoEntry 3 }

		
		-- 1.3.6.1.4.1.1916.2.131.50.1.4.3.5.1.1.4
		wingStatsRfdSmartRfRadioInfoHostname OBJECT-TYPE
			SYNTAX DisplayString (SIZE (64))
			MAX-ACCESS read-only
			STATUS current
			DESCRIPTION
				"Access point hostname in which this radio is present
				
				XPath: /wing-stats/rf_domain[name=key1]/smart-rf/radio_info[mac=key2]/hostname"
			::= { wingStatsRfdSmartRfRadioInfoEntry 4 }

		
		-- 1.3.6.1.4.1.1916.2.131.50.1.4.3.5.1.1.5
		wingStatsRfdSmartRfRadioInfoChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/radio_info[mac=key2]/channel"
			::= { wingStatsRfdSmartRfRadioInfoEntry 5 }

		
		-- 1.3.6.1.4.1.1916.2.131.50.1.4.3.5.1.1.6
		wingStatsRfdSmartRfRadioInfoPower OBJECT-TYPE
			SYNTAX Unsigned32 (0..23)
			UNITS "dBm"
			MAX-ACCESS read-only
			STATUS current
			DESCRIPTION
				"Smart-rf assigned transmit power for this radio
				
				XPath: /wing-stats/rf_domain[name=key1]/smart-rf/radio_info[mac=key2]/power"
			::= { wingStatsRfdSmartRfRadioInfoEntry 6 }

		
		-- 1.3.6.1.4.1.1916.2.131.50.1.4.3.5.1.1.7
		wingStatsRfdSmartRfRadioInfoRadioIdx OBJECT-TYPE
			SYNTAX Unsigned32
			MAX-ACCESS read-only
			STATUS current
			DESCRIPTION
				"Radio index of this radio in AP
				
				XPath: /wing-stats/rf_domain[name=key1]/smart-rf/radio_info[mac=key2]/radio_idx"
			::= { wingStatsRfdSmartRfRadioInfoEntry 7 }

		
		-- 1.3.6.1.4.1.1916.2.131.50.1.4.3.5.1.1.8
		wingStatsRfdSmartRfRadioInfoState OBJECT-TYPE
			SYNTAX DisplayString
			MAX-ACCESS read-only
			STATUS current
			DESCRIPTION
				"Current radio state
				
				Values:
				offline,
				normal,
				sensor
				
				XPath: /wing-stats/rf_domain[name=key1]/smart-rf/radio_info[mac=key2]/state"
			::= { wingStatsRfdSmartRfRadioInfoEntry 8 }

		
		-- 1.3.6.1.4.1.1916.2.131.50.1.4.3.5.1.1.9
		wingStatsRfdSmartRfRadioInfoType OBJECT-TYPE
			SYNTAX DisplayString
			MAX-ACCESS read-only
			STATUS current
			DESCRIPTION
				"Radio type
				
				Values:
				11an,
				11bgn
				
				XPath: /wing-stats/rf_domain[name=key1]/smart-rf/radio_info[mac=key2]/type"
			::= { wingStatsRfdSmartRfRadioInfoEntry 9 }

		
		-- 1.3.6.1.4.1.1916.2.131.50.1.4.3.5.2
		wingStatsRfdSmartRfRadioActTable OBJECT-TYPE
			SYNTAX SEQUENCE OF WingStatsRfdSmartRfRadioActEntry
			MAX-ACCESS not-accessible
			STATUS current
			DESCRIPTION
				"
				
				/wing-stats/rf_domain/smart-rf/radio_activity"
			::= { wingStatsRfdSmartRf 2 }

		
		-- 1.3.6.1.4.1.1916.2.131.50.1.4.3.5.2.1
		wingStatsRfdSmartRfRadioActEntry OBJECT-TYPE
			SYNTAX WingStatsRfdSmartRfRadioActEntry
			MAX-ACCESS not-accessible
			STATUS current
			DESCRIPTION
				"An entry in the table."
			INDEX { wingStatsRfdName, wingStatsRfdSmartRfRadioActMac }
			::= { wingStatsRfdSmartRfRadioActTable 1 }

		
		WingStatsRfdSmartRfRadioActEntry ::=
			SEQUENCE { 
				wingStatsRfdSmartRfRadioActMac
					WingIdentifier,
				wingStatsRfdSmartRfRadioActApMac
					DisplayString,
				wingStatsRfdSmartRfRadioActType
					DisplayString,
				wingStatsRfdSmartRfRadioActPowerChanges
					Unsigned32,
				wingStatsRfdSmartRfRadioActChannelChanges
					Unsigned32,
				wingStatsRfdSmartRfRadioActCoverageChanges
					Unsigned32
			 }

		-- 1.3.6.1.4.1.1916.2.131.50.1.4.3.5.2.1.1
		wingStatsRfdSmartRfRadioActMac OBJECT-TYPE
			SYNTAX WingIdentifier
			MAX-ACCESS read-only
			STATUS current
			DESCRIPTION
				"Radio MAC address
				
				XPath: /wing-stats/rf_domain[name=key1]/smart-rf/radio_activity[mac=key2]/mac"
			::= { wingStatsRfdSmartRfRadioActEntry 1 }

		
		-- 1.3.6.1.4.1.1916.2.131.50.1.4.3.5.2.1.3
		wingStatsRfdSmartRfRadioActApMac OBJECT-TYPE
			SYNTAX DisplayString
			MAX-ACCESS read-only
			STATUS current
			DESCRIPTION
				"Access point MAC address in which this radio is present
				
				XPath: /wing-stats/rf_domain[name=key1]/smart-rf/radio_activity[mac=key2]/ap_mac"
			::= { wingStatsRfdSmartRfRadioActEntry 3 }

		
		-- 1.3.6.1.4.1.1916.2.131.50.1.4.3.5.2.1.4
		wingStatsRfdSmartRfRadioActType OBJECT-TYPE
			SYNTAX DisplayString
			MAX-ACCESS read-only
			STATUS current
			DESCRIPTION
				"Radio type
				
				Values:
				11an,
				11bgn
				
				XPath: /wing-stats/rf_domain[name=key1]/smart-rf/radio_activity[mac=key2]/type"
			::= { wingStatsRfdSmartRfRadioActEntry 4 }

		
		-- 1.3.6.1.4.1.1916.2.131.50.1.4.3.5.2.1.5
		wingStatsRfdSmartRfRadioActPowerChanges OBJECT-TYPE
			SYNTAX Unsigned32 (0..1024)
			MAX-ACCESS read-only
			STATUS current
			DESCRIPTION
				"Number of neighbor recovery power changes for this radio
				
				XPath: /wing-stats/rf_domain[name=key1]/smart-rf/radio_activity[mac=key2]/power_changes"
			::= { wingStatsRfdSmartRfRadioActEntry 5 }

		
		-- 1.3.6.1.4.1.1916.2.131.50.1.4.3.5.2.1.6
		wingStatsRfdSmartRfRadioActChannelChanges OBJECT-TYPE
			SYNTAX Unsigned32 (0..1024)
			MAX-ACCESS read-only
			STATUS current
			DESCRIPTION
				"Number of channel changes for this radio
				
				XPath: /wing-stats/rf_domain[name=key1]/smart-rf/radio_activity[mac=key2]/channel_changes"
			::= { wingStatsRfdSmartRfRadioActEntry 6 }

		
		-- 1.3.6.1.4.1.1916.2.131.50.1.4.3.5.2.1.7
		wingStatsRfdSmartRfRadioActCoverageChanges OBJECT-TYPE
			SYNTAX Unsigned32 (0..1024)
			MAX-ACCESS read-only
			STATUS current
			DESCRIPTION
				"Number of coverage hole recovery power changes for this radio
				
				XPath: /wing-stats/rf_domain[name=key1]/smart-rf/radio_activity[mac=key2]/coverage_changes"
			::= { wingStatsRfdSmartRfRadioActEntry 7 }

		
		-- 1.3.6.1.4.1.1916.2.131.50.1.4.3.5.3
		wingStatsRfdSmartRfRadioNeighborsTable OBJECT-TYPE
			SYNTAX SEQUENCE OF WingStatsRfdSmartRfRadioNeighborsEntry
			MAX-ACCESS not-accessible
			STATUS current
			DESCRIPTION
				"
				
				/wing-stats/rf_domain/smart-rf/radio_neighbors"
			::= { wingStatsRfdSmartRf 3 }

		
		-- 1.3.6.1.4.1.1916.2.131.50.1.4.3.5.3.1
		wingStatsRfdSmartRfRadioNeighborsEntry OBJECT-TYPE
			SYNTAX WingStatsRfdSmartRfRadioNeighborsEntry
			MAX-ACCESS not-accessible
			STATUS current
			DESCRIPTION
				"An entry in the table."
			INDEX { wingStatsRfdName, wingStatsRfdSmartRfRadioNeighborsMac }
			::= { wingStatsRfdSmartRfRadioNeighborsTable 1 }

		
		WingStatsRfdSmartRfRadioNeighborsEntry ::=
			SEQUENCE { 
				wingStatsRfdSmartRfRadioNeighborsMac
					WingIdentifier,
				wingStatsRfdSmartRfRadioNeighborsApMac
					DisplayString,
				wingStatsRfdSmartRfRadioNeighborsHostname
					DisplayString,
				wingStatsRfdSmartRfRadioNeighborsChannel
					DisplayString,
				wingStatsRfdSmartRfRadioNeighborsRadioIdx
					Unsigned32,
				wingStatsRfdSmartRfRadioNeighborsType
					DisplayString
			 }

		-- 1.3.6.1.4.1.1916.2.131.50.1.4.3.5.3.1.1
		wingStatsRfdSmartRfRadioNeighborsMac OBJECT-TYPE
			SYNTAX WingIdentifier
			MAX-ACCESS read-only
			STATUS current
			DESCRIPTION
				"Radio MAC address
				
				XPath: /wing-stats/rf_domain[name=key1]/smart-rf/radio_neighbors[mac=key2]/mac"
			::= { wingStatsRfdSmartRfRadioNeighborsEntry 1 }

		
		-- 1.3.6.1.4.1.1916.2.131.50.1.4.3.5.3.1.3
		wingStatsRfdSmartRfRadioNeighborsApMac OBJECT-TYPE
			SYNTAX DisplayString
			MAX-ACCESS read-only
			STATUS current
			DESCRIPTION
				"Access point MAC address in which this radio is present
				
				XPath: /wing-stats/rf_domain[name=key1]/smart-rf/radio_neighbors[mac=key2]/ap_mac"
			::= { wingStatsRfdSmartRfRadioNeighborsEntry 3 }

		
		-- 1.3.6.1.4.1.1916.2.131.50.1.4.3.5.3.1.4
		wingStatsRfdSmartRfRadioNeighborsHostname OBJECT-TYPE
			SYNTAX DisplayString (SIZE (64))
			MAX-ACCESS read-only
			STATUS current
			DESCRIPTION
				"Access point hostname in which this radio is present
				
				XPath: /wing-stats/rf_domain[name=key1]/smart-rf/radio_neighbors[mac=key2]/hostname"
			::= { wingStatsRfdSmartRfRadioNeighborsEntry 4 }

		
		-- 1.3.6.1.4.1.1916.2.131.50.1.4.3.5.3.1.5
		wingStatsRfdSmartRfRadioNeighborsChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/radio_neighbors[mac=key2]/channel"
			::= { wingStatsRfdSmartRfRadioNeighborsEntry 5 }

		
		-- 1.3.6.1.4.1.1916.2.131.50.1.4.3.5.3.1.6
		wingStatsRfdSmartRfRadioNeighborsRadioIdx OBJECT-TYPE
			SYNTAX Unsigned32
			MAX-ACCESS read-only
			STATUS current
			DESCRIPTION
				"Radio index of this radio in AP
				
				XPath: /wing-stats/rf_domain[name=key1]/smart-rf/radio_neighbors[mac=key2]/radio_idx"
			::= { wingStatsRfdSmartRfRadioNeighborsEntry 6 }

		
		-- 1.3.6.1.4.1.1916.2.131.50.1.4.3.5.3.1.7
		wingStatsRfdSmartRfRadioNeighborsType OBJECT-TYPE
			SYNTAX DisplayString
			MAX-ACCESS read-only
			STATUS current
			DESCRIPTION
				"Radio type
				
				Values:
				11an,
				11bgn
				
				XPath: /wing-stats/rf_domain[name=key1]/smart-rf/radio_neighbors[mac=key2]/type"
			::= { wingStatsRfdSmartRfRadioNeighborsEntry 7 }

		
		-- 1.3.6.1.4.1.1916.2.131.50.1.4.3.5.4
		wingStatsRfdSmartRfRadioNeighborsNeighborsTable OBJECT-TYPE
			SYNTAX SEQUENCE OF WingStatsRfdSmartRfRadioNeighborsNeighborsEntry
			MAX-ACCESS not-accessible
			STATUS current
			DESCRIPTION
				"
				
				/wing-stats/rf_domain/smart-rf/radio_neighbors/neighbors"
			::= { wingStatsRfdSmartRf 4 }

		
		-- 1.3.6.1.4.1.1916.2.131.50.1.4.3.5.4.1
		wingStatsRfdSmartRfRadioNeighborsNeighborsEntry OBJECT-TYPE
			SYNTAX WingStatsRfdSmartRfRadioNeighborsNeighborsEntry
			MAX-ACCESS not-accessible
			STATUS current
			DESCRIPTION
				"An entry in the table."
			INDEX { wingStatsRfdName, wingStatsRfdSmartRfRadioNeighborsMac }
			::= { wingStatsRfdSmartRfRadioNeighborsNeighborsTable 1 }

		
		WingStatsRfdSmartRfRadioNeighborsNeighborsEntry ::=
			SEQUENCE { 
				wingStatsRfdSmartRfRadioNeighborsNeighborsMac
					DisplayString,
				wingStatsRfdSmartRfRadioNeighborsNeighborsApMac
					DisplayString,
				wingStatsRfdSmartRfRadioNeighborsNeighborsChannel
					DisplayString,
				wingStatsRfdSmartRfRadioNeighborsNeighborsPower
					Unsigned32,
				wingStatsRfdSmartRfRadioNeighborsNeighborsAttenuation
					Unsigned32,
				wingStatsRfdSmartRfRadioNeighborsNeighborsRadioIdx
					Unsigned32
			 }

		-- 1.3.6.1.4.1.1916.2.131.50.1.4.3.5.4.1.1
		wingStatsRfdSmartRfRadioNeighborsNeighborsMac OBJECT-TYPE
			SYNTAX DisplayString
			MAX-ACCESS read-only
			STATUS current
			DESCRIPTION
				"Neighbor radio MAC address
				
				XPath: /wing-stats/rf_domain[name=key1]/smart-rf/radio_neighbors[mac=key2]/neighbors/mac"
			::= { wingStatsRfdSmartRfRadioNeighborsNeighborsEntry 1 }

		
		-- 1.3.6.1.4.1.1916.2.131.50.1.4.3.5.4.1.2
		wingStatsRfdSmartRfRadioNeighborsNeighborsApMac OBJECT-TYPE
			SYNTAX DisplayString
			MAX-ACCESS read-only
			STATUS current
			DESCRIPTION
				"Access point MAC address in which this neighbor radio is present
				
				XPath: /wing-stats/rf_domain[name=key1]/smart-rf/radio_neighbors[mac=key2]/neighbors/ap_mac"
			::= { wingStatsRfdSmartRfRadioNeighborsNeighborsEntry 2 }

		
		-- 1.3.6.1.4.1.1916.2.131.50.1.4.3.5.4.1.3
		wingStatsRfdSmartRfRadioNeighborsNeighborsChannel OBJECT-TYPE
			SYNTAX DisplayString
			MAX-ACCESS read-only
			STATUS current
			DESCRIPTION
				"Smart-rf assigned neighbor radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/radio_neighbors[mac=key2]/neighbors/channel"
			::= { wingStatsRfdSmartRfRadioNeighborsNeighborsEntry 3 }

		
		-- 1.3.6.1.4.1.1916.2.131.50.1.4.3.5.4.1.4
		wingStatsRfdSmartRfRadioNeighborsNeighborsPower OBJECT-TYPE
			SYNTAX Unsigned32 (0..23)
			UNITS "dBm"
			MAX-ACCESS read-only
			STATUS current
			DESCRIPTION
				"Smart-rf assigned transmit power for this neighbor radio
				
				XPath: /wing-stats/rf_domain[name=key1]/smart-rf/radio_neighbors[mac=key2]/neighbors/power"
			::= { wingStatsRfdSmartRfRadioNeighborsNeighborsEntry 4 }

		
		-- 1.3.6.1.4.1.1916.2.131.50.1.4.3.5.4.1.5
		wingStatsRfdSmartRfRadioNeighborsNeighborsAttenuation OBJECT-TYPE
			SYNTAX Unsigned32
			UNITS "dB"
			MAX-ACCESS read-only
			STATUS current
			DESCRIPTION
				"Attenuation of neighbor radio
				
				XPath: /wing-stats/rf_domain[name=key1]/smart-rf/radio_neighbors[mac=key2]/neighbors/attenuation"
			::= { wingStatsRfdSmartRfRadioNeighborsNeighborsEntry 5 }

		
		-- 1.3.6.1.4.1.1916.2.131.50.1.4.3.5.4.1.6
		wingStatsRfdSmartRfRadioNeighborsNeighborsRadioIdx OBJECT-TYPE
			SYNTAX Unsigned32
			MAX-ACCESS read-only
			STATUS current
			DESCRIPTION
				"Radio index of this neighbor radio in AP
				
				XPath: /wing-stats/rf_domain[name=key1]/smart-rf/radio_neighbors[mac=key2]/neighbors/radio_idx"
			::= { wingStatsRfdSmartRfRadioNeighborsNeighborsEntry 6 }

		
		-- 1.3.6.1.4.1.1916.2.131.50.1.4.3.5.5
		wingStatsRfdSmartRfRadioEnergyTable OBJECT-TYPE
			SYNTAX SEQUENCE OF WingStatsRfdSmartRfRadioEnergyEntry
			MAX-ACCESS not-accessible
			STATUS current
			DESCRIPTION
				"
				
				/wing-stats/rf_domain/smart-rf/radio_energy"
			::= { wingStatsRfdSmartRf 5 }

		
		-- 1.3.6.1.4.1.1916.2.131.50.1.4.3.5.5.1
		wingStatsRfdSmartRfRadioEnergyEntry OBJECT-TYPE
			SYNTAX WingStatsRfdSmartRfRadioEnergyEntry
			MAX-ACCESS not-accessible
			STATUS current
			DESCRIPTION
				"An entry in the table."
			INDEX { wingStatsRfdName, wingStatsRfdSmartRfRadioEnergyMac }
			::= { wingStatsRfdSmartRfRadioEnergyTable 1 }

		
		WingStatsRfdSmartRfRadioEnergyEntry ::=
			SEQUENCE { 
				wingStatsRfdSmartRfRadioEnergyMac
					WingIdentifier,
				wingStatsRfdSmartRfRadioEnergyApMac
					DisplayString,
				wingStatsRfdSmartRfRadioEnergyHostname
					DisplayString,
				wingStatsRfdSmartRfRadioEnergyChannel
					DisplayString,
				wingStatsRfdSmartRfRadioEnergyRadioIdx
					Unsigned32,
				wingStatsRfdSmartRfRadioEnergyType
					DisplayString
			 }

		-- 1.3.6.1.4.1.1916.2.131.50.1.4.3.5.5.1.1
		wingStatsRfdSmartRfRadioEnergyMac OBJECT-TYPE
			SYNTAX WingIdentifier
			MAX-ACCESS read-only
			STATUS current
			DESCRIPTION
				"Radio MAC address
				
				XPath: /wing-stats/rf_domain[name=key1]/smart-rf/radio_energy[mac=key2]/mac"
			::= { wingStatsRfdSmartRfRadioEnergyEntry 1 }

		
		-- 1.3.6.1.4.1.1916.2.131.50.1.4.3.5.5.1.3
		wingStatsRfdSmartRfRadioEnergyApMac OBJECT-TYPE
			SYNTAX DisplayString
			MAX-ACCESS read-only
			STATUS current
			DESCRIPTION
				"Access point MAC address in which this radio is present
				
				XPath: /wing-stats/rf_domain[name=key1]/smart-rf/radio_energy[mac=key2]/ap_mac"
			::= { wingStatsRfdSmartRfRadioEnergyEntry 3 }

		
		-- 1.3.6.1.4.1.1916.2.131.50.1.4.3.5.5.1.4
		wingStatsRfdSmartRfRadioEnergyHostname OBJECT-TYPE
			SYNTAX DisplayString
			MAX-ACCESS read-only
			STATUS current
			DESCRIPTION
				"Access point hostname in which this radio is present
				
				XPath: /wing-stats/rf_domain[name=key1]/smart-rf/radio_energy[mac=key2]/hostname"
			::= { wingStatsRfdSmartRfRadioEnergyEntry 4 }

		
		-- 1.3.6.1.4.1.1916.2.131.50.1.4.3.5.5.1.5
		wingStatsRfdSmartRfRadioEnergyChannel OBJECT-TYPE
			SYNTAX DisplayString
			MAX-ACCESS read-only
			STATUS current
			DESCRIPTION
				"Smart-rf assigned radio channel
				
				Values:
				46
				
				XPath: /wing-stats/rf_domain[name=key1]/smart-rf/radio_energy[mac=key2]/channel"
			::= { wingStatsRfdSmartRfRadioEnergyEntry 5 }

		
		-- 1.3.6.1.4.1.1916.2.131.50.1.4.3.5.5.1.6
		wingStatsRfdSmartRfRadioEnergyRadioIdx OBJECT-TYPE
			SYNTAX Unsigned32
			MAX-ACCESS read-only
			STATUS current
			DESCRIPTION
				"Radio index of this radio in AP
				
				XPath: /wing-stats/rf_domain[name=key1]/smart-rf/radio_energy[mac=key2]/radio_idx"
			::= { wingStatsRfdSmartRfRadioEnergyEntry 6 }

		
		-- 1.3.6.1.4.1.1916.2.131.50.1.4.3.5.5.1.7
		wingStatsRfdSmartRfRadioEnergyType OBJECT-TYPE
			SYNTAX DisplayString
			MAX-ACCESS read-only
			STATUS current
			DESCRIPTION
				"Radio type
				
				Values:
				11bgn
				
				XPath: /wing-stats/rf_domain[name=key1]/smart-rf/radio_energy[mac=key2]/type"
			::= { wingStatsRfdSmartRfRadioEnergyEntry 7 }

		
		-- 1.3.6.1.4.1.1916.2.131.50.1.4.3.5.6
		wingStatsRfdSmartRfRadioEnergyEnergyTable OBJECT-TYPE
			SYNTAX SEQUENCE OF WingStatsRfdSmartRfRadioEnergyEnergyEntry
			MAX-ACCESS not-accessible
			STATUS current
			DESCRIPTION
				"
				
				/wing-stats/rf_domain/smart-rf/radio_energy/energy"
			::= { wingStatsRfdSmartRf 6 }

		
		-- 1.3.6.1.4.1.1916.2.131.50.1.4.3.5.6.1
		wingStatsRfdSmartRfRadioEnergyEnergyEntry OBJECT-TYPE
			SYNTAX WingStatsRfdSmartRfRadioEnergyEnergyEntry
			MAX-ACCESS not-accessible
			STATUS current
			DESCRIPTION
				"An entry in the table."
			INDEX { wingStatsRfdName, wingStatsRfdSmartRfRadioEnergyMac }
			::= { wingStatsRfdSmartRfRadioEnergyEnergyTable 1 }

		
		WingStatsRfdSmartRfRadioEnergyEnergyEntry ::=
			SEQUENCE { 
				wingStatsRfdSmartRfRadioEnergyEnergyChannel
					DisplayString,
				wingStatsRfdSmartRfRadioEnergyEnergyExternal
					Integer32,
				wingStatsRfdSmartRfRadioEnergyEnergyNeighbor
					Integer32,
				wingStatsRfdSmartRfRadioEnergyEnergyNoise
					Integer32,
				wingStatsRfdSmartRfRadioEnergyEnergyTotal
					Integer32
			 }

		-- 1.3.6.1.4.1.1916.2.131.50.1.4.3.5.6.1.1
		wingStatsRfdSmartRfRadioEnergyEnergyChannel OBJECT-TYPE
			SYNTAX DisplayString
			MAX-ACCESS read-only
			STATUS current
			DESCRIPTION
				"Channel for which energy readings have been taken
				
				Values:
				1,
				2,
				3,
				4,
				5,
				6,
				7,
				8,
				9,
				10,
				11,
				12,
				13,
				14,
				36,
				40,
				44,
				48,
				52,
				56,
				60,
				64,
				100,
				104,
				108,
				112,
				116,
				120,
				124,
				128,
				132,
				136,
				140,
				149,
				153,
				157,
				161,
				165,
				34,
				38,
				42,
				46
				
				XPath: /wing-stats/rf_domain[name=key1]/smart-rf/radio_energy[mac=key2]/energy/channel"
			::= { wingStatsRfdSmartRfRadioEnergyEnergyEntry 1 }

		
		-- 1.3.6.1.4.1.1916.2.131.50.1.4.3.5.6.1.2
		wingStatsRfdSmartRfRadioEnergyEnergyExternal OBJECT-TYPE
			SYNTAX Integer32
			UNITS "dbm"
			MAX-ACCESS read-only
			STATUS current
			DESCRIPTION
				"Interference due to external wireless sources
				
				XPath: /wing-stats/rf_domain[name=key1]/smart-rf/radio_energy[mac=key2]/energy/external"
			::= { wingStatsRfdSmartRfRadioEnergyEnergyEntry 2 }

		
		-- 1.3.6.1.4.1.1916.2.131.50.1.4.3.5.6.1.3
		wingStatsRfdSmartRfRadioEnergyEnergyNeighbor OBJECT-TYPE
			SYNTAX Integer32
			UNITS "dbm"
			MAX-ACCESS read-only
			STATUS current
			DESCRIPTION
				"Interference due to neighboring radios
				
				XPath: /wing-stats/rf_domain[name=key1]/smart-rf/radio_energy[mac=key2]/energy/neighbor"
			::= { wingStatsRfdSmartRfRadioEnergyEnergyEntry 3 }

		
		-- 1.3.6.1.4.1.1916.2.131.50.1.4.3.5.6.1.4
		wingStatsRfdSmartRfRadioEnergyEnergyNoise OBJECT-TYPE
			SYNTAX Integer32
			UNITS "dbm"
			MAX-ACCESS read-only
			STATUS current
			DESCRIPTION
				"Interference due to non-wifi sources
				
				XPath: /wing-stats/rf_domain[name=key1]/smart-rf/radio_energy[mac=key2]/energy/noise"
			::= { wingStatsRfdSmartRfRadioEnergyEnergyEntry 4 }

		
		-- 1.3.6.1.4.1.1916.2.131.50.1.4.3.5.6.1.5
		wingStatsRfdSmartRfRadioEnergyEnergyTotal OBJECT-TYPE
			SYNTAX Integer32
			UNITS "dbm"
			MAX-ACCESS read-only
			STATUS current
			DESCRIPTION
				"Total interference perceived by radio
				
				XPath: /wing-stats/rf_domain[name=key1]/smart-rf/radio_energy[mac=key2]/energy/total"
			::= { wingStatsRfdSmartRfRadioEnergyEnergyEntry 5 }

		
		-- 1.3.6.1.4.1.1916.2.131.50.1.4.3.5.7
		wingStatsRfdSmartRfRadioNonSsmTable OBJECT-TYPE
			SYNTAX SEQUENCE OF WingStatsRfdSmartRfRadioNonSsmEntry
			MAX-ACCESS not-accessible
			STATUS current
			DESCRIPTION
				"
				
				/wing-stats/rf_domain/smart-rf/radio"
			::= { wingStatsRfdSmartRf 7 }

		
		-- 1.3.6.1.4.1.1916.2.131.50.1.4.3.5.7.1
		wingStatsRfdSmartRfRadioNonSsmEntry OBJECT-TYPE
			SYNTAX WingStatsRfdSmartRfRadioNonSsmEntry
			MAX-ACCESS not-accessible
			STATUS current
			DESCRIPTION
				"An entry in the table."
			INDEX { wingStatsRfdName, wingStatsRfdSmartRfRadioNonSsmMac }
			::= { wingStatsRfdSmartRfRadioNonSsmTable 1 }

		
		WingStatsRfdSmartRfRadioNonSsmEntry ::=
			SEQUENCE { 
				wingStatsRfdSmartRfRadioNonSsmMac
					WingIdentifier,
				wingStatsRfdSmartRfRadioNonSsmInfoApMac
					DisplayString,
				wingStatsRfdSmartRfRadioNonSsmHostname
					DisplayString,
				wingStatsRfdSmartRfRadioNonSsmChannel
					DisplayString,
				wingStatsRfdSmartRfRadioNonSsmPower
					Unsigned32,
				wingStatsRfdSmartRfRadioNonSsmRadioIdx
					Unsigned32,
				wingStatsRfdSmartRfRadioNonSsmState
					DisplayString,
				wingStatsRfdSmartRfRadioNonSsmInfoType
					DisplayString,
				wingStatsRfdSmartRfRadioNonSsmActApMac
					DisplayString,
				wingStatsRfdSmartRfRadioNonSsmActType
					DisplayString,
				wingStatsRfdSmartRfRadioNonSsmPowerChanges
					Unsigned32,
				wingStatsRfdSmartRfRadioNonSsmChannelChanges
					Unsigned32,
				wingStatsRfdSmartRfRadioNonSsmCoverageChanges
					Unsigned32
			 }

		-- 1.3.6.1.4.1.1916.2.131.50.1.4.3.5.7.1.1
		wingStatsRfdSmartRfRadioNonSsmMac OBJECT-TYPE
			SYNTAX WingIdentifier
			MAX-ACCESS read-only
			STATUS current
			DESCRIPTION
				"Radio MAC address
				
				XPath: /wing-stats/rf_domain[name=key1]/smart-rf/radio[mac=key2]/mac"
			::= { wingStatsRfdSmartRfRadioNonSsmEntry 1 }

		
		-- 1.3.6.1.4.1.1916.2.131.50.1.4.3.5.7.1.3
		wingStatsRfdSmartRfRadioNonSsmInfoApMac OBJECT-TYPE
			SYNTAX DisplayString
			MAX-ACCESS read-only
			STATUS current
			DESCRIPTION
				"Access point MAC address in which this radio is present
				
				XPath: /wing-stats/rf_domain[name=key1]/smart-rf/radio[mac=key2]/info/ap_mac"
			::= { wingStatsRfdSmartRfRadioNonSsmEntry 3 }

		
		-- 1.3.6.1.4.1.1916.2.131.50.1.4.3.5.7.1.4
		wingStatsRfdSmartRfRadioNonSsmHostname OBJECT-TYPE
			SYNTAX DisplayString (SIZE (64))
			MAX-ACCESS read-only
			STATUS current
			DESCRIPTION
				"Access point hostname in which this radio is present
				
				XPath: /wing-stats/rf_domain[name=key1]/smart-rf/radio[mac=key2]/info/hostname"
			::= { wingStatsRfdSmartRfRadioNonSsmEntry 4 }

		
		-- 1.3.6.1.4.1.1916.2.131.50.1.4.3.5.7.1.5
		wingStatsRfdSmartRfRadioNonSsmChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/radio[mac=key2]/info/channel"
			::= { wingStatsRfdSmartRfRadioNonSsmEntry 5 }

		
		-- 1.3.6.1.4.1.1916.2.131.50.1.4.3.5.7.1.6
		wingStatsRfdSmartRfRadioNonSsmPower OBJECT-TYPE
			SYNTAX Unsigned32 (0..23)
			UNITS "dBm"
			MAX-ACCESS read-only
			STATUS current
			DESCRIPTION
				"Smart-rf assigned transmit power for this radio
				
				XPath: /wing-stats/rf_domain[name=key1]/smart-rf/radio[mac=key2]/info/power"
			::= { wingStatsRfdSmartRfRadioNonSsmEntry 6 }

		
		-- 1.3.6.1.4.1.1916.2.131.50.1.4.3.5.7.1.7
		wingStatsRfdSmartRfRadioNonSsmRadioIdx OBJECT-TYPE
			SYNTAX Unsigned32
			MAX-ACCESS read-only
			STATUS current
			DESCRIPTION
				"Radio index of this radio in AP
				
				XPath: /wing-stats/rf_domain[name=key1]/smart-rf/radio[mac=key2]/info/radio_idx"
			::= { wingStatsRfdSmartRfRadioNonSsmEntry 7 }

		
		-- 1.3.6.1.4.1.1916.2.131.50.1.4.3.5.7.1.8
		wingStatsRfdSmartRfRadioNonSsmState OBJECT-TYPE
			SYNTAX DisplayString
			MAX-ACCESS read-only
			STATUS current
			DESCRIPTION
				"Current radio state
				
				Values:
				offline,
				normal,
				sensor
				
				XPath: /wing-stats/rf_domain[name=key1]/smart-rf/radio[mac=key2]/info/state"
			::= { wingStatsRfdSmartRfRadioNonSsmEntry 8 }

		
		-- 1.3.6.1.4.1.1916.2.131.50.1.4.3.5.7.1.9
		wingStatsRfdSmartRfRadioNonSsmInfoType OBJECT-TYPE
			SYNTAX DisplayString
			MAX-ACCESS read-only
			STATUS current
			DESCRIPTION
				"Radio type
				
				Values:
				11an,
				11bgn
				
				XPath: /wing-stats/rf_domain[name=key1]/smart-rf/radio[mac=key2]/info/type"
			::= { wingStatsRfdSmartRfRadioNonSsmEntry 9 }

		
		-- 1.3.6.1.4.1.1916.2.131.50.1.4.3.5.7.1.10
		wingStatsRfdSmartRfRadioNonSsmActApMac OBJECT-TYPE
			SYNTAX DisplayString
			MAX-ACCESS read-only
			STATUS current
			DESCRIPTION
				"Access point MAC address in which this radio is present
				
				XPath: /wing-stats/rf_domain[name=key1]/smart-rf/radio[mac=key2]/activity/ap_mac"
			::= { wingStatsRfdSmartRfRadioNonSsmEntry 10 }

		
		-- 1.3.6.1.4.1.1916.2.131.50.1.4.3.5.7.1.11
		wingStatsRfdSmartRfRadioNonSsmActType OBJECT-TYPE
			SYNTAX DisplayString
			MAX-ACCESS read-only
			STATUS current
			DESCRIPTION
				"Radio type
				
				Values:
				11an,
				11bgn
				
				XPath: /wing-stats/rf_domain[name=key1]/smart-rf/radio[mac=key2]/activity/type"
			::= { wingStatsRfdSmartRfRadioNonSsmEntry 11 }

		
		-- 1.3.6.1.4.1.1916.2.131.50.1.4.3.5.7.1.12
		wingStatsRfdSmartRfRadioNonSsmPowerChanges OBJECT-TYPE
			SYNTAX Unsigned32 (0..1024)
			MAX-ACCESS read-only
			STATUS current
			DESCRIPTION
				"Number of neighbor recovery power changes for this radio
				
				XPath: /wing-stats/rf_domain[name=key1]/smart-rf/radio[mac=key2]/activity/power_changes"
			::= { wingStatsRfdSmartRfRadioNonSsmEntry 12 }

		
		-- 1.3.6.1.4.1.1916.2.131.50.1.4.3.5.7.1.13
		wingStatsRfdSmartRfRadioNonSsmChannelChanges OBJECT-TYPE
			SYNTAX Unsigned32 (0..1024)
			MAX-ACCESS read-only
			STATUS current
			DESCRIPTION
				"Number of channel changes for this radio
				
				XPath: /wing-stats/rf_domain[name=key1]/smart-rf/radio[mac=key2]/activity/channel_changes"
			::= { wingStatsRfdSmartRfRadioNonSsmEntry 13 }

		
		-- 1.3.6.1.4.1.1916.2.131.50.1.4.3.5.7.1.14
		wingStatsRfdSmartRfRadioNonSsmCoverageChanges OBJECT-TYPE
			SYNTAX Unsigned32 (0..1024)
			MAX-ACCESS read-only
			STATUS current
			DESCRIPTION
				"Number of coverage hole recovery power changes for this radio
				
				XPath: /wing-stats/rf_domain[name=key1]/smart-rf/radio[mac=key2]/activity/coverage_changes"
			::= { wingStatsRfdSmartRfRadioNonSsmEntry 14 }

		
		-- 1.3.6.1.4.1.1916.2.131.50.1.4.3.5.8
		wingStatsRfdSmartRfRadioNonSsmNeighborsTable OBJECT-TYPE
			SYNTAX SEQUENCE OF WingStatsRfdSmartRfRadioNonSsmNeighborsEntry
			MAX-ACCESS not-accessible
			STATUS current
			DESCRIPTION
				"
				
				/wing-stats/rf_domain/smart-rf/radio/neighbors"
			::= { wingStatsRfdSmartRf 8 }

		
		-- 1.3.6.1.4.1.1916.2.131.50.1.4.3.5.8.1
		wingStatsRfdSmartRfRadioNonSsmNeighborsEntry OBJECT-TYPE
			SYNTAX WingStatsRfdSmartRfRadioNonSsmNeighborsEntry
			MAX-ACCESS not-accessible
			STATUS current
			DESCRIPTION
				"An entry in the table."
			INDEX { wingStatsRfdName, wingStatsRfdSmartRfRadioNonSsmMac }
			::= { wingStatsRfdSmartRfRadioNonSsmNeighborsTable 1 }

		
		WingStatsRfdSmartRfRadioNonSsmNeighborsEntry ::=
			SEQUENCE { 
				wingStatsRfdSmartRfRadioNonSsmNeighborsMac
					DisplayString,
				wingStatsRfdSmartRfRadioNonSsmNeighborsApMac
					DisplayString,
				wingStatsRfdSmartRfRadioNonSsmNeighborsChannel
					DisplayString,
				wingStatsRfdSmartRfRadioNonSsmNeighborsPower
					Unsigned32,
				wingStatsRfdSmartRfRadioNonSsmNeighborsAttenuation
					Unsigned32,
				wingStatsRfdSmartRfRadioNonSsmNeighborsRadioIdx
					Unsigned32
			 }

		-- 1.3.6.1.4.1.1916.2.131.50.1.4.3.5.8.1.1
		wingStatsRfdSmartRfRadioNonSsmNeighborsMac OBJECT-TYPE
			SYNTAX DisplayString
			MAX-ACCESS read-only
			STATUS current
			DESCRIPTION
				"Radio MAC address
				
				XPath: /wing-stats/rf_domain[name=key1]/smart-rf/radio[mac=key2]/neighbors/mac"
			::= { wingStatsRfdSmartRfRadioNonSsmNeighborsEntry 1 }

		
		-- 1.3.6.1.4.1.1916.2.131.50.1.4.3.5.8.1.2
		wingStatsRfdSmartRfRadioNonSsmNeighborsApMac OBJECT-TYPE
			SYNTAX DisplayString
			MAX-ACCESS read-only
			STATUS current
			DESCRIPTION
				"Access point MAC address in which this radio is present
				
				XPath: /wing-stats/rf_domain[name=key1]/smart-rf/radio[mac=key2]/neighbors/ap_mac"
			::= { wingStatsRfdSmartRfRadioNonSsmNeighborsEntry 2 }

		
		-- 1.3.6.1.4.1.1916.2.131.50.1.4.3.5.8.1.3
		wingStatsRfdSmartRfRadioNonSsmNeighborsChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/radio[mac=key2]/neighbors/channel"
			::= { wingStatsRfdSmartRfRadioNonSsmNeighborsEntry 3 }

		
		-- 1.3.6.1.4.1.1916.2.131.50.1.4.3.5.8.1.4
		wingStatsRfdSmartRfRadioNonSsmNeighborsPower OBJECT-TYPE
			SYNTAX Unsigned32 (0..23)
			UNITS "dBm"
			MAX-ACCESS read-only
			STATUS current
			DESCRIPTION
				"Smart-rf assigned transmit power for this neighbor radio
				
				XPath: /wing-stats/rf_domain[name=key1]/smart-rf/radio[mac=key2]/neighbors/power"
			::= { wingStatsRfdSmartRfRadioNonSsmNeighborsEntry 4 }

		
		-- 1.3.6.1.4.1.1916.2.131.50.1.4.3.5.8.1.5
		wingStatsRfdSmartRfRadioNonSsmNeighborsAttenuation OBJECT-TYPE
			SYNTAX Unsigned32
			UNITS "dB"
			MAX-ACCESS read-only
			STATUS current
			DESCRIPTION
				"Attenuation of neighbor radio
				
				XPath: /wing-stats/rf_domain[name=key1]/smart-rf/radio[mac=key2]/neighbors/attenuation"
			::= { wingStatsRfdSmartRfRadioNonSsmNeighborsEntry 5 }

		
		-- 1.3.6.1.4.1.1916.2.131.50.1.4.3.5.8.1.6
		wingStatsRfdSmartRfRadioNonSsmNeighborsRadioIdx OBJECT-TYPE
			SYNTAX Unsigned32
			MAX-ACCESS read-only
			STATUS current
			DESCRIPTION
				"Radio index of this neighbor radio in AP
				
				XPath: /wing-stats/rf_domain[name=key1]/smart-rf/radio[mac=key2]/neighbors/radio_idx"
			::= { wingStatsRfdSmartRfRadioNonSsmNeighborsEntry 6 }

		
		-- 1.3.6.1.4.1.1916.2.131.50.1.4.3.5.9
		wingStatsRfdSmartRfRadioNonSsmEnergyTable OBJECT-TYPE
			SYNTAX SEQUENCE OF WingStatsRfdSmartRfRadioNonSsmEnergyEntry
			MAX-ACCESS not-accessible
			STATUS current
			DESCRIPTION
				"
				
				/wing-stats/rf_domain/smart-rf/radio/energy"
			::= { wingStatsRfdSmartRf 9 }

		
		-- 1.3.6.1.4.1.1916.2.131.50.1.4.3.5.9.1
		wingStatsRfdSmartRfRadioNonSsmEnergyEntry OBJECT-TYPE
			SYNTAX WingStatsRfdSmartRfRadioNonSsmEnergyEntry
			MAX-ACCESS not-accessible
			STATUS current
			DESCRIPTION
				"An entry in the table."
			INDEX { wingStatsRfdName, wingStatsRfdSmartRfRadioNonSsmMac }
			::= { wingStatsRfdSmartRfRadioNonSsmEnergyTable 1 }

		
		WingStatsRfdSmartRfRadioNonSsmEnergyEntry ::=
			SEQUENCE { 
				wingStatsRfdSmartRfRadioNonSsmEnergyChannel
					DisplayString,
				wingStatsRfdSmartRfRadioNonSsmEnergyExternal
					Integer32,
				wingStatsRfdSmartRfRadioNonSsmEnergyNeighbor
					Integer32,
				wingStatsRfdSmartRfRadioNonSsmEnergyNoise
					Integer32,
				wingStatsRfdSmartRfRadioNonSsmEnergyTotal
					Integer32
			 }

		-- 1.3.6.1.4.1.1916.2.131.50.1.4.3.5.9.1.1
		wingStatsRfdSmartRfRadioNonSsmEnergyChannel OBJECT-TYPE
			SYNTAX DisplayString
			MAX-ACCESS read-only
			STATUS current
			DESCRIPTION
				"Channel for which energy readings have been taken
				
				Values:
				1,
				2,
				3,
				4,
				5,
				6,
				7,
				8,
				9,
				10,
				11,
				12,
				13,
				14,
				36,
				40,
				44,
				48,
				52,
				56,
				60,
				64,
				100,
				104,
				108,
				112,
				116,
				120,
				124,
				128,
				132,
				136,
				140,
				149,
				153,
				157,
				161,
				165,
				34,
				38,
				42,
				46
				
				XPath: /wing-stats/rf_domain[name=key1]/smart-rf/radio[mac=key2]/energy/channel"
			::= { wingStatsRfdSmartRfRadioNonSsmEnergyEntry 1 }

		
		-- 1.3.6.1.4.1.1916.2.131.50.1.4.3.5.9.1.2
		wingStatsRfdSmartRfRadioNonSsmEnergyExternal OBJECT-TYPE
			SYNTAX Integer32
			UNITS "dbm"
			MAX-ACCESS read-only
			STATUS current
			DESCRIPTION
				"Interference due to external wireless sources
				
				XPath: /wing-stats/rf_domain[name=key1]/smart-rf/radio[mac=key2]/energy/external"
			::= { wingStatsRfdSmartRfRadioNonSsmEnergyEntry 2 }

		
		-- 1.3.6.1.4.1.1916.2.131.50.1.4.3.5.9.1.3
		wingStatsRfdSmartRfRadioNonSsmEnergyNeighbor OBJECT-TYPE
			SYNTAX Integer32
			UNITS "dbm"
			MAX-ACCESS read-only
			STATUS current
			DESCRIPTION
				"Interference due to neighboring radios
				
				XPath: /wing-stats/rf_domain[name=key1]/smart-rf/radio[mac=key2]/energy/neighbor"
			::= { wingStatsRfdSmartRfRadioNonSsmEnergyEntry 3 }

		
		-- 1.3.6.1.4.1.1916.2.131.50.1.4.3.5.9.1.4
		wingStatsRfdSmartRfRadioNonSsmEnergyNoise OBJECT-TYPE
			SYNTAX Integer32
			UNITS "dbm"
			MAX-ACCESS read-only
			STATUS current
			DESCRIPTION
				"Interference due to non-wifi sources
				
				XPath: /wing-stats/rf_domain[name=key1]/smart-rf/radio[mac=key2]/energy/noise"
			::= { wingStatsRfdSmartRfRadioNonSsmEnergyEntry 4 }

		
		-- 1.3.6.1.4.1.1916.2.131.50.1.4.3.5.9.1.5
		wingStatsRfdSmartRfRadioNonSsmEnergyTotal OBJECT-TYPE
			SYNTAX Integer32
			UNITS "dbm"
			MAX-ACCESS read-only
			STATUS current
			DESCRIPTION
				"Total interference perceived by radio
				
				XPath: /wing-stats/rf_domain[name=key1]/smart-rf/radio[mac=key2]/energy/total"
			::= { wingStatsRfdSmartRfRadioNonSsmEnergyEntry 5 }

		
		-- 1.3.6.1.4.1.1916.2.131.50.1.4.3.5.10
		wingStatsRfdSmartRfApTable OBJECT-TYPE
			SYNTAX SEQUENCE OF WingStatsRfdSmartRfApEntry
			MAX-ACCESS not-accessible
			STATUS current
			DESCRIPTION
				"
				
				/wing-stats/rf_domain/smart-rf/ap"
			::= { wingStatsRfdSmartRf 10 }

		
		-- 1.3.6.1.4.1.1916.2.131.50.1.4.3.5.10.1
		wingStatsRfdSmartRfApEntry OBJECT-TYPE
			SYNTAX WingStatsRfdSmartRfApEntry
			MAX-ACCESS not-accessible
			STATUS current
			DESCRIPTION
				"An entry in the table."
			INDEX { wingStatsRfdName, wingStatsRfdSmartRfApMac }
			::= { wingStatsRfdSmartRfApTable 1 }

		
		WingStatsRfdSmartRfApEntry ::=
			SEQUENCE { 
				wingStatsRfdSmartRfApMac
					WingIdentifier
			 }

		-- 1.3.6.1.4.1.1916.2.131.50.1.4.3.5.10.1.1
		wingStatsRfdSmartRfApMac OBJECT-TYPE
			SYNTAX WingIdentifier
			MAX-ACCESS read-only
			STATUS current
			DESCRIPTION
				"AP mac address
				
				XPath: /wing-stats/rf_domain[name=key1]/ap[mac=key2]/mac"
			::= { wingStatsRfdSmartRfApEntry 1 }

		
		-- 1.3.6.1.4.1.1916.2.131.50.1.4.3.5.11
		wingStatsRfdSmartRfApNeighborsTable OBJECT-TYPE
			SYNTAX SEQUENCE OF WingStatsRfdSmartRfApNeighborsEntry
			MAX-ACCESS not-accessible
			STATUS current
			DESCRIPTION
				"
				
				/wing-stats/rf_domain/smart-rf/ap/neighbors"
			::= { wingStatsRfdSmartRf 11 }

		
		-- 1.3.6.1.4.1.1916.2.131.50.1.4.3.5.11.1
		wingStatsRfdSmartRfApNeighborsEntry OBJECT-TYPE
			SYNTAX WingStatsRfdSmartRfApNeighborsEntry
			MAX-ACCESS not-accessible
			STATUS current
			DESCRIPTION
				"An entry in the table."
			INDEX { wingStatsRfdName, wingStatsRfdSmartRfApMac }
			::= { wingStatsRfdSmartRfApNeighborsTable 1 }

		
		WingStatsRfdSmartRfApNeighborsEntry ::=
			SEQUENCE { 
				wingStatsRfdSmartRfApNeighborsMac
					DisplayString,
				wingStatsRfdSmartRfApNeighborsApMac
					DisplayString,
				wingStatsRfdSmartRfApNeighborsHostname
					DisplayString,
				wingStatsRfdSmartRfApNeighborsChannel
					DisplayString,
				wingStatsRfdSmartRfApNeighborsPower
					Unsigned32,
				wingStatsRfdSmartRfApNeighborsAttenuation
					Unsigned32,
				wingStatsRfdSmartRfApNeighborsInterference
					Integer32,
				wingStatsRfdSmartRfApNeighborsRadioIdx
					Unsigned32,
				wingStatsRfdSmartRfApNeighborsListenerIdx
					Unsigned32,
				wingStatsRfdSmartRfApNeighborsListenerMac
					DisplayString,
				wingStatsRfdSmartRfApNeighborsType
					DisplayString
			 }

		-- 1.3.6.1.4.1.1916.2.131.50.1.4.3.5.11.1.1
		wingStatsRfdSmartRfApNeighborsMac OBJECT-TYPE
			SYNTAX DisplayString
			MAX-ACCESS read-only
			STATUS current
			DESCRIPTION
				"Neighbor radio MAC address
				
				XPath: /wing-stats/rf_domain[name=key1]/ap[mac=key2]/neighbors/mac"
			::= { wingStatsRfdSmartRfApNeighborsEntry 1 }

		
		-- 1.3.6.1.4.1.1916.2.131.50.1.4.3.5.11.1.2
		wingStatsRfdSmartRfApNeighborsApMac OBJECT-TYPE
			SYNTAX DisplayString
			MAX-ACCESS read-only
			STATUS current
			DESCRIPTION
				"Access point MAC address in which this neighbor radio is present
				
				XPath: /wing-stats/rf_domain[name=key1]/ap[mac=key2]/neighbors/ap_mac"
			::= { wingStatsRfdSmartRfApNeighborsEntry 2 }

		
		-- 1.3.6.1.4.1.1916.2.131.50.1.4.3.5.11.1.3
		wingStatsRfdSmartRfApNeighborsHostname OBJECT-TYPE
			SYNTAX DisplayString (SIZE (64))
			MAX-ACCESS read-only
			STATUS current
			DESCRIPTION
				"Access point hostname in which this neighbor radio is present
				
				XPath: /wing-stats/rf_domain[name=key1]/ap[mac=key2]/neighbors/hostname"
			::= { wingStatsRfdSmartRfApNeighborsEntry 3 }

		
		-- 1.3.6.1.4.1.1916.2.131.50.1.4.3.5.11.1.4
		wingStatsRfdSmartRfApNeighborsChannel OBJECT-TYPE
			SYNTAX DisplayString
			MAX-ACCESS read-only
			STATUS current
			DESCRIPTION
				"Smart-rf assigned neighbor radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/ap[mac=key2]/neighbors/channel"
			::= { wingStatsRfdSmartRfApNeighborsEntry 4 }

		
		-- 1.3.6.1.4.1.1916.2.131.50.1.4.3.5.11.1.5
		wingStatsRfdSmartRfApNeighborsPower OBJECT-TYPE
			SYNTAX Unsigned32 (0..23)
			UNITS "dBm"
			MAX-ACCESS read-only
			STATUS current
			DESCRIPTION
				"Smart-rf assigned transmit power for this neighbor radio
				
				XPath: /wing-stats/rf_domain[name=key1]/ap[mac=key2]/neighbors/power"
			::= { wingStatsRfdSmartRfApNeighborsEntry 5 }

		
		-- 1.3.6.1.4.1.1916.2.131.50.1.4.3.5.11.1.6
		wingStatsRfdSmartRfApNeighborsAttenuation OBJECT-TYPE
			SYNTAX Unsigned32
			UNITS "dB"
			MAX-ACCESS read-only
			STATUS current
			DESCRIPTION
				"Attenuation of neighbor radio
				
				XPath: /wing-stats/rf_domain[name=key1]/ap[mac=key2]/neighbors/attenuation"
			::= { wingStatsRfdSmartRfApNeighborsEntry 6 }

		
		-- 1.3.6.1.4.1.1916.2.131.50.1.4.3.5.11.1.7
		wingStatsRfdSmartRfApNeighborsInterference OBJECT-TYPE
			SYNTAX Integer32
			UNITS "dbm"
			MAX-ACCESS read-only
			STATUS current
			DESCRIPTION
				"Co Channel interference due to neighboring radios
				
				XPath: /wing-stats/rf_domain[name=key1]/ap[mac=key2]/neighbors/interference"
			::= { wingStatsRfdSmartRfApNeighborsEntry 7 }

		
		-- 1.3.6.1.4.1.1916.2.131.50.1.4.3.5.11.1.8
		wingStatsRfdSmartRfApNeighborsRadioIdx OBJECT-TYPE
			SYNTAX Unsigned32
			MAX-ACCESS read-only
			STATUS current
			DESCRIPTION
				"Radio index of this neighbor radio in AP
				
				XPath: /wing-stats/rf_domain[name=key1]/ap[mac=key2]/neighbors/radio_idx"
			::= { wingStatsRfdSmartRfApNeighborsEntry 8 }

		
		-- 1.3.6.1.4.1.1916.2.131.50.1.4.3.5.11.1.9
		wingStatsRfdSmartRfApNeighborsListenerIdx OBJECT-TYPE
			SYNTAX Unsigned32
			MAX-ACCESS read-only
			STATUS current
			DESCRIPTION
				"Radio index of the radio which hears this neighbor
				
				XPath: /wing-stats/rf_domain[name=key1]/ap[mac=key2]/neighbors/listener_idx"
			::= { wingStatsRfdSmartRfApNeighborsEntry 9 }

		
		-- 1.3.6.1.4.1.1916.2.131.50.1.4.3.5.11.1.10
		wingStatsRfdSmartRfApNeighborsListenerMac OBJECT-TYPE
			SYNTAX DisplayString
			MAX-ACCESS read-only
			STATUS current
			DESCRIPTION
				"MAC address of the radio which hears this neighbor
				
				XPath: /wing-stats/rf_domain[name=key1]/ap[mac=key2]/neighbors/listener_mac"
			::= { wingStatsRfdSmartRfApNeighborsEntry 10 }

		
		-- 1.3.6.1.4.1.1916.2.131.50.1.4.3.5.11.1.11
		wingStatsRfdSmartRfApNeighborsType OBJECT-TYPE
			SYNTAX DisplayString
			MAX-ACCESS read-only
			STATUS current
			DESCRIPTION
				"Radio type
				
				Values:
				11an,
				11bgn
				
				XPath: /wing-stats/rf_domain[name=key1]/ap[mac=key2]/neighbors/type"
			::= { wingStatsRfdSmartRfApNeighborsEntry 11 }

		
		-- 1.3.6.1.4.1.1916.2.131.50.1.4.3.5.12
		wingStatsRfdSmartRfHighActRadiosTable OBJECT-TYPE
			SYNTAX SEQUENCE OF WingStatsRfdSmartRfHighActRadiosEntry
			MAX-ACCESS not-accessible
			STATUS current
			DESCRIPTION
				"
				
				/wing-stats/rf_domain/smart-rf/high_activity_radios"
			::= { wingStatsRfdSmartRf 12 }

		
		-- 1.3.6.1.4.1.1916.2.131.50.1.4.3.5.12.1
		wingStatsRfdSmartRfHighActRadiosEntry OBJECT-TYPE
			SYNTAX WingStatsRfdSmartRfHighActRadiosEntry
			MAX-ACCESS not-accessible
			STATUS current
			DESCRIPTION
				"An entry in the table."
			INDEX { wingStatsRfdName }
			::= { wingStatsRfdSmartRfHighActRadiosTable 1 }

		
		WingStatsRfdSmartRfHighActRadiosEntry ::=
			SEQUENCE { 
				wingStatsRfdSmartRfHighActRadiosMac
					DisplayString,
				wingStatsRfdSmartRfHighActRadiosApMac
					DisplayString,
				wingStatsRfdSmartRfHighActRadiosHostname
					DisplayString,
				wingStatsRfdSmartRfHighActRadiosType
					DisplayString,
				wingStatsRfdSmartRfHighActRadiosPowerChanges
					Unsigned32,
				wingStatsRfdSmartRfHighActRadiosChannelChanges
					Unsigned32,
				wingStatsRfdSmartRfHighActRadiosCoverageChanges
					Unsigned32
			 }

		-- 1.3.6.1.4.1.1916.2.131.50.1.4.3.5.12.1.1
		wingStatsRfdSmartRfHighActRadiosMac OBJECT-TYPE
			SYNTAX DisplayString
			MAX-ACCESS read-only
			STATUS current
			DESCRIPTION
				"Radio MAC address
				
				XPath: /wing-stats/rf_domain[name=key1]/smart-rf/high_activity_radios/mac"
			::= { wingStatsRfdSmartRfHighActRadiosEntry 1 }

		
		-- 1.3.6.1.4.1.1916.2.131.50.1.4.3.5.12.1.2
		wingStatsRfdSmartRfHighActRadiosApMac OBJECT-TYPE
			SYNTAX DisplayString
			MAX-ACCESS read-only
			STATUS current
			DESCRIPTION
				"Access point MAC address in which this radio is present
				
				XPath: /wing-stats/rf_domain[name=key1]/smart-rf/high_activity_radios/ap_mac"
			::= { wingStatsRfdSmartRfHighActRadiosEntry 2 }

		
		-- 1.3.6.1.4.1.1916.2.131.50.1.4.3.5.12.1.3
		wingStatsRfdSmartRfHighActRadiosHostname OBJECT-TYPE
			SYNTAX DisplayString (SIZE (64))
			MAX-ACCESS read-only
			STATUS current
			DESCRIPTION
				"Access point hostname in which this radio is present
				
				XPath: /wing-stats/rf_domain[name=key1]/smart-rf/high_activity_radios/hostname"
			::= { wingStatsRfdSmartRfHighActRadiosEntry 3 }

		
		-- 1.3.6.1.4.1.1916.2.131.50.1.4.3.5.12.1.4
		wingStatsRfdSmartRfHighActRadiosType OBJECT-TYPE
			SYNTAX DisplayString
			MAX-ACCESS read-only
			STATUS current
			DESCRIPTION
				"Radio type
				
				Values:
				11an,
				11bgn
				
				XPath: /wing-stats/rf_domain[name=key1]/smart-rf/high_activity_radios/type"
			::= { wingStatsRfdSmartRfHighActRadiosEntry 4 }

		
		-- 1.3.6.1.4.1.1916.2.131.50.1.4.3.5.12.1.5
		wingStatsRfdSmartRfHighActRadiosPowerChanges OBJECT-TYPE
			SYNTAX Unsigned32 (0..1024)
			MAX-ACCESS read-only
			STATUS current
			DESCRIPTION
				"Number of neighbor recovery power changes for this radio
				
				XPath: /wing-stats/rf_domain[name=key1]/smart-rf/high_activity_radios/power_changes"
			::= { wingStatsRfdSmartRfHighActRadiosEntry 5 }

		
		-- 1.3.6.1.4.1.1916.2.131.50.1.4.3.5.12.1.6
		wingStatsRfdSmartRfHighActRadiosChannelChanges OBJECT-TYPE
			SYNTAX Unsigned32 (0..1024)
			MAX-ACCESS read-only
			STATUS current
			DESCRIPTION
				"Number of channel changes for this radio
				
				XPath: /wing-stats/rf_domain[name=key1]/smart-rf/high_activity_radios/channel_changes"
			::= { wingStatsRfdSmartRfHighActRadiosEntry 6 }

		
		-- 1.3.6.1.4.1.1916.2.131.50.1.4.3.5.12.1.7
		wingStatsRfdSmartRfHighActRadiosCoverageChanges OBJECT-TYPE
			SYNTAX Unsigned32 (0..1024)
			MAX-ACCESS read-only
			STATUS current
			DESCRIPTION
				"Number of coverage hole recovery power changes for this radio
				
				XPath: /wing-stats/rf_domain[name=key1]/smart-rf/high_activity_radios/coverage_changes"
			::= { wingStatsRfdSmartRfHighActRadiosEntry 7 }

		
		-- 1.3.6.1.4.1.1916.2.131.50.1.4.3.5.13
		wingStatsRfdSmartRfHistoryTable OBJECT-TYPE
			SYNTAX SEQUENCE OF WingStatsRfdSmartRfHistoryEntry
			MAX-ACCESS not-accessible
			STATUS current
			DESCRIPTION
				"
				
				/wing-stats/rf_domain/smart-rf/history"
			::= { wingStatsRfdSmartRf 13 }

		
		-- 1.3.6.1.4.1.1916.2.131.50.1.4.3.5.13.1
		wingStatsRfdSmartRfHistoryEntry OBJECT-TYPE
			SYNTAX WingStatsRfdSmartRfHistoryEntry
			MAX-ACCESS not-accessible
			STATUS current
			DESCRIPTION
				"An entry in the table."
			INDEX { wingStatsRfdName }
			::= { wingStatsRfdSmartRfHistoryTable 1 }

		
		WingStatsRfdSmartRfHistoryEntry ::=
			SEQUENCE { 
				wingStatsRfdSmartRfHistoryTime
					Unsigned32,
				wingStatsRfdSmartRfHistoryApMac
					DisplayString,
				wingStatsRfdSmartRfHistoryHostname
					DisplayString,
				wingStatsRfdSmartRfHistoryRadioMac
					DisplayString,
				wingStatsRfdSmartRfHistoryRadioIdx
					Integer32,
				wingStatsRfdSmartRfHistoryOldValue
					DisplayString,
				wingStatsRfdSmartRfHistoryNewValue
					DisplayString
			 }

		-- 1.3.6.1.4.1.1916.2.131.50.1.4.3.5.13.1.1
		wingStatsRfdSmartRfHistoryTime OBJECT-TYPE
			SYNTAX Unsigned32
			MAX-ACCESS read-only
			STATUS current
			DESCRIPTION
				"
				
				XPath: /wing-stats/rf_domain[name=key1]/smart-rf/history/time"
			::= { wingStatsRfdSmartRfHistoryEntry 1 }

		
		-- 1.3.6.1.4.1.1916.2.131.50.1.4.3.5.13.1.2
		wingStatsRfdSmartRfHistoryApMac OBJECT-TYPE
			SYNTAX DisplayString
			MAX-ACCESS read-only
			STATUS current
			DESCRIPTION
				"Access point MAC address
				
				XPath: /wing-stats/rf_domain[name=key1]/smart-rf/history/ap_mac"
			::= { wingStatsRfdSmartRfHistoryEntry 2 }

		
		-- 1.3.6.1.4.1.1916.2.131.50.1.4.3.5.13.1.3
		wingStatsRfdSmartRfHistoryHostname OBJECT-TYPE
			SYNTAX DisplayString (SIZE (64))
			MAX-ACCESS read-only
			STATUS current
			DESCRIPTION
				"Access point hostname
				
				XPath: /wing-stats/rf_domain[name=key1]/smart-rf/history/hostname"
			::= { wingStatsRfdSmartRfHistoryEntry 3 }

		
		-- 1.3.6.1.4.1.1916.2.131.50.1.4.3.5.13.1.4
		wingStatsRfdSmartRfHistoryRadioMac OBJECT-TYPE
			SYNTAX DisplayString
			MAX-ACCESS read-only
			STATUS current
			DESCRIPTION
				"Radio MAC address
				
				XPath: /wing-stats/rf_domain[name=key1]/smart-rf/history/radio_mac"
			::= { wingStatsRfdSmartRfHistoryEntry 4 }

		
		-- 1.3.6.1.4.1.1916.2.131.50.1.4.3.5.13.1.5
		wingStatsRfdSmartRfHistoryRadioIdx OBJECT-TYPE
			SYNTAX Integer32
			MAX-ACCESS read-only
			STATUS current
			DESCRIPTION
				"Radio index
				
				XPath: /wing-stats/rf_domain[name=key1]/smart-rf/history/radio_idx"
			::= { wingStatsRfdSmartRfHistoryEntry 5 }

		
		-- 1.3.6.1.4.1.1916.2.131.50.1.4.3.5.13.1.6
		wingStatsRfdSmartRfHistoryOldValue OBJECT-TYPE
			SYNTAX DisplayString (SIZE (32))
			MAX-ACCESS read-only
			STATUS current
			DESCRIPTION
				"Old value
				
				XPath: /wing-stats/rf_domain[name=key1]/smart-rf/history/old_value"
			::= { wingStatsRfdSmartRfHistoryEntry 6 }

		
		-- 1.3.6.1.4.1.1916.2.131.50.1.4.3.5.13.1.7
		wingStatsRfdSmartRfHistoryNewValue OBJECT-TYPE
			SYNTAX DisplayString (SIZE (32))
			MAX-ACCESS read-only
			STATUS current
			DESCRIPTION
				"Old value
				
				XPath: /wing-stats/rf_domain[name=key1]/smart-rf/history/new_value"
			::= { wingStatsRfdSmartRfHistoryEntry 7 }

		
		-- 1.3.6.1.4.1.1916.2.131.50.1.4.3.5.14
		wingStatsRfdSmartRfHistoryDaysTable OBJECT-TYPE
			SYNTAX SEQUENCE OF WingStatsRfdSmartRfHistoryDaysEntry
			MAX-ACCESS not-accessible
			STATUS current
			DESCRIPTION
				"
				
				/wing-stats/rf_domain/smart-rf/history_days"
			::= { wingStatsRfdSmartRf 14 }

		
		-- 1.3.6.1.4.1.1916.2.131.50.1.4.3.5.14.1
		wingStatsRfdSmartRfHistoryDaysEntry OBJECT-TYPE
			SYNTAX WingStatsRfdSmartRfHistoryDaysEntry
			MAX-ACCESS not-accessible
			STATUS current
			DESCRIPTION
				"An entry in the table."
			INDEX { wingStatsRfdName }
			::= { wingStatsRfdSmartRfHistoryDaysTable 1 }

		
		WingStatsRfdSmartRfHistoryDaysEntry ::=
			SEQUENCE { 
				wingStatsRfdSmartRfHistoryDaysTime
					Unsigned32,
				wingStatsRfdSmartRfHistoryDaysPowerChanges
					Unsigned32,
				wingStatsRfdSmartRfHistoryDaysChannelChanges
					Unsigned32,
				wingStatsRfdSmartRfHistoryDaysCoverageChanges
					Unsigned32
			 }

		-- 1.3.6.1.4.1.1916.2.131.50.1.4.3.5.14.1.1
		wingStatsRfdSmartRfHistoryDaysTime OBJECT-TYPE
			SYNTAX Unsigned32
			MAX-ACCESS read-only
			STATUS current
			DESCRIPTION
				"
				
				XPath: /wing-stats/rf_domain[name=key1]/smart-rf/history_days/time"
			::= { wingStatsRfdSmartRfHistoryDaysEntry 1 }

		
		-- 1.3.6.1.4.1.1916.2.131.50.1.4.3.5.14.1.2
		wingStatsRfdSmartRfHistoryDaysPowerChanges OBJECT-TYPE
			SYNTAX Unsigned32 (0..65535)
			MAX-ACCESS read-only
			STATUS current
			DESCRIPTION
				"Number of neighbor recovery power changes
				
				XPath: /wing-stats/rf_domain[name=key1]/smart-rf/history_days/power_changes"
			::= { wingStatsRfdSmartRfHistoryDaysEntry 2 }

		
		-- 1.3.6.1.4.1.1916.2.131.50.1.4.3.5.14.1.3
		wingStatsRfdSmartRfHistoryDaysChannelChanges OBJECT-TYPE
			SYNTAX Unsigned32 (0..65535)
			MAX-ACCESS read-only
			STATUS current
			DESCRIPTION
				"Number of channel changes
				
				XPath: /wing-stats/rf_domain[name=key1]/smart-rf/history_days/channel_changes"
			::= { wingStatsRfdSmartRfHistoryDaysEntry 3 }

		
		-- 1.3.6.1.4.1.1916.2.131.50.1.4.3.5.14.1.4
		wingStatsRfdSmartRfHistoryDaysCoverageChanges OBJECT-TYPE
			SYNTAX Unsigned32 (0..65535)
			MAX-ACCESS read-only
			STATUS current
			DESCRIPTION
				"Number of coverage hole recovery power changes
				
				XPath: /wing-stats/rf_domain[name=key1]/smart-rf/history_days/coverage_changes"
			::= { wingStatsRfdSmartRfHistoryDaysEntry 4 }

		
		-- 1.3.6.1.4.1.1916.2.131.50.1.4.3.5.15
		wingStatsRfdSmartRfHistoryHoursTable OBJECT-TYPE
			SYNTAX SEQUENCE OF WingStatsRfdSmartRfHistoryHoursEntry
			MAX-ACCESS not-accessible
			STATUS current
			DESCRIPTION
				"
				
				/wing-stats/rf_domain/smart-rf/history_hours"
			::= { wingStatsRfdSmartRf 15 }

		
		-- 1.3.6.1.4.1.1916.2.131.50.1.4.3.5.15.1
		wingStatsRfdSmartRfHistoryHoursEntry OBJECT-TYPE
			SYNTAX WingStatsRfdSmartRfHistoryHoursEntry
			MAX-ACCESS not-accessible
			STATUS current
			DESCRIPTION
				"An entry in the table."
			INDEX { wingStatsRfdName }
			::= { wingStatsRfdSmartRfHistoryHoursTable 1 }

		
		WingStatsRfdSmartRfHistoryHoursEntry ::=
			SEQUENCE { 
				wingStatsRfdSmartRfHistoryHoursTime
					Unsigned32,
				wingStatsRfdSmartRfHistoryHoursPowerChanges
					Unsigned32,
				wingStatsRfdSmartRfHistoryHoursChannelChanges
					Unsigned32,
				wingStatsRfdSmartRfHistoryHoursCoverageChanges
					Unsigned32
			 }

		-- 1.3.6.1.4.1.1916.2.131.50.1.4.3.5.15.1.1
		wingStatsRfdSmartRfHistoryHoursTime OBJECT-TYPE
			SYNTAX Unsigned32
			MAX-ACCESS read-only
			STATUS current
			DESCRIPTION
				"
				
				XPath: /wing-stats/rf_domain[name=key1]/smart-rf/history_hours/time"
			::= { wingStatsRfdSmartRfHistoryHoursEntry 1 }

		
		-- 1.3.6.1.4.1.1916.2.131.50.1.4.3.5.15.1.2
		wingStatsRfdSmartRfHistoryHoursPowerChanges OBJECT-TYPE
			SYNTAX Unsigned32 (0..65535)
			MAX-ACCESS read-only
			STATUS current
			DESCRIPTION
				"Number of neighbor recovery power changes
				
				XPath: /wing-stats/rf_domain[name=key1]/smart-rf/history_hours/power_changes"
			::= { wingStatsRfdSmartRfHistoryHoursEntry 2 }

		
		-- 1.3.6.1.4.1.1916.2.131.50.1.4.3.5.15.1.3
		wingStatsRfdSmartRfHistoryHoursChannelChanges OBJECT-TYPE
			SYNTAX Unsigned32 (0..65535)
			MAX-ACCESS read-only
			STATUS current
			DESCRIPTION
				"Number of channel changes
				
				XPath: /wing-stats/rf_domain[name=key1]/smart-rf/history_hours/channel_changes"
			::= { wingStatsRfdSmartRfHistoryHoursEntry 3 }

		
		-- 1.3.6.1.4.1.1916.2.131.50.1.4.3.5.15.1.4
		wingStatsRfdSmartRfHistoryHoursCoverageChanges OBJECT-TYPE
			SYNTAX Unsigned32 (0..65535)
			MAX-ACCESS read-only
			STATUS current
			DESCRIPTION
				"Number of coverage hole recovery power changes
				
				XPath: /wing-stats/rf_domain[name=key1]/smart-rf/history_hours/coverage_changes"
			::= { wingStatsRfdSmartRfHistoryHoursEntry 4 }

		
		-- 1.3.6.1.4.1.1916.2.131.50.1.4.3.5.16
		wingStatsRfdSmartRfDashboardHistoryTable OBJECT-TYPE
			SYNTAX SEQUENCE OF WingStatsRfdSmartRfDashboardHistoryEntry
			MAX-ACCESS not-accessible
			STATUS current
			DESCRIPTION
				"
				
				/wing-stats/rf_domain/smart-rf/dashboard_history"
			::= { wingStatsRfdSmartRf 16 }

		
		-- 1.3.6.1.4.1.1916.2.131.50.1.4.3.5.16.1
		wingStatsRfdSmartRfDashboardHistoryEntry OBJECT-TYPE
			SYNTAX WingStatsRfdSmartRfDashboardHistoryEntry
			MAX-ACCESS not-accessible
			STATUS current
			DESCRIPTION
				"An entry in the table."
			INDEX { wingStatsRfdName }
			::= { wingStatsRfdSmartRfDashboardHistoryTable 1 }

		
		WingStatsRfdSmartRfDashboardHistoryEntry ::=
			SEQUENCE { 
				wingStatsRfdSmartRfDashboardHistoryDetails
					DisplayString,
				wingStatsRfdSmartRfDashboardHistoryPowerChanges
					Unsigned32,
				wingStatsRfdSmartRfDashboardHistoryChannelChanges
					Unsigned32,
				wingStatsRfdSmartRfDashboardHistoryCoverageChanges
					Unsigned32
			 }

		-- 1.3.6.1.4.1.1916.2.131.50.1.4.3.5.16.1.1
		wingStatsRfdSmartRfDashboardHistoryDetails OBJECT-TYPE
			SYNTAX DisplayString
			MAX-ACCESS read-only
			STATUS current
			DESCRIPTION
				"
				
				Values:
				current_hour,
				last_hour,
				last_24_hours,
				last_7_days
				
				XPath: /wing-stats/rf_domain[name=key1]/smart-rf/dashboard_history/details"
			::= { wingStatsRfdSmartRfDashboardHistoryEntry 1 }

		
		-- 1.3.6.1.4.1.1916.2.131.50.1.4.3.5.16.1.2
		wingStatsRfdSmartRfDashboardHistoryPowerChanges OBJECT-TYPE
			SYNTAX Unsigned32 (0..65535)
			MAX-ACCESS read-only
			STATUS current
			DESCRIPTION
				"Number of neighbor recovery power changes
				
				XPath: /wing-stats/rf_domain[name=key1]/smart-rf/dashboard_history/power_changes"
			::= { wingStatsRfdSmartRfDashboardHistoryEntry 2 }

		
		-- 1.3.6.1.4.1.1916.2.131.50.1.4.3.5.16.1.3
		wingStatsRfdSmartRfDashboardHistoryChannelChanges OBJECT-TYPE
			SYNTAX Unsigned32 (0..65535)
			MAX-ACCESS read-only
			STATUS current
			DESCRIPTION
				"Number of channel changes
				
				XPath: /wing-stats/rf_domain[name=key1]/smart-rf/dashboard_history/channel_changes"
			::= { wingStatsRfdSmartRfDashboardHistoryEntry 3 }

		
		-- 1.3.6.1.4.1.1916.2.131.50.1.4.3.5.16.1.4
		wingStatsRfdSmartRfDashboardHistoryCoverageChanges OBJECT-TYPE
			SYNTAX Unsigned32 (0..65535)
			MAX-ACCESS read-only
			STATUS current
			DESCRIPTION
				"Number of coverage hole recovery power changes
				
				XPath: /wing-stats/rf_domain[name=key1]/smart-rf/dashboard_history/coverage_changes"
			::= { wingStatsRfdSmartRfDashboardHistoryEntry 4 }

		
		-- 1.3.6.1.4.1.1916.2.131.50.1.4.3.5.17
		wingStatsRfdSmartRfCalibrateResultTable OBJECT-TYPE
			SYNTAX SEQUENCE OF WingStatsRfdSmartRfCalibrateResultEntry
			MAX-ACCESS not-accessible
			STATUS current
			DESCRIPTION
				"
				
				/wing-stats/rf_domain/smart-rf/calibration_result"
			::= { wingStatsRfdSmartRf 17 }

		
		-- 1.3.6.1.4.1.1916.2.131.50.1.4.3.5.17.1
		wingStatsRfdSmartRfCalibrateResultEntry OBJECT-TYPE
			SYNTAX WingStatsRfdSmartRfCalibrateResultEntry
			MAX-ACCESS not-accessible
			STATUS current
			DESCRIPTION
				"An entry in the table."
			INDEX { wingStatsRfdName, wingStatsRfdSmartRfCalibrateResultMac }
			::= { wingStatsRfdSmartRfCalibrateResultTable 1 }

		
		WingStatsRfdSmartRfCalibrateResultEntry ::=
			SEQUENCE { 
				wingStatsRfdSmartRfCalibrateResultMac
					WingIdentifier,
				wingStatsRfdSmartRfCalibrateResultResultMac
					DisplayString,
				wingStatsRfdSmartRfCalibrateResultApMac
					DisplayString,
				wingStatsRfdSmartRfCalibrateResultChannel
					DisplayString,
				wingStatsRfdSmartRfCalibrateResultOldChannel
					DisplayString,
				wingStatsRfdSmartRfCalibrateResultPower
					Unsigned32,
				wingStatsRfdSmartRfCalibrateResultOldPower
					Unsigned32,
				wingStatsRfdSmartRfCalibrateResultRadioIdx
					Unsigned32,
				wingStatsRfdSmartRfCalibrateResultState
					DisplayString,
				wingStatsRfdSmartRfCalibrateResultType
					DisplayString,
				wingStatsRfdSmartRfCalibrateResultSmartSensor
					TruthValue
			 }

		-- 1.3.6.1.4.1.1916.2.131.50.1.4.3.5.17.1.1
		wingStatsRfdSmartRfCalibrateResultMac OBJECT-TYPE
			SYNTAX WingIdentifier
			MAX-ACCESS read-only
			STATUS current
			DESCRIPTION
				"Radio mac address
				
				XPath: /wing-stats/rf_domain[name=key1]/smart-rf/calibration_result[mac=key2]/mac"
			::= { wingStatsRfdSmartRfCalibrateResultEntry 1 }

		
		-- 1.3.6.1.4.1.1916.2.131.50.1.4.3.5.17.1.3
		wingStatsRfdSmartRfCalibrateResultResultMac OBJECT-TYPE
			SYNTAX DisplayString
			MAX-ACCESS read-only
			STATUS current
			DESCRIPTION
				"Radio MAC address
				
				XPath: /wing-stats/rf_domain[name=key1]/smart-rf/calibration_result[mac=key2]/result/mac"
			::= { wingStatsRfdSmartRfCalibrateResultEntry 3 }

		
		-- 1.3.6.1.4.1.1916.2.131.50.1.4.3.5.17.1.4
		wingStatsRfdSmartRfCalibrateResultApMac OBJECT-TYPE
			SYNTAX DisplayString
			MAX-ACCESS read-only
			STATUS current
			DESCRIPTION
				"Access point MAC address in which this radio is present
				
				XPath: /wing-stats/rf_domain[name=key1]/smart-rf/calibration_result[mac=key2]/result/ap_mac"
			::= { wingStatsRfdSmartRfCalibrateResultEntry 4 }

		
		-- 1.3.6.1.4.1.1916.2.131.50.1.4.3.5.17.1.5
		wingStatsRfdSmartRfCalibrateResultChannel OBJECT-TYPE
			SYNTAX DisplayString
			MAX-ACCESS read-only
			STATUS current
			DESCRIPTION
				"Smart-rf assigned radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/calibration_result[mac=key2]/result/channel"
			::= { wingStatsRfdSmartRfCalibrateResultEntry 5 }

		
		-- 1.3.6.1.4.1.1916.2.131.50.1.4.3.5.17.1.6
		wingStatsRfdSmartRfCalibrateResultOldChannel OBJECT-TYPE
			SYNTAX DisplayString
			MAX-ACCESS read-only
			STATUS current
			DESCRIPTION
				"Original radio channel
				
				Values:
				1,
				1+,
				2,
				2+,
				3,
				3+,
				4,
				4+,
				5,
				5+,
				5-,
				6,
				6+,
				6-,
				7,
				7+,
				7-,
				8,
				8+,
				8-,
				9,
				9+,
				9-,
				10,
				10-,
				11,
				11-,
				12,
				12-,
				13,
				13-,
				14,
				36,
				36+,
				40,
				40-,
				44,
				44+,
				48,
				48-,
				52,
				52+,
				56,
				56-,
				60,
				60+,
				64,
				64-,
				100,
				100+,
				104,
				104-,
				108,
				108+,
				112,
				112-,
				116,
				116+,
				120,
				120-,
				124,
				124+,
				128,
				128-,
				132,
				132+,
				136,
				136-,
				140,
				149,
				149+,
				153,
				153-,
				157,
				157+,
				161,
				161-,
				165,
				34,
				38,
				42,
				46
				
				XPath: /wing-stats/rf_domain[name=key1]/smart-rf/calibration_result[mac=key2]/result/old_channel"
			::= { wingStatsRfdSmartRfCalibrateResultEntry 6 }

		
		-- 1.3.6.1.4.1.1916.2.131.50.1.4.3.5.17.1.7
		wingStatsRfdSmartRfCalibrateResultPower OBJECT-TYPE
			SYNTAX Unsigned32 (0..23)
			UNITS "dBm"
			MAX-ACCESS read-only
			STATUS current
			DESCRIPTION
				"Smart-rf assigned transmit power for this radio
				
				XPath: /wing-stats/rf_domain[name=key1]/smart-rf/calibration_result[mac=key2]/result/power"
			::= { wingStatsRfdSmartRfCalibrateResultEntry 7 }

		
		-- 1.3.6.1.4.1.1916.2.131.50.1.4.3.5.17.1.8
		wingStatsRfdSmartRfCalibrateResultOldPower OBJECT-TYPE
			SYNTAX Unsigned32 (0..23)
			UNITS "dBm"
			MAX-ACCESS read-only
			STATUS current
			DESCRIPTION
				"Original transmit power for this radio
				
				XPath: /wing-stats/rf_domain[name=key1]/smart-rf/calibration_result[mac=key2]/result/old_power"
			::= { wingStatsRfdSmartRfCalibrateResultEntry 8 }

		
		-- 1.3.6.1.4.1.1916.2.131.50.1.4.3.5.17.1.9
		wingStatsRfdSmartRfCalibrateResultRadioIdx OBJECT-TYPE
			SYNTAX Unsigned32
			MAX-ACCESS read-only
			STATUS current
			DESCRIPTION
				"Radio index of this radio in AP
				
				XPath: /wing-stats/rf_domain[name=key1]/smart-rf/calibration_result[mac=key2]/result/radio_idx"
			::= { wingStatsRfdSmartRfCalibrateResultEntry 9 }

		
		-- 1.3.6.1.4.1.1916.2.131.50.1.4.3.5.17.1.10
		wingStatsRfdSmartRfCalibrateResultState OBJECT-TYPE
			SYNTAX DisplayString
			MAX-ACCESS read-only
			STATUS current
			DESCRIPTION
				"Current radio state
				
				Values:
				offline,
				normal,
				sensor
				
				XPath: /wing-stats/rf_domain[name=key1]/smart-rf/calibration_result[mac=key2]/result/state"
			::= { wingStatsRfdSmartRfCalibrateResultEntry 10 }

		
		-- 1.3.6.1.4.1.1916.2.131.50.1.4.3.5.17.1.11
		wingStatsRfdSmartRfCalibrateResultType OBJECT-TYPE
			SYNTAX DisplayString
			MAX-ACCESS read-only
			STATUS current
			DESCRIPTION
				"Radio type
				
				Values:
				11an,
				11bgn
				
				XPath: /wing-stats/rf_domain[name=key1]/smart-rf/calibration_result[mac=key2]/result/type"
			::= { wingStatsRfdSmartRfCalibrateResultEntry 11 }

		
		-- 1.3.6.1.4.1.1916.2.131.50.1.4.3.5.17.1.12
		wingStatsRfdSmartRfCalibrateResultSmartSensor OBJECT-TYPE
			SYNTAX TruthValue
			MAX-ACCESS read-only
			STATUS current
			DESCRIPTION
				"Has smart-rf assigned this radio as sensor
				
				XPath: /wing-stats/rf_domain[name=key1]/smart-rf/calibration_result[mac=key2]/result/smart_sensor"
			::= { wingStatsRfdSmartRfCalibrateResultEntry 12 }

		
		-- 1.3.6.1.4.1.1916.2.131.50.1.5
		wingAction OBJECT IDENTIFIER ::= { wingObjects 5 }

		
-- Copy from one file to another.
		-- 1.3.6.1.4.1.1916.2.131.50.1.5.1
		wingActionFileCopy OBJECT IDENTIFIER ::= { wingAction 1 }

		
-- Input objects for action.
		-- 1.3.6.1.4.1.1916.2.131.50.1.5.1.1
		wingActionFileCopyIn OBJECT IDENTIFIER ::= { wingActionFileCopy 1 }

		
		-- 1.3.6.1.4.1.1916.2.131.50.1.5.1.1.1
		wingActionFileCopyInMac OBJECT-TYPE
			SYNTAX MacAddress
			MAX-ACCESS read-write
			STATUS current
			DESCRIPTION
				"Mac address of the device."
			::= { wingActionFileCopyIn 1 }

		
		-- 1.3.6.1.4.1.1916.2.131.50.1.5.1.1.2
		wingActionFileCopyInFrom OBJECT-TYPE
			SYNTAX DisplayString
			MAX-ACCESS read-write
			STATUS current
			DESCRIPTION
				"File or URL from which to copy.
				
				Files: flash:/path/file
				       nvram:startup-config
				       system:running-config
				
				URLs:  tftp://<hostname|IP>[:port]/path/file
				       ftp://<user>:<passwd>@<hostname|IP>[:port]/path/file
				       sftp://<user>:<passwd>@<hostname|IP>[:port]>/path/file
				       http://<hostname|IP>[:port]/path/file"
			::= { wingActionFileCopyIn 2 }

		
		-- 1.3.6.1.4.1.1916.2.131.50.1.5.1.1.3
		wingActionFileCopyInTo OBJECT-TYPE
			SYNTAX DisplayString
			MAX-ACCESS read-write
			STATUS current
			DESCRIPTION
				"File or URL to which to copy.
				
				Files: flash:/path/file
				       nvram:startup-config
				       system:running-config
				
				URLs:  tftp://<hostname|IP>[:port]/path/file
				       ftp://<user>:<passwd>@<hostname|IP>[:port]/path/file
				       sftp://<user>:<passwd>@<hostname|IP>[:port]>/path/file
				       http://<hostname|IP>[:port]/path/file"
			::= { wingActionFileCopyIn 3 }

		
-- Output objects for action.
		-- 1.3.6.1.4.1.1916.2.131.50.1.5.1.2
		wingActionFileCopyOut OBJECT IDENTIFIER ::= { wingActionFileCopy 2 }

		
		-- 1.3.6.1.4.1.1916.2.131.50.1.5.1.2.1
		wingActionFileCopyOutStatus OBJECT-TYPE
			SYNTAX TruthValue
			MAX-ACCESS read-only
			STATUS current
			DESCRIPTION
				"Whether the action is successful."
			::= { wingActionFileCopyOut 1 }

		
		-- 1.3.6.1.4.1.1916.2.131.50.1.5.1.2.2
		wingActionFileCopyOutMessage OBJECT-TYPE
			SYNTAX DisplayString
			MAX-ACCESS read-only
			STATUS current
			DESCRIPTION
				"Error message if the action is not successful."
			::= { wingActionFileCopyOut 2 }

		
		-- 1.3.6.1.4.1.1916.2.131.50.1.5.1.3
		wingActionFileCopyRun OBJECT-TYPE
			SYNTAX WingDoActionNow
			MAX-ACCESS read-write
			STATUS current
			DESCRIPTION
				"Run action that copies from one file to another."
			::= { wingActionFileCopy 3 }

		
-- File Configuration Checksum
		-- 1.3.6.1.4.1.1916.2.131.50.1.5.2
		wingActionFileMD5sum OBJECT IDENTIFIER ::= { wingAction 2 }

		
-- Input objects for action.
		-- 1.3.6.1.4.1.1916.2.131.50.1.5.2.1
		wingActionFileMD5sumIn OBJECT IDENTIFIER ::= { wingActionFileMD5sum 1 }

		
		-- 1.3.6.1.4.1.1916.2.131.50.1.5.2.1.1
		wingActionFileMD5sumInMac OBJECT-TYPE
			SYNTAX MacAddress
			MAX-ACCESS read-write
			STATUS current
			DESCRIPTION
				"Mac address of the device."
			::= { wingActionFileMD5sumIn 1 }

		
		-- 1.3.6.1.4.1.1916.2.131.50.1.5.2.1.2
		wingActionFileMD5sumInPath OBJECT-TYPE
			SYNTAX DisplayString
			MAX-ACCESS read-write
			STATUS current
			DESCRIPTION
				"Local file path
				
				Files: flash:/path/file
				             nvram:startup-config
				             system:running-config"
			::= { wingActionFileMD5sumIn 2 }

		
-- Output objects for action.
		-- 1.3.6.1.4.1.1916.2.131.50.1.5.2.2
		wingActionFileMD5sumOut OBJECT IDENTIFIER ::= { wingActionFileMD5sum 2 }

		
		-- 1.3.6.1.4.1.1916.2.131.50.1.5.2.2.1
		wingActionFileMD5sumOutStatus OBJECT-TYPE
			SYNTAX TruthValue
			MAX-ACCESS read-only
			STATUS current
			DESCRIPTION
				"Whether the action is successful."
			::= { wingActionFileMD5sumOut 1 }

		
		-- 1.3.6.1.4.1.1916.2.131.50.1.5.2.2.2
		wingActionFileMD5sumOutMessage OBJECT-TYPE
			SYNTAX DisplayString
			MAX-ACCESS read-only
			STATUS current
			DESCRIPTION
				"MD5 sum on success or Error message if the action is not successful."
			::= { wingActionFileMD5sumOut 2 }

		
		-- 1.3.6.1.4.1.1916.2.131.50.1.5.2.3
		wingActionFileMD5sumRun OBJECT-TYPE
			SYNTAX WingDoActionNow
			MAX-ACCESS read-write
			STATUS current
			DESCRIPTION
				"Run action that compute checksum of file"
			::= { wingActionFileMD5sum 3 }

		
-- Disassociate Client 
		-- 1.3.6.1.4.1.1916.2.131.50.1.5.3
		wingActionDisassociateClient OBJECT IDENTIFIER ::= { wingAction 3 }

		
-- Input objects for action.
		-- 1.3.6.1.4.1.1916.2.131.50.1.5.3.1
		wingActionDisassociateClientIn OBJECT IDENTIFIER ::= { wingActionDisassociateClient 1 }

		
		-- 1.3.6.1.4.1.1916.2.131.50.1.5.3.1.1
		wingActionDisassociateClientInRfDomainName OBJECT-TYPE
			SYNTAX DisplayString
			MAX-ACCESS read-write
			STATUS current
			DESCRIPTION
				"RF domain name.
				
				"
			::= { wingActionDisassociateClientIn 1 }

		
-- Input objects Choice for action either Client Mac or Wlan Name.
		-- 1.3.6.1.4.1.1916.2.131.50.1.5.3.1.2
		wingActionDisassociateClientInWlanNameORClientMac OBJECT IDENTIFIER ::= { wingActionDisassociateClientIn 2 }

		
		-- 1.3.6.1.4.1.1916.2.131.50.1.5.3.1.2.1
		wingActionDisassociateClientInMac OBJECT-TYPE
			SYNTAX MacAddress
			MAX-ACCESS read-write
			STATUS current
			DESCRIPTION
				"wireless client mac-addresss, or string * to disassociate all clients in this rf-domain."
			::= { wingActionDisassociateClientInWlanNameORClientMac 1 }

		
		-- 1.3.6.1.4.1.1916.2.131.50.1.5.3.1.2.2
		wingActionDisassociateClientInWlanName OBJECT-TYPE
			SYNTAX DisplayString
			MAX-ACCESS read-write
			STATUS current
			DESCRIPTION
				"All wireless clients on the wlan would be disassociated,
				client_mac, if present, would be ignored."
			::= { wingActionDisassociateClientInWlanNameORClientMac 2 }

		
-- Output objects for action.
		-- 1.3.6.1.4.1.1916.2.131.50.1.5.3.2
		wingActionDisassociateClientOut OBJECT IDENTIFIER ::= { wingActionDisassociateClient 2 }

		
		-- 1.3.6.1.4.1.1916.2.131.50.1.5.3.2.1
		wingActionDisassociateClientOutStatus OBJECT-TYPE
			SYNTAX TruthValue
			MAX-ACCESS read-only
			STATUS current
			DESCRIPTION
				"Whether the action is successful."
			::= { wingActionDisassociateClientOut 1 }

		
		-- 1.3.6.1.4.1.1916.2.131.50.1.5.3.2.2
		wingActionDisassociateClientOutMessage OBJECT-TYPE
			SYNTAX DisplayString
			MAX-ACCESS read-only
			STATUS current
			DESCRIPTION
				"Detailed error message when requested action failed."
			::= { wingActionDisassociateClientOut 2 }

		
		-- 1.3.6.1.4.1.1916.2.131.50.1.5.3.3
		wingActionDisassociateClientRun OBJECT-TYPE
			SYNTAX WingDoActionNow
			MAX-ACCESS read-write
			STATUS current
			DESCRIPTION
				"Run action that disassociate client."
			::= { wingActionDisassociateClient 3 }

		
-- Halt and perform a warm reboot.
		-- 1.3.6.1.4.1.1916.2.131.50.1.5.4
		wingActionReload OBJECT IDENTIFIER ::= { wingAction 4 }

		
-- Input objects for action.
		-- 1.3.6.1.4.1.1916.2.131.50.1.5.4.1
		wingActionReloadIn OBJECT IDENTIFIER ::= { wingActionReload 1 }

		
		-- 1.3.6.1.4.1.1916.2.131.50.1.5.4.1.1
		wingActionReloadInMac OBJECT-TYPE
			SYNTAX MacAddress
			MAX-ACCESS read-write
			STATUS current
			DESCRIPTION
				"Mac address of the device."
			::= { wingActionReloadIn 1 }

		
		-- 1.3.6.1.4.1.1916.2.131.50.1.5.4.1.2
		wingActionReloadInForce OBJECT-TYPE
			SYNTAX TruthValue
			MAX-ACCESS read-write
			STATUS current
			DESCRIPTION
				"Force reboot ignoring conditions like upgrade in progress,
				unsaved changes etc.
				
				The default value of this object is false."
			::= { wingActionReloadIn 2 }

		
		-- 1.3.6.1.4.1.1916.2.131.50.1.5.4.1.3
		wingActionReloadInTimeout OBJECT-TYPE
			SYNTAX Unsigned32 (1..999)
			UNITS "minutes"
			MAX-ACCESS read-write
			STATUS current
			DESCRIPTION
				"Delay before reload (minutes).
				
				The default delay is 2 minutes."
			::= { wingActionReloadIn 3 }

		
		-- 1.3.6.1.4.1.1916.2.131.50.1.5.4.1.4
		wingActionReloadInReason OBJECT-TYPE
			SYNTAX DisplayString
			MAX-ACCESS read-write
			STATUS current
			DESCRIPTION
				"Reason for reload. This is printed on the serial console
				prior to reloading."
			::= { wingActionReloadIn 4 }

		
-- Output objects for action.
		-- 1.3.6.1.4.1.1916.2.131.50.1.5.4.2
		wingActionReloadOut OBJECT IDENTIFIER ::= { wingActionReload 2 }

		
		-- 1.3.6.1.4.1.1916.2.131.50.1.5.4.2.1
		wingActionReloadOutStatus OBJECT-TYPE
			SYNTAX TruthValue
			MAX-ACCESS read-only
			STATUS current
			DESCRIPTION
				"Whether the action is successful."
			::= { wingActionReloadOut 1 }

		
		-- 1.3.6.1.4.1.1916.2.131.50.1.5.4.2.2
		wingActionReloadOutMessage OBJECT-TYPE
			SYNTAX DisplayString
			MAX-ACCESS read-only
			STATUS current
			DESCRIPTION
				"Error message if the action is not successful."
			::= { wingActionReloadOut 2 }

		
		-- 1.3.6.1.4.1.1916.2.131.50.1.5.4.3
		wingActionReloadRun OBJECT-TYPE
			SYNTAX WingDoActionNow
			MAX-ACCESS read-write
			STATUS current
			DESCRIPTION
				"Run action that halts and performs a warm reboot."
			::= { wingActionReload 3 }

		
-- Re elect tunnel controller for this AP or this group of APs.
		-- 1.3.6.1.4.1.1916.2.131.50.1.5.5
		wingActionReElectTunnelController OBJECT IDENTIFIER ::= { wingAction 5 }

		
-- Input objects for action.
		-- 1.3.6.1.4.1.1916.2.131.50.1.5.5.1
		wingActionReElectTunnelControllerIn OBJECT IDENTIFIER ::= { wingActionReElectTunnelController 1 }

		
		-- 1.3.6.1.4.1.1916.2.131.50.1.5.5.1.1
		wingActionReElectTunnelControllerInMac OBJECT-TYPE
			SYNTAX MacAddress
			MAX-ACCESS read-write
			STATUS current
			DESCRIPTION
				"AP whose mac matches will re-elect it's tunnel controller."
			::= { wingActionReElectTunnelControllerIn 1 }

		
		-- 1.3.6.1.4.1.1916.2.131.50.1.5.5.1.2
		wingActionReElectTunnelControllerInName OBJECT-TYPE
			SYNTAX DisplayString
			MAX-ACCESS read-write
			STATUS current
			DESCRIPTION
				"all APs whose tunnel controller name matches will re-elect their tunnel controller."
			::= { wingActionReElectTunnelControllerIn 2 }

		
-- Output objects for action.
		-- 1.3.6.1.4.1.1916.2.131.50.1.5.5.2
		wingActionReElectTunnelControllerOut OBJECT IDENTIFIER ::= { wingActionReElectTunnelController 2 }

		
		-- 1.3.6.1.4.1.1916.2.131.50.1.5.5.2.1
		wingActionReElectTunnelControllerOutStatus OBJECT-TYPE
			SYNTAX TruthValue
			MAX-ACCESS read-only
			STATUS current
			DESCRIPTION
				"Whether the action is successful."
			::= { wingActionReElectTunnelControllerOut 1 }

		
		-- 1.3.6.1.4.1.1916.2.131.50.1.5.5.2.2
		wingActionReElectTunnelControllerOutMessage OBJECT-TYPE
			SYNTAX DisplayString
			MAX-ACCESS read-only
			STATUS current
			DESCRIPTION
				"Error message if the action is not successful."
			::= { wingActionReElectTunnelControllerOut 2 }

		
		-- 1.3.6.1.4.1.1916.2.131.50.1.5.5.3
		wingActionReElectTunnelControllerRun OBJECT-TYPE
			SYNTAX WingDoActionNow
			MAX-ACCESS read-write
			STATUS current
			DESCRIPTION
				"Run action for Re elect tunnel controller for this AP or this group of APs."
			::= { wingActionReElectTunnelController 3 }

		
-- Action clears the current state of OSPF process and re-initializes it.
		-- 1.3.6.1.4.1.1916.2.131.50.1.5.6
		wingActionClearIpOspf OBJECT IDENTIFIER ::= { wingAction 6 }

		
-- Input objects for action.
		-- 1.3.6.1.4.1.1916.2.131.50.1.5.6.1
		wingActionClearIpOspfIn OBJECT IDENTIFIER ::= { wingActionClearIpOspf 1 }

		
		-- 1.3.6.1.4.1.1916.2.131.50.1.5.6.1.1
		wingActionClearIpOspfInMac OBJECT-TYPE
			SYNTAX MacAddress
			MAX-ACCESS read-write
			STATUS current
			DESCRIPTION
				"Device whose mac matches will restart its OSPF process."
			::= { wingActionClearIpOspfIn 1 }

		
-- Output objects for action.
		-- 1.3.6.1.4.1.1916.2.131.50.1.5.6.2
		wingActionClearIpOspfOut OBJECT IDENTIFIER ::= { wingActionClearIpOspf 2 }

		
		-- 1.3.6.1.4.1.1916.2.131.50.1.5.6.2.1
		wingActionClearIpOspfOutStatus OBJECT-TYPE
			SYNTAX TruthValue
			MAX-ACCESS read-only
			STATUS current
			DESCRIPTION
				"Whether the action is successful."
			::= { wingActionClearIpOspfOut 1 }

		
		-- 1.3.6.1.4.1.1916.2.131.50.1.5.6.2.2
		wingActionClearIpOspfOutMessage OBJECT-TYPE
			SYNTAX DisplayString
			MAX-ACCESS read-only
			STATUS current
			DESCRIPTION
				"Error message if the action is not successful."
			::= { wingActionClearIpOspfOut 2 }

		
		-- 1.3.6.1.4.1.1916.2.131.50.1.5.6.3
		wingActionClearIpOspfRun OBJECT-TYPE
			SYNTAX WingDoActionNow
			MAX-ACCESS read-write
			STATUS current
			DESCRIPTION
				"Run action to clear the current state of OSPF process and re-initializes it."
			::= { wingActionClearIpOspf 3 }

		
-- vrrp action group
		-- 1.3.6.1.4.1.1916.2.131.50.1.5.7
		wingActionVrrp OBJECT IDENTIFIER ::= { wingAction 7 }

		
-- Action clears the vrrp router statistics and re-initializes it
		-- 1.3.6.1.4.1.1916.2.131.50.1.5.7.1
		wingActionClearVrrpRouterStats OBJECT IDENTIFIER ::= { wingActionVrrp 1 }

		
-- Input objects for action.
		-- 1.3.6.1.4.1.1916.2.131.50.1.5.7.1.1
		wingActionClearVrrpRouterStatsIn OBJECT IDENTIFIER ::= { wingActionClearVrrpRouterStats 1 }

		
		-- 1.3.6.1.4.1.1916.2.131.50.1.5.7.1.1.1
		wingActionClearVrrpRouterStatsInMac OBJECT-TYPE
			SYNTAX MacAddress
			MAX-ACCESS read-write
			STATUS current
			DESCRIPTION
				"Mac address of the device."
			::= { wingActionClearVrrpRouterStatsIn 1 }

		
-- Output objects for action.
		-- 1.3.6.1.4.1.1916.2.131.50.1.5.7.1.2
		wingActionClearVrrpRouterStatsOut OBJECT IDENTIFIER ::= { wingActionClearVrrpRouterStats 2 }

		
		-- 1.3.6.1.4.1.1916.2.131.50.1.5.7.1.2.1
		wingActionClearVrrpRouterStatsOutStatus OBJECT-TYPE
			SYNTAX TruthValue
			MAX-ACCESS read-only
			STATUS current
			DESCRIPTION
				"Whether the action is successful."
			::= { wingActionClearVrrpRouterStatsOut 1 }

		
		-- 1.3.6.1.4.1.1916.2.131.50.1.5.7.1.2.2
		wingActionClearVrrpRouterStatsOutMessage OBJECT-TYPE
			SYNTAX DisplayString
			MAX-ACCESS read-only
			STATUS current
			DESCRIPTION
				"Error message if the action is not successful."
			::= { wingActionClearVrrpRouterStatsOut 2 }

		
		-- 1.3.6.1.4.1.1916.2.131.50.1.5.7.1.3
		wingActionClearVrrpRouterStatsRun OBJECT-TYPE
			SYNTAX WingDoActionNow
			MAX-ACCESS read-write
			STATUS current
			DESCRIPTION
				"Run action which clears the vrrp router statistics and re-initializes it."
			::= { wingActionClearVrrpRouterStats 3 }

		
-- Action clears the vrrp error statistics and re-initializes it.
		-- 1.3.6.1.4.1.1916.2.131.50.1.5.7.2
		wingActionClearVrrpGlobalErrStats OBJECT IDENTIFIER ::= { wingActionVrrp 2 }

		
-- Input objects for action.
		-- 1.3.6.1.4.1.1916.2.131.50.1.5.7.2.1
		wingActionClearVrrpGlobalErrStatsIn OBJECT IDENTIFIER ::= { wingActionClearVrrpGlobalErrStats 1 }

		
		-- 1.3.6.1.4.1.1916.2.131.50.1.5.7.2.1.1
		wingActionClearVrrpGlobalErrStatsInMac OBJECT-TYPE
			SYNTAX MacAddress
			MAX-ACCESS read-write
			STATUS current
			DESCRIPTION
				"Mac address of the device."
			::= { wingActionClearVrrpGlobalErrStatsIn 1 }

		
-- Output objects for action.
		-- 1.3.6.1.4.1.1916.2.131.50.1.5.7.2.2
		wingActionClearVrrpGlobalErrStatsOut OBJECT IDENTIFIER ::= { wingActionClearVrrpGlobalErrStats 2 }

		
		-- 1.3.6.1.4.1.1916.2.131.50.1.5.7.2.2.1
		wingActionClearVrrpGlobalErrStatsOutStatus OBJECT-TYPE
			SYNTAX TruthValue
			MAX-ACCESS read-only
			STATUS current
			DESCRIPTION
				"Whether the action is successful."
			::= { wingActionClearVrrpGlobalErrStatsOut 1 }

		
		-- 1.3.6.1.4.1.1916.2.131.50.1.5.7.2.2.2
		wingActionClearVrrpGlobalErrStatsOutMessage OBJECT-TYPE
			SYNTAX DisplayString
			MAX-ACCESS read-only
			STATUS current
			DESCRIPTION
				"Error message if the action is not successful."
			::= { wingActionClearVrrpGlobalErrStatsOut 2 }

		
		-- 1.3.6.1.4.1.1916.2.131.50.1.5.7.2.3
		wingActionClearVrrpGlobalErrStatsRun OBJECT-TYPE
			SYNTAX WingDoActionNow
			MAX-ACCESS read-write
			STATUS current
			DESCRIPTION
				"Run action which clears the vrrp error statistics and re-initializes it."
			::= { wingActionClearVrrpGlobalErrStats 3 }

		
-- l2tpv3 action group.
		-- 1.3.6.1.4.1.1916.2.131.50.1.5.8
		wingActionL2pv3 OBJECT IDENTIFIER ::= { wingAction 8 }

		
-- Action resets all or specified l2tpv3 tunnel.
		-- 1.3.6.1.4.1.1916.2.131.50.1.5.8.1
		wingActionClearL2tpv3Tunnel OBJECT IDENTIFIER ::= { wingActionL2pv3 1 }

		
-- Input objects for action.
		-- 1.3.6.1.4.1.1916.2.131.50.1.5.8.1.1
		wingActionClearL2tpv3TunnelIn OBJECT IDENTIFIER ::= { wingActionClearL2tpv3Tunnel 1 }

		
		-- 1.3.6.1.4.1.1916.2.131.50.1.5.8.1.1.1
		wingActionClearL2tpv3TunnelInMac OBJECT-TYPE
			SYNTAX MacAddress
			MAX-ACCESS read-write
			STATUS current
			DESCRIPTION
				"Device whose mac matches will have its specified L2TPv3 tunnel(s) reset."
			::= { wingActionClearL2tpv3TunnelIn 1 }

		
-- Output objects for action.
		-- 1.3.6.1.4.1.1916.2.131.50.1.5.8.1.2
		wingActionClearL2tpv3TunnelOut OBJECT IDENTIFIER ::= { wingActionClearL2tpv3Tunnel 2 }

		
		-- 1.3.6.1.4.1.1916.2.131.50.1.5.8.1.2.1
		wingActionClearL2tpv3TunnelOutStatus OBJECT-TYPE
			SYNTAX TruthValue
			MAX-ACCESS read-only
			STATUS current
			DESCRIPTION
				"Whether the action is successful."
			::= { wingActionClearL2tpv3TunnelOut 1 }

		
		-- 1.3.6.1.4.1.1916.2.131.50.1.5.8.1.2.2
		wingActionClearL2tpv3TunnelOutMessage OBJECT-TYPE
			SYNTAX DisplayString
			MAX-ACCESS read-only
			STATUS current
			DESCRIPTION
				"Error message if the action is not successful."
			::= { wingActionClearL2tpv3TunnelOut 2 }

		
		-- 1.3.6.1.4.1.1916.2.131.50.1.5.8.1.3
		wingActionClearL2tpv3TunnelRun OBJECT-TYPE
			SYNTAX WingDoActionNow
			MAX-ACCESS read-write
			STATUS current
			DESCRIPTION
				"Run action which resets all or specified l2tpv3 tunnel."
			::= { wingActionClearL2tpv3Tunnel 3 }

		
-- Action re-establishes a specified l2tpv3 tunnel
		-- 1.3.6.1.4.1.1916.2.131.50.1.5.8.2
		wingActionConnectL2tpv3Tunnel OBJECT IDENTIFIER ::= { wingActionL2pv3 2 }

		
-- Input objects for action.
		-- 1.3.6.1.4.1.1916.2.131.50.1.5.8.2.1
		wingActionConnectL2tpv3TunnelIn OBJECT IDENTIFIER ::= { wingActionConnectL2tpv3Tunnel 1 }

		
		-- 1.3.6.1.4.1.1916.2.131.50.1.5.8.2.1.1
		wingActionConnectL2tpv3TunnelInMac OBJECT-TYPE
			SYNTAX MacAddress
			MAX-ACCESS read-write
			STATUS current
			DESCRIPTION
				"Device whose mac matches will have its specified L2TPv3 tunnel re-established."
			::= { wingActionConnectL2tpv3TunnelIn 1 }

		
-- Output objects for action.
		-- 1.3.6.1.4.1.1916.2.131.50.1.5.8.2.2
		wingActionConnectL2tpv3TunnelOut OBJECT IDENTIFIER ::= { wingActionConnectL2tpv3Tunnel 2 }

		
		-- 1.3.6.1.4.1.1916.2.131.50.1.5.8.2.2.1
		wingActionConnectL2tpv3TunnelOutStatus OBJECT-TYPE
			SYNTAX TruthValue
			MAX-ACCESS read-only
			STATUS current
			DESCRIPTION
				"Whether the action is successful."
			::= { wingActionConnectL2tpv3TunnelOut 1 }

		
		-- 1.3.6.1.4.1.1916.2.131.50.1.5.8.2.2.2
		wingActionConnectL2tpv3TunnelOutMessage OBJECT-TYPE
			SYNTAX DisplayString
			MAX-ACCESS read-only
			STATUS current
			DESCRIPTION
				"Error message if the action is not successful."
			::= { wingActionConnectL2tpv3TunnelOut 2 }

		
		-- 1.3.6.1.4.1.1916.2.131.50.1.5.8.2.3
		wingActionConnectL2tpv3TunnelRun OBJECT-TYPE
			SYNTAX WingDoActionNow
			MAX-ACCESS read-write
			STATUS current
			DESCRIPTION
				"Run action which re-establishes a specified l2tpv3 tunnel."
			::= { wingActionConnectL2tpv3Tunnel 3 }

		
                -- 1.3.6.1.4.1.1916.2.131.50.1.5.9
                wingActionLocator OBJECT IDENTIFIER ::= { wingAction 9 }


                -- 1.3.6.1.4.1.1916.2.131.50.1.5.9.1
                wingActionLocatorOn OBJECT IDENTIFIER ::= { wingActionLocator 1 }


-- Input objects for action.
                -- 1.3.6.1.4.1.1916.2.131.50.1.5.9.1.1
                wingActionLocatorOnIn OBJECT IDENTIFIER ::= { wingActionLocatorOn 1 }


                -- 1.3.6.1.4.1.1916.2.131.50.1.5.9.1.1.1
                wingActionLocatorOnInDuration OBJECT-TYPE
                        SYNTAX Unsigned32
                        MAX-ACCESS read-write
                        STATUS current
                        DESCRIPTION
                                "Minutes to flash LEDs"
                        ::= { wingActionLocatorOnIn 1 }


                -- 1.3.6.1.4.1.1916.2.131.50.1.5.9.1.1.2
                wingActionLocatorOnInMac OBJECT-TYPE
                        SYNTAX MacAddress
                        MAX-ACCESS read-write
                        STATUS current
                        DESCRIPTION
                                "Mac address of the device."
                        ::= { wingActionLocatorOnIn 2 }


-- Output objects for action.
                -- 1.3.6.1.4.1.1916.2.131.50.1.5.9.1.2
                wingActionLocatorOnOut OBJECT IDENTIFIER ::= { wingActionLocatorOn 2 }


                -- 1.3.6.1.4.1.1916.2.131.50.1.5.9.1.2.1
                wingActionLocatorOnOutStatus OBJECT-TYPE
                        SYNTAX TruthValue
                        MAX-ACCESS read-only
                        STATUS current
                        DESCRIPTION
                                "Whether the action is successful."
                        ::= { wingActionLocatorOnOut 1 }


                -- 1.3.6.1.4.1.1916.2.131.50.1.5.9.1.2.2
                wingActionLocatorOnOutMessage OBJECT-TYPE
                        SYNTAX DisplayString
                        MAX-ACCESS read-only
                        STATUS current
                        DESCRIPTION
                                "Error message if the action is not successful."
                        ::= { wingActionLocatorOnOut 2 }


                -- 1.3.6.1.4.1.1916.2.131.50.1.5.9.1.3
                wingActionLocatorOnRun OBJECT-TYPE
                        SYNTAX WingDoActionNow
                        MAX-ACCESS read-write
                        STATUS current
                        DESCRIPTION
                                "Run action"
                        ::= { wingActionLocatorOn 3 }


                -- 1.3.6.1.4.1.1916.2.131.50.1.5.9.2
                wingActionLocatorOff OBJECT IDENTIFIER ::= { wingActionLocator 2 }


-- Input objects for action.
                -- 1.3.6.1.4.1.1916.2.131.50.1.5.9.2.1
                wingActionLocatorOffIn OBJECT IDENTIFIER ::= { wingActionLocatorOff 1 }


                -- 1.3.6.1.4.1.1916.2.131.50.1.5.9.2.1.1
                wingActionLocatorOffInMac OBJECT-TYPE
                        SYNTAX MacAddress
                        MAX-ACCESS read-write
                        STATUS current
                        DESCRIPTION
                                "Mac address of the device."
                        ::= { wingActionLocatorOffIn 1 }


-- Output objects for action.
                -- 1.3.6.1.4.1.1916.2.131.50.1.5.9.2.2
                wingActionLocatorOffOut OBJECT IDENTIFIER ::= { wingActionLocatorOff 2 }


                -- 1.3.6.1.4.1.1916.2.131.50.1.5.9.2.2.1
                wingActionLocatorOffOutStatus OBJECT-TYPE
                        SYNTAX TruthValue
                        MAX-ACCESS read-only
                        STATUS current
                        DESCRIPTION
                                "Whether the action is successful."
                        ::= { wingActionLocatorOffOut 1 }


                -- 1.3.6.1.4.1.1916.2.131.50.1.5.9.2.2.2
                wingActionLocatorOffOutMessage OBJECT-TYPE
                        SYNTAX DisplayString
                        MAX-ACCESS read-only
                        STATUS current
                        DESCRIPTION
                                "Error message if the action is not successful."
                        ::= { wingActionLocatorOffOut 2 }


                -- 1.3.6.1.4.1.1916.2.131.50.1.5.9.2.3
                wingActionLocatorOffRun OBJECT-TYPE
                        SYNTAX WingDoActionNow
                        MAX-ACCESS read-write
                        STATUS current
                        DESCRIPTION
                                "Run action"
                        ::= { wingActionLocatorOff 3 }

		
		-- 1.3.6.1.4.1.1916.2.131.50.2
		wingConformance OBJECT IDENTIFIER ::= { wingMIB 2 }

		
		-- 1.3.6.1.4.1.1916.2.131.50.2.1
		wingCompliances OBJECT IDENTIFIER ::= { wingConformance 1 }

		
		-- 1.3.6.1.4.1.1916.2.131.50.2.1.1
		wingCompliance MODULE-COMPLIANCE
			STATUS current
			DESCRIPTION 
				"The compliance statement for agents that support the WiNG MIB."
			MODULE -- this module
				MANDATORY-GROUPS { wingObjectGroup, wingNotificationGroup }
			::= { wingCompliances 1 }

		
		-- 1.3.6.1.4.1.1916.2.131.50.2.2
		wingGroups OBJECT IDENTIFIER ::= { wingConformance 2 }

		
		-- 1.3.6.1.4.1.1916.2.131.50.2.2.1
		wingObjectGroup OBJECT-GROUP
			OBJECTS { wingEventMnemonic, wingEventModule, wingEventSeverity, wingEventMsg, wingEventSourceAddr, 
				wingConfigSysMacAddr, wingStatsDevMac, wingStatsDevType, wingStatsDevHostname,
				wingStatsDevVersion, wingStatsDevSerialNo, wingStatsDevRfDomainName, wingStatsDevOnline,
				wingStatsDevAdoptDevMac, wingStatsDevAdoptDevType, wingStatsDevAdoptDevHostname,
				wingStatsDevAdoptDevVersion, wingStatsDevAdoptDevSerialNo, wingStatsDevAdoptDevRfDomainName,
				wingStatsDevAdoptDevOnline, wingStatsRfdName, wingStatsRfdManager, wingStatsRfdWlClientMac,
				wingStatsRfdWlClientMacName, wingStatsRfdWlClientVendor, wingStatsRfdWlClientBss,
				wingStatsRfdWlClientAp, wingStatsRfdWlClientRadioNum, wingStatsRfdWlClientRadioType,
				wingStatsRfdWlClientRadioEnc, wingStatsRfdWlClientRadioAuth, wingStatsRfdWlClientWlan,
				wingStatsRfdWlClientState, wingStatsRfdWlClientHotspotAuthed, wingStatsRfdWlClientVlan,
				wingStatsRfdWlClientUserName, wingStatsRfdWlClientIp, wingStatsRfdWlClientRfdName,
				wingStatsRfdWlClientHostname, wingStatsRfdWlClientLocation, wingStatsRfdWlClientRadioId,
				wingStatsRfdWlClientRadioAlias, wingStatsRfdWlApInfoMac, wingStatsRfdWlApInfoFaultDetected,
				wingStatsRfdWlApInfoNumRadios, wingStatsRfdWlApInfoNumClients, wingStatsRfdWlApInfoLastCalTime,
				wingStatsRfdWlApInfoType, wingStatsRfdWlApInfoStatsMode, wingStatsRfdWlApInfoStatsInterval,
				wingStatsRfdWlApInfoHostname, wingStatsRfdWlApInfoRfDomainName, wingStatsRfdWlApInfoLocation,
				wingStatsRfdWlApInfoAdoptedTo, wingStatsDevAdoptPendingDevMac, wingStatsDevAdoptPendingDevType,
				wingStatsDevAdoptPendingDevTarget, wingStatsDevAdoptPendingDevDisOption, wingStatsDevAdoptPendingDevVersion,
				wingStatsDevAdoptPendingDevSerialNumber, wingStatsDevAdoptPendingDevReason, wingStatsDevAdoptPendingDevNumRadios,
				wingStatsDevAdoptPendingDevIp, wingStatsDevAdoptPendingDevVlan, wingStatsRfdWlClientDetailMac,
				wingStatsRfdWlClientDetailMacName, wingStatsRfdWlClientDetailVendor, wingStatsRfdWlClientDetailBss,
				wingStatsRfdWlClientDetailAp, wingStatsRfdWlClientDetailRadioNum, wingStatsRfdWlClientDetailRadioType,
				wingStatsRfdWlClientDetailEnc, wingStatsRfdWlClientDetailAuth, wingStatsRfdWlClientDetailWlan,
				wingStatsRfdWlClientDetailState, wingStatsRfdWlClientDetailHotspotAuthed, wingStatsRfdWlClientDetailVlan,
				wingStatsRfdWlClientDetailUsername, wingStatsRfdWlClientDetailIp, wingStatsRfdWlClientDetailRfDomainName,
				wingStatsRfdWlClientDetailMc2ucStreams, wingStatsRfdWlClientDetailHostname, wingStatsRfdWlClientDetailLocation,
				wingStatsRfdWlClientDetailRadioId, wingStatsRfdWlClientDetailRadioAlias, wingStatsRfdWlClientDetailSsid,
				wingStatsRfdWlClientDetailAid, wingStatsRfdWlClientDetailRates, wingStatsRfdWlClientDetailInPsp,
				wingStatsRfdWlClientDetailIsWmm, wingStatsRfdWlClientDetailUapsd, wingStatsRfdWlClientDetailSmPowersave,
				wingStatsRfdWlClientDetailHtCapable, wingStatsRfdWlClientDetailShortGi, wingStatsRfdWlClientDetailCurWidth40,
				wingStatsRfdWlClientDetailAmsduSize, wingStatsRfdWlClientDetailAmpduSize, wingStatsRfdWlClientDetailAmpduSpacing,
				wingStatsRfdWlClientDetailRifs, wingStatsRfdWlClientDetailLastActive, wingStatsRfdWlClientDetailLastAssoc,
				wingStatsRfdWlClientDetailSessTime, wingStatsRfdWlClientDetailIdleTime, wingStatsRfdWlClientDetailMaxPhyRate,
				wingStatsRfdWlClientDetailMaxUserRate, wingStatsRfdWlClientDetailIsVoice, wingStatsRfdWlClientDetailIsCallActive,
				wingStatsRfdWlClientStatMac, wingStatsRfdWlClientStatMacName, wingStatsRfdWlClientStatVendor, wingStatsRfdWlClientStatAp,
				wingStatsRfdWlClientStatTxPkts, wingStatsRfdWlClientStatRxPkts, wingStatsRfdWlClientStatTxDropped,
				wingStatsRfdWlClientStatRxErrors, wingStatsRfdWlClientStatTIndex, wingStatsRfdWlClientStatTxBps,
				wingStatsRfdWlClientStatRxBps, wingStatsRfdWlClientStatSignal, wingStatsRfdWlClientStatNoise, wingStatsRfdWlClientStatSnr,
				wingStatsRfdWlClientStatTxRate, wingStatsRfdWlClientStatRxRate, wingStatsRfdWlClientStatErrorRate,
				wingStatsRfdWlClientStatQIndex, wingStatsRfdWlClientStatDetailMac, wingStatsRfdWlClientStatDetailMacName,
				wingStatsRfdWlClientStatDetailVendor, wingStatsRfdWlClientStatDetailTxPkts, wingStatsRfdWlClientStatDetailRxPkts,
				wingStatsRfdWlClientStatDetailTxDropped, wingStatsRfdWlClientStatDetailRxErrors, wingStatsRfdWlClientStatDetailTIndex,
				wingStatsRfdWlClientStatDetailTxBps, wingStatsRfdWlClientStatDetailRxBps, wingStatsRfdWlClientStatDetailSignal,
				wingStatsRfdWlClientStatDetailNoise, wingStatsRfdWlClientStatDetailSnr, wingStatsRfdWlClientStatDetailTxRate,
				wingStatsRfdWlClientStatDetailRxRate, wingStatsRfdWlClientStatDetailErrorRate, wingStatsRfdWlClientStatDetailQIndex,
				wingStatsRfdWlClientStatDetailRawTxPkts, wingStatsRfdWlClientStatDetailRawRxPkts, wingStatsRfdWlClientStatDetailRawTotalPkts,
				wingStatsRfdWlClientStatDetailRawTxBps, wingStatsRfdWlClientStatDetailRawRxBps, wingStatsRfdWlClientStatDetailRawTotalBps,
				wingStatsRfdWlClientStatDetailRawTxPps, wingStatsRfdWlClientStatDetailRawRxPps, wingStatsRfdWlClientStatDetailRawTotalPps,
				wingStatsRfdWlClientStatDetailRawTxRate, wingStatsRfdWlClientStatDetailRawRxRate, wingStatsRfdWlClientStatDetailRawOverallRate,
				wingStatsRfdWlClientStatDetailTxPps, wingStatsRfdWlClientStatDetailRxPps, wingStatsRfdWlClientStatDetailTotalPps,
				wingStatsRfdWlClientStatDetailRxProbes, wingStatsRfdWlClientStatDetailRxActions, wingStatsRfdWlClientStatDetailRxPsPoll,
				wingStatsRfdWlClientStatDetailLastCallStatus, wingStatsRfdWlClientStatDetailCallTotal, wingStatsRfdWlClientStatDetailCallStatOk,
				wingStatsRfdWlClientStatDetailCallStatBusy, wingStatsRfdWlClientStatDetailCallStatNoAnswer,
				wingStatsRfdWlClientStatDetailCallStatUnknownDest, wingStatsRfdWlClientStatDetailCallStatAdmDenied,
				wingStatsRfdWlClientStatDetailCallStatDeclined, wingStatsRfdWlClientStatDetailCallStatUnauth,
				wingStatsRfdWlClientStatDetailCallStatUnsuppMedia, wingStatsRfdWlClientStatDetailCallStatTempUnavail,
				wingStatsRfdWlClientStatDetailCallStatNoForkAllowed, wingStatsRfdWlClientStatDetailCallStatSessInactive,
				wingStatsRfdWlClientStatDetailCallStatOther, wingStatsRfdWlClientStatDetailTotalPkts, wingStatsDevWlClientMac,
				wingStatsDevWlClientMacName, wingStatsDevWlClientVendor, wingStatsDevWlClientBss, wingStatsDevWlClientAp, wingStatsDevWlClientRadioNum,
				wingStatsDevWlClientRadioType, wingStatsDevWlClientRadioEnc, wingStatsDevWlClientRadioAuth, wingStatsDevWlClientWlan,
				wingStatsDevWlClientState, wingStatsDevWlClientHotspotAuthed, wingStatsDevWlClientVlan, wingStatsDevWlClientUserName,
				wingStatsDevWlClientIp, wingStatsDevWlClientRfdName, wingStatsDevWlClientHostname, wingStatsDevWlClientLocation,
				wingStatsDevWlClientRadioId, wingStatsDevWlClientRadioAlias, wingStatsRfdWlRadioId, wingStatsRfdWlRadioDeviceMac,
				wingStatsRfdWlRadioAlias, wingStatsRfdWlRadioMac, wingStatsRfdWlRadioType, wingStatsRfdWlRadioHostname, wingStatsRfdWlRadioRfdName,
				wingStatsRfdWlRadioLocation, wingStatsRfdWlRadioState, wingStatsRfdWlRadioCurChannel, wingStatsRfdWlRadioConfigChannel,
				wingStatsRfdWlRadioCurPower, wingStatsRfdWlRadioConfigPower, wingStatsRfdWlRadioMaxUserRate, wingStatsRfdWlRadioNumClient,
				wingStatsRfdWlRadioStatId, wingStatsRfdWlRadioStatDeviceMac, wingStatsRfdWlRadioStatAlias, wingStatsRfdWlRadioStatMac,
				wingStatsRfdWlRadioStatType, wingStatsRfdWlRadioStatTxPkts, wingStatsRfdWlRadioStatRxPkts, wingStatsRfdWlRadioStatTxDropped,
				wingStatsRfdWlRadioStatRxErrors, wingStatsRfdWlRadioStatTIndex, wingStatsRfdWlRadioStatTxBps, wingStatsRfdWlRadioStatRxBps,
				wingStatsRfdWlRadioStatSignal, wingStatsRfdWlRadioStatNoise, wingStatsRfdWlRadioStatSnr, wingStatsRfdWlRadioStatTxRate,
				wingStatsRfdWlRadioStatRxRate, wingStatsRfdWlRadioStatErrorRate, wingStatsRfdWlRadioStatQIndex, wingStatsRfdWlRadioStatNumClients,
				wingStatsRfdWlRadioStatNumBClients, wingStatsRfdWlRadioStatNumBgClients, wingStatsRfdWlRadioStatNumBgnClients,
				wingStatsRfdWlRadioStatNumAClients, wingStatsRfdWlRadioStatNumAnClients, wingStatsRfdWlRadioStatMediumErrorRate,
				wingStatsRfdWlRadioDetailId, wingStatsRfdWlRadioDetailDeviceMac, wingStatsRfdWlRadioDetailAlias, wingStatsRfdWlRadioDetailMac,
				wingStatsRfdWlRadioDetailType, wingStatsRfdWlRadioDetailHostname, wingStatsRfdWlRadioDetailRfdName, wingStatsRfdWlRadioDetailLocation,
				wingStatsRfdWlRadioDetailState, wingStatsRfdWlRadioDetailCurChannel, wingStatsRfdWlRadioDetailConfigChannel,
				wingStatsRfdWlRadioDetailCurPower, wingStatsRfdWlRadioDetailConfigPower, wingStatsRfdWlRadioDetailMaxUserRate,
				wingStatsRfdWlRadioDetailNumClient, wingStatsRfdWlRadioDetailSpectrumMgmt, wingStatsRfdWlRadioDetailShortPreamble,
				wingStatsRfdWlRadioDetailNonErpPresent, wingStatsRfdWlRadioDetailErpProtectionOn, wingStatsRfdWlRadioDetailNonErpDetected,
				wingStatsRfdWlRadioDetailHtProtectionOn, wingStatsRfdWlRadioDetailHt20Present, wingStatsRfdWlRadioDetailNonHtDetected,
				wingStatsRfdWlRadioDetailDualChannelOn, wingStatsRfdWlRadioDetailTxAntennaUsed, wingStatsRfdWlRadioDetailRxAntennaUsed,
				wingStatsRfdWlRadioDetailMaxPhyRate, wingStatsRfdWlRadioDetailCurMcastStreams, wingStatsRfdWlRadioDetailMaxMcastStreams,
				wingStatsRfdWlRadioDetailMcastStreams, wingStatsRfdWlRadioDetailLastError, wingStatsRfdWlRadioStatDetailId,
				wingStatsRfdWlRadioStatDetailDeviceMac, wingStatsRfdWlRadioStatDetailAlias, wingStatsRfdWlRadioStatDetailMac,
				wingStatsRfdWlRadioStatDetailType, wingStatsRfdWlRadioStatDetailTxPkts, wingStatsRfdWlRadioStatDetailRxPkts,
				wingStatsRfdWlRadioStatDetailTxDropped, wingStatsRfdWlRadioStatDetailRxErrors, wingStatsRfdWlRadioStatDetailTIndex,
				wingStatsRfdWlRadioStatDetailTxBps, wingStatsRfdWlRadioStatDetailRxBps, wingStatsRfdWlRadioStatDetailSignal,
				wingStatsRfdWlRadioStatDetailNoise, wingStatsRfdWlRadioStatDetailSnr, wingStatsRfdWlRadioStatDetailTxRate,
				wingStatsRfdWlRadioStatDetailRxRate, wingStatsRfdWlRadioStatDetailErrorRate, wingStatsRfdWlRadioStatDetailQIndex,
				wingStatsRfdWlRadioStatDetailNumClients, wingStatsRfdWlRadioStatDetailNumBClients, wingStatsRfdWlRadioStatDetailNumBgClients,
				wingStatsRfdWlRadioStatDetailNumBgnClients, wingStatsRfdWlRadioStatDetailNumAClients, wingStatsRfdWlRadioStatDetailNumAnClients,
				wingStatsRfdWlRadioStatDetailMediumErrorRate, wingStatsRfdWlRadioStatDetailRawTxPkts, wingStatsRfdWlRadioStatDetailRawRxPkts,
				wingStatsRfdWlRadioStatDetailRawTotalPkts, wingStatsRfdWlRadioStatDetailRawTxBps, wingStatsRfdWlRadioStatDetailRawRxBps,
				wingStatsRfdWlRadioStatDetailRawTotalBps, wingStatsRfdWlRadioStatDetailRawTxPps, wingStatsRfdWlRadioStatDetailRawRxPps,
				wingStatsRfdWlRadioStatDetailRawTotalPps, wingStatsRfdWlRadioStatDetailRawTxRate, wingStatsRfdWlRadioStatDetailRawRxRate,
				wingStatsRfdWlRadioStatDetailRawOverallRate, wingStatsRfdWlRadioStatDetailTxPps, wingStatsRfdWlRadioStatDetailRxPps,
				wingStatsRfdWlRadioStatDetailTotalPps, wingStatsRfdWlRadioStatDetailRxProbes, wingStatsRfdWlRadioStatDetailRxActions,
				wingStatsRfdWlRadioStatDetailRxPsPoll, wingStatsRfdWlRadioStatDetailLastCallStatus, wingStatsRfdWlRadioStatDetailCallTotal,
				wingStatsRfdWlRadioStatDetailCallStatOk, wingStatsRfdWlRadioStatDetailCallStatBusy, wingStatsRfdWlRadioStatDetailCallStatNoAnswer,
				wingStatsRfdWlRadioStatDetailCallStatUnknownDest, wingStatsRfdWlRadioStatDetailCallStatAdmDenied,
				wingStatsRfdWlRadioStatDetailCallStatDeclined, wingStatsRfdWlRadioStatDetailCallStatUnauth,
				wingStatsRfdWlRadioStatDetailCallStatUnsuppMedia, wingStatsRfdWlRadioStatDetailCallStatTempUnavail,
				wingStatsRfdWlRadioStatDetailCallStatNoForkAllowed, wingStatsRfdWlRadioStatDetailCallStatSessInactive,
				wingStatsRfdWlRadioStatDetailCallStatOther, wingStatsRfdWlRadioStatDetailTotalPkts, wingStatsRfdWlRadioStatDetailRxCrcErrors,
				wingStatsRfdWlRadioStatDetailRxUndecryptable, wingStatsRfdWlRadioStatDetailRxIncomplete, wingStatsRfdWlRadioStatDetailRxLengthErrors,
				wingStatsRfdWlRadioStatDetailRxOtherErrors, wingStatsRfdWlRadioStatDetailLongPreambleClients, wingStatsRfdWlRadioStatDetailLtClients,
				wingStatsRfdWlRadioStatDetailHt20Clients, wingStatsRfdWlRadioStatDetailLongSlotClients, wingCfgWlanName, wingCfgWlanShutdown,
				wingCfgWlanSsid, wingCfgWlanDescr, wingCfgWlanEncType, wingCfgWlanAuthType, wingCfgWlanCaptivePortalEnforcement, wingCfgWlanClientPower,
				wingCfgWlanNasId, wingCfgWlanNasPortId, wingCfgWlanBroadcastSsid, wingCfgWlanAnswerBroadcastProbes, wingCfgWlanClientClientCommunication,
				wingCfgWlanHoldTime, wingCfgWlanInactivityTimeout, wingCfgWlanCredCacheAgeout, wingCfgWlanVlanCacheAgeout, wingCfgWlanMaxFirewallSessions,
				wingCfgWlanReauth, wingCfgWlanPmfMode, wingCfgWlanPmfSaQueryTimeout, wingCfgWlanPmfSaQueryAttempts, wingCfgWlanWpaWpa2Psk,
				wingCfgWlanWpaWpa2ExcludeWpa2Tkip, wingCfgWlanWpaWpa2KeyRotationUnicast, wingCfgWlanWpaWpa2KeyRotationBroadcast, wingCfgWlanWpaWpa2PmkCaching,
				wingCfgWlanWpaWpa2OpmkCaching, wingCfgWlanWpaWpa2Preauth, wingCfgWlanWpaWpa2TkipCntrmeasHoldTime, wingCfgWlanWep64TransmitKey,
				wingCfgWlanWep128TransmitKey, wingCfgWlanRadiusAssignedVlans, wingCfgWlanRadiusDynamicAuthorization,
				wingCfgWlanAccountingRadius, wingCfgWlanMotoExtnMoveCmd, wingCfgWlanMotoExtnSmartScan, wingCfgWlanMotoExtnWmmLoadBalance,
				wingCfgWlanMotoExtnSymbolLoadInfo, wingCfgWlanClientLoadBal, wingCfgWlanClientLoadBalSingleBandClients5ghz,
				wingCfgWlanClientLoadBalSingleBandClients24ghz, wingCfgWlanClientLoadBalMaxProbeReq24ghz, wingCfgWlanClientLoadBalMaxProbeReq5ghz,
				wingCfgWlanClientLoadBalProbeReqIntvl5ghz, wingCfgWlanClientLoadBalProbeReqIntvl24ghz, wingCfgWlanClientLoadBalBandDiscoveryIntvl,
				wingCfgWlanClientLoadBalCapabilityAgeoutTime, wingCfgWlanQosPolicy, wingCfgWlanAaaPolicy, wingCfgWlanCaptivePortal, wingCfgWlanAssocAcl,
				wingCfgWlanIpInAcl, wingCfgWlanMacInAcl, wingCfgWlanIpOutAcl, wingCfgWlanMacOutAcl, wingCfgWlanArpTrust, wingCfgWlanDhcpTrust,
				wingCfgWlanArpHeaderMismatchValidation, wingCfgWlanServiceAllowHtOnly, wingCfgWlanEnforceDhcp, wingCfgWlanProxyArpMode,
				wingCfgWlanBroadcastDhcpValidateOffer, wingCfgWlanKerberosRealm, wingCfgWlanKerberosTimeout, wingCfgWlanKerberosPassword,
				wingCfgWlanKerberosPrimaryServer, wingCfgWlanKerberosPrimaryServerPort, wingCfgWlanKerberosSecondaryServer, wingCfgWlanKerberosSecondaryServerPort,
				wingCfgWlanAcctSyslogEnable, wingCfgWlanAcctSyslogHost, wingCfgWlanAcctSyslogPort, wingCfgWlanClientDenyLimitThresholdRate,
				wingCfgWlanClientDenyLimitAction, wingCfgWlanClientDenyLimitBlacklistAgeout, wingCfgWlanQosName, wingCfgWlanQosClassification,
				wingCfgWlanQosNonWmmClassification, wingCfgWlanQosMulticastMaskPrimary, wingCfgWlanQosMulticastMaskSecondary, wingCfgWlanQosMulticastMaskAc,
				wingCfgWlanQosVoicePrioritization, wingCfgWlanQosSvpPrioritization, wingCfgWlanQosWmmPowerSave, wingCfgWlanQosWmmQbssLoadElement,
				wingCfgWlanQosWmmBestEffortTxopLimit, wingCfgWlanQosWmmBestEffortAifsn, wingCfgWlanQosWmmBestEffortCwMin, wingCfgWlanQosWmmBestEffortCwMax,
				wingCfgWlanQosWmmBackgroundTxopLimit, wingCfgWlanQosWmmBackgroundAifsn, wingCfgWlanQosWmmBackgroundCwMin, wingCfgWlanQosWmmBackgroundCwMax,
				wingCfgWlanQosWmmVideoTxopLimit, wingCfgWlanQosWmmVideoAifsn, wingCfgWlanQosWmmVideoCwMin, wingCfgWlanQosWmmVideoCwMax,
				wingCfgWlanQosWmmVoiceTxopLimit, wingCfgWlanQosWmmVoiceAifsn, wingCfgWlanQosWmmVoiceCwMin, wingCfgWlanQosWmmVoiceCwMax,
				wingCfgWlanQosWlanRlDownEnable, wingCfgWlanQosWlanRlDownRate, wingCfgWlanQosWlanRlDownBurstSize, wingCfgWlanQosWlanRlDownThreshBackground,
				wingCfgWlanQosWlanRlDownThreshBestEffort, wingCfgWlanQosWlanRlDownThreshVoice, wingCfgWlanQosWlanRlDownThreshVideo, wingCfgWlanQosWlanRlUpEnable,
				wingCfgWlanQosWlanRlUpRate, wingCfgWlanQosWlanRlUpBurstSize, wingCfgWlanQosWlanRlUpThreshBackground, wingCfgWlanQosWlanRlUpThreshBestEffort,
				wingCfgWlanQosWlanRlUpThreshVoice, wingCfgWlanQosWlanRlUpThreshVideo, wingCfgWlanQosMuRlDownEnable, wingCfgWlanQosMuRlDownRate,
				wingCfgWlanQosMuRlDownBurstSize, wingCfgWlanQosMuRlDownThreshBackground, wingCfgWlanQosMuRlDownThreshBestEffort,
				wingCfgWlanQosMuRlDownThreshVoice, wingCfgWlanQosMuRlDownThreshVideo, wingCfgWlanQosMuRlUpEnable, wingCfgWlanQosMuRlUpRate,
				wingCfgWlanQosMuRlUpBurstSize, wingCfgWlanQosMuRlUpThreshBackground, wingCfgWlanQosMuRlUpThreshBestEffort, wingCfgWlanQosMuRlUpThreshVoice,
				wingCfgWlanQosMuRlUpThreshVideo, wingCfgWlanQosQosTrustDscp, wingCfgWlanQosQosTrustWmm, wingCfgWlanQosMcastStreamAddr,
				wingCfgWlanQosMcastStreamPriority, wingCfgRadioQosName, wingCfgRadioQosWmmBestEffortTxopLimit, wingCfgRadioQosWmmBestEffortAifsn,
				wingCfgRadioQosWmmBestEffortCwMin, wingCfgRadioQosWmmBestEffortCwMax, wingCfgRadioQosWmmBackgroundTxopLimit, wingCfgRadioQosWmmBackgroundAifsn,
				wingCfgRadioQosWmmBackgroundCwMin, wingCfgRadioQosWmmBackgroundCwMax, wingCfgRadioQosWmmVideoTxopLimit, wingCfgRadioQosWmmVideoAifsn,
				wingCfgRadioQosWmmVideoCwMin, wingCfgRadioQosWmmVideoCwMax, wingCfgRadioQosWmmVoiceTxopLimit, wingCfgRadioQosWmmVoiceAifsn,
				wingCfgRadioQosWmmVoiceCwMin, wingCfgRadioQosWmmVoiceCwMax, wingCfgRadioQosAdmCtrlFirewallDetectedTraffic, wingCfgRadioQosAdmCtrlImplicitTspec,
				wingCfgRadioQosAdmCtrlVoiceEnable, wingCfgRadioQosAdmCtrlVoiceMaxClients, wingCfgRadioQosAdmCtrlVoiceMaxRoamedClients,
				wingCfgRadioQosAdmCtrlVoiceMaxAirtimePercent, wingCfgRadioQosAdmCtrlVoiceReservedForRoamPercent, wingCfgRadioQosAdmCtrlVideoEnable,
				wingCfgRadioQosAdmCtrlVideoMaxClients, wingCfgRadioQosAdmCtrlVideoMaxRoamedClients, wingCfgRadioQosAdmCtrlVideoMaxAirtimePercent,
				wingCfgRadioQosAdmCtrlVideoReservedForRoamPercent, wingCfgRadioQosAdmCtrlBestEffortEnable, wingCfgRadioQosAdmCtrlBestEffortMaxClients,
				wingCfgRadioQosAdmCtrlBestEffortMaxRoamedClients, wingCfgRadioQosAdmCtrlBestEffortMaxAirtimePercent,
				wingCfgRadioQosAdmCtrlBestEffortReservedForRoamPercent, wingCfgRadioQosAdmCtrlBackgroundEnable, wingCfgRadioQosAdmCtrlBackgroundMaxClients,
				wingCfgRadioQosAdmCtrlBackgroundMaxRoamedClients, wingCfgRadioQosAdmCtrlBackgroundMaxAirtimePercent,
				wingCfgRadioQosAdmCtrlBackgroundReservedForRoamPercent, wingCfgRadioQosAccelMcastMaxStreams, wingCfgRadioQosAccelMcastOverflowPolicy,
				wingCfgRadioQosAccelMcastMaxClientStreams, wingCfgRadioQosAccelMcastStreamThreshold, wingCfgRadioQosAccelMcastClientTimeout, wingCfgAaaName,
				wingCfgAaaServerPoolingMode, wingCfgAaaMacAddrFormat, wingCfgAaaMacAddrCase, wingCfgAaaMacAddrAttributes, wingCfgAaaEapClientTimeout,
				wingCfgAaaEapClientAttempts, wingCfgAaaEapClientRetryFactor, wingCfgAaaEapClientIdReqTimeout, wingCfgAaaAuthProtocol, wingCfgAaaAccountingType,
				wingCfgAaaInterimAccountingInterval, wingCfgAaaNacList, wingCfgAssocAclName, wingCfgSmartRfName, wingCfgSmartRfEnable,
				wingCfgSmartRfSensitivity, wingCfgSmartRfAutoAssignSensor, wingCfgSmartRfMinPowerA, wingCfgSmartRfMaxPowerA, wingCfgSmartRfMinPowerBg,
				wingCfgSmartRfMaxPowerBg, wingCfgSmartRfChannelWidthA, wingCfgSmartRfChannelWidthBg, wingCfgSmartRfGroupByArea, wingCfgSmartRfGroupByFloor,
				wingCfgSmartRfSmartOcsMonitoring, wingCfgSmartRfOcsDurationA, wingCfgSmartRfOcsDurationBg, wingCfgSmartRfOcsFrequencyA,
				wingCfgSmartRfOcsFrequencyBg, wingCfgSmartRfOcsSampleCountA, wingCfgSmartRfOcsSampleCountBg, wingCfgSmartRfOcsExtendedScanFrequencyA,
				wingCfgSmartRfOcsExtendedScanFrequencyBg, wingCfgSmartRfOcsVoiceAwareA, wingCfgSmartRfOcsVoiceAwareBg, wingCfgSmartRfOcsPspAwareA,
				wingCfgSmartRfOcsPspAwareBg, wingCfgSmartRfInterferenceRecovery, wingCfgSmartRfIrNoise, wingCfgSmartRfIrInterference,
				wingCfgSmartRfIrClientThreshold, wingCfgSmartRfIrChannelSwitchDeltaA, wingCfgSmartRfIrChannelSwitchDeltaBg, wingCfgSmartRfNeighborRecovery,
				wingCfgSmartRfNrPowerThresholdA, wingCfgSmartRfNrPowerThresholdBg, wingCfgSmartRfCoverageHoleRecovery, wingCfgSmartRfChrIntervalA,
				wingCfgSmartRfChrIntervalBg, wingCfgSmartRfChrCovIntervalA, wingCfgSmartRfChrCovIntervalBg, wingCfgSmartRfChrSnrThresholdA,
				wingCfgSmartRfChrSnrThresholdBg, wingCfgSmartRfChrClientThresholdA, wingCfgSmartRfChrClientThresholdBg, wingCfgSmartRfChannelHoldTime,
				wingCfgSmartRfPowerHoldTime, wingCfgCaptPrtlName, wingCfgCaptPrtlAccessType, wingCfgCaptPrtlAccessTime, wingCfgCaptPrtlCustomAuthInfo,
				wingCfgCaptPrtlConnectionMode, wingCfgCaptPrtlInactivityTimeout, wingCfgCaptPrtlServer, wingCfgCaptPrtlServerMode, wingCfgCaptPrtlSimultaneousUsers,
				wingCfgCaptPrtlTermsAgreement, wingCfgCaptPrtlWebpageLocation, wingCfgCaptPrtlAccountingRadius, wingCfgCaptPrtlAaaPolicy,
				wingCfgCaptPrtlDnsWhitelist, wingCfgCaptPrtlAcctSyslogEnable, wingCfgCaptPrtlAcctSyslogHost, wingCfgCaptPrtlAcctSyslogPort, wingCfgDnsWhitelistName,
				wingCfgDnsWhitelistInstName, wingCfgDnsWhitelistInstSuffix, wingCfgIpAclName, wingCfgDhcpSvrName, wingCfgDhcpSvrIgnoreBootp, wingCfgDhcpSvrPingInterval,
				wingCfgDhcpSvrClassName, wingCfgDhcpSvrClassMultipleUserClass, wingCfgMacAclName, wingCfgProfName, wingCfgProfType, wingCfgProfDomainLookup,
				wingCfgProfDomainName, wingCfgProfArpTimeout, wingCfgProfApIpAddr, wingCfgProfAutoConfUpdate, wingCfgProfAutoFwUpdate,
				wingCfgProfAutoupgradeCount, wingCfgProfServiceWatchdog, wingCfgProfRadiusServerPolicy, wingCfgProfDhcpServerPolicy, wingCfgProfManagementPolicy,
				wingCfgProfFirewallPolicy, wingCfgProfAdvancedWipsPolicy, wingCfgProfRolePolicy, wingCfgProfAdoptionPolicy, wingCfgProfBridgingPolicy,
				wingCfgProfEventSystemPolicy, wingCfgProfRoutingPolicy, wingCfgProfRfDomainMgrCapable, wingCfgProfRfDomainMgrPriority, wingCfgProfDhcpcSendHostname, 
				wingCfgProfDhcpcPersistentLease, wingCfgProfDnsServerForward, wingCfgProfBridgeAgingTime, wingCfgProfLogging, wingCfgProfAggregationTime,
				wingCfgProfConsole, wingCfgProfBuffered, wingCfgProfSyslog, wingCfgProfFacility, wingCfgProfEvents, wingCfgProfEventsForward, wingCfgProfLed,
				wingCfgProfRemoteLogging, wingCfgProfPowerConfig3afOption, wingCfgProfPowerConfig3atOption, wingCfgProfPowerConfigMode, wingCfgProfCriticalResourcePolicy, 
				wingCfgProfControllerApSupported, wingCfgProfControllerVlan, wingCfgProfControllerGroup, wingCfgProfPreferredControllerGroup, 
				wingCfgProfIpRouting, wingCfgProfIfRadioRfMode, wingCfgProfIfRadioChannel, wingCfgProfIfRadioPower, wingCfgProfIfRadioPlacement,
				wingCfgProfIfRadioBeaconInterval, wingCfgProfIfRadioRtsThreshold, wingCfgProfIfRadioOffChannelScan, wingCfgProfIfRadioPreambleShort,
				wingCfgProfIfRadioGuardInterval, wingCfgProfIfRadioAmpduMode, wingCfgProfIfRadioAmsduMode, wingCfgProfIfRadioRifsMode, wingCfgProfIfRadioAmpduMaxAggrSizeRx,
				wingCfgProfIfRadioAmpduMaxAggrSizeTx, wingCfgProfIfRadioAmpduMinSpacing, wingCfgProfIfRadioAntennaMode, wingCfgProfIfRadioNonUnicastForwarding,
				wingCfgProfIfRadioDynamicChainSelection, wingCfgProfIfRadioLockRfMode, wingCfgProfIfRadioSnifferRedirHost, wingCfgProfIfRadioSnifferRedirChannel,
				wingCfgProfIfRadioMesh, wingCfgProfIfRadioMeshLinks, wingCfgProfIfRadioProbeResponseRetry, wingCfgProfIfRadioProbeResponseRate,
				wingCfgProfIfRadioMaxClients, wingCfgProfIfRadioRadioTapMode, wingCfgProfIfRadioWirelessClientPower, wingCfgProfIfRadioLoadBalLfCount,
				wingCfgProfIfRadioLoadBalLfThroughput, wingCfgProfIfRadioLoadBalWmCount, wingCfgProfIfRadioLoadBalWmTput, wingCfgProfIfRadioAssocAcl,
				wingCfgProfDot11WepSharedKeyAuth, wingCfgProfDot11LegacyAutoUpdateAp650, wingCfgProfDot11LegacyAutoUpdateImgAp7131, 	wingCfgProfDot11LegacyAutoDowngrade,
				wingCfgProfDot11NasIdentifier, wingCfgProfDot11NasPortId, wingCfgProfDot11LegacyAutoDowngrade, wingCfgProfDot11NasIdentifier,
				wingCfgProfDot11NasPortId, wingCfgRfdName, wingCfgRfdLocation, wingCfgRfdContact, wingCfgRfdTimezone, wingCfgRfdCountryCode, wingCfgRfdSmartRfPolicy,
				wingCfgRfdWipsPolicyName, wingCfgRfdNocUpdateInterval, wingCfgRfdControlVlan, wingCfgRfdSmartscanChanlistDynamic, wingCfgRfdStatsUpdateInterval,
				wingCfgDevMac, wingCfgDevHostname, wingCfgDevBuilding, wingCfgDevFloor, wingCfgDevNumRadios, wingCfgDevProfileName, wingCfgDevRfDomainName,
				wingCfgDevHttpsTrustpoint, wingCfgDevRadiusCaTrustpoint, wingCfgDevRadiusServerTrustpoint, wingCfgDevSshRsaKey, wingCfgDevHasOverrides,
				wingCfgDevDot11WepSharedKeyAuth, wingCfgDevDot11LegacyAutoUpdateAp650, wingCfgDevDot11LegacyAutoUpdateImgAp7131, wingCfgDevDot11LegacyAutoDowngrade,
				wingCfgDevDot11NasIdentifier, wingCfgDevDot11NasPortId,	wingCfgMgmtName, wingCfgMgmtTelnetEnable, wingCfgMgmtTelnetPort, wingCfgMgmtHttpEnable,
				wingCfgMgmtHttpsEnable, wingCfgMgmtSshEnable, wingCfgMgmtSshPort, wingCfgMgmtSnmpV2Enable, wingCfgMgmtSnmpV3Enable, wingCfgMgmtSnmpTrapEnable,
				wingCfgMgmtSnmpCommunityName, wingCfgMgmtSnmpCommunityAccess, wingCfgMgmtAdminUsername, wingCfgMgmtAdminPassword, wingCfgMgmtAdminRole,
				wingCfgDhcpSvrOptionName, wingCfgDhcpSvrOptionCode, wingCfgDhcpSvrOptionType, wingCfgDhcpSvrPoolName, wingCfgDhcpSvrPoolNetwork,
				wingCfgDhcpSvrPoolDomainName, wingCfgDhcpSvrPoolNetbiosNodeType, wingCfgDhcpSvrPoolBootfile, wingCfgDhcpSvrPoolLeaseTime,
				wingCfgDhcpSvrPoolBootpNextServer, wingCfgDhcpSvrPoolUpdateDns, wingCfgDhcpSvrPoolDdnsDomainName, wingCfgDhcpSvrPoolDdnsTtl,
				wingCfgDhcpSvrPoolDdnsMultiUserClass, wingCfgProfIfEthSpeed, wingCfgProfIfEthDuplex, wingCfgProfIfEthSwitchportMode, wingCfgProfIfEthSwitchportNativeVlan,
				wingCfgProfIfEthSwitchportNativeVlanTagged, wingCfgProfIfEthArpTrust, wingCfgProfIfEthDhcpTrust, wingCfgProfIfEthArpHeaderMismatchValidation,
				wingCfgProfIfEthQosTrustDscp, wingCfgProfIfEthQosTrust802dot1p, wingCfgProfIfEthStaticChannelGroup, wingCfgProfIfEthPoeSupported,
				wingCfgProfIfEthPoePower, wingCfgProfIfEthPoeLimit, wingCfgProfIfEthPoePriority, wingCfgProfIfEthDot1xSupported, wingCfgProfIfEthDot1xEnable,
				wingCfgProfIfEthDot1xUsername, wingCfgProfIfEthDot1xPassword, wingCfgProfIfEthCdpReceive, wingCfgProfIfEthCdpTransmit, wingCfgProfIfEthLldpReceive,
				wingCfgProfIfEthLldpTransmit, wingCfgProfIfEthPortChannelLoadBalance, wingCfgProfIfVlanVlan, wingCfgProfIfVlanDhcpcOptAll, wingCfgProfIfVlanNatDirection,
				wingCfgProfIfVlanCryptoMap, wingCfgProfIfVlanDhcpRelayIncoming, wingCfgProfIfVlanOspfAuth, wingCfgProfIfVlanOspfAuthKey, wingCfgProfIfVlanOspfNetworkType,
				wingCfgProfIfSpanTreeLinkType, wingCfgProfIfSpanTreePortfast, wingCfgProfIfSpanTreeEdgeport, wingCfgProfIfSpanTreeBpduguard,
				wingCfgProfIfSpanTreeBpdufilter, wingCfgProfIfSpanTreePortCiscoInterop, wingCfgProfIfSpanTreeForceVersion, wingCfgProfIfSpanTreeGuard,
				wingCfgWipsName, wingCfgWipsEnable, wingCfgWipsHistoryThrottleDuration, wingCfgWipsApDetection, wingCfgWipsApDetectionAgeout,
				wingCfgWipsApDetectionWaitTime, wingCfgWipsDeviceCategorization, wingCfgRfdWlanSsidOverrideWlan, wingCfgRfdWlanSsidOverrideSsid,
				wingCfgRfdWlanVlanOverrideWlan,	wingCfgMgmtSnmpUsmUserName, wingCfgMgmtSnmpUsmUserAuthentication, wingCfgMgmtSnmpUsmUserEncryption,
				wingCfgMgmtSnmpUsmUserPassword, wingCfgProfRouteNetwork, wingCfgProfRouteGateway, wingCfgProfNtpSvrServerIp, wingCfgProfNtpSvrAuthenkey,
				wingCfgProfNtpSvrAutokey, wingCfgProfNtpSvrKeyStr, wingCfgProfNtpSvrPrefer, wingCfgProfNtpSvrVersion, wingCfgProfClstClstName,
				wingCfgProfClstClstMemberVlan, wingCfgProfClstClstMode,	wingCfgProfClstClstMasterPriority, wingCfgProfClstHandleStp, wingCfgProfMintLevel1AreaId, wingCfgProfMintSpfLatency,
				wingCfgProfMintDisPriorityAdjustment, wingCfgProfIfWwanApn, wingCfgProfIfWwanAuth, 
				wingCfgProfIfWwanUser, wingCfgProfIfWwanPwd, wingCfgProfCrlUpdateTrustpoint, 
				wingCfgProfCrlUpdateUrl, wingCfgProfCrlUpdateInterval, wingCfgProfNatPoolName, wingCfgProfControllerHostHost, wingCfgProfControllerHostPool,
				wingCfgProfControllerHostLevel, wingCfgMacAclRulePrecedence, wingCfgMacAclRuleAllow, wingCfgMacAclRulePriorityField, wingCfgMacAclRuleMarkDscp,
				wingCfgMacAclRuleMark8021p, wingCfgMacAclRuleDescription, wingCfgMacAclRuleSmac, wingCfgMacAclRuleSmacMask, wingCfgMacAclRuleDmac, wingCfgMacAclRuleDmacMask,
				wingCfgMacAclRuleMatchVlan, wingCfgMacAclRuleMatchDot1p, wingCfgMacAclRuleMatchType, wingCfgWlanVlanId, wingCfgWlanVlanLimit, wingCfgAaaAuthSrvrIdx, 
				wingCfgAaaAuthSrvrType, wingCfgAaaAuthSrvrHost, wingCfgAaaAuthSrvrSecret, wingCfgAaaAuthSrvrPort, wingCfgAaaAuthSrvrTimeout, wingCfgAaaAuthSrvrAttempts, 
				wingCfgAaaAuthSrvrProxyMode, wingCfgAaaAuthSrvrNaiRouting, wingCfgAaaAuthSrvrRealmType, wingCfgAaaAuthSrvrRealm, wingCfgAaaAuthSrvrStripRealm, 
				wingCfgAaaAuthSrvrRetryTimeoutFactor, wingCfgAaaAuthSrvrNacEnable, wingCfgAaaAuthSrvrDscp, wingCfgAaaAcctSrvrIdx, wingCfgAaaAcctSrvrType, 
				wingCfgAaaAcctSrvrHost, wingCfgAaaAcctSrvrSecret, wingCfgAaaAcctSrvrPort, wingCfgAaaAcctSrvrTimeout, wingCfgAaaAcctSrvrAttempts, wingCfgAaaAcctSrvrProxyMode, 
				wingCfgAaaAcctSrvrNaiRouting, wingCfgAaaAcctSrvrRealmType, wingCfgAaaAcctSrvrRealm, wingCfgAaaAcctSrvrStripRealm, wingCfgAaaAcctSrvrRetryTimeoutFactor, 
				wingCfgAaaAcctSrvrDscp, wingCfgAssocAclRulePrecedence, wingCfgAssocAclRulePermit, wingCfgAssocAclRuleMac0, wingCfgAssocAclRuleMac1, 
				wingCfgIpAclRulePrecedence, wingCfgIpAclRuleAllow, wingCfgIpAclRulePriorityField, wingCfgIpAclRuleMarkDscp, wingCfgIpAclRuleMark8021p, 
				wingCfgIpAclRuleDescription, wingCfgIpAclRuleProtocol, wingCfgIpAclRuleSip, wingCfgIpAclRuleDip, wingCfgRfdStatsWindowIdx, 
				wingCfgRfdStatsWindowSampleInterval, wingCfgRfdStatsWindowWindowSize, wingCfgProfBridgeVlanId, wingCfgProfBridgeVlanDesc, wingCfgProfBridgeVlanEdgeVlan, 
				wingCfgProfBridgeVlanBridgingMode, wingCfgProfBridgeVlanIpArpTrust, wingCfgProfBridgeVlanIpDhcpTrust, wingCfgProfBridgeVlanTunnelMacOutAcl, 
				wingCfgProfBridgeVlanTunnelIpOutAcl, wingCfgRfdSensorSvrIdx, wingCfgRfdSensorSvrIp, wingCfgRfdSensorSvrPort, wingCfgDevIfName, wingCfgDevIfDescription,
				wingCfgDevIfType, wingCfgDevIfShutdown, wingCfgDevIfIpInAcl, wingCfgDevIfMacInAcl, wingCfgDevIfRadioRfMode, wingCfgDevIfRadioChannel,
				wingCfgDevIfRadioPower, wingCfgDevIfRadioPlacement, wingCfgDevIfRadioBeaconInterval, wingCfgDevIfRadioRtsThreshold, wingCfgDevIfRadioOffChannelScan,
				wingCfgDevIfRadioPreambleShort, wingCfgDevIfRadioGuardInterval, wingCfgDevIfRadioAmpduMode, wingCfgDevIfRadioAmsduMode, wingCfgDevIfRadioRifsMode,
				wingCfgDevIfRadioAmpduMaxAggrSizeRx, wingCfgDevIfRadioAmpduMaxAggrSizeTx, wingCfgDevIfRadioAmpduMinSpacing, wingCfgDevIfRadioAntennaMode,
				wingCfgDevIfRadioNonUnicastForwarding, wingCfgDevIfRadioDynamicChainSelection, wingCfgDevIfRadioLockRfMode, wingCfgDevIfRadioSnifferRedirHost,
				wingCfgDevIfRadioSnifferRedirChannel, wingCfgDevIfRadioMesh, wingCfgDevIfRadioMeshLinks, wingCfgDevIfRadioProbeResponseRetry,
				wingCfgDevIfRadioProbeResponseRate, wingCfgDevIfRadioMaxClients, wingCfgDevIfRadioRadioTapMode, wingCfgDevIfRadioWirelessClientPower,
				wingCfgDevIfRadioLoadBalLfCount, wingCfgDevIfRadioLoadBalLfThroughput, wingCfgDevIfRadioLoadBalWmCount, wingCfgDevIfRadioLoadBalWmTput,
				wingCfgDevIfRadioAssocAcl, wingCfgDevIfRadioQosPolicy, wingCfgDevWlanSsidOverrideWlan, wingCfgDevWlanSsidOverrideSsid, wingCfgDevWlanVlanOverrideWlan,
				wingCfgDevIfEthSpeed, wingCfgDevIfEthDuplex, wingCfgDevIfEthSwitchportMode, wingCfgDevIfEthSwitchportNativeVlan, 
				wingCfgDevIfEthSwitchportNativeVlanTagged, wingCfgDevIfEthArpTrust, wingCfgDevIfEthDhcpTrust, wingCfgDevIfEthArpHeaderMismatchValidation, 
				wingCfgDevIfEthQosTrustDscp, wingCfgDevIfEthQosTrust802dot1p, wingCfgDevIfEthStaticChannelGroup, wingCfgDevIfEthPoeSupported, wingCfgDevIfEthPoePower, 
				wingCfgDevIfEthPoeLimit, wingCfgDevIfEthPoePriority, wingCfgDevIfEthDot1xSupported, wingCfgDevIfEthDot1xEnable, wingCfgDevIfEthDot1xUsername, 
				wingCfgDevIfEthDot1xPassword, wingCfgDevIfEthCdpReceive, wingCfgDevIfEthCdpTransmit, wingCfgDevIfEthLldpReceive, wingCfgDevIfEthLldpTransmit, 
				wingCfgDevIfEthPortChannelLoadBalance, wingCfgDevIfVlanVlan, wingCfgDevIfVlanDhcpcOptAll, wingCfgDevIfVlanNatDirection, wingCfgDevIfVlanCryptoMap, 
				wingCfgDevIfVlanDhcpRelayIncoming, wingCfgDevIfSpanTreeLinkType, wingCfgDevIfSpanTreePortfast, wingCfgDevIfSpanTreeEdgeport, 
				wingCfgDevIfSpanTreeBpduguard, wingCfgDevIfSpanTreeBpdufilter, wingCfgDevIfSpanTreePortCiscoInterop, wingCfgDevIfSpanTreeForceVersion, 
				wingCfgDevIfSpanTreeGuard, wingCfgProfVpnLifetimeSeconds, wingCfgProfVpnLifetimeKb, wingCfgProfVpnIkev1GlobalDpdKeepalive, 
				wingCfgProfVpnIkev1GlobalDpdRetries, wingCfgProfVpnIkev1GlobalNatKeepalive, wingCfgProfVpnIkev2GlobalDpdKeepalive, wingCfgProfVpnIkev2GlobalDpdRetries, 
				wingCfgProfVpnIkev2GlobalNatKeepalive, wingCfgProfVpnCookieChallengeThreshold, wingCfgProfVpnMaxInNegotiationSa, wingCfgProfVpnDfBit,
				wingCfgProfVpnIkev1Name, wingCfgProfVpnIkev1Mode, wingCfgProfVpnIkev1IsakmpLifetime, wingCfgProfVpnIkev1DpdKeepalive, wingCfgProfVpnIkev1DpdRetries, 
				wingCfgProfVpnIkev1IsakmpHash, wingCfgProfVpnIkev2Name, 
				wingCfgProfVpnIkev2IsakmpLifetime, wingCfgProfVpnIkev2DpdKeepalive, 
				wingCfgProfVpnIkev2IsakmpHash, wingCfgProfVpnIkev1PeerName, 
				wingCfgProfVpnIkev1PeerIpType, wingCfgProfVpnIkev1PeerIpValue, 
				wingCfgProfVpnIkev1PeerLocalidType, wingCfgProfVpnIkev1PeerLocalidValue, wingCfgProfVpnIkev1PeerRemoteidType, wingCfgProfVpnIkev1PeerRemoteidValue, 
				wingCfgProfVpnIkev1PeerIkev1Policy, wingCfgProfVpnIkev2PeerName, wingCfgProfVpnIkev2PeerIpType, wingCfgProfVpnIkev2PeerIpValue, 
				wingCfgProfVpnIkev2PeerLocalidType, wingCfgProfVpnIkev2PeerLocalidValue, wingCfgProfVpnIkev2PeerRemoteidType, wingCfgProfVpnIkev2PeerRemoteidValue, 
				wingCfgProfVpnIkev2PeerIkev2Policy, wingCfgProfVpnTransformName, wingCfgProfVpnTransformCipherAlgo,
				wingCfgProfVpnTransformAuthAlgo, wingCfgProfVpnTransformMode, wingCfgProfVpnCryptoName, 
				wingCfgProfNtpSvrServerIp, wingCfgProfBridgeVlanIgsIpIgsQuerierMaxResponseTime, 
				wingCfgProfVrrpVersion, wingCfgProfVrrpGroupVirtualRouterId, wingCfgProfVrrpGroupDescription, wingCfgProfVrrpGroupPriority, 
				wingCfgProfVrrpGroupAdvertisementIntervalV2, wingCfgProfVrrpGroupAdvertisementIntervalV3, wingCfgProfVrrpGroupPreempt, wingCfgProfVrrpGroupPreemptDelay, 
				wingCfgProfVrrpGroupCrmAction, wingCfgProfVrrpGroupDeltaPriority, wingCfgProfVrrpGroupInterface, wingCfgProfVrrpGroupSyncGroup, wingCfgDevVrrpVersion, 
				wingCfgDevVrrpGroupVirtualRouterId, wingCfgDevVrrpGroupDescription, wingCfgDevVrrpGroupPriority, wingCfgDevVrrpGroupAdvertisementIntervalV2, 
				wingCfgDevVrrpGroupAdvertisementIntervalV3, wingCfgDevVrrpGroupPreempt, wingCfgDevVrrpGroupPreemptDelay, wingCfgDevVrrpGroupCrmAction, 
				wingCfgDevVrrpGroupDeltaPriority, wingCfgDevVrrpGroupInterface, wingCfgDevVrrpGroupSyncGroup, wingCfgProfDynRouteOspfEnabled, 
				wingCfgProfDynRouteOspfRouterId, wingCfgProfDynRouteOspfAutoCost, wingCfgProfDynRouteOspfPassiveAll, 
				wingCfgProfIfVlanOspfOspfAuthentication, wingCfgProfIfVlanOspfOspfAuthKey, wingCfgProfIfVlanOspfOspfPriority, 
				wingCfgProfIfVlanOspfOspfCost, wingCfgDevIfVlanOspfOspfAuthentication, wingCfgDevIfVlanOspfOspfAuthKey, wingCfgDevIfVlanOspfOspfPriority, 
				wingCfgDevIfVlanOspfOspfCost, wingCfgDevIfPppoeAuthType, wingCfgDevIfPppoeIdleTime, wingCfgDevIfPppoeKeepalive, wingCfgDevIfPppoeUsername, 
				wingCfgDevIfPppoePassword, wingCfgDevIfPppoeService, wingCfgDevIfPppoeLocalnetVlan, wingCfgDevIfPppoeMtu, wingCfgProfIfPppoeAuthType, 
				wingCfgProfIfPppoeIdleTime, wingCfgProfIfPppoeKeepalive, wingCfgProfIfPppoeUsername, wingCfgProfIfPppoePassword, wingCfgProfIfPppoeService, 
				wingCfgProfIfPppoeLocalnetVlan, wingCfgProfIfPppoeMtu, wingCfgDevBridgeVlanId, wingCfgDevBridgeVlanDescription, wingCfgDevBridgeVlanEdgeVlan, 
				wingCfgDevBridgeVlanBridgingMode, wingCfgDevBridgeVlanIpArpTrust, wingCfgDevBridgeVlanIpDhcpTrust, wingCfgDevBridgeVlanTunnelMacOutAcl, 
				wingCfgDevBridgeVlanTunnelIpOutAcl, wingCfgDevBridgeVlanIgsIpIgs, wingCfgDevBridgeVlanIgsIpIgsQuerier, 
				wingCfgDevBridgeVlanIgsIpIgsQuerierMaxResponseTime, wingCfgDevBridgeVlanIgsIpIgsQuerierVersion, wingCfgDevBridgeVlanIgsIpIgsQuerierAddress, 
				wingCfgDevBridgeVlanIgsIpIgsOtherQuerierTimerExpiry, wingCfgDevBridgeVlanIgsIpIgsForwardUnknownMcast, wingCfgDevBridgeVlanIgsIpIgsMrouterLearnPimDvmrp, 
				wingCfgRouteName, wingCfgRouteLogging, wingCfgRouteLocalPbr, wingCfgRouteMapPrecedence, wingCfgRouteMapMatchClauseAcl, wingCfgRouteMapMatchClauseDscp, 
				wingCfgRouteMapMatchClauseWlan, wingCfgRouteMapRolePolicy, wingCfgRouteMapUserRole, wingCfgRouteMapMatchClauseIncomingInterface, wingCfgRouteMapNextHop1, 
				wingCfgRouteMapNextHop2, wingCfgRouteMapSetClauseDefaultNextHop, wingCfgRouteUseCrm, 
				wingCfgRouteMapSetClauseFallback, wingCfgRouteMapSetClauseMarkDscp, wingCfgProfBridgeVlanIgsIpIgs, wingCfgProfBridgeVlanIgsIpIgsQuerier, 
				wingCfgProfBridgeVlanIgsIpIgsQuerierMaxResponseTime, wingCfgProfBridgeVlanIgsIpIgsQuerierVersion, wingCfgProfBridgeVlanIgsIpIgsQuerierAddress, 
				wingCfgProfBridgeVlanIgsIpIgsOtherQuerierTimerExpiry, wingCfgProfBridgeVlanIgsIpIgsForwardUnknownMcast, wingCfgProfBridgeVlanIgsIpIgsMrouterLearnPimDvmrp, 
				wingCfgProfIgsIpIgmpSnooping, wingCfgProfIgsIpIgmpSnoopingForwardUnknownMulticast, wingCfgProfIgsIpIgmpSnoopingQuerier, 
				wingCfgProfIgsIpIgmpSnoopingQuerierAddress, wingCfgProfIgsIpIgmpSnoopingQuerierMaxResponseTime, wingCfgProfIgsIpIgmpSnoopingQuerierOtherQuerierTimerExpiry, 
				wingCfgProfIgsIpIgmpSnoopingQuerierVersion, wingCfgProfIgsIpIgmpSnoopingQuerierQueryInterval, wingCfgProfIgsIpIgmpSnoopingQuerierRobustnessVariable, 
				wingCfgDevIgsIpIgmpSnooping, wingCfgDevIgsIpIgmpSnoopingForwardUnknownMulticast, wingCfgDevIgsIpIgmpSnoopingQuerier, 
				wingCfgDevIgsIpIgmpSnoopingQuerierAddress, wingCfgDevIgsIpIgmpSnoopingQuerierMaxResponseTime, wingCfgDevIgsIpIgmpSnoopingQuerierOtherQuerierTimerExpiry, 
				wingCfgDevIgsIpIgmpSnoopingQuerierVersion, wingCfgDevIgsIpIgmpSnoopingQuerierQueryInterval, wingCfgDevIgsIpIgmpSnoopingQuerierRobustnessVariable, 
				wingCfgDevVpnLifetimeSeconds, wingCfgDevVpnLifetimeKb, wingCfgDevVpnIkev1GlobalDpdKeepalive, wingCfgDevVpnIkev1GlobalDpdRetries, 
				wingCfgDevVpnIkev1GlobalNatKeepalive, wingCfgDevVpnIkev2GlobalDpdKeepalive, wingCfgDevVpnIkev2GlobalDpdRetries, wingCfgDevVpnIkev2GlobalNatKeepalive, 
				wingCfgDevVpnCookieChallengeThreshold, wingCfgDevVpnMaxInNegotiationSa, wingCfgDevVpnIkev1Name, wingCfgDevVpnIkev1Mode, wingCfgDevVpnIkev1IsakmpLifetime, 
				wingCfgDevVpnIkev1DpdKeepalive, wingCfgDevVpnIkev1DpdRetries, wingCfgDevVpnIkev2Name, wingCfgDevVpnIkev2IkeLifetime, wingCfgDevVpnIkev2DpdKeepalive, 
				wingCfgProfVpnIkev1PeerName, wingCfgProfVpnIkev1PeerIpType, wingCfgProfVpnIkev1PeerIpValue, wingCfgProfVpnIkev1PeerAuthType, 
				wingCfgProfVpnIkev1PeerAuthKey, wingCfgProfVpnIkev1PeerLocalidType, wingCfgProfVpnIkev1PeerLocalidValue, wingCfgProfVpnIkev1PeerRemoteidType, 
				wingCfgProfVpnIkev1PeerRemoteidValue, wingCfgProfVpnIkev1PeerIkev1Policy, wingCfgProfVpnIkev2PeerName, wingCfgProfVpnIkev2PeerIpType, 
				wingCfgProfVpnIkev2PeerIpValue, wingCfgProfVpnIkev2PeerLocalAuthType, wingCfgProfVpnIkev2PeerLocalAuthKey, wingCfgProfVpnIkev2PeerRemoteAuthType, 
				wingCfgProfVpnIkev2PeerRemoteAuthKey, wingCfgProfVpnIkev2PeerLocalidType, wingCfgProfVpnIkev2PeerLocalidValue, wingCfgProfVpnIkev2PeerRemoteidType, 
				wingCfgProfVpnIkev2PeerRemoteidValue, wingCfgProfVpnIkev2PeerIkev2Policy, wingCfgDevVpnIkev1PeerName, wingCfgDevVpnIkev1PeerIpType, 
				wingCfgDevVpnIkev1PeerIpValue, wingCfgDevVpnIkev1PeerAuthType, wingCfgDevVpnIkev1PeerAuthKey, wingCfgDevVpnIkev1PeerLocalidType, 
				wingCfgDevVpnIkev1PeerLocalidValue, wingCfgDevVpnIkev1PeerRemoteidType, wingCfgDevVpnIkev1PeerRemoteidValue, wingCfgDevVpnIkev1PeerIkev1Policy, 
				wingCfgDevVpnIkev2PeerName, wingCfgDevVpnIkev2PeerIpType, wingCfgDevVpnIkev2PeerIpValue, wingCfgDevVpnIkev2PeerLocalAuthType, 
				wingCfgDevVpnIkev2PeerLocalAuthKey, wingCfgDevVpnIkev2PeerRemoteAuthType, wingCfgDevVpnIkev2PeerRemoteAuthKey, wingCfgDevVpnIkev2PeerLocalidType, 
				wingCfgDevVpnIkev2PeerLocalidValue, wingCfgDevVpnIkev2PeerRemoteidType, wingCfgDevVpnIkev2PeerRemoteidValue, wingCfgDevVpnIkev2PeerIkev2Policy,
				wingCfgVersionVal, wingCfgPasswordEncVal, wingCfgPasswordEncSetOldPassphrase, wingCfgPasswordEncSetNewPassphrase, wingCfgDevDynRouteOspfEnabled, 
				wingCfgDevDynRouteOspfRouterId, wingCfgDevDynRouteOspfAutoCost, wingCfgDevDynRouteOspfPassiveAll, 
				wingCfgDevVpnTransformName, wingCfgDevVpnTransformCipherAlgo, wingCfgDevVpnTransformAuthAlgo, 
				wingCfgDevVpnTransformMode, wingCfgDevVpnCryptoName, wingCfgProfVpnIkev1RemoteAuthMethod, wingCfgProfVpnIkev1RemoteAaaPolicy, 
				wingCfgProfVpnIkev1RemoteIpLocalPool, wingCfgProfVpnIkev1RemoteWinsServerType, wingCfgProfVpnIkev1RemoteWinsServerIp, 
				wingCfgProfVpnIkev1RemoteNameServerType, wingCfgProfVpnIkev1RemoteNameServerIp, wingCfgProfVpnIkev2RemoteAuthMethod, 
				wingCfgProfVpnIkev2RemoteAaaPolicy, wingCfgProfVpnIkev2RemoteIpLocalPool, wingCfgProfVpnIkev2RemoteDhcpServerType, 
				wingCfgProfVpnIkev2RemoteDhcpServer, wingCfgProfVpnIkev2RemoteDhcpServerGiaddr, wingCfgProfVpnIkev2RemoteNetmask, wingCfgProfVpnIkev2RemoteWinsServerType, 
				wingCfgProfVpnIkev2RemoteWinsServerIp, wingCfgProfVpnIkev2RemoteNameServerType, wingCfgProfVpnIkev2RemoteNameServerIp, 
				wingCfgDevVpnIkev1RemoteAuthMethod, wingCfgDevVpnIkev1RemoteAaaPolicy, wingCfgDevVpnIkev1RemoteIpLocalPool, wingCfgDevVpnIkev1RemoteWinsServerType, 
				wingCfgDevVpnIkev1RemoteWinsServerIp, wingCfgDevVpnIkev1RemoteNameServerType, wingCfgDevVpnIkev1RemoteNameServerIp, wingCfgDevVpnIkev2RemoteAuthMethod, 
				wingCfgDevVpnIkev2RemoteAaaPolicy, wingCfgDevVpnIkev2RemoteIpLocalPool, wingCfgDevVpnIkev2RemoteDhcpServerType, wingCfgDevVpnIkev2RemoteDhcpServer, 
				wingCfgDevVpnIkev2RemoteDhcpServerGiaddr, wingCfgDevVpnIkev2RemoteNetmask, wingCfgDevVpnIkev2RemoteWinsServerType, wingCfgDevVpnIkev2RemoteWinsServerIp, 
				wingCfgDevVpnIkev2RemoteNameServerType, wingCfgDevVpnIkev2RemoteNameServerIp, wingStatsRfdWlRadioStatDetailTxBytes, wingStatsRfdWlRadioStatDetailRxBytes,
				wingStatsDevSysInfoFreeMem, wingStatsDevSysInfoTotalMem, wingStatsDevSysInfoFreeRamCurrent, wingStatsDevSysInfoFreeRamLimit, wingStatsDevSysInfoFdMax,
				wingStatsDevSysInfoFdCurrent, wingStatsDevSysInfoFdLimit, wingStatsDevSysInfoLoadLimitS0, wingStatsDevSysInfoLoadLimitS1, wingStatsDevSysInfoLoadLimitS2,
				wingStatsDevSysInfoBufferCurrent0, wingStatsDevSysInfoBufferCurrent1, wingStatsDevSysInfoBufferCurrent2, wingStatsDevSysInfoBufferCurrent3,
				wingStatsDevSysInfoBufferCurrent4, wingStatsDevSysInfoBufferCurrent5, wingStatsDevSysInfoBufferCurrent6, wingStatsDevSysInfoBufferCurrent7,
				wingStatsDevSysInfoBufferCurrent8, wingStatsDevSysInfoBufferCurrent9, wingStatsDevSysInfoBufferCurrent10, wingStatsDevSysInfoBufferCurrent11,
				wingStatsDevSysInfoBufferCurrent12, wingStatsDevSysInfoBufferTotal0, wingStatsDevSysInfoBufferTotal1, wingStatsDevSysInfoBufferTotal2,
				wingStatsDevSysInfoBufferTotal3, wingStatsDevSysInfoBufferTotal4, wingStatsDevSysInfoBufferTotal5, wingStatsDevSysInfoBufferTotal6,
				wingStatsDevSysInfoBufferTotal7, wingStatsDevSysInfoBufferTotal8, wingStatsDevSysInfoBufferTotal9, wingStatsDevSysInfoBufferTotal10,
				wingStatsDevSysInfoBufferTotal11, wingStatsDevSysInfoBufferTotal12, wingStatsDevSysProductName, wingStatsDevSysSerialNo, wingStatsDevSysVersion,
				wingStatsDevSysPrimaryVersion, wingStatsDevSysSecondaryVersion, wingStatsDevSysPrimaryBuildDate, wingStatsDevSysSecondaryBuildDate,
				wingStatsDevSysPrimaryInstallDate, wingStatsDevSysSecondaryInstallDate, wingStatsDevSysBootPartition, wingStatsDevSysNextBoot, wingStatsDevSysIsFallback,
				wingStatsDevSysImgFallback, wingStatsDevSysUptime, wingStatsDevSysCpu, wingStatsDevSysRam, wingStatsDevSysClock, wingStatsDevSysUpgradeStatus,
				wingStatsDevSysUpgradeTime, wingStatsDevSysPoeFwVersion, wingStatsDevSysFpgaVersion, wingStatsDevSysModelNumber, wingStatsDevIfName, wingStatsDevIfIndex,
				wingStatsDevIfHwType, wingStatsDevIfMode, wingStatsDevIfMac, wingStatsDevIfStatusAdmin, wingStatsDevIfMtu, wingStatsDevIfGoodOctetsRcv, wingStatsDevIfGoodPktsRcv,
				wingStatsDevIfDropEvents, wingStatsDevIfUcPktsRcv, wingStatsDevIfBrdcPktsRcv, wingStatsDevIfMcPktsRcv, wingStatsDevIfBadPktsRcv, wingStatsDevIfUndersizePkts,
				wingStatsDevIfOversizePkts, wingStatsDevIfBadCrc, wingStatsDevIfMacRcvError, wingStatsDevIfFragmentsPkts, wingStatsDevIfJabberPkts, wingStatsDevIfGoodOctetsSent,
				wingStatsDevIfGoodPktsSent, wingStatsDevIfMacTransmitErr, wingStatsDevIfUcPktsSent, wingStatsDevIfBrdcPktsSent, wingStatsDevIfMcPktsSent,
				wingStatsDevIfLateCollisions, wingStatsDevIfExcessiveCollisions, wingStatsDevIfCollisions, wingStatsDevIfMetric, wingStatsDevIfRxFifoErrors,
				wingStatsDevIfRxOverErrors, wingStatsDevIfTxWindowErrors, wingStatsDevIfTxFifoErrors, wingStatsDevIfTxAbortedErrors, wingStatsDevIfTxCarrierErrors,
				wingStatsDevIfTxDropped, wingStatsDevIfRxLengthErrors, wingStatsDevIfRxMissedErrors, wingStatsDevIfRxFrameErrors, wingStatsDevIfTxErrors,
				wingStatsDevIfTxHeartbeatErrors, wingStatsRfdWlClientStatTxBytes, wingStatsRfdWlClientStatRxBytes, wingStatsRfdWlClientStatDetailTxBytes,
				wingStatsRfdWlClientStatDetailRxBytes, wingStatsRfdWlClientStatDetailRawTxBytes, wingStatsRfdWlClientStatDetailRawRxBytes,
				wingStatsRfdWlClientStatDetailRawTotalBytes, wingStatsRfdWlClientStatDetailTxBcmcPkts, wingStatsRfdWlClientStatDetailRxBcmcPkts,
				wingStatsRfdWlClientStatDetailTotalBcmcPkts, wingStatsRfdWlClientStatDetailTxMgmtPkts, wingStatsRfdWlClientStatDetailRxMgmtPkts,
				wingStatsRfdWlClientStatDetailTotalMgmtPkts, wingStatsRfdWlClientStatDetailTxRetries, wingStatsRfdWlClientStatDetailTotalBytes,
				wingStatsRfdWlRadioStatTxBytes, wingStatsRfdWlRadioStatRxBytes, wingStatsRfdWlRadioStatDetailRawTxBytes, wingStatsRfdWlRadioStatDetailRawRxBytes,
				wingStatsRfdWlRadioStatDetailRawTotalBytes, wingStatsRfdWlRadioStatDetailTxBcmcPkts, wingStatsRfdWlRadioStatDetailRxBcmcPkts,
				wingStatsRfdWlRadioStatDetailTotalBcmcPkts, wingStatsRfdWlRadioStatDetailTxMgmtPkts, wingStatsRfdWlRadioStatDetailRxMgmtPkts,
				wingStatsRfdWlRadioStatDetailTotalMgmtPkts, wingStatsRfdWlRadioStatDetailTxRetries, wingStatsRfdWlRadioStatDetailTotalBytes,
				wingStatsRfdWlRadioStatDetailRxRetries, wingCfgProfIfRadioBssmapWlan, wingCfgProfIfRadioBssmapBss, wingCfgProfIfRadioBssmapPrimary,
				wingCfgRfdWlanVlanOverrideInstVlan, wingCfgRfdWlanVlanOverrideInstLimit, wingCfgDevIfRadioBssmapWlan, wingCfgDevIfRadioBssmapBss,
				wingCfgDevIfRadioBssmapPrimary, wingCfgDevWlanVlanOverrideInstVlan, wingCfgDevWlanVlanOverrideInstLimit,
				wingCfgDevStatsWindowIdx, wingCfgDevStatsWindowSampleInterval, wingCfgDevStatsWindowWindowSize, wingActionFileCopyInMac, wingActionFileCopyInFrom,
				wingActionFileCopyInTo, wingActionFileCopyOutStatus, wingActionFileCopyOutMessage, wingActionFileCopyRun,
				wingStatsNocDevMac, wingStatsNocDevHostname, wingStatsNocDevType, wingStatsNocDevClusterName, wingStatsNocDevRfDomainName,
				wingStatsNocDevAdoptedBy, wingStatsNocDevOnline, wingStatsNocDevReporter, wingStatsNocDevLastUpdate, wingStatsNocDevHasRadio, wingStatsNocDevIsController,
				wingStatsNocDevProfileName, wingStatsRfdWlClientStatDetailTxRetriedBytes, wingStatsRfdWlRadioStatDetailTxRetriedBytes, wingStatsRfdWlApInfoIp,
				wingActionFileMD5sumInMac, wingActionFileMD5sumInPath, wingActionFileMD5sumOutStatus, wingActionFileMD5sumOutMessage, wingActionFileMD5sumRun,
				wingActionDisassociateClientInRfDomainName, wingActionDisassociateClientInMac, wingActionDisassociateClientInWlanName, wingActionDisassociateClientOutStatus,
				wingActionDisassociateClientOutMessage, wingActionDisassociateClientRun, wingStatsDevAdoptDevBy, wingStatsDevAdoptDevLastAdoption,
				wingStatsDevAdoptDevModelNumber, wingStatsDevAdoptDevStartup, wingStatsDevAdoptDevCfgStatus, wingStatsDevCdpNeighborIndex, wingStatsDevCdpNeighborDevId,
				wingStatsDevCdpNeighborPlatform, wingStatsDevCdpNeighborIpList, wingStatsDevCdpNeighborPortId, wingStatsDevCdpNeighborTtl, wingStatsDevCdpNeighborLocalPort,
				wingStatsDevCdpNeighborDuplex, wingCfgSysCommitLastError, wingStatsDevWlApDetectMac, wingStatsDevWlApDetectVendor, wingStatsDevWlApDetectChannel,
				wingStatsDevWlApDetectRadioType, wingStatsDevWlApDetectApMode, wingStatsDevWlApDetectSsid, wingStatsDevWlApDetectRssi, wingStatsDevWlApDetectLastSeen,
				wingStatsDevWlApDetectFirstSeen, wingStatsDevWlApDetectEncryption, wingStatsDevWlApDetectReportingApMac, wingStatsDevWlApDetectReportingApRadioNum,
				wingCfgSysRunningConfigChecksum, wingStatsRfdWlRadioDetailWlanMapWlanName, wingStatsRfdWlRadioDetailWlanMapBssIndex, wingStatsRfdWlRadioDetailWlanMapIsPrimary,
				wingStatsRfdWlRadioDetailBssMapBssIndex, wingStatsRfdWlRadioDetailBssMapBasicRates, wingStatsRfdWlRadioDetailBssMapSupportedRates,
				wingCfgDevVpnCryptoInstPeerListPriority, wingCfgDevVpnCryptoInstPeerListType, wingCfgDevVpnCryptoInstPeerListIkev1Peer, 
				wingCfgDevVpnCryptoInstPeerListIkev2Peer, wingCfgProfVpnCryptoInstAhSessionDirection, wingCfgProfVpnCryptoInstAhSessionSpi,
				wingCfgProfVpnCryptoInstAhSessionAuth, wingCfgProfVpnCryptoInstAhSessionKey, 
                                wingCfgDevDynRouteOspfNetworkAreaId, wingCfgDevDynRouteOspfAreaId, wingCfgDevDynRouteOspfAreaAuthentication, 
				wingCfgDevDynRouteOspfAreaRange, wingCfgDevDynRouteOspfAreaType, wingCfgDevDynRouteOspfAreaDefaultCost, 
				wingCfgDevDynRouteOspfAreaTranslateType, wingCfgDevDynRouteDefaultInfoOriginate, wingCfgDevDynRouteDefaultInfoAlways,
                                wingCfgDevDynRouteDefaultInfoRtMetric, wingCfgDevDynRouteDefaultInfoRtMetricType, wingCfgDevDynRouteRedistributeRouteType, 
				wingCfgDevDynRouteRedistributeMetric, wingCfgDevDynRouteRedistributeMetricType, wingCfgDevDynRouteOspfNetwork, 
				wingCfgDevDynRouteOspfVrrpStateCheck, wingCfgDevDynRouteOspfPassiveRemoved,
                                wingCfgDevDynRouteOspfPassive, wingCfgProfDynRouteDefaultInfoRtMetricType, wingCfgProfDynRouteDefaultInfoRtMetric, 
				wingCfgProfDynRouteDefaultInfoAlways, wingCfgProfDynRouteOspfPassive, wingCfgProfDynRouteOspfPassiveRemoved, wingCfgProfDynRouteOspfVrrpStateCheck, 
				wingCfgProfDynRouteDefaultInfoOriginate, wingStatsDevDynRouteIpOspfShutdownFlag, wingStatsDevDynRouteIpOspfShutdownDueTime, wingStatsDevDynRouteIpOspfTos,
                                wingStatsDevDynRouteIpOspfRFC2328ConformanceFlag, wingStatsDevDynRouteIpOspfRFC1583CompatFlag, wingStatsDevDynRouteIpOspfOpaquelsaFlag, wingStatsDevDynRouteIpOspfOpaquelsaOriginationBlockedFlag, wingStatsDevDynRouteIpOspfStubRouterAdvFlag,
                                wingStatsDevDynRouteIpOspfStubRouterStartupTime, wingStatsDevDynRouteIpOspfStubRouterShutdownTime, wingStatsDevDynRouteIpOspfDelay, wingStatsDevDynRouteIpOspfHoldTime, wingStatsDevDynRouteIpOspfMaxHoldTime,
                                wingStatsDevDynRouteIpOspfHoldMultiplier, wingStatsDevDynRouteIpOspfExecutedFlag, wingStatsDevDynRouteIpOspfExecutedWhen, wingStatsDevDynRouteIpOspfTimerDueFlag, wingStatsDevDynRouteIpOspfDueIn,
                                wingStatsDevDynRouteIpOspflsaRefreshTimer, wingStatsDevDynRouteIpOspfAbrFlag, wingStatsDevDynRouteIpOspfAbrType, wingStatsDevDynRouteIpOspfAsbrFlag, wingStatsDevDynRouteIpOspfExtLsdbCount,
                                wingStatsDevDynRouteIpOspfExtLsdbCsum, wingStatsDevDynRouteIpOspfOpaqueLsdbCount, wingStatsDevDynRouteIpOspfOpaqueExtLsdbCsum, wingStatsDevDynRouteIpOspfNumAreasAttached, wingStatsDevDynRouteOspfAreaId,
                                wingStatsDevDynRouteOspfAreaType, wingStatsDevDynRouteOspfAreaBackboneFlag, wingStatsDevDynRouteOspfAreaNoSummaryFlag, wingStatsDevDynRouteOspfAreaShortcutType, wingStatsDevDynRouteOspfAreaShortcutCapability,
                                wingStatsDevDynRouteOspfAreaInterfaceNum, wingStatsDevDynRouteOspfAreaActiveInterfaces, wingStatsDevDynRouteOspfAreaNssaFlag, wingStatsDevDynRouteOspfAreaNssaTransType, wingStatsDevDynRouteOspfAreaStubRouterStateFlag,
                                wingStatsDevDynRouteOspfAreaAdminStubRoutedFlag, wingStatsDevDynRouteOspfAreaStartupTimeDue, wingStatsDevDynRouteOspfAreaNumFullyAdjNbrs, wingStatsDevDynRouteOspfAreaAuthType,
                                wingStatsDevDynRouteOspfAreaNumFullVirtualAdj, wingStatsDevDynRouteOspfAreaNumSpfExecuted, wingStatsDevDynRouteOspfAreaNumTotalLsa, wingStatsDevDynRouteOspfAreaNumRouterLsa, wingStatsDevDynRouteOspfAreaRouterLsaCsum,
                                wingStatsDevDynRouteOspfAreaNumNetworkLsa, wingStatsDevDynRouteOspfAreaNetworkLsaCsum, wingStatsDevDynRouteOspfAreaNumSummaryLsa, wingStatsDevDynRouteOspfAreaSummaryLsaCsum, wingStatsDevDynRouteOspfAreaNumAsbrSummaryLsa,
                                wingStatsDevDynRouteOspfAreaAsbrSummaryLsaCsum, wingStatsDevDynRouteOspfAreaNumNssaLsa, wingStatsDevDynRouteOspfAreaNssaLsaCsum, wingStatsDevDynRouteOspfAreaNumOpaqueLinkLsa, wingStatsDevDynRouteOspfAreaOpaqueLinkLsaCsum,
                                wingStatsDevDynRouteOspfAreaNumOpaqueAreaLsa, wingStatsDevDynRouteOspfAreaOpaqueAreaLsaCsum, wingStatsDevDynRouteIpOspfNetworkRoute, wingStatsDevDynRouteIpOspfNetworkRoutesPathType, wingStatsDevDynRouteIpOspfNetworkRoutesDestType,
                                wingStatsDevDynRouteIpOspfNetworkRoutesCost, wingStatsDevDynRouteIpOspfNetworkRoutesArea, wingStatsDevDynRouteIpOspfNetworkRoutesMPathsIndex, wingStatsDevDynRouteIpOspfNetworkRoutesAttachedFlags, wingStatsDevDynRouteIpOspfNetworkRoutesIfName,
                                wingStatsDevDynRouteIpOspfNetworkRoutesNextHop, wingStatsDevDynRouteIpOspfRouterRoute, wingStatsDevDynRouteIpOspfRouterRoutesInfoIndex, wingStatsDevDynRouteIpOspfRouterRoutePathType, wingStatsDevDynRouteIpOspfRouterRouteArea,
                                wingStatsDevDynRouteIpOspfRouterRouteCost, wingStatsDevDynRouteIpOspfRouterRouteFlags, wingStatsDevDynRouteIpOspfRouterRouteAttachedFlag, wingStatsDevDynRouteIpOspfRouterRouteIfName, wingStatsDevDynRouteIpOspfRouterRouteNextHop,
                                wingstatsDevDynRouteIpOspfExtRoute, wingstatsDevDynRouteIpOspfExtRoutePathType, wingstatsDevDynRouteIpOspfExtRouteArea, wingstatsDevDynRouteIpOspfExtRouteCost, wingstatsDevDynRouteIpOspfExtRouteType2Cost,
                                wingstatsDevDynRouteIpOspfExtRouteTag, wingstatsDevDynRouteIpOspfExtRoutesMPathsIndex, wingstatsDevDynRouteIpOspfExtRouteAttachedFlag, wingstatsDevDynRouteIpOspfExtRouteIfName, wingstatsDevDynRouteIpOspfExtRouteNextHop,
                                wingStatsDevDynRouteBorderRouter, wingStatsDevDynRouteBorderRoutersInfoIndex, wingStatsDevDynRouteBorderRouterPathType, wingStatsDevDynRouteBorderRouterArea, wingStatsDevDynRouteBorderRouterCost,
                                wingStatsDevDynRouteBorderRouterFlags, wingStatsDevDynRouteBorderRouterAttachedFlag, wingStatsDevDynRouteBorderRouterIfName, wingStatsDevDynRouteBorderRouterNextHop, wingStatsDevDynRouteOspfIfName,
                                wingStatsDevDynRouteOspfIfStatusFlag, wingStatsDevDynRouteOspfIfIndex, wingStatsDevDynRouteOspfIfMtu, wingStatsDevDynRouteOspfIfBandwidth, wingStatsDevDynRouteOspfIfFlags,
                                wingStatsDevDynRouteOspfIfEnabled, wingStatsDevDynRouteOspfIfInfoIndex, wingStatsDevDynRouteOspfIfIpAddr, wingStatsDevDynRouteOspfIfMask, wingStatsDevDynRouteOspfIfBroadcastOrP2P,
                                wingStatsDevDynRouteOspfIfBroadcastOrP2PIpAddr, wingStatsDevDynRouteOspfIfAreaId, wingStatsDevDynRouteOspfIfMtuMismatchDetectFlag, wingStatsDevDynRouteOspfIfRouterId, wingStatsDevDynRouteOspfIfNetworkType,
                                wingStatsDevDynRouteOspfIfCost, wingStatsDevDynRouteOspfIfTransmitDelay, wingStatsDevDynRouteOspfIfIsmState, wingStatsDevDynRouteOspfIfPriority, wingStatsDevDynRouteOspfIfDesgRouterId,
                                wingStatsDevDynRouteOspfIfDesgRouterAddr, wingStatsDevDynRouteOspfIfBackupDesgRouterId, wingStatsDevDynRouteOspfIfBackupDesgRouterAddr, wingStatsDevDynRouteOspfIfMcastMembership, wingStatsDevDynRouteOspfIfSubSecHelloFlag,
                                wingStatsDevDynRouteOspfIfHelloInterval, wingStatsDevDynRouteOspfIfDeadInterval, wingStatsDevDynRouteOspfIfWaitInterval, wingStatsDevDynRouteOspfIfRetransmitInterval, wingStatsDevDynRouteOspfIfPassiveFlag,
                                wingStatsDevDynRouteOspfIfHelloDueIn, wingStatsDevDynRouteOspfIfNeighborCount, wingStatsDevDynRouteOspfIfAdjNeighborCount, wingStatsDevDynRouteNeighborIndex, wingStatsDevDynRouteNeighborRouterId,
                                wingStatsDevDynRouteNeighborPriority, wingStatsDevDynRouteNeighborSelfState, wingStatsDevDynRouteNeighborDeadTime, wingStatsDevDynRouteNeighborAddr, wingStatsDevDynRouteNeighborIfName,
                                wingStatsDevDynRouteNeighborSrcAddr, wingStatsDevDynRouteNeighborRetansmitCount, wingStatsDevDynRouteNeighborRequestCount, wingStatsDevDynRouteNeighborSummaryCount, wingStatsDevDynRouteIpOspfRouterId,
                                wingCfgProfDynRouteDefaultInfoAlways, wingCfgProfDynRouteOspfPassive, wingCfgProfDynRouteOspfPassiveRemoved, wingCfgProfDynRouteOspfVrrpStateCheck,
                                wingCfgProfDynRouteDefaultInfoOriginate, wingStatsDevPbrRuleString, wingCfgDevVpnAutoIPSecSecureGroupId, wingCfgDevVpnAutoIPSecSecureGroupIdAuthType, 
				wingCfgDevVpnAutoIPSecSecureGroupIdAuthKey, wingCfgDevVpnAutoIPSecSecureRemoteGWIkeVersion, wingCfgProfVpnAutoIPSecSecureGroupId, wingCfgProfVpnAutoIPSecSecureGroupIdAuthType, 
				wingCfgProfVpnAutoIPSecSecureGroupIdAuthKey, wingCfgProfVpnAutoIPSecSecureRemoteGWIkeVersion, wingCfgl2tpv3PolicyName, wingCfgl2tpv3PolicyHelloInterval, 
				wingCfgl2tpv3PolicyRetryAttempts, wingCfgl2tpv3PolicyRetryInterval, wingCfgl2tpv3PolicyHideAVPs, wingCfgl2tpv3PolicyCookieSize, 
				wingCfgl2tpv3PolicyRxWindowSize, wingCfgl2tpv3PolicyTxWindowSize, wingCfgl2tpv3PolicySequencingRequired, wingCfgl2tpv3PolicyReconnectInterval, 
				wingCfgl2tpv3PolicyReconnectAttempts, wingStatsDevPbrRuleString, wingCfgDevIfPppoeDefaultRoutePriority,
				wingCfgProfVpnIkev1IsakmpName, wingCfgProfVpnIkev1IsakmpEncryption, wingCfgProfVpnIkev1IsakmpGroup, 
				wingCfgProfVpnIkev1IsakmpHash, wingCfgProfVpnIkev2IsakmpName, wingCfgProfVpnIkev2IsakmpEncryption, wingCfgProfVpnIkev2IsakmpGroup, 
				wingCfgProfVpnIkev2IsakmpHash, wingCfgDevVpnIkev1IsakmpName, wingCfgDevVpnIkev1IsakmpEncryption, wingCfgDevVpnIkev1IsakmpGroup, 
				wingCfgDevVpnIkev1IsakmpHash, wingCfgDevVpnIkev2IsakmpName, wingCfgDevVpnIkev2IsakmpEncryption, wingCfgDevVpnIkev2IsakmpGroup, 
				wingCfgDevVpnIkev2IsakmpHash, wingCfgProfVpnCryptoInstSequence, wingCfgProfVpnCryptoInstType, wingCfgProfVpnCryptoInstIpAcl, 
				wingCfgProfVpnCryptoInstTransformSet, wingCfgProfVpnCryptoInstLocalip, wingCfgProfVpnCryptoInstPfs, wingCfgProfVpnCryptoInstLifetimeSeconds,
				wingCfgProfVpnCryptoInstLifetimeKb, wingCfgProfVpnCryptoInstRemoteType, wingCfgProfVpnCryptoInstModeconfig, wingCfgProfVpnCryptoInstPeer,
				wingCfgProfVpnCryptoInstProtocol, wingCfgProfVpnCryptoInstMode, 
                                wingCfgDevDynRouteOspfNetworkAreaId, wingCfgDevDynRouteOspfAreaId, wingCfgDevDynRouteOspfAreaAuthentication, wingCfgDevDynRouteOspfAreaRange,
                                wingCfgDevDynRouteOspfAreaType, wingCfgDevDynRouteOspfAreaDefaultCost, wingCfgDevDynRouteOspfAreaTranslateType, wingCfgDevDynRouteDefaultInfoOriginate, wingCfgDevDynRouteDefaultInfoAlways,
                                wingCfgDevDynRouteDefaultInfoRtMetric, wingCfgDevDynRouteDefaultInfoRtMetricType, wingCfgDevDynRouteRedistributeRouteType, wingCfgDevDynRouteRedistributeMetric,
                                wingCfgDevDynRouteRedistributeMetricType, wingCfgDevDynRouteOspfNetwork, wingCfgDevDynRouteOspfVrrpStateCheck, wingCfgDevDynRouteOspfPassiveRemoved,
                                wingCfgDevDynRouteOspfPassive, wingCfgProfDynRouteDefaultInfoRtMetricType, wingCfgProfDynRouteDefaultInfoRtMetric, wingCfgProfDynRouteDefaultInfoAlways, wingCfgProfDynRouteOspfPassive,
                                wingCfgProfDynRouteOspfPassiveRemoved, wingCfgProfDynRouteOspfVrrpStateCheck, wingCfgProfDynRouteDefaultInfoOriginate,
				wingCfgProfVrrpGroupAdvertisementUnit, wingCfgProfVrrpGroupAdvertisementIntervalV2Msec, wingCfgDevVrrpGroupAdvertisementUnit,
				wingCfgDevVrrpGroupAdvertisementIntervalV2Msec, wingCfgProfCriticalResMonitorInt, wingCfgProfCriticalResPolicyVia, 
				wingCfgProfCriticalResPolicyAnyAll, wingCfgProfCriticalResourcesAddr, wingCfgProfCriticalResourcesMonitorType, 
				wingCfgProfCriticalResourcesVlan, wingCfgDevCriticalResMonitorInt, wingCfgDevCriticalResPolicyVia, wingCfgDevCriticalResPolicyAnyAll, 
				wingCfgDevCriticalResourcesAddr, wingCfgDevCriticalResourcesMonitorType, wingCfgDevCriticalResourcesVlan, wingStatsDevVrrpGlobalErrIpTtlErrs, 
				wingStatsDevVrrpGlobalErrVersionMismatch, wingStatsDevVrrpGlobalErrPacketLenErr, wingStatsDevVrrpGlobalErrChecksumErr, 
				wingStatsDevVrrpGlobalErrInvalidVirtualRouterId, wingStatsDevVrrpGlobalErrAuthMismatch, wingStatsDevVrrpGlobalErrInvalidTypePackets, 
				wingStatsDevVrrpGlobalErrLastProtocolErrReason, wingStatsDevVrrpOperationVirtualRouterId, wingStatsDevVrrpOperationIfName, 
				wingStatsDevVrrpOperationVersion, wingStatsDevVrrpOperationState, wingStatsDevVrrpOperationPriority, wingStatsDevVrrpOperationVirtualAddr, 
				wingStatsDevVrrpOperationMasterAddr, wingStatsDevVrrpOperationExpiryTimer, wingStatsDevVrrpOperationMasterDeadTimer, 
				wingStatsDevVrrpDetailVirtualRouterId, wingStatsDevVrrpDetailIfName, wingStatsDevVrrpDetailVersion, wingStatsDevVrrpDetailConfiguredPriority, 
				wingStatsDevVrrpDetailAdvertisementInterval, wingStatsDevVrrpDetailLocalIpAddress, wingStatsDevVrrpDetailIfStatusAdmin, 
				wingStatsDevVrrpDetailVirtualAddressCount, wingStatsDevVrrpDetailPreempt, wingStatsDevVrrpDetailPreemptDelay, wingStatsDevVrrpDetailCrmDownAction, 
				wingStatsDevVrrpDetailCrmStatus, wingStatsDevVrrpDetailCfgedDeltaPriority, wingStatsDevVrrpDetailVirtualMacAddr, wingStatsDevVrrpDetailSyncGroup, 
				wingStatsDevVrrpDetailFailoverSyncGroup, wingStatsDevVrrpDetailMonitorIf, wingStatsDevVrrpDetailMonitorIfStatusAdmin, 
				wingStatsDevVrrpRouterStatsVirtualRouterId, wingStatsDevVrrpRouterStatsMasterTransitions, wingStatsDevVrrpRouterStatsNewMasterReason, 
				wingStatsDevVrrpRouterStatsNumReceivedAdvertisement, wingStatsDevVrrpRouterStatsAdvertisementIntervalErrs, 
				wingStatsDevVrrpRouterStatsNumSendAdvertisement, wingStatsDevVrrpRouterStatsReceivedAdvtInitState, 
				wingStatsDevVrrpRouterStatsReceivedPriorityZeroPackets, wingStatsDevVrrpRouterStatsSendPriorityZeroPackets, 
				wingStatsDevPbrRouteMapPrecedence, wingStatsDevPbrPrimaryNextHopIfName, wingStatsDevPbrPrimaryNextHopIpAddr, 
				wingStatsDevPbrPrimaryNextHopState, wingStatsDevPbrPrimaryNextHopMonitorMode, wingStatsDevPbrSecondaryNextHopIfName, 
				wingStatsDevPbrSecondaryNextHopIpAddr, wingStatsDevPbrSecondaryNextHopState, wingStatsDevPbrSecondaryNextHopMonitorMode, 
				wingStatsDevPbrDefaultNextHopIfName, wingStatsDevPbrDefaultNextHopIpAddr, wingStatsDevPbrDefaultNextHopState, 
				wingStatsDevPbrDefaultNextHopMonitorMode, wingStatsDevPbrWlan, wingStatsDevPbrWirelessClientRole, wingStatsDevPbrInInterface, 
				wingStatsDevPbrIpDscp, wingStatsDevPbrRuleString, wingStatsDevPbrRulesHitcount, wingStatsDevDynRouteIpOspfShutdownFlag, wingStatsDevDynRouteIpOspfShutdownDueTime, wingStatsDevDynRouteIpOspfTos,
                                wingStatsDevDynRouteIpOspfRFC2328ConformanceFlag, wingStatsDevDynRouteIpOspfRFC1583CompatFlag, wingStatsDevDynRouteIpOspfOpaquelsaFlag, wingStatsDevDynRouteIpOspfOpaquelsaOriginationBlockedFlag, wingStatsDevDynRouteIpOspfStubRouterAdvFlag,
                                wingStatsDevDynRouteIpOspfStubRouterStartupTime, wingStatsDevDynRouteIpOspfStubRouterShutdownTime, wingStatsDevDynRouteIpOspfDelay, wingStatsDevDynRouteIpOspfHoldTime, wingStatsDevDynRouteIpOspfMaxHoldTime,
                                wingStatsDevDynRouteIpOspfHoldMultiplier, wingStatsDevDynRouteIpOspfExecutedFlag, wingStatsDevDynRouteIpOspfExecutedWhen, wingStatsDevDynRouteIpOspfTimerDueFlag, wingStatsDevDynRouteIpOspfDueIn,
                                wingStatsDevDynRouteIpOspflsaRefreshTimer, wingStatsDevDynRouteIpOspfAbrFlag, wingStatsDevDynRouteIpOspfAbrType, wingStatsDevDynRouteIpOspfAsbrFlag, wingStatsDevDynRouteIpOspfExtLsdbCount,
                                wingStatsDevDynRouteIpOspfExtLsdbCsum, wingStatsDevDynRouteIpOspfOpaqueLsdbCount, wingStatsDevDynRouteIpOspfOpaqueExtLsdbCsum, wingStatsDevDynRouteIpOspfNumAreasAttached, wingStatsDevDynRouteOspfAreaId,
                                wingStatsDevDynRouteOspfAreaType, wingStatsDevDynRouteOspfAreaBackboneFlag, wingStatsDevDynRouteOspfAreaNoSummaryFlag, wingStatsDevDynRouteOspfAreaShortcutType, wingStatsDevDynRouteOspfAreaShortcutCapability,
                                wingStatsDevDynRouteOspfAreaInterfaceNum, wingStatsDevDynRouteOspfAreaActiveInterfaces, wingStatsDevDynRouteOspfAreaNssaFlag, wingStatsDevDynRouteOspfAreaNssaTransType, wingStatsDevDynRouteOspfAreaStubRouterStateFlag,
                                wingStatsDevDynRouteOspfAreaAdminStubRoutedFlag, wingStatsDevDynRouteOspfAreaStartupTimeDue, wingStatsDevDynRouteOspfAreaNumFullyAdjNbrs, wingStatsDevDynRouteOspfAreaAuthType, 
                                wingStatsDevDynRouteOspfAreaNumFullVirtualAdj, wingStatsDevDynRouteOspfAreaNumSpfExecuted, wingStatsDevDynRouteOspfAreaNumTotalLsa, wingStatsDevDynRouteOspfAreaNumRouterLsa, wingStatsDevDynRouteOspfAreaRouterLsaCsum,
                                wingStatsDevDynRouteOspfAreaNumNetworkLsa, wingStatsDevDynRouteOspfAreaNetworkLsaCsum, wingStatsDevDynRouteOspfAreaNumSummaryLsa, wingStatsDevDynRouteOspfAreaSummaryLsaCsum, wingStatsDevDynRouteOspfAreaNumAsbrSummaryLsa,
                                wingStatsDevDynRouteOspfAreaAsbrSummaryLsaCsum, wingStatsDevDynRouteOspfAreaNumNssaLsa, wingStatsDevDynRouteOspfAreaNssaLsaCsum, wingStatsDevDynRouteOspfAreaNumOpaqueLinkLsa, wingStatsDevDynRouteOspfAreaOpaqueLinkLsaCsum,
                                wingStatsDevDynRouteOspfAreaNumOpaqueAreaLsa, wingStatsDevDynRouteOspfAreaOpaqueAreaLsaCsum, wingStatsDevDynRouteIpOspfNetworkRoute, wingStatsDevDynRouteIpOspfNetworkRoutesPathType, wingStatsDevDynRouteIpOspfNetworkRoutesDestType,
                                wingStatsDevDynRouteIpOspfNetworkRoutesCost, wingStatsDevDynRouteIpOspfNetworkRoutesArea, wingStatsDevDynRouteIpOspfNetworkRoutesMPathsIndex, wingStatsDevDynRouteIpOspfNetworkRoutesAttachedFlags, wingStatsDevDynRouteIpOspfNetworkRoutesIfName,
                                wingStatsDevDynRouteIpOspfNetworkRoutesNextHop, wingStatsDevDynRouteIpOspfRouterRoute, wingStatsDevDynRouteIpOspfRouterRoutesInfoIndex, wingStatsDevDynRouteIpOspfRouterRoutePathType, wingStatsDevDynRouteIpOspfRouterRouteArea,
                                wingStatsDevDynRouteIpOspfRouterRouteCost, wingStatsDevDynRouteIpOspfRouterRouteFlags, wingStatsDevDynRouteIpOspfRouterRouteAttachedFlag, wingStatsDevDynRouteIpOspfRouterRouteIfName, wingStatsDevDynRouteIpOspfRouterRouteNextHop,
                                wingstatsDevDynRouteIpOspfExtRoute, wingstatsDevDynRouteIpOspfExtRoutePathType, wingstatsDevDynRouteIpOspfExtRouteArea, wingstatsDevDynRouteIpOspfExtRouteCost, wingstatsDevDynRouteIpOspfExtRouteType2Cost,
                                wingstatsDevDynRouteIpOspfExtRouteTag, wingstatsDevDynRouteIpOspfExtRoutesMPathsIndex, wingstatsDevDynRouteIpOspfExtRouteAttachedFlag, wingstatsDevDynRouteIpOspfExtRouteIfName, wingstatsDevDynRouteIpOspfExtRouteNextHop,
                                wingStatsDevDynRouteBorderRouter, wingStatsDevDynRouteBorderRoutersInfoIndex, wingStatsDevDynRouteBorderRouterPathType, wingStatsDevDynRouteBorderRouterArea, wingStatsDevDynRouteBorderRouterCost,
                                wingStatsDevDynRouteBorderRouterFlags, wingStatsDevDynRouteBorderRouterAttachedFlag, wingStatsDevDynRouteBorderRouterIfName, wingStatsDevDynRouteBorderRouterNextHop, wingStatsDevDynRouteOspfIfName,
                                wingStatsDevDynRouteOspfIfStatusFlag, wingStatsDevDynRouteOspfIfIndex, wingStatsDevDynRouteOspfIfMtu, wingStatsDevDynRouteOspfIfBandwidth, wingStatsDevDynRouteOspfIfFlags,
                                wingStatsDevDynRouteOspfIfEnabled, wingStatsDevDynRouteOspfIfInfoIndex, wingStatsDevDynRouteOspfIfIpAddr, wingStatsDevDynRouteOspfIfMask, wingStatsDevDynRouteOspfIfBroadcastOrP2P,
                                wingStatsDevDynRouteOspfIfBroadcastOrP2PIpAddr, wingStatsDevDynRouteOspfIfAreaId, wingStatsDevDynRouteOspfIfMtuMismatchDetectFlag, wingStatsDevDynRouteOspfIfRouterId, wingStatsDevDynRouteOspfIfNetworkType,
                                wingStatsDevDynRouteOspfIfCost, wingStatsDevDynRouteOspfIfTransmitDelay, wingStatsDevDynRouteOspfIfIsmState, wingStatsDevDynRouteOspfIfPriority, wingStatsDevDynRouteOspfIfDesgRouterId,
                                wingStatsDevDynRouteOspfIfDesgRouterAddr, wingStatsDevDynRouteOspfIfBackupDesgRouterId, wingStatsDevDynRouteOspfIfBackupDesgRouterAddr, wingStatsDevDynRouteOspfIfMcastMembership, wingStatsDevDynRouteOspfIfSubSecHelloFlag,
                                wingStatsDevDynRouteOspfIfHelloInterval, wingStatsDevDynRouteOspfIfDeadInterval, wingStatsDevDynRouteOspfIfWaitInterval, wingStatsDevDynRouteOspfIfRetransmitInterval, wingStatsDevDynRouteOspfIfPassiveFlag,
                                wingStatsDevDynRouteOspfIfHelloDueIn, wingStatsDevDynRouteOspfIfNeighborCount, wingStatsDevDynRouteOspfIfAdjNeighborCount, wingStatsDevDynRouteNeighborIndex, wingStatsDevDynRouteNeighborRouterId,
                                wingStatsDevDynRouteNeighborPriority, wingStatsDevDynRouteNeighborSelfState, wingStatsDevDynRouteNeighborDeadTime, wingStatsDevDynRouteNeighborAddr, wingStatsDevDynRouteNeighborIfName,
                                wingStatsDevDynRouteNeighborSrcAddr, wingStatsDevDynRouteNeighborRetansmitCount, wingStatsDevDynRouteNeighborRequestCount, wingStatsDevDynRouteNeighborSummaryCount, wingStatsDevDynRouteIpOspfRouterId,
                                wingCfgProfDynRouteDefaultInfoAlways, wingCfgProfDynRouteOspfPassive, wingCfgProfDynRouteOspfPassiveRemoved, wingCfgProfDynRouteOspfVrrpStateCheck, 
                                wingCfgProfDynRouteDefaultInfoOriginate, wingStatsDevPbrRuleString,
				wingCfgProfVpnIkev1RemoteLocalUsersName, wingCfgProfVpnIkev1RemoteLocalUsersPassword, wingCfgDevVpnIkev1RemoteLocalUsersName, 
				wingCfgDevVpnIkev1RemoteLocalUsersPassword, wingCfgProfVpnIkev2RemoteLocalUsersName, wingCfgProfVpnIkev2RemoteLocalUsersPassword, 
				wingCfgDevVpnIkev2RemoteLocalUsersName, wingCfgDevVpnIkev2RemoteLocalUsersPassword, wingCfgDevVpnCryptoInstSequence, 
				wingCfgDevVpnCryptoInstType, wingCfgDevVpnCryptoInstIpAcl, wingCfgDevVpnCryptoInstTransformSet, wingCfgDevVpnCryptoInstLocalip, 
				wingCfgDevVpnCryptoInstPfs, wingCfgDevVpnCryptoInstLifetimeSeconds, wingCfgDevVpnCryptoInstLifetimeKb, 
				wingCfgDevVpnCryptoInstRemoteType, wingCfgDevVpnCryptoInstModeconfig, wingCfgDevVpnCryptoInstPeer, wingCfgDevVpnCryptoInstProtocol, 
				wingCfgDevVpnCryptoInstMode, wingCfgDevVpnIkev2RemoteLocalUsersName, wingCfgDevVpnIkev2RemoteLocalUsersPassword, 
				wingCfgDevVpnAutoIPSecSecureGroupId, wingCfgDevVpnAutoIPSecSecureGroupIdAuthType, 
				wingCfgDevVpnAutoIPSecSecureGroupIdAuthKey, wingCfgDevVpnAutoIPSecSecureRemoteGWIkeVersion, 
				wingCfgProfVpnAutoIPSecSecureGroupId, wingCfgProfVpnAutoIPSecSecureGroupIdAuthType, 
				wingCfgProfVpnAutoIPSecSecureGroupIdAuthKey, wingCfgProfVpnAutoIPSecSecureRemoteGWIkeVersion, wingCfgProfVpnCryptoInstPeerListPriority,
				wingCfgProfVpnCryptoInstPeerListType, wingCfgProfVpnCryptoInstPeerListIkev1Peer, wingCfgProfVpnCryptoInstPeerListIkev2Peer,
				wingStatsRfdWlRadioDetailWlanMapWlanName, wingStatsRfdWlRadioDetailWlanMapBssIndex, wingStatsRfdWlRadioDetailWlanMapIsPrimary,
				wingStatsRfdWlRadioDetailBssMapBssIndex, wingStatsRfdWlRadioDetailBssMapBasicRates, wingStatsRfdWlRadioDetailBssMapSupportedRates,
				wingCfgDevVpnCryptoInstPeerListPriority, wingCfgDevVpnCryptoInstPeerListType, wingCfgDevVpnCryptoInstPeerListIkev1Peer, 
				wingCfgDevVpnCryptoInstPeerListIkev2Peer, wingCfgProfVpnCryptoInstAhSessionDirection, wingCfgProfVpnCryptoInstAhSessionSpi,
				wingCfgProfVpnCryptoInstAhSessionAuth, wingCfgProfVpnCryptoInstAhSessionKey, wingCfgDevVpnCryptoInstAhSessionDirection, 
				wingCfgDevVpnCryptoInstAhSessionSpi, wingCfgDevVpnCryptoInstAhSessionAuthAlgo, wingCfgDevVpnCryptoInstAhSessionKey, 
				wingCfgProfVpnCryptoInstEspSessionDirection, wingCfgProfVpnCryptoInstEspSessionSpi, wingCfgProfVpnCryptoInstEspSessionCipherAlgo, 
				wingCfgProfVpnCryptoInstEspSessionCipherKey, wingCfgProfVpnCryptoInstEspSessionAuthAlgo, wingCfgProfVpnCryptoInstEspSessionAuthKey, 
				wingCfgDevVpnCryptoInstEspSessionDirection, wingCfgDevVpnCryptoInstEspSessionSpi, wingCfgDevVpnCryptoInstEspSessionCipherAlgo, 
				wingCfgDevVpnCryptoInstEspSessionCipherKey, wingCfgDevVpnCryptoInstEspSessionAuthAlgo, wingCfgDevVpnCryptoInstEspSessionAuthKey,
				wingCfgProfIfPppoeDefaultRoutePriority, wingCfgProfIfPppoeIp, wingCfgDevIfPppoeDefaultRoutePriority, wingCfgDevIfPppoeIp, 
				wingStatsDevPppoeStatusPeer, wingStatsDevPppoeStatusSid, wingStatsDevPppoeStatusService, wingStatsDevPppoeStatusStatus, 
				wingStatsDevPppoeStatusMtu, wingStatsDevPppoeStatusDns1, wingStatsDevPppoeStatusDns2, wingStatsDevPppoeCfgAuthtype, 
				wingStatsDevPppoeCfgIdleTime, wingStatsDevPppoeCfgKalive, wingStatsDevPppoeCfgMtu, wingStatsDevPppoeCfgNet, 
				wingStatsDevPppoeCfgService, wingStatsDevPppoeCfgUsername, wingStatsDevPppoeCfgPasswd, wingStatsDevPppoeCfgShutdown,
				wingCfgProfControllerHostIndex, wingCfgProfControllerHostRowStatus, wingCfgDevControllerHostIndex, wingCfgDevControllerHostRowStatus,
				wingCfgDevControllerHostHost, wingCfgDevControllerHostPool, wingCfgDevControllerHostLevel, wingActionReloadInMac,
				wingActionReloadInForce, wingActionReloadInTimeout, wingActionReloadInReason, wingActionReloadOutStatus, wingActionReloadOutMessage,
				wingActionReloadRun,
wingCfgLegacyApIndex, wingCfgLegacyApCountryCode, wingCfgLegacyApLed, wingCfgLegacyApLocation, wingCfgLegacyApIpAddr, wingCfgLegacyApGateway, wingCfgLegacyApPreferredControllerGroup,
				wingCfgLegacyApIfName, wingCfgLegacyApIfDescr, wingCfgLegacyApIfShutdown, wingCfgLegacyApIfRfMode, wingCfgLegacyApIfAntennaDiversity, wingCfgLegacyApIfBeaconInterval, wingCfgLegacyApIfChannel, wingCfgLegacyApIfMaxClients, wingCfgLegacyApIfPlacement, wingCfgLegacyApIfPower, wingCfgLegacyApIfPreambleShort, wingCfgLegacyApIfOnChannelScan, wingCfgLegacyApIfRtsThreshold, wingCfgLegacyApIfQosPolicy, wingCfgLegacyApIfWirelessClientPower,	
				wingCfgLegacyApIfWlanBssMapWlan, wingCfgLegacyApIfWlanBssMapBss, wingCfgLegacyApIfWlanBssMapPrimary, wingStatsRfdWlRadioStatTxRetries, wingStatsRfdWlRadioStatTxRetriedBytes,
				wingStatsNocAdoptDevMac, wingStatsNocAdoptDevType, wingStatsNocAdoptDevHostname, wingStatsNocAdoptDevVersion, wingStatsNocAdoptDevSerialNo, wingStatsNocAdoptDevRfDomainName,
				wingStatsNocAdoptDevOnline, wingStatsNocAdoptDevBy, wingStatsNocAdoptDevLastAdoption, wingStatsNocAdoptDevModelNumber, wingStatsNocAdoptDevStartup,
				wingStatsNocAdoptDevCfgStatus, wingStatsNocAdoptPendingDevMac, wingStatsNocAdoptPendingDevType, wingStatsNocAdoptPendingDevTarget, wingStatsNocAdoptPendingDevDisOption,
				wingStatsNocAdoptPendingDevVersion, wingStatsNocAdoptPendingDevSerialNumber, wingStatsNocAdoptPendingDevReason, wingStatsNocAdoptPendingDevNumRadios,
				wingStatsNocAdoptPendingDevIp, wingStatsNocAdoptPendingDevVlan, wingCfgAltDevMac, wingCfgAltDevHostname, wingCfgAltDevBuilding, wingCfgAltDevFloor, wingCfgAltDevNumRadios,
				wingCfgAltDevProfileName, wingCfgAltDevRfDomainName, wingCfgAltDevHttpsTrustpoint, wingCfgAltDevRadiusCaTrustpoint, wingCfgAltDevRadiusServerTrustpoint,
				wingCfgAltDevSshRsaKey, wingCfgAltDevHasOverrides, wingCfgAltDevIfName, wingCfgAltDevIfDescription, wingCfgAltDevIfType, wingCfgAltDevIfShutdown, wingCfgAltDevIfIpInAcl,
				wingCfgAltDevIfMacInAcl, wingCfgAltDevIfRadioBssmapWlan, wingCfgAltDevIfRadioBssmapBss, wingCfgAltDevIfRadioBssmapPrimary, wingCfgProfNatPoolAddrStartIp,
				wingCfgProfNatPoolAddrEndIp, wingCfgProfNatBridgeSrcDynamicAcl, wingCfgProfNatBridgeSrcDynamicIfName, wingCfgProfNatBridgeSrcDynamicIfOverloadType,
				wingCfgProfNatBridgeSrcDynamicIfOverloadIp, wingCfgProfNatBridgeSrcDynamicIfNatPool, wingCfgDevNatPoolAddrStartIp, wingCfgDevNatPoolAddrEndIp,
				wingCfgDevNatBridgeSrcDynamicAcl, wingCfgDevNatBridgeSrcDynamicIfName, wingCfgDevNatBridgeSrcDynamicIfOverloadType, wingCfgDevNatBridgeSrcDynamicIfOverloadIp,
				wingCfgDevNatBridgeSrcDynamicIfNatPool, wingCfgDevNatPoolName, wingStatsDevl2tpv3TunnelName, wingStatsDevl2tpv3TunnelCtrlConnId, wingStatsDevl2tpv3TunnelUpTime,
				wingStatsDevl2tpv3TunnelPeerAddr, wingStatsDevl2tpv3TunnelLocalAddr, wingStatsDevl2tpv3TunnelMtu, wingStatsDevl2tpv3TunnelNativeVlanId,
				wingStatsDevl2tpv3TunnelTrunkSession, wingStatsDevl2tpv3TunnelNativeVlanTagged, wingStatsDevl2tpv3TunnelPeerHostName, wingStatsDevl2tpv3TunnelPeerCtrlConnId,
				wingStatsDevl2tpv3TunnelPeerVendorName, wingStatsDevl2tpv3TunnelState, wingStatsDevl2tpv3TunnelNextTxSeqNum, wingStatsDevl2tpv3TunnelNextRxSeqNum,
				wingStatsDevl2tpv3TunnelRxAckSeqNum, wingStatsDevl2tpv3TunnelRetransmitCount, wingStatsDevl2tpv3TunnelReconnectCount, wingStatsDevl2tpv3SessionsVlanId,
				wingStatsDevl2tpv3SessionsName, wingStatsDevl2tpv3SessionsPseudoWireType, wingStatsDevl2tpv3SessionsCallSerialNumber, wingStatsDevl2tpv3SessionsLocalSessionId,
				wingStatsDevl2tpv3SessionsRemoteSessionId, wingStatsDevl2tpv3SessionsLocalCookieSize, wingStatsDevl2tpv3SessionsLocalcookieWord1,
				wingStatsDevl2tpv3SessionsLocalCookieWord2, wingStatsDevl2tpv3SessionsRemoteCookieSize, wingStatsDevl2tpv3SessionsRemoteCookieWord1,
				wingStatsDevl2tpv3SessionsRemoteCookieWord2, wingStatsDevl2tpv3SessionsState, wingStatsDevl2tpv3SessionsRemoteEndId, wingCfgProfTunnelController,
				wingCfgProfPreferredTunnelController, wingCfgProfMintMlcpVlan, wingCfgProfMintMlcpIp, wingCfgProfMintTunnelControllerLoadBalancingLevel1, wingCfgProfl2tpv3lUdpListenPort,
				wingCfgProfl2tpv3RouterId, wingCfgProfl2tpv3HostName, wingCfgProfl2tpv3InterTunnelBridging, wingCfgProfl2tpv3TunnelName, wingCfgProfl2tpv3TunnelLocalIpAddrss,
				wingCfgProfl2tpv3TunnelMtu, wingCfgProfl2tpv3TunnelUseTunnelPolicy, wingCfgProfl2tpv3TunnelHostname, wingCfgProfl2tpv3TunnelRouterId, wingCfgProfl2tpv3TunnelPeerId,
				wingCfgProfl2tpv3TunnelPeerIp, wingCfgProfl2tpv3TunnelPeerHostName, wingCfgProfl2tpv3TunnelPeerRouterId, wingCfgProfl2tpv3TunnelPeerEncapsulation,
				wingCfgProfl2tpv3TunnelPeerUDPPort, wingCfgProfl2tpv3TunnelSessionName, wingCfgProfl2tpv3TunnelSessionPseudoWireId, wingCfgProfl2tpv3TunnelSessionTrafficSourceType,
				wingCfgProfl2tpv3TunnelSessionTrafficSourceValue, wingCfgProfl2tpv3TunnelSessionNativeVlan, wingCfgProfl2tpv3ManualSessionName, wingCfgProfl2tpv3ManualSessionLocalIpAddr,
				wingCfgProfl2tpv3ManualSessionPeerIp, wingCfgProfl2tpv3ManualSessionPeerEncapsulation, wingCfgProfl2tpv3ManualSessionPeerUDPPort, wingCfgProfl2tpv3ManualSessionMtu,
				wingCfgProfl2tpv3ManualSessionTrafficSource, wingCfgProfl2tpv3ManualSessionTrafficSourceValue, wingCfgProfl2tpv3ManualSessionNativeVlan,
				wingCfgProfl2tpv3ManualSessionLocalSessionId, wingCfgProfl2tpv3ManualSessionRemoteSessionId, wingCfgProfl2tpv3ManualSessionCookieEndpoint,
				wingCfgProfl2tpv3ManualSessionCookieSize, wingCfgProfl2tpv3ManualSessionCookieVal1, wingCfgProfl2tpv3ManualSessionCookieVal2, wingCfgDevTunnelController,
				wingCfgDevPreferredTunnelController, wingCfgDevMintLevel1AreaId, wingCfgDevMintSpfLatency, wingCfgDevMintDisPriorityAdjustment, wingCfgDevMintMlcpVlan,
				wingCfgDevMintMlcpIp, wingCfgDevMintTunnelControllerLoadBalancingLevel1, wingCfgDevl2tpv3lUdpListenPort, wingCfgDevl2tpv3RouterId, wingCfgDevl2tpv3HostName,
				wingCfgDevl2tpv3InterTunnelBridging, wingCfgDevl2tpv3TunnelName, wingCfgDevl2tpv3TunnelLocalIpAddrss, wingCfgDevl2tpv3TunnelMtu, wingCfgDevl2tpv3TunnelUseTunnelPolicy,
				wingCfgDevl2tpv3TunnelHostname, wingCfgDevl2tpv3TunnelRouterId, wingCfgDevl2tpv3TunnelPeerId, wingCfgDevl2tpv3TunnelPeerIp, wingCfgDev2tpv3TunnelPeerHostName,
				wingCfgDevl2tpv3TunnelPeerRouterId, wingCfgDevl2tpv3TunnelPeerEncapsulation, wingCfgDevl2tpv3TunnelPeerUDPPort, wingCfgDevl2tpv3TunnelSessionName,
				wingCfgDevl2tpv3TunnelSessionPseudoWireId, wingCfgDevl2tpv3TunnelSessionTrafficSourceType, wingCfgDevl2tpv3TunnelSessionTrafficSourceValue,
				wingCfgDevl2tpv3TunnelSessionNativeVlan, wingCfgDevl2tpv3ManualSessionName, wingCfgDevl2tpv3ManualSessionLocalIpAddr, wingCfgDevl2tpv3ManualSessionPeerIp,
				wingCfgDevl2tpv3ManualSessionPeerEncapsulation, wingCfgDevl2tpv3ManualSessionPeerUDPPort, wingCfgDevl2tpv3ManualSessionMtu, wingCfgDevl2tpv3ManualSessionTrafficSource,
				wingCfgDevl2tpv3ManualSessionTrafficSourceValue, wingCfgDevl2tpv3ManualSessionNativeVlan, wingCfgDevl2tpv3ManualSessionLocalSessionId,
				wingCfgDevl2tpv3ManualSessionRemoteSessionId, wingCfgDevl2tpv3ManualSessionCookieEndpoint, wingCfgDevl2tpv3ManualSessionCookieSize, wingCfgDevl2tpv3ManualSessionCookieVal1,
				wingCfgDevl2tpv3ManualSessionCookieVal2, wingStatsDevDynRouteIpOspfMaxRoutes, wingStatsDevDynRouteIpOspfRoutesReceived, wingStatsDevDynRouteIpOspfMaxIgnoreStateCount,
				wingStatsDevDynRouteIpOspfIgnoreStateCount, wingStatsDevDynRouteIpOspfIgnoreStateTimeout, wingStatsDevDynRouteIpOspfIgnoreStateMonitorTimeout,
				wingStatsDevDynRouteIpOspfState, wingCfgProfDynRouteOspfDefaultRoutePriority, wingCfgProfDynRouteOspfNumRoutes, wingCfgProfDynRouteOspfRetryCount,
				wingCfgProfDynRouteOspfRetryTimeout, wingCfgProfDynRouteOspfResetTime, wingCfgDevDynRouteOspfDefaultRoutePriority, wingCfgDevDynRouteOspfNumRoutes,
				wingCfgDevDynRouteOspfRetryCount, wingCfgDevDynRouteOspfRetryTimeout, wingCfgDevDynRouteOspfResetTime, wingCfgProfIfVlanOspfOspfBandWidth,
				wingCfgProfIfVlanOspfMsgDigestKeyId, wingCfgProfIfVlanOspfMsgDigestMessageDigest, wingCfgDevIfVlanOspfOspfBandWidth, wingCfgDevIfVlanOspfMsgDigestKeyId,
				wingCfgDevIfVlanOspfMsgDigestMessageDigest, wingStatsDevl2tpv3TunnelEncapsulationProtocol, wingStatsDevl2tpv3SessionsRxPktCounter,
				wingStatsDevl2tpv3SessionsRxBytesCounter, wingStatsDevl2tpv3SessionsTxPktCounter, wingStatsDevl2tpv3SessionsTxBytesCounter,
				wingStatsDevl2tpv3SessionsNumDroppedPkts, wingCfgProfIfRadioAntennaDowntilt, wingCfgProfIfRadioExtendedRange, wingCfgDevIfRadioAntennaDowntilt, wingCfgDevIfRadioExtendedRange,
				wingCfgProfIfT1E1Media, wingCfgProfIfT1E1ClockMode, wingCfgProfIfT1E1HighImpedance, wingCfgProfIfT1E1LineBuildOut, wingCfgProfIfT1E1LineEncoding,
				wingCfgProfIfT1E1RxSensitivityLevel, wingCfgProfIfSerialAuthentication, wingCfgProfIfSerialEncapsulation, wingCfgProfIfSerialLocalIpAddress, wingCfgProfIfSerialUsername,
				wingCfgProfIfSerialPassword, wingCfgProfIfSerialRemoteIpSubnet, wingCfgDevIfT1E1Media, wingCfgDevIfT1E1ClockMode, wingCfgDevIfT1E1HighImpedance,
				wingCfgDevIfT1E1LineBuildOut, wingCfgDevIfT1E1LineEncoding, wingCfgDevIfT1E1RxSensitivityLevel, wingCfgDevIfSerialAuthentication, wingCfgDevIfSerialEncapsulation,
				wingCfgDevIfSerialLocalIpAddress, wingCfgDevIfSerialUsername, wingCfgDevIfSerialPassword, wingCfgDevIfSerialRemoteIpSubnet, 
				wingCfgProfIfDot1xAuthHostMode, wingCfgProfIfDot1xAuthGuestVlan, wingCfgProfIfDot1xAuthPortControl, 
				wingCfgProfIfDot1xAuthReauthenticate, wingCfgProfIfDot1xAuthMaxReauthCount, wingCfgProfIfDot1xAuthMaxReq, 
				wingCfgProfIfDot1xAuthQuietPeriod, wingCfgProfIfDot1xAuthReauthPeriod, wingCfgDevIfDot1xAuthHostMode, 
				wingCfgDevIfDot1xAuthGuestVlan, wingCfgDevIfDot1xAuthPortControl, wingCfgDevIfDot1xAuthReauthenticate, 
				wingCfgDevIfDot1xAuthMaxReauthCount, wingCfgDevIfDot1xAuthMaxReq, wingCfgDevIfDot1xAuthQuietPeriod, 
				wingCfgDevIfDot1xAuthReauthPeriod, wingCfgProfDot1xSysAuthCtrl, wingCfgProfDot1xGuestVlanCtrl, 
				wingCfgProfDot1xAaaPolicy, wingCfgDevDot1xSysAuthCtrl, wingCfgDevDot1xGuestVlanCtrl, 
				wingCfgDevDot1xAaaPolicy, wingCfgProfCriticalResourcesPort, wingCfgDevCriticalResourcesPort, 
				wingStatsDevCrmMonitorInterval, wingStatsDevCrmCriticalResVia, 	wingStatsDevCrmCriticalResStatus, 
				wingStatsDevCrmCriticalResErrorReason, 	wingStatsDevCrmCriticalResMode, wingStatsDevCrmCriticalResResAddr, 
				wingStatsDevCrmCriticalResResMonitorMode, wingStatsDevCrmCriticalResResArpVlan, wingStatsDevCrmCriticalResResStatus, 
				wingStatsDevCrmCriticalResResArpPort, wingCfgProfMeshpointDevName, wingCfgProfMeshpointDevIsRootDev, 
				wingCfgProfMeshpointDevPreferredRoot, wingCfgProfMeshpointDevPreferredNeighbor, wingCfgProfMeshpointDevPreferredIf, wingCfgProfMeshpointDevPathMethod,
				wingCfgDevMeshpointDevName, wingCfgDevMeshpointDevIsRootDev, wingCfgDevMeshpointDevPreferredRoot, 
				wingCfgDevMeshpointDevPreferredNeighbor, wingCfgDevMeshpointDevPreferredIf, wingCfgSmartRfOcsMeshpointA, 
				wingCfgSmartRfOcsMeshpointBg, wingCfgMcxMeshpointName, wingCfgMcxMeshpointShutdown, wingCfgMcxMeshpointMeshid, 
				wingCfgMcxMeshpointDescription, wingCfgMcxMeshpointBeaconFormat, wingCfgMcxMeshpointControlVlan, 
				wingCfgMcxMeshpointNeighborInactivityTimeout, wingCfgMcxMeshpointQosPolicy, wingCfgMcxMeshpointSecurityMode, 
				wingCfgMcxMeshpointWpa2Psk, wingCfgMcxMeshpointWpa2KeyRotationUnicast, wingCfgMcxMeshpointWpa2KeyRotationBroadcast, 
				wingCfgMcxMeshpointIsRoot, wingCfgMcxMeshpointMonitorCriticalResources, wingCfgMcxMeshpointMonitorPriPortLink, 
				wingCfgMcxMeshpointQosName, wingCfgMcxMeshpointQosMeshpointRlDownEnable, wingCfgMcxMeshpointQosMeshpointRlDownRate, 
				wingCfgMcxMeshpointQosMeshpointRlDownBurstSize, wingCfgMcxMeshpointQosMeshpointRlDownThreshBackground, 
				wingCfgMcxMeshpointQosMeshpointRlDownThreshBestEffort, wingCfgMcxMeshpointQosMeshpointRlDownThreshVoice, 
				wingCfgMcxMeshpointQosMeshpointRlDownThreshVideo, wingCfgMcxMeshpointQosMeshpointRlUpEnable, wingCfgMcxMeshpointQosMeshpointRlUpRate, 
				wingCfgMcxMeshpointQosMeshpointRlUpBurstSize, wingCfgMcxMeshpointQosMeshpointRlUpThreshBackground, 
				wingCfgMcxMeshpointQosMeshpointRlUpThreshBestEffort, wingCfgMcxMeshpointQosMeshpointRlUpThreshVoice, 
				wingCfgMcxMeshpointQosMeshpointRlUpThreshVideo, wingCfgMcxMeshpointQosNeighborRlDownEnable, 
				wingCfgMcxMeshpointQosNeighborRlDownRate, wingCfgMcxMeshpointQosNeighborRlDownBurstSize, 
				wingCfgMcxMeshpointQosNeighborRlDownThreshBackground, wingCfgMcxMeshpointQosNeighborRlDownThreshBestEffort, 
				wingCfgMcxMeshpointQosNeighborRlDownThreshVoice, wingCfgMcxMeshpointQosNeighborRlDownThreshVideo, 
				wingCfgMcxMeshpointQosNeighborRlUpEnable, wingCfgMcxMeshpointQosNeighborRlUpRate, wingCfgMcxMeshpointQosNeighborRlUpBurstSize, 
				wingCfgMcxMeshpointQosNeighborRlUpThreshBackground, wingCfgMcxMeshpointQosNeighborRlUpThreshBestEffort, 
				wingCfgMcxMeshpointQosNeighborRlUpThreshVoice, wingCfgMcxMeshpointQosNeighborRlUpThreshVideo, wingCfgMcxMeshpointQosAddr, 
				wingCfgMcxMeshpointQosPriority, wingCfgProfIfMeshpointBssmapMeshpoint, wingCfgProfIfMeshpointBssmapBss, 
				wingCfgDevIfMeshpointBssmapMeshpoint, wingCfgDevIfMeshpointBssmapBss, wingStatsDevWlMcxMeshpointMpid, wingStatsDevWlMcxMeshpointName, 
				wingStatsDevWlMcxMeshpointHostname, wingStatsDevWlMcxMeshpointDeviceMac, wingStatsDevWlMcxMeshpointIsRoot, 
				wingStatsDevWlMcxMeshpointIsCfgRoot, wingStatsDevWlMcxMeshpointRootMpid, wingStatsDevWlMcxMeshpointNextHop, 
				wingStatsDevWlMcxMeshpointRootHops, wingStatsDevWlMcxMeshpointIfidCnt, wingStatsDevWlMcxMeshpointIfid, 
				wingStatsDevWlMcxMeshpointIfidDataDesc, wingStatsDevWlMcxMeshpointStatsName, wingStatsDevWlMcxMeshpointStatsMeshid, 
				wingStatsDevWlMcxMeshpointStatsNumRadios, wingStatsDevWlMcxMeshpointStatsNumNeighbors, 
				wingStatsDevWlMcxMeshpointStatsTxBytes, wingStatsDevWlMcxMeshpointStatsRxBytes, wingStatsDevWlMcxMeshpointStatsTxPkts, 
				wingStatsDevWlMcxMeshpointStatsRxPkts, wingStatsDevWlMcxMeshpointStatsTxDropped, wingStatsDevWlMcxMeshpointStatsRxErrors, 
				wingStatsDevWlMcxMeshpointStatsTIndex, wingStatsDevWlMcxMeshpointStatsTotalBytes, wingStatsDevWlMcxMeshpointStatsTotalPkts, 
				wingStatsDevWlMcxMeshpointStatsTxBps, wingStatsDevWlMcxMeshpointStatsRxBps, wingStatsDevWlMcxMeshpointStatsTotalBps, 
				wingStatsDevWlMcxMeshpointStatsTxPps, wingStatsDevWlMcxMeshpointStatsRxPps, wingStatsDevWlMcxMeshpointStatsTotalPps, 
				wingStatsDevWlMcxMeshpointStatsTxBcmcPkts, wingStatsDevWlMcxMeshpointStatsRxBcmcPkts, wingStatsDevWlMcxMeshpointStatsTotalBcmcPkts, 
				wingStatsDevWlMcxMeshpointStatsTxMgmtPkts, wingStatsDevWlMcxMeshpointStatsRxMgmtPkts, wingStatsDevWlMcxMeshpointStatsTotalMgmtPkts, 
				wingStatsDevWlMcxMeshpointStatsMaxUserRate, wingStatsDevWlMcxMeshpointNeighborsMpid, 
				wingStatsDevWlMcxMeshpointNeighborsName, wingStatsDevWlMcxMeshpointNeighborsHostname, wingStatsDevWlMcxMeshpointNeighborsDeviceMac, 
				wingStatsDevWlMcxMeshpointNeighborsNumEntries, wingStatsDevWlMcxMeshpointNeighborsEntriesNeighborIfid, 
				wingStatsDevWlMcxMeshpointNeighborsEntriesNeighborMpid, wingStatsDevWlMcxMeshpointNeighborsEntriesBoundRoot, 
				wingStatsDevWlMcxMeshpointNeighborsEntriesRootMetric, wingStatsDevWlMcxMeshpointNeighborsEntriesRootHops, 
				wingStatsDevWlMcxMeshpointNeighborsEntriesValid, wingStatsDevWlMcxMeshpointNeighborsEntriesRoot, 
				wingStatsDevWlMcxMeshpointNeighborsEntriesProxy, wingStatsDevWlMcxMeshpointNeighborsEntriesGeoReference, 
				wingStatsDevWlMcxMeshpointNeighborsEntriesMobile, wingStatsDevWlMcxMeshpointNeighborsEntriesInterfaceId, 
				wingStatsDevWlMcxMeshpointNeighborsEntriesAuthState, wingStatsDevWlMcxMeshpointNeighborsEntriesRank, 
				wingStatsDevWlMcxMeshpointNeighborsEntriesResourced, wingStatsDevWlMcxMeshpointNeighborsEntriesLinkQuality, 
				wingStatsDevWlMcxMeshpointNeighborsEntriesLinkMetric, wingStatsDevWlMcxMeshpointNeighborsEntriesAge, 
				wingStatsDevWlMcxMeshpointPathsMpid, wingStatsDevWlMcxMeshpointPathsName, wingStatsDevWlMcxMeshpointPathsHostname, 
				wingStatsDevWlMcxMeshpointPathsDeviceMac, wingStatsDevWlMcxMeshpointPathsNumEntries, 
				wingStatsDevWlMcxMeshpointPathsEntriesDestMpid, wingStatsDevWlMcxMeshpointPathsEntriesNextHopIfid, 
				wingStatsDevWlMcxMeshpointPathsEntriesPathMetric, wingStatsDevWlMcxMeshpointPathsEntriesHops, 
				wingStatsDevWlMcxMeshpointPathsEntriesPathState, wingStatsDevWlMcxMeshpointPathsEntriesBindState, 
				wingStatsDevWlMcxMeshpointPathsEntriesValid, wingStatsDevWlMcxMeshpointPathsEntriesRoot, wingStatsDevWlMcxMeshpointPathsEntriesProxy, 
				wingStatsDevWlMcxMeshpointPathsEntriesGeoReference, wingStatsDevWlMcxMeshpointPathsEntriesMobile, 
				wingStatsDevWlMcxMeshpointPathsEntriesDestinationSequence, wingStatsDevWlMcxMeshpointPathsEntriesPathTimeout, 
				wingStatsDevWlMcxMeshpointPathsEntriesNewRouteTimeout, wingStatsDevWlMcxMeshpointPathsEntriesDestMintId, 
				wingStatsDevWlMcxMeshpointRootsMpid, wingStatsDevWlMcxMeshpointRootsName, wingStatsDevWlMcxMeshpointRootsHostname, 
				wingStatsDevWlMcxMeshpointRootsDeviceMac, wingStatsDevWlMcxMeshpointRootsNumEntries, wingStatsDevWlMcxMeshpointRootsEntriesRootMpid, 
				wingStatsDevWlMcxMeshpointRootsEntriesNextHopIfid, wingStatsDevWlMcxMeshpointRootsEntriesInterfaceId, 
				wingStatsDevWlMcxMeshpointRootsEntriesRecommended, wingStatsDevWlMcxMeshpointRootsEntriesBindFailed, 
				wingStatsDevWlMcxMeshpointRootsEntriesPathFailed, wingStatsDevWlMcxMeshpointRootsEntriesPathMetric, 
				wingStatsDevWlMcxMeshpointRootsEntriesNeighborBias, 
				wingStatsDevWlMcxMeshpointRootsEntriesRootBias, wingStatsDevWlMcxMeshpointProxiesMpid, 
				wingStatsDevWlMcxMeshpointProxiesName, wingStatsDevWlMcxMeshpointProxiesHostname, wingStatsDevWlMcxMeshpointProxiesDeviceMac, 
				wingStatsDevWlMcxMeshpointProxiesNumEntries, wingStatsDevWlMcxMeshpointProxiesEntriesProxyAddr, 
				wingStatsDevWlMcxMeshpointProxiesEntriesProxyOwner, wingStatsDevWlMcxMeshpointProxiesEntriesPersistence, 
				wingStatsDevWlMcxMeshpointProxiesEntriesAge, wingStatsDevWlMcxMeshpointProxiesEntriesVlan, wingStatsDevWlMcxMeshpointLsaMpid, 
				wingStatsDevWlMcxMeshpointLsaName, wingStatsDevWlMcxMeshpointLsaHostname, wingStatsDevWlMcxMeshpointLsaDeviceMac, 
				wingStatsDevWlMcxMeshpointLsaNumEntries, wingStatsDevWlMcxMeshpointLsaMeshid, wingStatsDevWlMcxMeshpointLsaR0Valid, 
				wingStatsDevWlMcxMeshpointLsaR0mdid, wingStatsDevWlMcxMeshpointLsaR0khid, wingStatsDevWlMcxMeshpointLsaEntriesLinkAddr, 
				wingStatsDevWlMcxMeshpointLsaEntriesInterfaceId, wingStatsDevWlMcxMeshpointLsaEntriesKeepAlive, 
				wingStatsDevWlMcxMeshpointLsaEntriesLinkState, wingStatsDevWlMcxMeshpointLsaEntriesLinkTimeout, 
				wingStatsDevWlMcxMeshpointMcastPathsMpid, wingStatsDevWlMcxMeshpointMcastPathsName, wingStatsDevWlMcxMeshpointMcastPathsHostname, 
				wingStatsDevWlMcxMeshpointMcastPathsDeviceMac, wingStatsDevWlMcxMeshpointMcastPathsNumEntries, 
				wingStatsDevWlMcxMeshpointMcastPathsEntriesGroupAddr, wingStatsDevWlMcxMeshpointMcastPathsEntriesMemberAddr, 
				wingStatsDevWlMcxMeshpointMcastPathsEntriesPathTimeout, 
				wingStatsRfdSmartRfRadioInfoMac, wingStatsRfdSmartRfRadioInfoApMac, wingStatsRfdSmartRfRadioInfoHostname, 
				wingStatsRfdSmartRfRadioInfoChannel, wingStatsRfdSmartRfRadioInfoPower, wingStatsRfdSmartRfRadioInfoRadioIdx, 
				wingStatsRfdSmartRfRadioInfoState, wingStatsRfdSmartRfRadioInfoType, wingStatsRfdSmartRfRadioActMac, 
				wingStatsRfdSmartRfRadioActApMac, wingStatsRfdSmartRfRadioActType, wingStatsRfdSmartRfRadioActPowerChanges, 
				wingStatsRfdSmartRfRadioActChannelChanges, wingStatsRfdSmartRfRadioActCoverageChanges, wingStatsRfdSmartRfRadioNeighborsMac, 
				wingStatsRfdSmartRfRadioNeighborsApMac, wingStatsRfdSmartRfRadioNeighborsHostname, wingStatsRfdSmartRfRadioNeighborsChannel, 
				wingStatsRfdSmartRfRadioNeighborsRadioIdx, wingStatsRfdSmartRfRadioNeighborsType, wingStatsRfdSmartRfRadioNeighborsNeighborsMac, 
				wingStatsRfdSmartRfRadioNeighborsNeighborsApMac, wingStatsRfdSmartRfRadioNeighborsNeighborsChannel, 
				wingStatsRfdSmartRfRadioNeighborsNeighborsPower, wingStatsRfdSmartRfRadioNeighborsNeighborsAttenuation, 
				wingStatsRfdSmartRfRadioNeighborsNeighborsRadioIdx, wingStatsRfdSmartRfRadioEnergyMac, 
				wingStatsRfdSmartRfRadioEnergyApMac, wingStatsRfdSmartRfRadioEnergyHostname, wingStatsRfdSmartRfRadioEnergyChannel, 
				wingStatsRfdSmartRfRadioEnergyRadioIdx, wingStatsRfdSmartRfRadioEnergyType, wingStatsRfdSmartRfRadioEnergyEnergyChannel, 
				wingStatsRfdSmartRfRadioEnergyEnergyExternal, wingStatsRfdSmartRfRadioEnergyEnergyNeighbor, wingStatsRfdSmartRfRadioEnergyEnergyNoise, 
				wingStatsRfdSmartRfRadioEnergyEnergyTotal, wingStatsRfdSmartRfRadioNonSsmMac, wingStatsRfdSmartRfRadioNonSsmInfoApMac, 
				wingStatsRfdSmartRfRadioNonSsmHostname, wingStatsRfdSmartRfRadioNonSsmChannel, wingStatsRfdSmartRfRadioNonSsmPower, 
				wingStatsRfdSmartRfRadioNonSsmRadioIdx, wingStatsRfdSmartRfRadioNonSsmState, wingStatsRfdSmartRfRadioNonSsmInfoType, 
				wingStatsRfdSmartRfRadioNonSsmActApMac, wingStatsRfdSmartRfRadioNonSsmActType, wingStatsRfdSmartRfRadioNonSsmPowerChanges, 
				wingStatsRfdSmartRfRadioNonSsmChannelChanges, wingStatsRfdSmartRfRadioNonSsmCoverageChanges, wingStatsRfdSmartRfRadioNonSsmNeighborsMac, 
				wingStatsRfdSmartRfRadioNonSsmNeighborsApMac, wingStatsRfdSmartRfRadioNonSsmNeighborsChannel, wingStatsRfdSmartRfRadioNonSsmNeighborsPower, 
				wingStatsRfdSmartRfRadioNonSsmNeighborsAttenuation, wingStatsRfdSmartRfRadioNonSsmNeighborsRadioIdx, 
				wingStatsRfdSmartRfRadioNonSsmEnergyChannel, wingStatsRfdSmartRfRadioNonSsmEnergyExternal, wingStatsRfdSmartRfRadioNonSsmEnergyNeighbor, 
				wingStatsRfdSmartRfRadioNonSsmEnergyNoise, wingStatsRfdSmartRfRadioNonSsmEnergyTotal, 
				wingStatsRfdSmartRfApMac, wingStatsRfdSmartRfApNeighborsMac, wingStatsRfdSmartRfApNeighborsApMac, 
				wingStatsRfdSmartRfApNeighborsHostname, wingStatsRfdSmartRfApNeighborsChannel, wingStatsRfdSmartRfApNeighborsPower, 
				wingStatsRfdSmartRfApNeighborsAttenuation, wingStatsRfdSmartRfApNeighborsInterference, wingStatsRfdSmartRfApNeighborsRadioIdx, 
				wingStatsRfdSmartRfApNeighborsListenerIdx, wingStatsRfdSmartRfApNeighborsListenerMac, wingStatsRfdSmartRfApNeighborsType, 
				wingStatsRfdSmartRfHighActRadiosMac, wingStatsRfdSmartRfHighActRadiosApMac, wingStatsRfdSmartRfHighActRadiosHostname, 
				wingStatsRfdSmartRfHighActRadiosType, wingStatsRfdSmartRfHighActRadiosPowerChanges, wingStatsRfdSmartRfHighActRadiosChannelChanges, 
				wingStatsRfdSmartRfHighActRadiosCoverageChanges, wingStatsRfdSmartRfHistoryTime, wingStatsRfdSmartRfHistoryApMac, 
				wingStatsRfdSmartRfHistoryHostname, wingStatsRfdSmartRfHistoryRadioMac, wingStatsRfdSmartRfHistoryRadioIdx, wingStatsRfdSmartRfHistoryOldValue, 
				wingStatsRfdSmartRfHistoryNewValue, wingStatsRfdSmartRfHistoryDaysTime, wingStatsRfdSmartRfHistoryDaysPowerChanges, 
				wingStatsRfdSmartRfHistoryDaysChannelChanges, wingStatsRfdSmartRfHistoryDaysCoverageChanges, wingStatsRfdSmartRfHistoryHoursTime, 
				wingStatsRfdSmartRfHistoryHoursPowerChanges, wingStatsRfdSmartRfHistoryHoursChannelChanges, wingStatsRfdSmartRfHistoryHoursCoverageChanges, 
				wingStatsRfdSmartRfDashboardHistoryDetails, wingStatsRfdSmartRfDashboardHistoryPowerChanges, wingStatsRfdSmartRfDashboardHistoryChannelChanges, 
				wingStatsRfdSmartRfDashboardHistoryCoverageChanges, wingStatsRfdSmartRfCalibrateResultMac, wingStatsRfdSmartRfCalibrateResultResultMac, 
				wingStatsRfdSmartRfCalibrateResultApMac, wingStatsRfdSmartRfCalibrateResultChannel, wingStatsRfdSmartRfCalibrateResultOldChannel, 
				wingStatsRfdSmartRfCalibrateResultPower, wingStatsRfdSmartRfCalibrateResultOldPower, wingStatsRfdSmartRfCalibrateResultRadioIdx, 
				wingStatsRfdSmartRfCalibrateResultState, wingStatsRfdSmartRfCalibrateResultType, wingStatsRfdSmartRfCalibrateResultSmartSensor, wingStatsDevIfStatusOper,
				wingStatsNocAdoptDevProductName, wingStatsDevAdoptDevProductName, wingStatsRfdWlRadioProtocol, wingEventSourceHostname,
				wingStatsDevWlApInfoMac, wingStatsDevWlApInfoFaultDetected,
				wingStatsDevWlApInfoNumRadios, wingStatsDevWlApInfoNumClients, wingStatsDevWlApInfoLastCalTime, wingStatsDevWlApInfoType, wingStatsDevWlApInfoStatsMode,
				wingStatsDevWlApInfoStatsInterval, wingStatsDevWlApInfoHostname, wingStatsDevWlApInfoRfDomainName, wingStatsDevWlApInfoLocation, wingStatsDevWlApInfoAdoptedTo,
				wingStatsDevWlApInfoIp, wingStatsDevWlClientStatMac, wingStatsDevWlClientStatMacName, wingStatsDevWlClientStatVendor, wingStatsDevWlClientStatAp,
				wingStatsDevWlClientStatTxBytes, wingStatsDevWlClientStatRxBytes, wingStatsDevWlClientStatTxPkts, wingStatsDevWlClientStatRxPkts, wingStatsDevWlClientStatTxDropped,
				wingStatsDevWlClientStatRxErrors, wingStatsDevWlClientStatTIndex, wingStatsDevWlClientStatTxBps, wingStatsDevWlClientStatRxBps, wingStatsDevWlClientStatSignal,
				wingStatsDevWlClientStatNoise, wingStatsDevWlClientStatSnr, wingStatsDevWlClientStatTxRate, wingStatsDevWlClientStatRxRate, wingStatsDevWlClientStatErrorRate,
				wingStatsDevWlClientStatQIndex, wingStatsDevWlRadioId, wingStatsDevWlRadioDeviceMac, wingStatsDevWlRadioAlias, wingStatsDevWlRadioMac, wingStatsDevWlRadioType,
				wingStatsDevWlRadioHostname, wingStatsDevWlRadioRfdName, wingStatsDevWlRadioLocation, wingStatsDevWlRadioState, wingStatsDevWlRadioCurChannel,
				wingStatsDevWlRadioConfigChannel, wingStatsDevWlRadioCurPower, wingStatsDevWlRadioConfigPower, wingStatsDevWlRadioMaxUserRate, wingStatsDevWlRadioNumClient,
				wingStatsDevWlRadioProtocol, wingStatsDevWlRadioStatId, wingStatsDevWlRadioStatDeviceMac, wingStatsDevWlRadioStatAlias, wingStatsDevWlRadioStatMac,
				wingStatsDevWlRadioStatType, wingStatsDevWlRadioStatTxBytes, wingStatsDevWlRadioStatRxBytes, wingStatsDevWlRadioStatTxPkts, wingStatsDevWlRadioStatRxPkts,
				wingStatsDevWlRadioStatTxDropped, wingStatsDevWlRadioStatRxErrors, wingStatsDevWlRadioStatTIndex, wingStatsDevWlRadioStatTxBps, wingStatsDevWlRadioStatRxBps,
				wingStatsDevWlRadioStatSignal, wingStatsDevWlRadioStatNoise, wingStatsDevWlRadioStatSnr, wingStatsDevWlRadioStatTxRate, wingStatsDevWlRadioStatRxRate,
				wingStatsDevWlRadioStatErrorRate, wingStatsDevWlRadioStatQIndex, wingStatsDevWlRadioStatNumClients, wingStatsDevWlRadioStatNumBClients,
				wingStatsDevWlRadioStatNumBgClients, wingStatsDevWlRadioStatNumBgnClients, wingStatsDevWlRadioStatNumAClients, wingStatsDevWlRadioStatNumAnClients,
				wingStatsDevWlRadioStatMediumErrorRate, wingStatsDevWlRadioStatTxRetries, wingStatsDevWlRadioStatTxRetriedBytes,
				wingStatsDevCdpNeighborAdvertisedVersion, wingStatsDevCdpNeighborVtpDomain, wingStatsDevCdpNeighborNativeVlan, wingStatsDevCdpNeighborUntrustedPortCos, 
				wingStatsDevCdpNeighborMgmtAddrList, wingStatsDevCdpNeighborVersion, wingStatsNocAdoptDevProductName, wingStatsDevAdoptDevProductName, 
				wingStatsRfdWlRadioProtocol, wingActionLocatorOnInDuration, wingActionLocatorOnInMac, wingActionLocatorOnOutStatus, wingActionLocatorOnOutMessage,
				wingActionLocatorOnRun, wingActionLocatorOffInMac, wingActionLocatorOffOutStatus, wingActionLocatorOffOutMessage, wingActionLocatorOffRun,wingStatsDevWlMcxMeshpointNeighborsEntriesIndex, 
				wingStatsDevWlMcxMeshpointPathsEntriesIndex, wingStatsDevWlMcxMeshpointRootsEntriesIndex, wingStatsDevWlMcxMeshpointProxiesEntriesIndex, 
				wingStatsDevWlMcxMeshpointLsaEntriesIndex, wingStatsDevWlMcxMeshpointMcastPathsEntriesIndex, wingCfgProfIfWwanDefaultRoutePriority
				}
			STATUS current
			DESCRIPTION 
				"This group is mandatory for all WiNG devices."
			::= { wingGroups 1 }

		
		-- 1.3.6.1.4.1.1916.2.131.50.2.2.2
		wingNotificationGroup NOTIFICATION-GROUP
				NOTIFICATIONS { wingTrapGeneric, wingTrapAaaRadiusDisconMsg, wingTrapAaaRadiusVlanUpdate
				, wingTrapAaaRadiusSessionNotStarted, wingTrapAaaRadiusSessionExpired, wingTrapAdvWipsAdvWipsEvent1
				, wingTrapAdvWipsAdvWipsEvent2, wingTrapAdvWipsAdvWipsEvent3, wingTrapAdvWipsAdvWipsEvent10
				, wingTrapAdvWipsAdvWipsEvent11, wingTrapAdvWipsAdvWipsEvent12, wingTrapAdvWipsAdvWipsEvent13
				, wingTrapAdvWipsAdvWipsEvent14, wingTrapAdvWipsAdvWipsEvent16, wingTrapAdvWipsAdvWipsEvent19
				, wingTrapAdvWipsAdvWipsEvent21, wingTrapAdvWipsAdvWipsEvent25, wingTrapAdvWipsAdvWipsEvent29
				, wingTrapAdvWipsAdvWipsEvent47, wingTrapAdvWipsAdvWipsEvent87, wingTrapAdvWipsAdvWipsEvent105
				, wingTrapAdvWipsAdvWipsEvent109, wingTrapAdvWipsAdvWipsEvent110, wingTrapAdvWipsAdvWipsEvent111
				, wingTrapAdvWipsAdvWipsEvent112, wingTrapAdvWipsAdvWipsEvent113, wingTrapAdvWipsAdvWipsEvent114
				, wingTrapAdvWipsAdvWipsEvent115, wingTrapAdvWipsAdvWipsEvent116, wingTrapAdvWipsAdvWipsEvent117
				, wingTrapAdvWipsAdvWipsEvent118, wingTrapAdvWipsAdvWipsEvent119, wingTrapAdvWipsAdvWipsEvent120
				, wingTrapAdvWipsAdvWipsEvent121, wingTrapAdvWipsAdvWipsEvent142, wingTrapAdvWipsAdvWipsEvent221
				, wingTrapAdvWipsAdvWipsEvent222, wingTrapAdvWipsAdvWipsEvent63, wingTrapAdvWipsAdvWipsEvent26
				, wingTrapAdvWipsAdvWipsEvent220, wingTrapApAdopted, wingTrapApUnadopted
				, wingTrapApAdoptedToController, wingTrapApReset, wingTrapApSwConnLost
				, wingTrapApApAutoupTimeout, wingTrapApApAutoupReboot, wingTrapApApAutoupNoNeed
				, wingTrapApApAutoupNeeded, wingTrapApApAutoupDone, wingTrapApApAutoupFail
				, wingTrapApApAutoupVer, wingTrapApNoImageFile, wingTrapApImageParseFailure
				, wingTrapApLegacyAutoUpdate, wingTrapApApAdopted, wingTrapApApUnadopted
				, wingTrapApApResetDetected, wingTrapApApResetRequest, wingTrapApApTimeout
				, wingTrapCaptivePortalAuthSuccess, wingTrapCaptivePortalAuthFailed, wingTrapCaptivePortalSessionTimeout
				, wingTrapCaptivePortalClientDisconnect, wingTrapCaptivePortalPurgeClient, wingTrapCaptivePortalFlexLogAccess
				, wingTrapCaptivePortalInactivityTimeout, wingTrapCaptivePortalAllowAccess, wingTrapCaptivePortalClientRemoved
				, wingTrapCaptivePortalPageCreFailed, wingTrapCaptivePortalDataLimitExceed, wingTrapCertmgrRsaKeyActionsSuccess
				, wingTrapCertmgrRsaKeyActionsFailure, wingTrapCertmgrCaCertActionsSuccess, wingTrapCertmgrCaCertActionsFailure
				, wingTrapCertmgrSrvCertActionsSuccess, wingTrapCertmgrSvrCertActionsFailure, wingTrapCertmgrCsrExportSuccess
				, wingTrapCertmgrCsrExportFailure, wingTrapCertmgrCrlActionsSuccess, wingTrapCertmgrCrlActionsFailure
				, wingTrapCertmgrDeleteTrustpointAction, wingTrapCertmgrImportTrustpoint, wingTrapCertmgrExportTrustpoint
				, wingTrapCertmgrCertExpiry, wingTrapCertmgrCaKeyActionsSuccess, wingTrapCertmgrCaKeyActionsFailure
				, wingTrapCfgdAclRuleAltered, wingTrapCfgdAclAttachedAltered, wingTrapClusterCmasterCfgUpdateFail
				, wingTrapClusterMaxExceeded, wingTrapDhcpsvrRelayNoIface, wingTrapDhcpsvrRelayIfaceNoIp
				, wingTrapDhcpsvrRelayStart, wingTrapDhcpsvrRelayStop, wingTrapDhcpsvrDhcpsvrStart
				, wingTrapDhcpsvrDhcpsvrStop, wingTrapDhcpsvrDhcpsvrStop, wingTrapDiagFanUnderspeed
				, wingTrapDiagUnderVoltage, wingTrapDiagOverVoltage, wingTrapDiagLowTemp
				, wingTrapDiagHighTemp, wingTrapDiagOverTemp, wingTrapDiagWdStateChange
				, wingTrapDiagElapsedTime, wingTrapDiagAutogenTechSprt, wingTrapDiagPoeInitFail
				, wingTrapDiagPoePowerLevel, wingTrapDiagPoeReadFail, wingTrapDiagPoeStateChange
				, wingTrapDiagRaidDegraded, wingTrapDiagRaidError, wingTrapDiagPwrsplyFail
				, wingTrapDiagWdResetSys, wingTrapDiagCpuLoad, wingTrapDiagRamUsage
				, wingTrapDiagBufUsage, wingTrapDiagHeadCacheUsage, wingTrapDiagIpDestUsage
				, wingTrapDiagFreeRam, wingTrapDiagFreeFlashDisk, wingTrapDiagFreeFlashInodes
				, wingTrapDiagFreeNvramDisk, wingTrapDiagFreeNvramInodes, wingTrapDiagFreeRamDisk
				, wingTrapDiagFreeRamInodes, wingTrapDiagFdCount, wingTrapDiagDiskUsage
				, wingTrapDiagNewLedState, wingTrapDiagLedIdentify, wingTrapDot11CountryCode
				, wingTrapDot11CountryCodeError, wingTrapDot11ClientAssociated, wingTrapDot11ClientDisassociated
				, wingTrapDot11ClientDeniedAssoc, wingTrapDot11WpaWpa2Success, wingTrapDot11WpaWpa2Failed
				, wingTrapDot11WpaWpa2KeyRotn, wingTrapDot11TkipMicFailReport, wingTrapDot11TkipMicFailure
				, wingTrapDot11TkipCntrmeasStart, wingTrapDot11TkipCntrmeasEnd, wingTrapDot11EapSuccess
				, wingTrapDot11EapFailed, wingTrapDot11EapClientTimeout, wingTrapDot11EapServerTimeout
				, wingTrapDot11EapCachedKeys, wingTrapDot11EapOppCachedKeys, wingTrapDot11EapPreauthSuccess
				, wingTrapDot11EapPreauthFailed, wingTrapDot11EapPreauthClientTimeout, wingTrapDot11EapPreauthServerTimeout
				, wingTrapDot11KerberosWlanSuccess, wingTrapDot11KerberosWlanTimeout, wingTrapDot11KerberosWlanFailed
				, wingTrapDot11KerberosClientSuccess, wingTrapDot11KerberosClientFailed, wingTrapDot11VoiceCallFailed
				, wingTrapDot11VoiceCallEstablished, wingTrapDot11VoiceCallCompleted, wingTrapDot11UnsanctionedApActive
				, wingTrapDot11UnsanctionedApInactive, wingTrapDot11UnsanctionedApStatusChange, wingTrapDot11NeighborDeniedAssoc
				, wingTrapDot11WlanTimeAccessDisable, wingTrapDot11WlanTimeAccessEnable, wingTrapDot11MoveOperationSuccess
				, wingTrapDot11FtRoamSuccess, wingTrapFwuFwudone, wingTrapFwuFwuaborted
				, wingTrapFwuFwunoneed, wingTrapFwuFwusyserr, wingTrapFwuFwubadconfig
				, wingTrapFwuFwuserverundef, wingTrapFwuFwufileundef, wingTrapFwuFwuserverunreachable
				, wingTrapFwuFwucouldntgetfile, wingTrapFwuFwuvermismatch, wingTrapFwuFwuprodmismatch
				, wingTrapFwuFwucorruptedfile, wingTrapFwuFwusignmismatch, wingTrapFwuFwuunsupportedhw
				, wingTrapLicmgrLicInstalled, wingTrapLicmgrLicInstallDefault, wingTrapLicmgrLicInstallCount
				, wingTrapLicmgrLicRemoved, wingTrapLicmgrLicInvalid, wingTrapMeshMeshLinkUp
				, wingTrapMeshMeshLinkDown, wingTrapMeshMeshpointUp, wingTrapMeshMeshpointDown
				, wingTrapMeshMeshpointLoopPreventOn, wingTrapMeshMeshpointLoopPreventOff, wingTrapMeshMeshpointRootChange
				, wingTrapMeshMeshpointPathChange, wingTrapNsmIfup, wingTrapNsmIfdown
				, wingTrapNsmDhcpip, wingTrapNsmDhcpdefrt, wingTrapNsmDhcpipchg
				, wingTrapNsmDhcpnodefrt, wingTrapNsmIfipcfg, wingTrapNsmDhcpcErr
				, wingTrapNsmDhcpipnoadd, wingTrapNsmDhcplsexp, wingTrapNsmDhcpnak
				, wingTrapNsmNsmNtp, wingTrapNsmIfFailover, wingTrapNsmIfFailback
				, wingTrapPmProcstart, wingTrapPmProcrstrt, wingTrapPmProcmaxrstrt
				, wingTrapPmProcsysrstrt, wingTrapPmProcstop, wingTrapPmProcid
				, wingTrapPmStartupcomplete, wingTrapPmProcnoresp, wingTrapRadconfRadiusdstart
				, wingTrapRadconfRadiusdstop, wingTrapRadconfCouldNotStopRadiusd, wingTrapRadioChannelCountryMismatch
				, wingTrapRadioRadioStateChange, wingTrapRadioRadarScanStarted, wingTrapRadioRadarScanCompleted
				, wingTrapRadioRadarDetected, wingTrapRadioRadarDetInfo, wingTrapRadioResumeHomeChannel
				, wingTrapRadioAcsScanStarted, wingTrapRadioAcsScanComplete, wingTrapRadioRadioAntennaError
				, wingTrapRadioRadioAntennaSetting, wingTrapSmrtCalibrationStarted, wingTrapSmrtCalibrationDone
				, wingTrapSmrtNeighborRecovery, wingTrapSmrtPowerAdjustment, wingTrapSmrtInterferenceRecovery
				, wingTrapSmrtRootRecovery, wingTrapSmrtCovHoleRecovery, wingTrapSmrtCovHoleRecoveryDone
				, wingTrapSmrtConfigCleared, wingTrapSmrtChannelChange, wingTrapSmtpnotSmtpauth
				, wingTrapSmtpnotNet, wingTrapSmtpnotSmtpinfo, wingTrapSmtpnotCfg
				, wingTrapSmtpnotCfginc, wingTrapSmtpnotSmtperr, wingTrapSmtpnotProto
				, wingTrapSystemPanic, wingTrapSystemHttpErr, wingTrapSystemProcStop
				, wingTrapSystemClockReset, wingTrapSystemUiUserAuthFail, wingTrapSystemUiUserAuthSuccess
				, wingTrapSystemLogin, wingTrapSystemLoginFail, wingTrapSystemLoginFailAccess
				, wingTrapSystemLoginFailBadRole, wingTrapSystemLogout, wingTrapSystemServerUnreachable
				, wingTrapSystemSystemAutoupEnable, wingTrapSystemSystemAutoupDisable, wingTrapSystemGuestUserExp
				, wingTrapWipsWipsEvent, wingTrapWipsWipsClientBlacklisted, wingTrapWipsWipsClientRemBlacklist
				, wingTrapDot1xDot1xSuccess, wingTrapDot1xDot1xFailed }

			STATUS current
			DESCRIPTION 
				"This group must be supported for all WiNG devices
				if notifications are supported."
			::= { wingGroups 2 }

		
	
	END

--
-- WING-MIB.my
--
