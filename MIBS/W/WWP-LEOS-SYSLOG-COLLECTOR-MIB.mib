-- This file was included in WWP MIB release 04-10-01-0027
 --
 -- WWP-LEOS-SYSLOG-COLLECTOR-MIB.my
 --

 WWP-LEOS-SYSLOG-COLLECTOR-MIB DEFINITIONS ::= BEGIN

 IMPORTS 
    IpAddress, Integer32, OBJECT-TYPE, MODULE-IDENTITY			
	FROM SNMPv2-SMI			
    RowStatus, TruthValue, DisplayString, TEXTUAL-CONVENTION			
	FROM SNMPv2-TC
    InetAddressType,InetAddress
        FROM INET-ADDRESS-MIB            
    wwpModulesLeos		
	FROM WWP-SMI;
	 
 wwpLeosSyslogCollectorMIB MODULE-IDENTITY
    LAST-UPDATED "201204050000Z"
    ORGANIZATION
	     "   Ciena Inc"
    CONTACT-INFO
	     "   Mib Meister
		  			115 North Sullivan Road
					Spokane Valley, WA 99037
		        	USA		 		
		        	Phone:  +1 509 242 9000
					Email:  support@ciena.com"
		     
     DESCRIPTION
	     "A MIB module to manage syslog collectors on the
	     LEOS based WWP products."
     REVISION    "201204050000Z"
     DESCRIPTION
 	     "Add new MIB OIDs to support IP protocol version 
              independent Inet addressing.
              New attributes include: wwpLeosSyslogCollectorResolvedInetAddrType and
              wwpLeosSyslogCollectorResolvedInetAddress."
     REVISION    "200604181012Z"
     DESCRIPTION
	     " Added new table wwpLeosSyslogCollectorSeverityTable to support syslog collector severity.
	       Deprecated wwpLeosSyslogCollectorMinSeverity and wwpLeosSyslogCollectorMaxSeverity.
	       "
     REVISION    "200301211012Z"
     DESCRIPTION
	     "Initial Creation"
     ::= { wwpModulesLeos 21 }

 
 -- -------------------------------------------------------------
 -- Textual Conventions
 -- -------------------------------------------------------------

 SyslogFacility  ::=  TEXTUAL-CONVENTION
     STATUS  current
     DESCRIPTION
         "This textual convention enumerates the facilities
         that originate syslog messages.

         The value noMap(24) indicates that the appropriate
         facility will be provided by the individual applications
         on the managed entity.  If this option is not available
         on a particular entity attempt set the facillity to this
         value will fail with an error-status of wrongValue."
     SYNTAX  INTEGER {
                       kernel          (0), -- kernel messages
                       user            (1), -- user-level messages
                       mail            (2), -- mail system
                       daemon          (3), -- system daemons
                       auth            (4), -- authorization messages
                       syslog          (5), -- messages generated by syslogd
                       lpr             (6), -- line printer subsystem
                       news            (7), -- network news subsystem
                       uucp            (8), -- UUCP subsystem
                       cron            (9), -- clock daemon
                       authPriv        (10),-- authorization messages
                                            --    (private)
                       ftp             (11),-- ftp daemon
                       ntp             (12),-- NTP subsystem
                       security        (13),-- security subsystems
                                            --    (firewalling, etc.)
                       console         (14),-- /dev/console output
                       clockd2         (15),
                       local0          (16),
                       local1          (17),
                       local2          (18),
                       local3          (19),
                       local4          (20),
                       local5          (21),
                       local6          (22),
                       local7          (23),
                       noMap           (24)
                     }

 
 SyslogSeverity  ::=  TEXTUAL-CONVENTION
     STATUS  current
     DESCRIPTION
         "This textual convention enumerates the severity levels
          of syslog messages.  The syslog protocol uses the values
          0 (emergency), to 7 (debug)."
     SYNTAX  INTEGER {
                       emergency       (0),  -- system is unusable
                       alert           (1),  -- action must be taken
                                             --          immediately
                       critical        (2),  -- critical conditions
                       error           (3),  -- error conditions
                       warning         (4),  -- warning conditions
                       notice          (5),  -- normal but significant
                                             -- condition
                       info            (6),  -- informational
                       debug           (7),  -- debug-level messages
                       other           (99)  -- None of the above
                     }

 --
 -- Node definitions
 --	
 
 wwpLeosSyslogCollMIBObjects OBJECT IDENTIFIER ::= { wwpLeosSyslogCollectorMIB 1 }
 
 wwpLeosSyslogSystem  OBJECT IDENTIFIER ::= { wwpLeosSyslogCollMIBObjects 1 }
 
 wwpLeosSyslogColl    OBJECT IDENTIFIER ::= { wwpLeosSyslogCollMIBObjects 2 }
 
 -- Notifications 

 wwpLeosSyslogCollMIBNotificationPrefix  OBJECT IDENTIFIER ::= { wwpLeosSyslogCollectorMIB 2 } 
 wwpLeosSyslogCollMIBNotifications       OBJECT IDENTIFIER ::= { wwpLeosSyslogCollMIBNotificationPrefix 0 }

 -- Conformance information 
 
 wwpLeosSyslogCollMIBConformance OBJECT IDENTIFIER ::= { wwpLeosSyslogCollectorMIB 3 } 
 wwpLeosSyslogCollMIBCompliances OBJECT IDENTIFIER ::= { wwpLeosSyslogCollMIBConformance 1 } 		
 wwpLeosSyslogCollMIBGroups      OBJECT IDENTIFIER ::= { wwpLeosSyslogCollMIBConformance 2 }
 
 -- The system wide parameters

 wwpLeosSyslogEnable OBJECT-TYPE
     SYNTAX      TruthValue
     MAX-ACCESS  read-write
     STATUS      current
     DESCRIPTION
             "Specifies whether or not the syslog client is enabled.
             This is the system wide parameter and will overwrite 
	     any collector specific managed object to enable
	     or disable the syslog client."
     DEFVAL { true }
     ::= { wwpLeosSyslogSystem 1 }                                
 
     
 -- -------------------------------------------------------------
 -- wwpLeosSyslogCollector Table
 -- -------------------------------------------------------------
 -- Each row in this table defines a destination to which the
 -- message will be forwarded
 -- Indexed by Address and Addr Type

 wwpLeosSyslogCollectorTable OBJECT-TYPE
     SYNTAX      SEQUENCE OF WwpLeosSyslogCollectorEntry
     MAX-ACCESS  not-accessible
     STATUS      current
     DESCRIPTION
         "A table containing Syslog collector information.
	  To create entries in this table use SNMP multiple set 
	  operation.

	  wwpLeosSyslogCollectorAddr, wwpLeosSyslogIndex and 
	  wwpLeosSyslogCollectorStatus are required fields 
	  that needs to be set to create entry.
	  
	  To delete entry set wwpLeosSyslogCollectorStatus to destroy."
     ::= { wwpLeosSyslogColl 1 }

 wwpLeosSyslogCollectorEntry OBJECT-TYPE
     SYNTAX      WwpLeosSyslogCollectorEntry
     MAX-ACCESS  not-accessible
     STATUS      current
     DESCRIPTION
         "Defines the information pertaining to a syslog collector
          to which a syslog messages will be relayed.

          Entries within this table with an access level of read-
          create MUST be considered non-volatile and MUST be
	  maintained across entity resets."
     INDEX  { wwpLeosSyslogIndex }
     ::= { wwpLeosSyslogCollectorTable 1 }

 WwpLeosSyslogCollectorEntry ::=
     SEQUENCE {
         	wwpLeosSyslogIndex						Integer32,	 
         	wwpLeosSyslogCollectorAddr				DisplayString,
	 		wwpLeosSyslogCollectorResolvedAddr		IpAddress,
         	wwpLeosSyslogCollectorUDPPort			Integer32,
         	wwpLeosSyslogCollectorFacility			SyslogFacility,
         	wwpLeosSyslogCollectorMinSeverity		SyslogSeverity,
	 		wwpLeosSyslogCollectorMaxSeverity		SyslogSeverity,
	 		wwpLeosSyslogCollectorUserAdminState	INTEGER,
	 		wwpLeosSyslogCollectorDhcpAdminState	INTEGER,
	 		wwpLeosSyslogCollectorOperState			INTEGER,
         	wwpLeosSyslogCollectorStatus			RowStatus,
         	wwpLeosSyslogCollectorCustomPrefix		DisplayString,
	 	wwpLeosSyslogCollectorResolvedInetAddrType	InetAddressType,
  		wwpLeosSyslogCollectorResolvedInetAddress	InetAddress
     }

 wwpLeosSyslogIndex OBJECT-TYPE
     SYNTAX      Integer32 (1..10)
     MAX-ACCESS  not-accessible
     STATUS      current
     DESCRIPTION
           "Specifies the unique index used to represent each row in the table."
     ::= { wwpLeosSyslogCollectorEntry 1 }

 wwpLeosSyslogCollectorAddr OBJECT-TYPE
     SYNTAX      DisplayString
     MAX-ACCESS  read-create
     STATUS      current
     DESCRIPTION
           "The address for the Syslog message collector.
            It can be Host Name or IP Address."
     ::= { wwpLeosSyslogCollectorEntry 2 }
 
 wwpLeosSyslogCollectorResolvedAddr OBJECT-TYPE
     SYNTAX      IpAddress
     MAX-ACCESS  read-only
     STATUS      current  
     DESCRIPTION
	     "When wwpLeosSyslogCollectorAddr represents:
          Host name    : The resolved address will either be Ipv4 address or Ipv6 address. 
          Ipv4 address : The resolved address will be the same Ipv4 address.
          Ipv6 address : The resolved address will be the same Ipv6 address.
              
          When the resolved address represents:
          Ipv4 address : wwpLeosSyslogCollectorResolvedAddr will represent the resolved Ipv4 address.
          wwpLeosSyslogCollectorResolvedInetAddr used in conjunction with wwpLeosSyslogCollectorResolvedInetAddrType 
          will represent the same Ipv4 address.
          Ipv6 address : wwpLeosSyslogCollectorResolvedAddr will represent 0.0.0.0.
          wwpLeosSyslogCollectorResolvedInetAddr used in conjunction with wwpLeosSyslogCollectorResolvedInetAddrType 
          will represent the Ipv6 address."
     ::= { wwpLeosSyslogCollectorEntry 3 }
 
 wwpLeosSyslogCollectorUDPPort OBJECT-TYPE
     SYNTAX      Integer32 (1..65535)
     MAX-ACCESS  read-create
     STATUS      current
     DESCRIPTION
         "The port number on the destination to which the
          syslog message will be forwarded over the udp 
	  transport."
     DEFVAL   { 514 }
     ::= { wwpLeosSyslogCollectorEntry 4 }

 wwpLeosSyslogCollectorFacility OBJECT-TYPE
     SYNTAX      SyslogFacility
     MAX-ACCESS  read-create
     STATUS      current
     DESCRIPTION
         "The syslog facility code that will be added to the messages forwarded
          to this collector."
     DEFVAL   { daemon } 
     ::= { wwpLeosSyslogCollectorEntry 5 }

 wwpLeosSyslogCollectorMinSeverity OBJECT-TYPE
     SYNTAX      SyslogSeverity
     MAX-ACCESS  read-create
     STATUS      deprecated
     DESCRIPTION
          "Any syslog message with a severity less than the severity
	  specified by this object will be ignored by the collector.
          note: severity level numeric values increase as their severity
          decreases, e.g. error(3) is more severe than debug(7)."
     DEFVAL   { alert } 
     ::= { wwpLeosSyslogCollectorEntry 6 }
     
 wwpLeosSyslogCollectorMaxSeverity OBJECT-TYPE
     SYNTAX      SyslogSeverity
     MAX-ACCESS  read-create
     STATUS      deprecated
     DESCRIPTION
          "Any syslog message with a severity greater than the severity
	  specified by this object will be ignored by the collector.
          note: severity level numeric values increase as their severity 
	  decreases, e.g. error(3) is more severe than debug(7)."
     DEFVAL   { emergency } 
     ::= { wwpLeosSyslogCollectorEntry 7 }
 
  wwpLeosSyslogCollectorUserAdminState OBJECT-TYPE
     SYNTAX      INTEGER {
			disabled(1),
			enabled(2)			
		 }
     MAX-ACCESS  read-create
     STATUS      current
     DESCRIPTION
           "Specifies the admin state of the wwpLeosSyslogCollectorAddr 
	    configured by user."
     ::= { wwpLeosSyslogCollectorEntry 8 }
  
 wwpLeosSyslogCollectorDhcpAdminState OBJECT-TYPE
     SYNTAX      INTEGER {
			disabled(1),
			enabled(2)			
		 }
     MAX-ACCESS  read-only
     STATUS      current
     DESCRIPTION
           "Specifies the admin state of the wwpLeosSyslogCollectorAddr 
	    configured by DHCP."
     ::= { wwpLeosSyslogCollectorEntry 9 }

 wwpLeosSyslogCollectorOperState OBJECT-TYPE
     SYNTAX      INTEGER {
			disabled(1),
			enabled(2)			
		 }
     MAX-ACCESS  read-only
     STATUS      current
     DESCRIPTION
           "Specifies the operational state of the wwpLeosSyslogCollectorAddr."
     ::= { wwpLeosSyslogCollectorEntry 10 }

 wwpLeosSyslogCollectorStatus OBJECT-TYPE
     SYNTAX      RowStatus
     MAX-ACCESS  read-create
     STATUS      current
     DESCRIPTION
         "Used to manage the creation and deletion of the conceptual rows in this table.
          To create a row in this table, a manager must set this object to 'createAndGo'
          and specify at least wwpLeosSyslogIndex and wwpLeosSyslogCollectorAddr. 
          To delete the entry set this object to 'destroy'."
     ::= { wwpLeosSyslogCollectorEntry 11 }     
  
  wwpLeosSyslogCollectorCustomPrefix OBJECT-TYPE
     SYNTAX      DisplayString(SIZE(0..15))
     MAX-ACCESS  read-create
     STATUS      current         
     DESCRIPTION
             "Specifies the syslog custom prefix that will be prepended to all syslog log messages 
              before device sends syslog messages to syslog collectors."     
     DEFVAL		 {''H}
     ::= { wwpLeosSyslogCollectorEntry 12 } 
 
 wwpLeosSyslogCollectorResolvedInetAddrType OBJECT-TYPE
     SYNTAX      InetAddressType
     MAX-ACCESS  read-only
     STATUS      current
     DESCRIPTION
	     "Specifies the resolved IP address type .	Used in conjunction with 
              wwpLeosSyslogCollectorResolvedInetAddress.
              When set to :
              ipv4 : wwpLeosSyslogCollectorResolvedInetAddress should be compliant with 
                     InetAddressIPv4 
              ipv6 : wwpLeosSyslogCollectorResolvedInetAddress should be compliant with 
                     InetAddressIPv6 "
   
     ::= { wwpLeosSyslogCollectorEntry 13 }
 
 wwpLeosSyslogCollectorResolvedInetAddress OBJECT-TYPE
     SYNTAX      InetAddress
     MAX-ACCESS  read-only
     STATUS      current
     DESCRIPTION
           "Specifies the resolved ip address for given wwpLeosSyslogCollectorAddr. 
	    If wwpLeosSyslogCollectorAddr is set to host name then 
	    wwpLeosSyslogCollectorResolvedInetAddr will display the resolved IP address. 
	    If wwpLeosSyslogCollectorAddr is set to IP address then 
	    wwpLeosSyslogCollectorResolvedInetAddr will display same value as 
	    wwpLeosSyslogCollectorAddr.  This OID should be used in conjuction 
	    with wwpLeosSyslogCollectorResolvedInetAddrType. "
     ::= { wwpLeosSyslogCollectorEntry 14 }

 -- -------------------------------------------------------------
 -- wwpLeosSyslogSeverity Table
 -- -------------------------------------------------------------
 -- Each row in this table defines a messages of this severity level that 
 -- this collector will receive
 wwpLeosSyslogCollectorSeverityTable OBJECT-TYPE
     SYNTAX      SEQUENCE OF WwpLeosSyslogCollectorSeverityEntry
     MAX-ACCESS  not-accessible
     STATUS      current
     DESCRIPTION
         "A table containing Syslog collector severity information.
	  	  To create entries in this table following objects must be specified.
              - Indexes must be specified
              - 
	  	  To delete entry set wwpLeosSyslogCollectorStatus to destroy."
     ::= { wwpLeosSyslogColl 2 }

 wwpLeosSyslogCollectorSeverityEntry OBJECT-TYPE
     SYNTAX      WwpLeosSyslogCollectorSeverityEntry
     MAX-ACCESS  not-accessible
     STATUS      current
     DESCRIPTION
         "Defines the information pertaining to a syslog collector severity
          to which a syslog messages will be relayed. Syslog Collector will
          only receive messages of severity that exist in this table."
     INDEX  { wwpLeosSyslogIndex,  wwpLeosSyslogCollectorSeverity}
     ::= { wwpLeosSyslogCollectorSeverityTable 1 }

 WwpLeosSyslogCollectorSeverityEntry ::=
     SEQUENCE {
         wwpLeosSyslogCollectorSeverity		SyslogSeverity,
	     wwpLeosSyslogCollectorSeverityRowStatus    RowStatus
     }                                    
     
 wwpLeosSyslogCollectorSeverity OBJECT-TYPE
     SYNTAX      SyslogSeverity
     MAX-ACCESS  not-accessible
     STATUS      current
     DESCRIPTION
          "This mib object specifies the severity of the syslog message that this collector 
           should receive."
     ::= { wwpLeosSyslogCollectorSeverityEntry 1 }  
     
 wwpLeosSyslogCollectorSeverityRowStatus OBJECT-TYPE
     SYNTAX      RowStatus
     MAX-ACCESS  read-create
     STATUS      current
     DESCRIPTION
          "Used to manage the creation and deletion of the 
	     conceptual rows in this table.
	     
	     To create a row in this table, a manager must
         set this object to 'createAndGo'. 
         To delete the entry set this to 'destroy'."
     ::= { wwpLeosSyslogCollectorSeverityEntry 2 }  
    
     
  END

 --
 -- WWP-SYSLOG-COLLECTOR-MIB.my
 --
