--
--  Compaq Computer Corporation
--
--  WL400 Object Identifier Registrations
--
--  Version 2.0.0
--

WL400-GLOBAL-REG DEFINITIONS ::= BEGIN

IMPORTS
	MODULE-IDENTITY, OBJECT-IDENTITY, enterprises
		FROM SNMPv2-SMI;


wl400GlobalRegModule MODULE-IDENTITY
	LAST-UPDATED	"9905260000Z"
	ORGANIZATION	"Compaq Computer Corporation"
	CONTACT-INFO	"
		 Name: 		Compaq Computer Corporation
		 Address:	20555 SH 249
		 Zip:		77070
		 City:		Houston
		 Country:	USA
		 Phone:		
		 Fax:	
		 e-mail:			
		 "
	DESCRIPTION
		"The Compaq WL400 central registration module."
	::= { wl400Modules 1 }


-- the Compaq root subtree
compaq				OBJECT IDENTIFIER ::= { enterprises 232 }

-- subtree for registrations and modules
wl400Reg			OBJECT IDENTIFIER ::= { compaq 143 }
wl400Modules		OBJECT IDENTIFIER ::= { wl400Reg 1 }

-- subtree for company-wide objects and events
wl400Generic		OBJECT IDENTIFIER ::= { compaq 144 }

-- subtree for product-specific objects and events
wl400Products		OBJECT IDENTIFIER ::= { compaq 145 }

-- subtree for experiments
wl400Experimental	OBJECT IDENTIFIER ::= { compaq 146 }



--
--  Products - registration
--

wl400HAP	OBJECT-IDENTITY
	STATUS			current
	DESCRIPTION		"WL400 Wireless HAP"
	::= { wl400Reg 7 }


END



--
--  Textual Conventions - none at the moment
--
