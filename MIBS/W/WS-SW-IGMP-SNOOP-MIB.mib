--
-- WS-SW-IGMP-SNOOP-MIB.my
-- MIB generated by MG-SOFT Visual MIB Builder Version 6.0  Build 88
-- Thursday, January 08, 2009 at 19:39:49
--

	WS-SW-IGMP-SNOOP-MIB DEFINITIONS ::= BEGIN
 
		IMPORTS
			OBJECT-GROUP, MODULE-COMPLIANCE			
				FROM SNMPv2-CONF			
			IpAddress, Integer32, OBJECT-TYPE, MODULE-IDENTITY			
				FROM SNMPv2-SMI			
			TruthValue			
				FROM SNMPv2-TC			
			wsSwIgmpSnoop			
				FROM WS-SW-SMI;
	
	
		-- 1.3.6.1.4.1.388.14.2.17.1
		wsSwIgmpSnoopMibModule MODULE-IDENTITY 
			LAST-UPDATED "200812111316Z"		-- December 11, 2008 at 13:16 GMT
			ORGANIZATION 
				"Symbol Technologies, Inc."
			CONTACT-INFO 
				"Symbol Technologies, Inc.
				 Customer Service
				 Postal:
				 One Symbol Plaza
				 Holtsville, NY 11742-1300
				 USA
				 Tel: +1. 631.738.6213
				 E-mail: support@symbol.com
				 Web: http://www.symbol.com/support"
			DESCRIPTION 
				"IGMP SNOOP MIB module defines the configuration parameters for
				 the IGMP Snoop feature which is used to optimize the multicast 
				 traffic using IGMP protocol."
			REVISION "200901081938Z"		-- January 08, 2009 at 19:38 GMT
			DESCRIPTION 
				"02a4
				Added disabled state for Querier Operational state."
			REVISION "200812111907Z"		-- December 11, 2008 at 19:07 GMT
			DESCRIPTION 
				"02a3
				Added IGMP Snoop Querier Table and its corresponding scalars.
				The last member query interval configuration from Scalars as
				well as the IGMP Vlan configuration table has been removed.
				The Group specific query for IGMP V2 leave is not required
				any more, hence the supporting configuration has been removed."
			REVISION "200810172208Z"		-- October 17, 2008 at 22:08 GMT
			DESCRIPTION 
				"02a2
				 Removed the Row status from VlanConfigTable. Mrouter Table
				 removed as get is now merged with VlanConfig Table.
				 VlanConfigTable now shows 4094 entries."
			REVISION "200810021338Z"		-- October 02, 2008 at 13:38 GMT
			DESCRIPTION 
				"02a1
				 Created IGMP Snoop MIB"
			::= { wsSwIgmpSnoop 1 }

		
	
	
--
-- Node definitions
--
	
		-- 1.3.6.1.4.1.388.14.2.17.1.1
		wsSwIgmpSnoopMIB OBJECT IDENTIFIER ::= { wsSwIgmpSnoopMibModule 1 }

		
		-- 1.3.6.1.4.1.388.14.2.17.1.1.1
		wsSwIgmpSnoopScalars OBJECT IDENTIFIER ::= { wsSwIgmpSnoopMIB 1 }

		
		-- 1.3.6.1.4.1.388.14.2.17.1.1.1.1
		wsSwIgmpSnoopEnableDefault OBJECT-TYPE
			SYNTAX TruthValue
			MAX-ACCESS read-write
			STATUS current
			DESCRIPTION
				"By Default IGMP Snooping is enabled.
				 The default value is TRUE."
			::= { wsSwIgmpSnoopScalars 1 }

		
		-- 1.3.6.1.4.1.388.14.2.17.1.1.1.2
		wsSwIgmpSnoopUnknownMcastFwdDefault OBJECT-TYPE
			SYNTAX TruthValue
			MAX-ACCESS read-write
			STATUS current
			DESCRIPTION
				"This configures the default behaviour for unknown multicast
				 forward for all Vlans. 
				 Enabling unknown multicast packets will cause flooding of
				 multicast packets which fall outside the range of 224.0.0.X
				 and have not been joined by any host.
				 Disabling will cause forwarding of such packets only to
				 multicast router ports.
				 The default value is FALSE."
			::= { wsSwIgmpSnoopScalars 2 }

		
		-- 1.3.6.1.4.1.388.14.2.17.1.1.1.3
		wsSwIgmpSnoopQuerierEnableDefault OBJECT-TYPE
			SYNTAX TruthValue
			MAX-ACCESS read-write
			STATUS current
			DESCRIPTION
				"Enable/Disable IGMP Snooping Querier at global level.
				 The default value is disabled(FALSE)."
			::= { wsSwIgmpSnoopScalars 3 }

		
		-- 1.3.6.1.4.1.388.14.2.17.1.1.1.4
		wsSwIgmpSnoopQuerierVersionDefault OBJECT-TYPE
			SYNTAX INTEGER
				{
				igmpv1(1),
				igmpv2(2),
				igmpv3(3)
				}
			MAX-ACCESS read-write
			STATUS current
			DESCRIPTION
				"The default IGMP Version for the queries to be generated by
				 the querier.
				 The default value is igmpv3(3) version."
			::= { wsSwIgmpSnoopScalars 4 }

		
		-- 1.3.6.1.4.1.388.14.2.17.1.1.1.5
		wsSwIgmpSnoopQuerierMaxResponseTimeDefault OBJECT-TYPE
			SYNTAX Integer32 (1..25)
			UNITS "seconds"
			MAX-ACCESS read-write
			STATUS current
			DESCRIPTION
				"The default IGMP Querier maximum response time used in building
				 IGMP V2/V3 queries, indicating the maximum time in seconds in
				 which the interested hosts should respond back with a report.
				 The default value is 10 seconds."
			::= { wsSwIgmpSnoopScalars 5 }

		
		-- 1.3.6.1.4.1.388.14.2.17.1.1.1.6
		wsSwIgmpSnoopQuerierPresentTimeoutDefault OBJECT-TYPE
			SYNTAX Integer32 (60..300)
			UNITS "seconds"
			MAX-ACCESS read-write
			STATUS current
			DESCRIPTION
				"The default timeout value for the external IGMP querier connected
				 to the switch. This value is used to start of the local Querier
				 to send the locally generated IGMP query based on the Querier 
				 configuration when ever the Multicast router goes away and a Query
				 loss is detected.
				 The default value is 60 seconds.
				"
			::= { wsSwIgmpSnoopScalars 6 }

		
		-- 1.3.6.1.4.1.388.14.2.17.1.1.1.7
		wsSwIgmpSnoopQuerierQueryIntervalDefault OBJECT-TYPE
			SYNTAX Integer32 (1..18000)
			UNITS "seconds"
			MAX-ACCESS read-write
			STATUS current
			DESCRIPTION
				"The default query interval which will be used by the
				 IGMP querier to build and send the locally generated IGMP
				 queries periodically. The configured query interval will
				 be common across all VLAN.
				 The default value is 60 seconds."
			::= { wsSwIgmpSnoopScalars 7 }

		
		-- 1.3.6.1.4.1.388.14.2.17.1.1.1.8
		wsSwIgmpSnoopQuerierIPAddressDefault OBJECT-TYPE
			SYNTAX IpAddress
			MAX-ACCESS read-write
			STATUS current
			DESCRIPTION
				"The Default source IP Address used by the querier as source IP while generating
				 the IGMP queries.
				 The default value is 0.0.0.0. "
			::= { wsSwIgmpSnoopScalars 8 }

		
		-- 1.3.6.1.4.1.388.14.2.17.1.1.2
		wsSwIgmpSnoopVlanConfigTable OBJECT-TYPE
			SYNTAX SEQUENCE OF WsSwIgmpSnoopVlanConfigEntry
			MAX-ACCESS not-accessible
			STATUS current
			DESCRIPTION
				"Configures IGMP Snooping configuration per Vlan. User can
				 provide static multicast router ports for each vlan and
				 needs to configure the learning mode to be static in
				 case he is configuring static entries else write will fail."
			::= { wsSwIgmpSnoopMIB 2 }

		
		-- 1.3.6.1.4.1.388.14.2.17.1.1.2.1
		wsSwIgmpSnoopVlanConfigEntry OBJECT-TYPE
			SYNTAX WsSwIgmpSnoopVlanConfigEntry
			MAX-ACCESS not-accessible
			STATUS current
			DESCRIPTION
				"An entry in wsSwIgmpSnoopingVlanConfigTable"
			INDEX { wsSwIgmpSnoopVlanIndex }
			::= { wsSwIgmpSnoopVlanConfigTable 1 }

		
		WsSwIgmpSnoopVlanConfigEntry ::=
			SEQUENCE { 
				wsSwIgmpSnoopVlanIndex
					Integer32,
				wsSwIgmpSnoopEnable
					TruthValue,
				wsSwIgmpSnoopUnknownMcastFwd
					TruthValue,
				wsSwIgmpSnoopLearningMode
					INTEGER,
				wsSwIgmpSnoopMrouterSetStaticPort
					OCTET STRING
			 }

		-- 1.3.6.1.4.1.388.14.2.17.1.1.2.1.1
		wsSwIgmpSnoopVlanIndex OBJECT-TYPE
			SYNTAX Integer32 (1..4094)
			MAX-ACCESS read-only
			STATUS current
			DESCRIPTION
				"The Index for the current table and is the actual VLAN's
				configured on the switch."
			::= { wsSwIgmpSnoopVlanConfigEntry 1 }

		
		-- 1.3.6.1.4.1.388.14.2.17.1.1.2.1.2
		wsSwIgmpSnoopEnable OBJECT-TYPE
			SYNTAX TruthValue
			MAX-ACCESS read-write
			STATUS current
			DESCRIPTION
				"Enable/Disable IGMP Snooping on this Vlan.
				 By Default IGMP Snooping is enabled.
				 The default value is TRUE."
			DEFVAL { 1 }
			::= { wsSwIgmpSnoopVlanConfigEntry 2 }

		
		-- 1.3.6.1.4.1.388.14.2.17.1.1.2.1.3
		wsSwIgmpSnoopUnknownMcastFwd OBJECT-TYPE
			SYNTAX TruthValue
			MAX-ACCESS read-write
			STATUS current
			DESCRIPTION
				"Enabling unknown multicast packets will cause flooding of
				 multicast packets which fall outside the range of 224.0.0.X
				 and have not been joined by any host.
				 Disabling will cause forwarding of such packets only to multicast 
				 router ports.
				 The Default value if False."
			DEFVAL { 1 }
			::= { wsSwIgmpSnoopVlanConfigEntry 3 }

		
		-- 1.3.6.1.4.1.388.14.2.17.1.1.2.1.4
		wsSwIgmpSnoopLearningMode OBJECT-TYPE
			SYNTAX INTEGER
				{
				pimDvmrp(1),
				static(2)
				}
			MAX-ACCESS read-write
			STATUS current
			DESCRIPTION
				"This object specifies the multicast router port learning method for
				 IGMP Snooping as described below: 
				 pimDvmrp(1)    : Protocol Independent Multicast and Distance Vector
				 static(2)      : Static entry
				
				 The Default value is pimDvmrp(1)."
			DEFVAL { pimDvmrp }
			::= { wsSwIgmpSnoopVlanConfigEntry 4 }

		
		-- 1.3.6.1.4.1.388.14.2.17.1.1.2.1.5
		wsSwIgmpSnoopMrouterSetStaticPort OBJECT-TYPE
			SYNTAX OCTET STRING
			MAX-ACCESS read-write
			STATUS current
			DESCRIPTION
				"In case if the learning of multicast router ports is static then
				 one can do a set operation over this OID to configure the set of
				 physical ports for this vlan where the Multicast routers are connected.
				 If learn mode is pim-dvmrp the set over this OID will give a commit fail
				 as an error condition. For multiple ports to be configured user can
				 give comma separated port names Eg. ge1,ge3."
			::= { wsSwIgmpSnoopVlanConfigEntry 5 }

		
		-- 1.3.6.1.4.1.388.14.2.17.1.1.3
		wsSwIgmpSnoopQuerierTable OBJECT-TYPE
			SYNTAX SEQUENCE OF WsSwIgmpSnoopQuerierEntry
			MAX-ACCESS not-accessible
			STATUS current
			DESCRIPTION
				"This table provides the configuration for the IGMP Querier
				 which is used to send out the IGMP general queries locally
				 in the absence of any external Querier."
			::= { wsSwIgmpSnoopMIB 3 }

		
		-- 1.3.6.1.4.1.388.14.2.17.1.1.3.1
		wsSwIgmpSnoopQuerierEntry OBJECT-TYPE
			SYNTAX WsSwIgmpSnoopQuerierEntry
			MAX-ACCESS not-accessible
			STATUS current
			DESCRIPTION
				"An entry in the wsSwIgmpSnoopQuerierTable."
			INDEX { wsSwIgmpSnoopQuerierVlanIndex }
			::= { wsSwIgmpSnoopQuerierTable 1 }

		
		WsSwIgmpSnoopQuerierEntry ::=
			SEQUENCE { 
				wsSwIgmpSnoopQuerierVlanIndex
					Integer32,
				wsSwIgmpSnoopQuerierEnable
					TruthValue,
				wsSwIgmpSnoopQuerierVersion
					INTEGER,
				wsSwIgmpSnoopQuerierMaxResponseTime
					INTEGER,
				wsSwIgmpSnoopQuerierPresentTimeout
					INTEGER,
				wsSwIgmpSnoopQuerierIPAddress
					IpAddress,
				wsSwIgmpSnoopQuerierOperationalState
					INTEGER
			 }

		-- 1.3.6.1.4.1.388.14.2.17.1.1.3.1.1
		wsSwIgmpSnoopQuerierVlanIndex OBJECT-TYPE
			SYNTAX Integer32 (1..4094)
			MAX-ACCESS read-only
			STATUS current
			DESCRIPTION
				"The Index for the current table and is the actual VLAN's
				 configured on the switch."
			::= { wsSwIgmpSnoopQuerierEntry 1 }

		
		-- 1.3.6.1.4.1.388.14.2.17.1.1.3.1.2
		wsSwIgmpSnoopQuerierEnable OBJECT-TYPE
			SYNTAX TruthValue
			MAX-ACCESS read-write
			STATUS current
			DESCRIPTION
				"Enable/Disable IGMP Snooping Querier on this Vlan.
				 By Default IGMP Snooping Querier is disabled.
				 The default value is FALSE."
			DEFVAL { 2 }
			::= { wsSwIgmpSnoopQuerierEntry 2 }

		
		-- 1.3.6.1.4.1.388.14.2.17.1.1.3.1.3
		wsSwIgmpSnoopQuerierVersion OBJECT-TYPE
			SYNTAX INTEGER
				{
				igmpv1(1),
				igmpv2(2),
				igmpv3(3)
				}
			MAX-ACCESS read-write
			STATUS current
			DESCRIPTION
				"The IGMP Version for the queries to be generated by
				 the querier. The Default value is igmpv3(3) version."
			DEFVAL { igmpv3 }
			::= { wsSwIgmpSnoopQuerierEntry 3 }

		
		-- 1.3.6.1.4.1.388.14.2.17.1.1.3.1.4
		wsSwIgmpSnoopQuerierMaxResponseTime OBJECT-TYPE
			SYNTAX INTEGER (1..25)
			UNITS "seconds"
			MAX-ACCESS read-write
			STATUS current
			DESCRIPTION
				"The IGMP Querier maximum response time used in building
				 IGMP V2/V3 queries, indicating the maximum time in seconds in
				 which the interested hosts should resond back with a report."
			DEFVAL { 10 }
			::= { wsSwIgmpSnoopQuerierEntry 4 }

		
		-- 1.3.6.1.4.1.388.14.2.17.1.1.3.1.5
		wsSwIgmpSnoopQuerierPresentTimeout OBJECT-TYPE
			SYNTAX INTEGER (60..300)
			UNITS "seconds"
			MAX-ACCESS read-write
			STATUS current
			DESCRIPTION
				"The timeout value for the external IGMP querier connected
				 to the switch. This value is used to start of the local Querier
				 to send the locally generated IGMP query based on the Querier 
				 configuration when ever the Multicast router goes away and a Query
				 loss is detected.
				"
			DEFVAL { 60 }
			::= { wsSwIgmpSnoopQuerierEntry 5 }

		
		-- 1.3.6.1.4.1.388.14.2.17.1.1.3.1.6
		wsSwIgmpSnoopQuerierIPAddress OBJECT-TYPE
			SYNTAX IpAddress
			MAX-ACCESS read-write
			STATUS current
			DESCRIPTION
				"The source IP Address used by the querier while generating
				 the IGMP queries. By default this is zero. If the querier is
				 enabled and it's IP address is not configured then switch will
				 try to the following IP address in the given prefrence:
				 1. Use the Querier global default IP address.
				 2. use the corresponding SVI IP.
				 3. Try to use the first occurring IP address among all the
				    interfaces.
				 If none of the above has been configured for an IP address then it will not send
				 send out the query."
			DEFVAL { 0 }
			::= { wsSwIgmpSnoopQuerierEntry 6 }

		
		-- 1.3.6.1.4.1.388.14.2.17.1.1.3.1.7
		wsSwIgmpSnoopQuerierOperationalState OBJECT-TYPE
			SYNTAX INTEGER
				{
				querier(1),
				nonquerier(2),
				disabled(3)
				}
			MAX-ACCESS read-only
			STATUS current
			DESCRIPTION
				"This OID shows the operational status of the Querier.
				 The Querier goes to non-querier state when ever wireless switch
				 detects a query coming from a Multicast router or any other querier
				 from an external network. In the absence of a multicast router or a
				 query loss is detected and if the IGMP Querier is enabled globally
				 and on this vlan then it will move to querier state.
				
				"
			DEFVAL { disabled }
			::= { wsSwIgmpSnoopQuerierEntry 7 }

		
		-- 1.3.6.1.4.1.388.14.2.17.1.1.20
		wsSwIgmpSnoopConf OBJECT IDENTIFIER ::= { wsSwIgmpSnoopMIB 20 }

		
		-- 1.3.6.1.4.1.388.14.2.17.1.1.20.1
		wsSwIgmpSnoopGroups OBJECT IDENTIFIER ::= { wsSwIgmpSnoopConf 1 }

		
		-- 1.3.6.1.4.1.388.14.2.17.1.1.20.1.1
		wsSwIgmpSnoopObjectGroup OBJECT-GROUP
			OBJECTS { wsSwIgmpSnoopUnknownMcastFwdDefault, wsSwIgmpSnoopVlanIndex, wsSwIgmpSnoopUnknownMcastFwd, wsSwIgmpSnoopMrouterSetStaticPort, wsSwIgmpSnoopLearningMode, 
				wsSwIgmpSnoopQuerierIPAddress, wsSwIgmpSnoopQuerierPresentTimeout, wsSwIgmpSnoopQuerierMaxResponseTime, wsSwIgmpSnoopQuerierVersion, wsSwIgmpSnoopQuerierEnable, 
				wsSwIgmpSnoopQuerierVlanIndex, wsSwIgmpSnoopQuerierIPAddressDefault, wsSwIgmpSnoopQuerierQueryIntervalDefault, wsSwIgmpSnoopQuerierPresentTimeoutDefault, wsSwIgmpSnoopQuerierMaxResponseTimeDefault, 
				wsSwIgmpSnoopQuerierVersionDefault, wsSwIgmpSnoopQuerierEnableDefault, wsSwIgmpSnoopQuerierOperationalState, wsSwIgmpSnoopEnable, wsSwIgmpSnoopEnableDefault
				 }
			STATUS current
			DESCRIPTION 
				"Description."
			::= { wsSwIgmpSnoopGroups 1 }

		
		-- 1.3.6.1.4.1.388.14.2.17.1.1.20.2
		wsSwIgmpSnoopCompliances OBJECT IDENTIFIER ::= { wsSwIgmpSnoopConf 2 }

		
		-- 1.3.6.1.4.1.388.14.2.17.1.1.20.2.1
		wsSwIgmpSnoopCompliance MODULE-COMPLIANCE
			STATUS current
			DESCRIPTION 
				"Description."
			MODULE -- this module
				MANDATORY-GROUPS { wsSwIgmpSnoopObjectGroup }
			::= { wsSwIgmpSnoopCompliances 1 }

		
	
	END

--
-- WS-SW-IGMP-SNOOP-MIB.my
--
