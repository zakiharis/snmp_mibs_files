--
-- WS-SW-MSTP-MIB.my
-- MIB generated by MG-SOFT Visual MIB Builder Version 6.0  Build 88
-- Tuesday, February 19, 2008 at 17:16:44
--


	WS-SW-MSTP-MIB DEFINITIONS ::= BEGIN
 
		IMPORTS
			dot1dBridge, BridgeId			
				FROM BRIDGE-MIB			
			VlanId			
				FROM Q-BRIDGE-MIB			
			OBJECT-GROUP, MODULE-COMPLIANCE			
				FROM SNMPv2-CONF			
			Integer32, OBJECT-TYPE, MODULE-IDENTITY, Counter32			
				FROM SNMPv2-SMI			
			DisplayString			
				FROM SNMPv2-TC			
			wsSw			
				FROM WS-SMI			
			AbbrevRowStatus			
				FROM WS-TYPE-MIB;
	
	
		-- 1.3.6.1.4.1.388.14.2.14
		wsSwMstp MODULE-IDENTITY 
			LAST-UPDATED "200802191716Z"		-- February 19, 2008 at 17:16 GMT
			ORGANIZATION 
				"Symbol Technologies"
			CONTACT-INFO 
				"Symbol Technologies, Inc.
				Customer Service
				Postal:
				One Symbol Plaza
				Holtsville, NY 11742-1300
				USA
				Tel: +1. 631.738.6213
				E-mail: support@symbol.com
				Web: http://www.symbol.com/support"
			DESCRIPTION 
				"Symbol MIB for MSTP"
			REVISION "200802191716Z"		-- February 19, 2008 at 17:16 GMT
			DESCRIPTION 
				"removed value 
				disabledWithBridgeForward(3) 
				from object wsSwMstpGlobalState."
			REVISION "200702051436Z"		-- February 05, 2007 at 14:36 GMT
			DESCRIPTION 
				"replaced wsSwMstpDisable with wsSwMstpGlobalState"
			REVISION "200702051307Z"		-- February 05, 2007 at 13:07 GMT
			DESCRIPTION 
				"added wsSwMstpDisable"
			REVISION "200701241205Z"		-- January 24, 2007 at 12:05 GMT
			DESCRIPTION 
				"01a01"
			REVISION "200611221200Z"		-- November 22, 2006 at 12:00 GMT
			DESCRIPTION 
				"Initial version.
				Based on a draft proposal ruzin-mstp-mib-04.txt, with several extensions."
			::= { wsSw 14 }

		
	
--
-- Type definitions
--
	
		TruthValue ::= INTEGER
			{
			true(1),
			false(2)
			}

		MstiOrCistInstanceIndex ::= INTEGER (0..16)

		PortIndex ::= INTEGER (1..4094)

		PortIndexOrZero ::= INTEGER (0..2147483647)

		PortId ::= OCTET STRING (SIZE (2))

		BpduCounter ::= Counter32

		MstiInstanceIndex ::= INTEGER (1..64)

	
--
-- Node definitions
--
	
		-- 1.3.6.1.4.1.388.14.2.14.10
		wsSwMstpGen OBJECT IDENTIFIER ::= { wsSwMstp 10 }

		
		-- 1.3.6.1.4.1.388.14.2.14.10.14
		wsSwMstpGenMaxHops OBJECT-TYPE
			SYNTAX INTEGER (7..127)
			MAX-ACCESS read-write
			STATUS current
			DESCRIPTION
				"Specifies the maximum allowed hops for a BPDU in an MST
				region. This parameter is used by all the instances
				of the MST."
			REFERENCE
				"IEEE 802.1Q-2003 clause 13.22.f"
			::= { wsSwMstpGen 14 }

		
		-- 1.3.6.1.4.1.388.14.2.14.10.19
		wsSwMstpVersionsSupported OBJECT-TYPE
			SYNTAX BITS
				{
				nonStp(0),
				dot1d1998(1),
				dot1w(2),
				dot1d2004(3),
				dot1s(4),
				dot1q(5),
				reserved6(6),
				reserved7(7),
				reserved8(8),
				reserved9(9),
				reserved10(10),
				reserved11(11),
				reserved12(12),
				reserved13(13),
				reserved14(14),
				unknown(15)
				}
			MAX-ACCESS read-only
			STATUS current
			DESCRIPTION
				"An indication of wheter the Bridge supports
				Spanning Tree Protocol.
				The bit nonStp(0) indicates, the Bridge doesn't
				support any Spanning Tree Protocol.
				The bit 'dot1d1998(1)' indicates the Spanning Tree Protocol
				specified in EEE 802.1D-1998, 'dot1w(2)' indicates the Rapid
				Spanning Tree Protocol specified in IEEE Std 802.1w,
				'dot1d2004' indicates IEEE Std 802.1D-2004 and
				'dot1s(4) means MSTP IEEE Std 802.1s.
				When the bridge supprts a non-listed version, the bit unknown(15) should
				be set."
			::= { wsSwMstpGen 19 }

		
		-- 1.3.6.1.4.1.388.14.2.14.10.20
		wsSwMstpGenProtocolVersion OBJECT-TYPE
			SYNTAX INTEGER
				{
				forceNonStp(0),
				forceLegacyDot1d(1),
				forceDot1w(2),
				autoDot1s(3),
				unknown(15)
				}
			MAX-ACCESS read-write
			STATUS current
			DESCRIPTION
				"This object is relevant if the Bridges that can supply a number of versions of STP.
				For GET operation this object reflects the mode in which the Bridge works
				currently. If the Bridge works currently in the version, not listed here, the
				value unknown(4) must be returned.
				For SET operation the value unknown(15) must be rejected. Another value may be
				rejected too if the Bridge does not support correspond mode (see wsSwMstpVersionsSupported). 
				The value forceNonStp(0) indicates, the Spanning Tree Protocol
				is disabled on the Bridge (or the Spanning Tree Protocol
				Emulation operates). Other possible values are described
				in IEEE Std 802.1s clause 12.8.1.3.e)"
			::= { wsSwMstpGen 20 }

		
		-- 1.3.6.1.4.1.388.14.2.14.10.30
		wsSwMstpGenCfgIdFmtSel OBJECT-TYPE
			SYNTAX Integer32
			MAX-ACCESS read-only
			STATUS current
			DESCRIPTION
				"Configuration Identificator Format Selector."
			REFERENCE
				"IEEE 802.1Q-2003 clause 12.12.3.4.2.a)"
			::= { wsSwMstpGen 30 }

		
		-- 1.3.6.1.4.1.388.14.2.14.10.31
		wsSwMstpGenCfgIdName OBJECT-TYPE
			SYNTAX DisplayString (SIZE (32))
			MAX-ACCESS read-write
			STATUS current
			DESCRIPTION
				"The configuration name that identifies the MST
				region and is used as one of the inputs in the 
				computation of the MST Configuration Identifier."
			REFERENCE
				"IEEE 802.1Q-2003 clause 12.12.3.4.2.b)"
			::= { wsSwMstpGen 31 }

		
		-- 1.3.6.1.4.1.388.14.2.14.10.32
		wsSwMstpGenCfgIdRevLevel OBJECT-TYPE
			SYNTAX INTEGER (0..255)
			MAX-ACCESS read-write
			STATUS current
			DESCRIPTION
				"This object identifies the MST revision that 
				identifies the MST region and is used as one
				of the inputs in the computation of the MST 
				configuration Identifier."
			REFERENCE
				"IEEE 802.1Q-2003 clause 12.12.3.4.2.c)"
			::= { wsSwMstpGen 32 }

		
		-- 1.3.6.1.4.1.388.14.2.14.10.33
		wsSwMstpGenCfgIdDigest OBJECT-TYPE
			SYNTAX OCTET STRING (SIZE (16))
			MAX-ACCESS read-only
			STATUS current
			DESCRIPTION
				"The computed Configuration Digest."
			REFERENCE
				"IEEE 802.1Q-2003 clause 12.12.3.3.3.a.4"
			::= { wsSwMstpGen 33 }

		
		-- 1.3.6.1.4.1.388.14.2.14.10.36
		wsSwMstpGenRegionalRoot OBJECT-TYPE
			SYNTAX BridgeId
			MAX-ACCESS read-only
			STATUS current
			DESCRIPTION
				"Regional root of the CIST."
			::= { wsSwMstpGen 36 }

		
		-- 1.3.6.1.4.1.388.14.2.14.10.37
		wsSwMstpGenExternalRootCost OBJECT-TYPE
			SYNTAX Integer32
			MAX-ACCESS read-only
			STATUS current
			DESCRIPTION
				"External root cost of CIST."
			::= { wsSwMstpGen 37 }

		
		-- 1.3.6.1.4.1.388.14.2.14.10.50
		wsSwMstpErrdisableTimeout OBJECT-TYPE
			SYNTAX TruthValue
			MAX-ACCESS read-write
			STATUS current
			DESCRIPTION
				"The BPDU guard feature shuts down the port on receiving
				a BPDU on a BPDU-guard enabled port. This object associates
				a timer with the feature such that the port gets enabled 
				back without manual intervention after a set interval.
				This interval can be configured by the user using object
				wsSwMstpErrdisableTimeoutInterval"
			::= { wsSwMstpGen 50 }

		
		-- 1.3.6.1.4.1.388.14.2.14.10.51
		wsSwMstpErrdisableTimeoutInterval OBJECT-TYPE
			SYNTAX Integer32 (10..10000000)
			MAX-ACCESS read-write
			STATUS current
			DESCRIPTION
				"Specifies the time interval in seconds after
				which a port for which wsSwMstpErrdisableTimeout
				is true, is brought back up."
			::= { wsSwMstpGen 51 }

		
		-- 1.3.6.1.4.1.388.14.2.14.10.52
		wsSwMstpPortfastBpduFilter OBJECT-TYPE
			SYNTAX TruthValue
			MAX-ACCESS read-write
			STATUS current
			DESCRIPTION
				"Enabling the BPDU Filter feature ensures that 
				PortFastenabled ports (edge ports for which
				dot1dStpPortOperEdgePort is true) do not transmit or
				receive any BPDUs"
			::= { wsSwMstpGen 52 }

		
		-- 1.3.6.1.4.1.388.14.2.14.10.53
		wsSwMstpPortFastBpduGuard OBJECT-TYPE
			SYNTAX TruthValue
			MAX-ACCESS read-write
			STATUS current
			DESCRIPTION
				"When the BPDU Guard feature is set for a bridge, all
				portfast-enabled ports (edge ports for which
				dot1dStpPortOperEdgePort is true) of the bridge that have
				bpdu-guard set to default shut down the port on receiving 
				a BPDU. In this case, the BPDU is not processed."
			::= { wsSwMstpGen 53 }

		
		-- 1.3.6.1.4.1.388.14.2.14.10.54
		wsSwMstpAdminCiscoInteroperability OBJECT-TYPE
			SYNTAX TruthValue
			MAX-ACCESS read-write
			STATUS current
			DESCRIPTION
				"Enabled interoperability with Cisco's
				version of MSTP"
			::= { wsSwMstpGen 54 }

		
		-- 1.3.6.1.4.1.388.14.2.14.10.55
		wsSwMstpOperCiscoInteroperability OBJECT-TYPE
			SYNTAX Integer32
			MAX-ACCESS read-only
			STATUS current
			DESCRIPTION
				"The operational value of the Cisco 
				interoperability parameter. True if
				Cisco interoperability is administratively
				enabled and a Cisco BPDU is detected."
			::= { wsSwMstpGen 55 }

		
		-- 1.3.6.1.4.1.388.14.2.14.10.56
		wsSwMstpGlobalState OBJECT-TYPE
			SYNTAX INTEGER
				{
				enabled(1),
				disabled(2)
				}
			MAX-ACCESS read-write
			STATUS current
			DESCRIPTION
				"The global state of MSTP in the switch.
				The possible states are enabled, disabled 
				and disabledWithBridgeForward"
			::= { wsSwMstpGen 56 }

		
		-- 1.3.6.1.4.1.388.14.2.14.11
		wsSwMstMapTable OBJECT-TYPE
			SYNTAX SEQUENCE OF WsSwMstMapEntry
			MAX-ACCESS not-accessible
			STATUS current
			DESCRIPTION
				"This table contains one entry for each instance of MSTP."
			::= { wsSwMstp 11 }

		
		-- 1.3.6.1.4.1.388.14.2.14.11.1
		wsSwMstMapEntry OBJECT-TYPE
			SYNTAX WsSwMstMapEntry
			MAX-ACCESS not-accessible
			STATUS current
			DESCRIPTION
				"A conceptual row containing the status of the MSTP instance."
			INDEX { wsSwMstMapIndex }
			::= { wsSwMstMapTable 1 }

		
		WsSwMstMapEntry ::=
			SEQUENCE { 
				wsSwMstMapIndex
					MstiOrCistInstanceIndex,
				wsSwMstMapVlans1k
					OCTET STRING,
				wsSwMstMapVlans2k
					OCTET STRING,
				wsSwMstMapVlans3k
					OCTET STRING,
				wsSwMstMapVlans4k
					OCTET STRING
			 }

		-- 1.3.6.1.4.1.388.14.2.14.11.1.1
		wsSwMstMapIndex OBJECT-TYPE
			SYNTAX MstiOrCistInstanceIndex
			MAX-ACCESS read-only
			STATUS current
			DESCRIPTION
				"Uniquely identifies an instance. The entry of this table with index 0
				presents always, represents CIST. However, a SET operation
				at the CIST index returns an error."
			::= { wsSwMstMapEntry 1 }

		
		-- 1.3.6.1.4.1.388.14.2.14.11.1.6
		wsSwMstMapVlans1k OBJECT-TYPE
			SYNTAX OCTET STRING (SIZE (0..128))
			MAX-ACCESS read-write
			STATUS current
			DESCRIPTION
				"A string of octets containing one bit per VLAN. The
				first octet corresponds to VLANs with VlanIndex values
				1 through 8; the second octet to VLANs 9 through
				16 etc.  The most significant bit of each octet
				corresponds to the lowest VlanIndex value in that octet.
				
				For each VLAN that is mapped to this MSTP instance,
				the bit corresponding to that VLAN is set to '1'.
				Empty (zero) most significant octes are not mandatory."
			::= { wsSwMstMapEntry 6 }

		
		-- 1.3.6.1.4.1.388.14.2.14.11.1.7
		wsSwMstMapVlans2k OBJECT-TYPE
			SYNTAX OCTET STRING (SIZE (0..128))
			MAX-ACCESS read-write
			STATUS current
			DESCRIPTION
				"A string of octets containing one bit per VLAN for
				VLANS with VlanIndex values 1024 through 2047. The
				first octet corresponds to VLANs with VlanIndex values
				1024 through 1031; the second octet to VLANs 1032
				through 1039 etc.  The most significant bit of each
				octet corresponds to the lowest VlanIndex value in that
				octet.
				
				For each VLAN that is mapped to this MSTP instance,
				the bit corresponding to that VLAN is set to '1'.
				
				Empty (zero) most significant octes are not mandatory."
			::= { wsSwMstMapEntry 7 }

		
		-- 1.3.6.1.4.1.388.14.2.14.11.1.8
		wsSwMstMapVlans3k OBJECT-TYPE
			SYNTAX OCTET STRING (SIZE (0..128))
			MAX-ACCESS read-write
			STATUS current
			DESCRIPTION
				"A string of octets containing one bit per VLAN for
				VLANS with VlanIndex values 2048 through 3071. The
				first octet corresponds to VLANs with VlanIndex values
				of 2048 through 2055; the second octet to VLANs 2056
				through 2063 etc.  The most significant bit of each
				octet corresponds to the lowest VlanIndex value in that
				octet.
				
				For each VLAN that is mapped to this MSTP instance,
				the bit corresponding to that VLAN is set to '1'.
				
				Empty (zero) most significant octes are not mandatory."
			::= { wsSwMstMapEntry 8 }

		
		-- 1.3.6.1.4.1.388.14.2.14.11.1.9
		wsSwMstMapVlans4k OBJECT-TYPE
			SYNTAX OCTET STRING (SIZE (0..128))
			MAX-ACCESS read-write
			STATUS current
			DESCRIPTION
				"A string of octets containing one bit per VLAN for
				VLANS with VlanIndex values 3072 through 4095. The
				first octet corresponds to VLANs with VlanIndex values
				3072 through 3079; the second octet to VLANs 3080
				through 3087 etc.  The most significant bit of each
				octet corresponds to the lowest VlanIndex value in that
				octet.
				
				For each VLAN that is mapped to this MSTP instance,
				the bit corresponding to that VLAN is set to '1'.
				
				Empty (zero) most significant octes are not mandatory."
			::= { wsSwMstMapEntry 9 }

		
		-- 1.3.6.1.4.1.388.14.2.14.12
		wsSwMstVlanTable OBJECT-TYPE
			SYNTAX SEQUENCE OF WsSwMstVlanEntry
			MAX-ACCESS not-accessible
			STATUS current
			DESCRIPTION
				"This table contains one entry for each VlanId."
			::= { wsSwMstp 12 }

		
		-- 1.3.6.1.4.1.388.14.2.14.12.1
		wsSwMstVlanEntry OBJECT-TYPE
			SYNTAX WsSwMstVlanEntry
			MAX-ACCESS not-accessible
			STATUS current
			DESCRIPTION
				"Information regarding the instance to which each Vlan is mapped."
			INDEX { wsSwMstVlanIndex }
			::= { wsSwMstVlanTable 1 }

		
		WsSwMstVlanEntry ::=
			SEQUENCE { 
				wsSwMstVlanIndex
					VlanId,
				wsSwMstVlanMstIndex
					MstiOrCistInstanceIndex
			 }

		-- 1.3.6.1.4.1.388.14.2.14.12.1.1
		wsSwMstVlanIndex OBJECT-TYPE
			SYNTAX VlanId
			MAX-ACCESS read-only
			STATUS current
			DESCRIPTION
				"The VlanId for which this entry contains the instance mapped."
			::= { wsSwMstVlanEntry 1 }

		
		-- 1.3.6.1.4.1.388.14.2.14.12.1.2
		wsSwMstVlanMstIndex OBJECT-TYPE
			SYNTAX MstiOrCistInstanceIndex
			MAX-ACCESS read-only
			STATUS current
			DESCRIPTION
				"An integer with values ranging from 0 to 16 that identify 
				the CIST/MSTI instance to which this VLAN is mapped"
			::= { wsSwMstVlanEntry 2 }

		
		-- 1.3.6.1.4.1.388.14.2.14.13
		wsSwMstpPortTable OBJECT-TYPE
			SYNTAX SEQUENCE OF WsSwMstpPortEntry
			MAX-ACCESS not-accessible
			STATUS current
			DESCRIPTION
				"A table that contains generic information about
				every port that is associated with this bridge."
			::= { wsSwMstp 13 }

		
		-- 1.3.6.1.4.1.388.14.2.14.13.1
		wsSwMstpPortEntry OBJECT-TYPE
			SYNTAX WsSwMstpPortEntry
			MAX-ACCESS not-accessible
			STATUS current
			DESCRIPTION
				"A list of information for each port of the
				bridge."
			INDEX { wsSwMstpPortIndex }
			::= { wsSwMstpPortTable 1 }

		
		WsSwMstpPortEntry ::=
			SEQUENCE { 
				wsSwMstpPortIndex
					PortIndex,
				wsSwMstpPortAdminMACEnable
					TruthValue,
				wsSwMstpPortOperMACEnable
					TruthValue,
				wsSwMstpPortAutoEdge
					TruthValue,
				wsSwMstpPortDesignatedBridge
					BridgeId,
				wsSwMstpPortGuardRoot
					TruthValue,
				wsSwMstpAdminPortPortfastBpduFilter
					INTEGER,
				wsSwMstpOperPortPortfastBpduFilter
					TruthValue,
				wsSwMstpAdminPortPortfastBpduGuard
					INTEGER,
				wsSwMstpOperPortPortfastBpduGuard
					TruthValue,
				wsSwMstpPortVersion
					INTEGER
			 }

		-- 1.3.6.1.4.1.388.14.2.14.13.1.1
		wsSwMstpPortIndex OBJECT-TYPE
			SYNTAX PortIndex
			MAX-ACCESS read-only
			STATUS current
			DESCRIPTION
				"A unique value, greater than zero, for each Port.
				The value for each interface sub-layer
				must remain constant at least from one re-initialization
				of the entity's network management system to the next re-
				initialization."
			::= { wsSwMstpPortEntry 1 }

		
		-- 1.3.6.1.4.1.388.14.2.14.13.1.2
		wsSwMstpPortAdminMACEnable OBJECT-TYPE
			SYNTAX TruthValue
			MAX-ACCESS read-write
			STATUS current
			DESCRIPTION
				"The value of the MAC Enabled parameter (6.4.2 of IEEE Std 802.1D, 1998 Edition).
				May be present if the implementation supports the MAC Enabled parameter."
			REFERENCE
				"IEEE Std 802.1s Clause 12.8.2.5.2"
			::= { wsSwMstpPortEntry 2 }

		
		-- 1.3.6.1.4.1.388.14.2.14.13.1.3
		wsSwMstpPortOperMACEnable OBJECT-TYPE
			SYNTAX TruthValue
			MAX-ACCESS read-only
			STATUS current
			DESCRIPTION
				"The operational value of the MAC Enabled parameter (6.4.2 of IEEE Std 802.1D, 1998 Edition).
				May be present if the implementation supports the MAC Enabled parameter."
			REFERENCE
				"IEEE Std 802.1s Clause 12.8.2.5.2"
			::= { wsSwMstpPortEntry 3 }

		
		-- 1.3.6.1.4.1.388.14.2.14.13.1.9
		wsSwMstpPortAutoEdge OBJECT-TYPE
			SYNTAX TruthValue
			MAX-ACCESS read-write
			STATUS current
			DESCRIPTION
				"Optional and provided only by MSTP Bridges that support the automatic
				identification of edge ports."
			REFERENCE
				"IEEE Std 8021D-2004 Clause 17.25"
			::= { wsSwMstpPortEntry 9 }

		
		-- 1.3.6.1.4.1.388.14.2.14.13.1.14
		wsSwMstpPortDesignatedBridge OBJECT-TYPE
			SYNTAX BridgeId
			MAX-ACCESS read-only
			STATUS current
			DESCRIPTION
				"The designated bridge for this port"
			::= { wsSwMstpPortEntry 14 }

		
		-- 1.3.6.1.4.1.388.14.2.14.13.1.50
		wsSwMstpPortGuardRoot OBJECT-TYPE
			SYNTAX TruthValue
			MAX-ACCESS read-write
			STATUS current
			DESCRIPTION
				"If set to true, makes sure that the port on which it is 
				enabled is a designated port. If the Root Guard enabled
				port receives a superior BPDU, it goes to a discarding state."
			::= { wsSwMstpPortEntry 50 }

		
		-- 1.3.6.1.4.1.388.14.2.14.13.1.51
		wsSwMstpAdminPortPortfastBpduFilter OBJECT-TYPE
			SYNTAX INTEGER
				{
				enabled(0),
				disabled(1),
				default(2)
				}
			MAX-ACCESS read-write
			STATUS current
			DESCRIPTION
				"Enabling the Port BPDU Filter feature ensures that 
				PortFastenabled ports (edge ports for which
				dot1dStpPortOperEdgePort is true) do not transmit or
				receive any BPDUs.
				When set to enabled or disabled, this configuration takes
				precedence over wsSwMstpPortfastBpduFilter. However, when
				setto default, the bridge level BPDU-filter configuration
				takes effect for the port."
			::= { wsSwMstpPortEntry 51 }

		
		-- 1.3.6.1.4.1.388.14.2.14.13.1.52
		wsSwMstpOperPortPortfastBpduFilter OBJECT-TYPE
			SYNTAX TruthValue
			MAX-ACCESS read-only
			STATUS current
			DESCRIPTION
				"The operational value for Portfast BPDU 
				Filter for this port"
			::= { wsSwMstpPortEntry 52 }

		
		-- 1.3.6.1.4.1.388.14.2.14.13.1.53
		wsSwMstpAdminPortPortfastBpduGuard OBJECT-TYPE
			SYNTAX INTEGER
				{
				enabled(0),
				disabled(1),
				default(2)
				}
			MAX-ACCESS read-write
			STATUS current
			DESCRIPTION
				"When the BPDU Guard feature is set for a bridge, all
				portfast-enabled ports (edge ports for which
				dot1dStpPortOperEdgePort is true) of the bridge that have
				bpdu-guard set to default shut down the port on receiving 
				a BPDU. In this case, the BPDU is not processed.
				When set to enabled or disabled, this configuration takes
				precedence over wsSwMstpPortfastBpduGuard. However, when
				setto default, the bridge level BPDU-guard configuration
				takes effect for the port."
			::= { wsSwMstpPortEntry 53 }

		
		-- 1.3.6.1.4.1.388.14.2.14.13.1.54
		wsSwMstpOperPortPortfastBpduGuard OBJECT-TYPE
			SYNTAX TruthValue
			MAX-ACCESS read-only
			STATUS current
			DESCRIPTION
				"The operational value for Portfast BPDU guard
				for this port"
			::= { wsSwMstpPortEntry 54 }

		
		-- 1.3.6.1.4.1.388.14.2.14.13.1.55
		wsSwMstpPortVersion OBJECT-TYPE
			SYNTAX INTEGER
				{
				stp(0),
				reserved(1),
				rstp(2),
				mstp(3)
				}
			MAX-ACCESS read-write
			STATUS current
			DESCRIPTION
				"The spanning tree version used by BPDU's sent
				and received on this port"
			::= { wsSwMstpPortEntry 55 }

		
		-- 1.3.6.1.4.1.388.14.2.14.14
		wsSwMstpXstTable OBJECT-TYPE
			SYNTAX SEQUENCE OF WsSwMstpXstEntry
			MAX-ACCESS not-accessible
			STATUS current
			DESCRIPTION
				"A table that contains information about
				every MST instance on this bridge."
			::= { wsSwMstp 14 }

		
		-- 1.3.6.1.4.1.388.14.2.14.14.1
		wsSwMstpXstEntry OBJECT-TYPE
			SYNTAX WsSwMstpXstEntry
			MAX-ACCESS not-accessible
			STATUS current
			DESCRIPTION
				"A list of information for each instance on this bridge"
			INDEX { wsSwMstpXstId }
			::= { wsSwMstpXstTable 1 }

		
		WsSwMstpXstEntry ::=
			SEQUENCE { 
				wsSwMstpXstId
					MstiOrCistInstanceIndex,
				wsSwMstpXstBridgePriority
					INTEGER,
				wsSwMstpXstBridgeId
					BridgeId,
				wsSwMstpXstDesignatedRoot
					BridgeId,
				wsSwMstpXstInternalRootCost
					Integer32,
				wsSwMstpXstRootPort
					PortIndexOrZero,
				wsSwMstpXstMasterPort
					PortIndexOrZero,
				wsSwMstpXstRowStatus
					AbbrevRowStatus
			 }

		-- 1.3.6.1.4.1.388.14.2.14.14.1.1
		wsSwMstpXstId OBJECT-TYPE
			SYNTAX MstiOrCistInstanceIndex
			MAX-ACCESS read-only
			STATUS current
			DESCRIPTION
				"The instance id."
			::= { wsSwMstpXstEntry 1 }

		
		-- 1.3.6.1.4.1.388.14.2.14.14.1.2
		wsSwMstpXstBridgePriority OBJECT-TYPE
			SYNTAX INTEGER (0..61440)
			MAX-ACCESS read-create
			STATUS current
			DESCRIPTION
				"Bridge priority, in steps of 4096."
			DEFVAL { 32768 }
			::= { wsSwMstpXstEntry 2 }

		
		-- 1.3.6.1.4.1.388.14.2.14.14.1.3
		wsSwMstpXstBridgeId OBJECT-TYPE
			SYNTAX BridgeId
			MAX-ACCESS read-only
			STATUS current
			DESCRIPTION
				"The bridge ID for this instance"
			::= { wsSwMstpXstEntry 3 }

		
		-- 1.3.6.1.4.1.388.14.2.14.14.1.4
		wsSwMstpXstDesignatedRoot OBJECT-TYPE
			SYNTAX BridgeId
			MAX-ACCESS read-only
			STATUS current
			DESCRIPTION
				"The designated root for this instance"
			::= { wsSwMstpXstEntry 4 }

		
		-- 1.3.6.1.4.1.388.14.2.14.14.1.6
		wsSwMstpXstInternalRootCost OBJECT-TYPE
			SYNTAX Integer32
			MAX-ACCESS read-only
			STATUS current
			DESCRIPTION
				"The internal root cost for this instance"
			::= { wsSwMstpXstEntry 6 }

		
		-- 1.3.6.1.4.1.388.14.2.14.14.1.7
		wsSwMstpXstRootPort OBJECT-TYPE
			SYNTAX PortIndexOrZero
			MAX-ACCESS read-only
			STATUS current
			DESCRIPTION
				"The root port for this instance, if on this bridge."
			::= { wsSwMstpXstEntry 7 }

		
		-- 1.3.6.1.4.1.388.14.2.14.14.1.8
		wsSwMstpXstMasterPort OBJECT-TYPE
			SYNTAX PortIndexOrZero
			MAX-ACCESS read-only
			STATUS current
			DESCRIPTION
				"The master port for this instance, if on this bridge.
				Non zero value may not be in CIST."
			::= { wsSwMstpXstEntry 8 }

		
		-- 1.3.6.1.4.1.388.14.2.14.14.1.9
		wsSwMstpXstRowStatus OBJECT-TYPE
			SYNTAX AbbrevRowStatus
			MAX-ACCESS read-create
			STATUS current
			DESCRIPTION
				"row status: only createAndGo, destroy, active are supported."
			::= { wsSwMstpXstEntry 9 }

		
		-- 1.3.6.1.4.1.388.14.2.14.15
		wsSwMstpXstPortTable OBJECT-TYPE
			SYNTAX SEQUENCE OF WsSwMstpXstPortEntry
			MAX-ACCESS not-accessible
			STATUS current
			DESCRIPTION
				"A table to manage ports inside instances - both CIST
				and MSTIs. It contains objects, describing
				ports and is common for these both types of instances."
			::= { wsSwMstp 15 }

		
		-- 1.3.6.1.4.1.388.14.2.14.15.1
		wsSwMstpXstPortEntry OBJECT-TYPE
			SYNTAX WsSwMstpXstPortEntry
			MAX-ACCESS not-accessible
			STATUS current
			DESCRIPTION
				"A list of information for each port in each instance for this bridge."
			REFERENCE
				"."
			INDEX { wsSwMstpXstPortIndex, wsSwMstpXstPortXstId }
			::= { wsSwMstpXstPortTable 1 }

		
		WsSwMstpXstPortEntry ::=
			SEQUENCE { 
				wsSwMstpXstPortXstId
					MstiOrCistInstanceIndex,
				wsSwMstpXstPortIndex
					PortIndex,
				wsSwMstpXstPortState
					INTEGER,
				wsSwMstpXstPortRole
					INTEGER,
				wsSwMstpXstPortInternalRootCost
					Integer32,
				wsSwMstpXstPortDesignatedBridge
					BridgeId,
				wsSwMstpXstPortDesignatedPort
					PortId,
				wsSwMstpXstPortPriority
					INTEGER,
				wsSwMstpXstPortAdminInternalPathCost
					INTEGER,
				wsSwMstpXstPortOperInternalPathCost
					Integer32
			 }

		-- 1.3.6.1.4.1.388.14.2.14.15.1.1
		wsSwMstpXstPortXstId OBJECT-TYPE
			SYNTAX MstiOrCistInstanceIndex
			MAX-ACCESS read-only
			STATUS current
			DESCRIPTION
				"The instance id. 0 means CIST."
			::= { wsSwMstpXstPortEntry 1 }

		
		-- 1.3.6.1.4.1.388.14.2.14.15.1.2
		wsSwMstpXstPortIndex OBJECT-TYPE
			SYNTAX PortIndex
			MAX-ACCESS read-only
			STATUS current
			DESCRIPTION
				"The value of wsSwMstpPortIndex of the Port
				in wsSwMstpPortTable."
			::= { wsSwMstpXstPortEntry 2 }

		
		-- 1.3.6.1.4.1.388.14.2.14.15.1.3
		wsSwMstpXstPortState OBJECT-TYPE
			SYNTAX INTEGER
				{
				disabled(0),
				discarding(1),
				learning(2),
				forwarding(3),
				unknown(4)
				}
			MAX-ACCESS read-only
			STATUS current
			DESCRIPTION
				"The state the port is in."
			::= { wsSwMstpXstPortEntry 3 }

		
		-- 1.3.6.1.4.1.388.14.2.14.15.1.4
		wsSwMstpXstPortRole OBJECT-TYPE
			SYNTAX INTEGER
				{
				disabled(1),
				alternate(2),
				backup(3),
				root(4),
				designated(5),
				master(6),
				nonStp(7),
				unknown(8)
				}
			MAX-ACCESS read-only
			STATUS current
			DESCRIPTION
				"The role of this port"
			::= { wsSwMstpXstPortEntry 4 }

		
		-- 1.3.6.1.4.1.388.14.2.14.15.1.9
		wsSwMstpXstPortInternalRootCost OBJECT-TYPE
			SYNTAX Integer32
			MAX-ACCESS read-only
			STATUS current
			DESCRIPTION
				"The internal root path cost for this port in this instance"
			::= { wsSwMstpXstPortEntry 9 }

		
		-- 1.3.6.1.4.1.388.14.2.14.15.1.10
		wsSwMstpXstPortDesignatedBridge OBJECT-TYPE
			SYNTAX BridgeId
			MAX-ACCESS read-only
			STATUS current
			DESCRIPTION
				"The designated bridge ID for this port in this instance"
			::= { wsSwMstpXstPortEntry 10 }

		
		-- 1.3.6.1.4.1.388.14.2.14.15.1.14
		wsSwMstpXstPortDesignatedPort OBJECT-TYPE
			SYNTAX PortId
			MAX-ACCESS read-only
			STATUS current
			DESCRIPTION
				"The designated port id"
			::= { wsSwMstpXstPortEntry 14 }

		
		-- 1.3.6.1.4.1.388.14.2.14.15.1.15
		wsSwMstpXstPortPriority OBJECT-TYPE
			SYNTAX INTEGER (0..255)
			MAX-ACCESS read-create
			STATUS current
			DESCRIPTION
				"Port priority, in steps of 16."
			DEFVAL { 128 }
			::= { wsSwMstpXstPortEntry 15 }

		
		-- 1.3.6.1.4.1.388.14.2.14.15.1.16
		wsSwMstpXstPortAdminInternalPathCost OBJECT-TYPE
			SYNTAX INTEGER (0..200000000)
			MAX-ACCESS read-create
			STATUS current
			DESCRIPTION
				"The value of the internal path cost. The value 0 means,
				that the cost will be selected automatically."
			DEFVAL { 0 }
			::= { wsSwMstpXstPortEntry 16 }

		
		-- 1.3.6.1.4.1.388.14.2.14.15.1.17
		wsSwMstpXstPortOperInternalPathCost OBJECT-TYPE
			SYNTAX Integer32
			MAX-ACCESS read-only
			STATUS current
			DESCRIPTION
				"The operational value of the internal path cost"
			::= { wsSwMstpXstPortEntry 17 }

		
		-- 1.3.6.1.4.1.388.14.2.14.16
		wsSwMstpOptionSupport OBJECT IDENTIFIER ::= { wsSwMstp 16 }

		
		-- 1.3.6.1.4.1.388.14.2.14.16.1
		wsSwMstpOptionPortAdminMACEnable OBJECT-TYPE
			SYNTAX TruthValue
			MAX-ACCESS read-only
			STATUS current
			DESCRIPTION
				"If this is true, swWsMstpPortAdminMACEnable can be set"
			::= { wsSwMstpOptionSupport 1 }

		
		-- 1.3.6.1.4.1.388.14.2.14.16.2
		wsSwMstpOptionPortAutoEdge OBJECT-TYPE
			SYNTAX TruthValue
			MAX-ACCESS read-only
			STATUS current
			DESCRIPTION
				"If this is true wsSwMstpPortAutoEdge can be set"
			::= { wsSwMstpOptionSupport 2 }

		
		-- 1.3.6.1.4.1.388.14.2.14.100
		wsSwMstpConformance OBJECT IDENTIFIER ::= { wsSwMstp 100 }

		
		-- 1.3.6.1.4.1.388.14.2.14.100.1
		wsSwMstpGroups OBJECT IDENTIFIER ::= { wsSwMstpConformance 1 }

		
		-- 1.3.6.1.4.1.388.14.2.14.100.1.1
		currentObjectGroup OBJECT-GROUP
			OBJECTS { wsSwMstpGenMaxHops, wsSwMstpVersionsSupported, wsSwMstpGenProtocolVersion, wsSwMstpGenCfgIdFmtSel, wsSwMstpGenCfgIdName, 
				wsSwMstpGenCfgIdRevLevel, wsSwMstpGenCfgIdDigest, wsSwMstpGenRegionalRoot, wsSwMstpGenExternalRootCost, wsSwMstpErrdisableTimeout, 
				wsSwMstpErrdisableTimeoutInterval, wsSwMstpPortFastBpduGuard, wsSwMstpAdminCiscoInteroperability, wsSwMstpOperCiscoInteroperability, wsSwMstMapIndex, 
				wsSwMstMapVlans1k, wsSwMstMapVlans2k, wsSwMstMapVlans3k, wsSwMstMapVlans4k, wsSwMstVlanIndex, 
				wsSwMstVlanMstIndex, wsSwMstpPortIndex, wsSwMstpPortAdminMACEnable, wsSwMstpPortOperMACEnable, wsSwMstpPortAutoEdge, 
				wsSwMstpPortDesignatedBridge, wsSwMstpPortGuardRoot, wsSwMstpAdminPortPortfastBpduFilter, wsSwMstpOperPortPortfastBpduFilter, wsSwMstpAdminPortPortfastBpduGuard, 
				wsSwMstpOperPortPortfastBpduGuard, wsSwMstpXstId, wsSwMstpXstBridgePriority, wsSwMstpXstBridgeId, wsSwMstpXstDesignatedRoot, 
				wsSwMstpXstInternalRootCost, wsSwMstpXstRootPort, wsSwMstpXstMasterPort, wsSwMstpXstPortXstId, wsSwMstpXstPortIndex, 
				wsSwMstpXstPortState, wsSwMstpXstPortRole, wsSwMstpXstPortInternalRootCost, wsSwMstpXstPortDesignatedBridge, wsSwMstpXstPortDesignatedPort, 
				wsSwMstpXstPortPriority, wsSwMstpXstPortAdminInternalPathCost, wsSwMstpXstPortOperInternalPathCost, wsSwMstpOptionPortAdminMACEnable, wsSwMstpOptionPortAutoEdge, 
				wsSwMstpXstRowStatus, wsSwMstpPortVersion, wsSwMstpPortfastBpduFilter, wsSwMstpGlobalState }
			STATUS current
			DESCRIPTION 
				"OBJECT-GROUP for WS-SW-MSTP-MIB"
			::= { wsSwMstpGroups 1 }

		
		-- 1.3.6.1.4.1.388.14.2.14.100.2
		wsSwMstpCompliances OBJECT IDENTIFIER ::= { wsSwMstpConformance 2 }

		
		-- 1.3.6.1.4.1.388.14.2.14.100.2.1
		basicCompliance MODULE-COMPLIANCE
			STATUS current
			DESCRIPTION 
				"MODULE-COMPLIANCE for WS-SW-MSTP-MIB"
			MODULE -- this module
				MANDATORY-GROUPS { currentObjectGroup }
			::= { wsSwMstpCompliances 1 }

		
	
	END

--
-- WS-SW-MSTP-MIB.my
--
