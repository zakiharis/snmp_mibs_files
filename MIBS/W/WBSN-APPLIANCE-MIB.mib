-------------------------------------------------------------------------------
-------------------------------------------------------------------------------
--                           Websense Appliance MIB File
--                               Websense, Inc.
--                         Copyright (c) 1996 - 2011
--                          10240 Sorrento Valley Rd
--                           San Diego, CA 92121
--                              (858) 320-8000
--
-------------------------------------------------------------------------------
-------------------------------------------------------------------------------
WBSN-APPLIANCE-MIB DEFINITIONS ::= BEGIN

        IMPORTS
                TRAP-TYPE 
                FROM RFC-1215

                enterprises,         MODULE-IDENTITY,    OBJECT-TYPE, Integer32
                FROM SNMPv2-SMI

                DisplayString, DateAndTime
                FROM SNMPv2-TC

                ssCpuUser, ssErrorName, ssCpuSystem, ssCpuIdle, memTotalReal, memAvailReal, memTotalFree, memShared, memBuffer, memCached, memTotalSwap, memAvailSwap, dskPath, dskErrorMsg, memErrorName, memSwapErrorMsg, fileName, fileErrorMsg
                FROM UCD-SNMP-MIB;

        websense MODULE-IDENTITY
                LAST-UPDATED "201202200000Z"
                ORGANIZATION "Websense, Inc."
                CONTACT-INFO "http://www.websense.com"
                DESCRIPTION  "Websense Appliance SNMP"
                ::= { enterprises 23365 }

        appliance OBJECT IDENTIFIER ::= { websense 10000 }

        moduleName OBJECT-TYPE
                SYNTAX      DisplayString
                MAX-ACCESS  read-only
                STATUS      current
                DESCRIPTION
                    "The name of current module: Appliance Controller, Websense Content Gateway, Websense Web Security, Network Agent, Websense Email Security Gateway"
                ::= { appliance 1 }
        memUsageFlag OBJECT-TYPE
                SYNTAX      INTEGER
                MAX-ACCESS  read-only
                STATUS      current
                DESCRIPTION
                    "The flag to indicate memory usage exceed"
                ::= { appliance 2 }
        vmTable OBJECT-TYPE
                SYNTAX      SEQUENCE OF VmEntry
                MAX-ACCESS  not-accessible
                STATUS      current
                DESCRIPTION
                    "A list of virtual machines."
                ::= { appliance 3 }
        vmEntry OBJECT-TYPE
                SYNTAX      VmEntry
                MAX-ACCESS  not-accessible
                STATUS      current
                DESCRIPTION
                    "A concept row of virtual machine table."
                INDEX { vmName }
                ::= { vmTable 1 }
        VmEntry ::=
                SEQUENCE {
                        vmStatus        INTEGER,
                        vmName          DisplayString
                }
        vmStatus OBJECT-TYPE
                SYNTAX  INTEGER { online(0), offline(1) }   
                MAX-ACCESS  read-only
                STATUS      current
                DESCRIPTION
                    "The status of virtual machine."
                ::= { vmEntry 1 }
        vmName OBJECT-TYPE
                SYNTAX  DisplayString    
                MAX-ACCESS  read-only
                STATUS      current
                DESCRIPTION
                    "The name of virtual machine."
                ::= { vmEntry 2 }

        hostname OBJECT IDENTIFIER
                ::= { appliance 4 }
        hostnameChangeFlag OBJECT-TYPE
                SYNTAX      INTEGER
                MAX-ACCESS  read-only
                STATUS      current
                DESCRIPTION
                    "The flag to indicate hostname change."
                ::= { hostname 1 }
        prevHostname OBJECT-TYPE
                SYNTAX      DisplayString
                MAX-ACCESS  read-only
                STATUS      current
                DESCRIPTION
                    "The hostname before changed."
                ::= { hostname 2 }
        currHostname OBJECT-TYPE
                SYNTAX      DisplayString
                MAX-ACCESS  read-only
                STATUS      current
                DESCRIPTION
                    "The current hostname."
                ::= { hostname 3 }
        ifaTable OBJECT-TYPE
                SYNTAX      SEQUENCE OF IfaEntry
                MAX-ACCESS  not-accessible
                STATUS      current
                DESCRIPTION
                    "A list of monitoring interface IP addresses."
                ::= { appliance 5 }
        ifaEntry OBJECT-TYPE
                SYNTAX      IfaEntry
                MAX-ACCESS  not-accessible
                STATUS      current
                DESCRIPTION
                    "A concept row of monitoring interface IP address table."
                INDEX {ifaName }
                ::= { ifaTable 1 }
        IfaEntry ::=
                SEQUENCE {
                        ifaChangeFlag           INTEGER,
                        ifaName                 DisplayString,
                        ifaPrevAddress          DisplayString,
                        ifaCurrAddress          DisplayString,
                        ifaSpeed                INTEGER,
                        ifaInboundExceedFlag    INTEGER,
                        ifaOutboundExceedFlag   INTEGER,
                        ifaPhysAddress          DisplayString,
                        ifaChangeFlagv6         Integer32,
                        ifaPrevAddressv6        DisplayString,
                        ifaCurrAddressv6        DisplayString
                }
        ifaChangeFlag OBJECT-TYPE
                SYNTAX  INTEGER   
                MAX-ACCESS  read-only
                STATUS      current
                DESCRIPTION
                    "The flag to indicate whether the IP address of monitoring interface has been changed."
                ::= { ifaEntry 1 }
        ifaName OBJECT-TYPE
                SYNTAX  DisplayString    
                MAX-ACCESS  read-only
                STATUS      current
                DESCRIPTION
                    "The name of monitoring interface."
                ::= { ifaEntry 2 }
        ifaPrevAddress OBJECT-TYPE
                SYNTAX  DisplayString    
                MAX-ACCESS  read-only
                STATUS      current
                DESCRIPTION
                    "The previous IP address of monitoring interface."
                ::= { ifaEntry 3 }
        ifaCurrAddress OBJECT-TYPE
                SYNTAX  DisplayString    
                MAX-ACCESS  read-only
                STATUS      current
                DESCRIPTION
                    "The current IP address of monitoring interface."
                ::= { ifaEntry 4 }
        ifaSpeed OBJECT-TYPE
                SYNTAX  INTEGER   
                MAX-ACCESS  read-only
                STATUS      current
                DESCRIPTION
                    "The speed of monitoring interface."
                ::= { ifaEntry 5 }
        ifaInboundExceedFlag OBJECT-TYPE
                SYNTAX  INTEGER   
                MAX-ACCESS  read-only
                STATUS      current
                DESCRIPTION
                    "The flag to indicate whether the inbound network traffic of monitoring interface exceeds its threhold."
                ::= { ifaEntry 6 }
        ifaOutboundExceedFlag OBJECT-TYPE
                SYNTAX  INTEGER   
                MAX-ACCESS  read-only
                STATUS      current
                DESCRIPTION
                    "The flag to indicate whether the outbound network traffic of monitoring interface exceeds its threhold."
                ::= { ifaEntry 7 }
        ifaPhysAddress OBJECT-TYPE
                SYNTAX  DisplayString    
                MAX-ACCESS  read-only
                STATUS      current
                DESCRIPTION
                    "The physical address of monitoring interface."
                ::= { ifaEntry 8 }
        ifaChangeFlagv6 OBJECT-TYPE
                SYNTAX  INTEGER   
                MAX-ACCESS  read-only
                STATUS      current
                DESCRIPTION
                    "The flag to indicate whether the IPv6 address of monitoring interface has been changed."
                ::= { ifaEntry 9 }
        ifaPrevAddressv6 OBJECT-TYPE
                SYNTAX  DisplayString    
                MAX-ACCESS  read-only
                STATUS      current
                DESCRIPTION
                    "The previous IPv6 address of monitoring interface."
                ::= { ifaEntry 10 }
        ifaCurrAddressv6 OBJECT-TYPE
                SYNTAX  DisplayString    
                MAX-ACCESS  read-only
                STATUS      current
                DESCRIPTION
                    "The current IPv6 address of monitoring interface."
                ::= { ifaEntry 11 }
        raidStatus OBJECT IDENTIFIER ::= { appliance 6 }
        raidErrorFlag OBJECT-TYPE
                SYNTAX  INTEGER   
                MAX-ACCESS  read-only
                STATUS      current
                DESCRIPTION
                    "The flag is set when disk error is detected."
                ::= { raidStatus 1 }
        dskPhysicalNr OBJECT-TYPE
                SYNTAX  DisplayString    
                MAX-ACCESS  read-only
                STATUS      current
                DESCRIPTION
                    "The number of physical disks in the RAID controller."
                ::= { raidStatus 2 }
        dskCriticalNr OBJECT-TYPE
                SYNTAX  DisplayString    
                MAX-ACCESS  read-only
                STATUS      current
                DESCRIPTION
                    "The number of physical disks in critical state."
                ::= { raidStatus 3 }
        dskFailedNr OBJECT-TYPE
                SYNTAX  DisplayString    
                MAX-ACCESS  read-only
                STATUS      current
                DESCRIPTION
                    "The number of physical disks in failed state."
                ::= { raidStatus 4 }
        dskPhysErrMsg OBJECT-TYPE
                SYNTAX  DisplayString    
                MAX-ACCESS  read-only
                STATUS      current
                DESCRIPTION
                    "The error message to describe the abnormal state of physical disks."
                ::= { raidStatus 5 }
        dskVirtualNr OBJECT-TYPE
                SYNTAX  DisplayString    
                MAX-ACCESS  read-only
                STATUS      current
                DESCRIPTION
                    "The number of virtual drives in the RAID controller."
                ::= { raidStatus 6 }
        dskDegradedNr OBJECT-TYPE
                SYNTAX  DisplayString    
                MAX-ACCESS  read-only
                STATUS      current
                DESCRIPTION
                    "The number of degraded virtual drives."
                ::= { raidStatus 7 }
        dskOfflineNr OBJECT-TYPE
                SYNTAX  DisplayString    
                MAX-ACCESS  read-only
                STATUS      current
                DESCRIPTION
                    "The number of offline virtual drives."
                ::= { raidStatus 8 }

        svcTable OBJECT-TYPE
                SYNTAX      SEQUENCE OF SvcEntry
                MAX-ACCESS  not-accessible
                STATUS      current
                DESCRIPTION
                    "A list of service entries."
                ::= { appliance 7 }
        svcEntry OBJECT-TYPE
                SYNTAX      SvcEntry
                MAX-ACCESS  not-accessible
                STATUS      current
                DESCRIPTION
                    "A concept row of service table."
                INDEX { svcName }
                ::= { svcTable 1 }
        SvcEntry ::=
                SEQUENCE {
                        svcStatus        INTEGER,
                        svcName          DisplayString
                }
        svcStatus OBJECT-TYPE
                SYNTAX  INTEGER { up(0), down(1), yellow(2), resetting(3), disabled(4) }   
                MAX-ACCESS  read-only
                STATUS      current
                DESCRIPTION
                    "The status of service."
                ::= { svcEntry 1 }
        svcName OBJECT-TYPE
                SYNTAX  DisplayString    
                MAX-ACCESS  read-only
                STATUS      current
                DESCRIPTION
                    "The name of service."
                ::= { svcEntry 2 }
        loadAvg OBJECT IDENTIFIER ::= { appliance 8 }
        loadErrorFlag OBJECT-TYPE
                SYNTAX  INTEGER   
                MAX-ACCESS  read-only
                STATUS      current
                DESCRIPTION
                    "The flag is set when load average limit is met."
                ::= { loadAvg 1 }
        loadName OBJECT-TYPE
                SYNTAX  DisplayString    
                MAX-ACCESS  read-only
                STATUS      current
                DESCRIPTION
                    "The load name."
                ::= { loadAvg 2 }
        loadErrorMessage OBJECT-TYPE
                SYNTAX  DisplayString    
                MAX-ACCESS  read-only
                STATUS      current
                DESCRIPTION
                    "The message to describe current load error."
                ::= { loadAvg 3 }

        wsAlert OBJECT IDENTIFIER ::= { appliance 9 }
        wsAlertMessage OBJECT-TYPE
                SYNTAX  DisplayString   
                MAX-ACCESS  read-only
                STATUS      current
                DESCRIPTION
                    "The detailed message to describe current alert."
                ::= { wsAlert 1 }

        evtInfo OBJECT IDENTIFIER ::= { appliance 10 }
        evtTimestamp OBJECT-TYPE
                SYNTAX      DisplayString
                MAX-ACCESS  read-only
                STATUS      current
                DESCRIPTION
                    "Timestamp when current event occurred"
                ::= { evtInfo 1 }
        evtDir OBJECT-TYPE
                SYNTAX      INTEGER { assertion(0), deassertion(1) }
                MAX-ACCESS  read-only
                STATUS      current
                DESCRIPTION
                    "The direction of the event"
                ::= { evtInfo 2 }
        evtSensor OBJECT-TYPE
                SYNTAX      DisplayString
                MAX-ACCESS  read-only
                STATUS      current
                DESCRIPTION
                    "The name of sensor: Power Supply, Temperature, Fan, Voltage, System ACPI Power State, Event Logging Disabled, Physical Security (Chassis
Intrusion), Battery"
                ::= { evtInfo 3 }
        evtDesc OBJECT-TYPE
                SYNTAX      DisplayString
                MAX-ACCESS  read-only
                STATUS      current
                DESCRIPTION
                    "The name of current event"
                ::= { evtInfo 4 }
        triggerReading OBJECT-TYPE
                SYNTAX      DisplayString
                MAX-ACCESS  read-only
                STATUS      current
                DESCRIPTION
                    "The trigger reading of sensor"
                ::= { evtInfo 5 }
        triggerThreshold OBJECT-TYPE
                SYNTAX      DisplayString
                MAX-ACCESS  read-only
                STATUS      current
                DESCRIPTION
                    "The threshold to trigger this event"
                ::= { evtInfo 6 }

        errorClear OBJECT IDENTIFIER
                ::= { appliance 10000 }

        --                Websense appliance Enterprise Alerts
        --                Supported Alarming Events (Traps)
        -----------------------------------------------------------------------

        -----------------------------------------------------------------------
        -- System Monitoring
        -----------------------------------------------------------------------
        testEvent       TRAP-TYPE
                ENTERPRISE appliance
                DESCRIPTION
                     " Websense Alert: this event is for testing use"
                ::= 10

        cpuMaxUsageExceed        TRAP-TYPE
                ENTERPRISE appliance
                VARIABLES { ssErrorName,
                        ssCpuUser,
                        ssCpuSystem,
                        ssCpuIdle}
                DESCRIPTION
                        " Websense Alert: high CPU usage"
                ::= 1000 

        cpuMaxUsageExceedClear        TRAP-TYPE
                ENTERPRISE errorClear
                VARIABLES { ssErrorName,
                        ssCpuUser,
                        ssCpuSystem,
                        ssCpuIdle}
                DESCRIPTION
                        " Websense Alert: 'high CPU usage' is cleared"
                ::= 1000 

        memMaxUsageExceed        TRAP-TYPE
                ENTERPRISE appliance
                VARIABLES { memTotalReal,
                        memAvailReal,
                        memTotalFree,
                        memShared,
                        memBuffer,
                        memCached,
                        memTotalSwap,
                        memAvailSwap }
                DESCRIPTION
                        " Websense Alert: high memory usage"
                ::= 1001

        memMaxUsageExceedClear       TRAP-TYPE
                ENTERPRISE errorClear
                VARIABLES { memTotalReal,
                        memAvailReal,
                        memTotalFree,
                        memShared,
                        memBuffer,
                        memCached,
                        memTotalSwap,
                        memAvailSwap }
                DESCRIPTION
                        " Websense Alert: 'high memory usage' is cleared"
                ::= 1001

        networkMaxBandwidthExceed        TRAP-TYPE
                ENTERPRISE appliance
                VARIABLES { ifaName,
                            ifaCurrAddress,
                            ifaSpeed,
                            ifaPhysAddress }
                DESCRIPTION
                        " Websense Alert: heavy network traffic on interface"
                ::= 1002

        networkMaxBandwidthExceedClear       TRAP-TYPE
                ENTERPRISE errorClear
                VARIABLES { ifaName,
                            ifaCurrAddress,
                            ifaSpeed,
                            ifaPhysAddress }
                DESCRIPTION
                        " Websense Alert: 'heavy network traffic on interface' is cleared"
                ::= 1002

        diskFreeMinSizeExceed        TRAP-TYPE
                ENTERPRISE appliance
                VARIABLES {
                        dskPath,
                        dskErrorMsg }
                DESCRIPTION
                        " Websense Alert: low free disk space"
                ::= 1003

        diskFreeMinSizeExceedClear        TRAP-TYPE
                ENTERPRISE errorClear
                VARIABLES {
                        dskPath,
                        dskErrorMsg }
                DESCRIPTION
                        " Websense Alert: 'low free disk space' is cleared"
                ::= 1003

        swapMinFreeExceed        TRAP-TYPE
                ENTERPRISE appliance
                VARIABLES {
                        memErrorName,
                        memSwapErrorMsg }
                DESCRIPTION
                        " Websense Alert: low free swap space"
                ::= 1004

        swapMinFreeExceedClear        TRAP-TYPE
                ENTERPRISE errorClear
                VARIABLES {
                        memErrorName,
                        memSwapErrorMsg }
                DESCRIPTION
                        " Websense Alert: 'low free swap space' is cleared"
                ::= 1004

        systemLoad        TRAP-TYPE
                ENTERPRISE appliance
                VARIABLES {
                        loadName,
                        loadErrorMessage }
                DESCRIPTION
                        " Websense Alert: heavy system load"
                ::= 1005

        systemLoadClear        TRAP-TYPE
                ENTERPRISE errorClear
                VARIABLES {
                        loadName,
                        loadErrorMessage }
                DESCRIPTION
                        " Websense Alert: 'heavy system load' is cleared"
                ::= 1005

        logFileMaxSizeExceed        TRAP-TYPE
                ENTERPRISE appliance
                VARIABLES {
                        fileName,
                        fileErrorMsg }
                DESCRIPTION
                        " Websense Alert: too large log file size"
                ::= 1006

        logFileMaxSizeExceedClear        TRAP-TYPE
                ENTERPRISE errorClear
                VARIABLES {
                        fileName,
                        fileErrorMsg }
                DESCRIPTION
                        " Websense Alert: 'too large log file size' is cleared"
                ::= 1006

        logCacheMinFreeExceed        TRAP-TYPE
                ENTERPRISE appliance
                VARIABLES { wsAlertMessage }
                DESCRIPTION
                        " Websense Alert: low free log cache space"
                ::= 1007

        logCacheMinFreeExceedClear        TRAP-TYPE
                ENTERPRISE errorClear
                VARIABLES { wsAlertMessage }
                DESCRIPTION
                        " Websense Alert: 'low free log cache space' is cleared"
                ::= 1007

        moduleDown        TRAP-TYPE
                ENTERPRISE appliance
                VARIABLES { vmName
                          }
                DESCRIPTION
                        " Websense Alert: appliance module down"
                ::= 1050

        moduleDownClear        TRAP-TYPE
                ENTERPRISE errorClear
                VARIABLES { vmName
                          }
                DESCRIPTION
                        " Websense Alert: 'appliance module down' is cleared"
                ::= 1050

        serviceDown        TRAP-TYPE
                ENTERPRISE appliance
                VARIABLES { svcStatus, 
                        svcName
                        }
                DESCRIPTION
                        " Websense Alert: appliance service down"
                ::= 1051

        serviceDownClear        TRAP-TYPE
                ENTERPRISE errorClear
                VARIABLES { svcStatus, 
                        svcName
                        }
                DESCRIPTION
                        " Websense Alert: 'appliance service down' is cleared"
                ::= 1051

        backupFailure        TRAP-TYPE
                ENTERPRISE appliance
                VARIABLES { 
                        wsAlertMessage
                        }
                DESCRIPTION
                        " Websense Alert: appliance backup failure"
                ::= 1052

        logServerConnectionLost        TRAP-TYPE
                ENTERPRISE appliance
                VARIABLES { 
                        wsAlertMessage
                        }
                DESCRIPTION
                        " Websense Alert: log server connection lost"
                ::= 1053

        logServerConnectionLostClear        TRAP-TYPE
                ENTERPRISE errorClear
                VARIABLES { 
                        wsAlertMessage
                        }
                DESCRIPTION
                        " Websense Alert: 'log server connection lost' is cleared"
                ::= 1053

        hostnameChange        TRAP-TYPE
                ENTERPRISE appliance
                VARIABLES { prevHostname,
                        currHostname }
                DESCRIPTION
                        " Websense Alert: appliance hostname changed"
                ::= 1061

        ipAddressChange        TRAP-TYPE
                ENTERPRISE appliance
                VARIABLES { ifaName,
                        ifaPrevAddress,
                        ifaCurrAddress,
                        ifaPrevAddressv6,
                        ifaCurrAddressv6 }
                DESCRIPTION
                        " Websense Alert: appliance IP address changed"
                ::= 1062

        -----------------------------------------------------------------------
        -- Hardware Monitoring
        -----------------------------------------------------------------------
        powerSupply        TRAP-TYPE
                ENTERPRISE appliance
                VARIABLES { evtTimestamp,
                        evtDir,
                        evtSensor,
                        evtDesc }
                DESCRIPTION
                " Websense Alert: appliance power supply warning"
                ::= 2001

        powerSupplyClear        TRAP-TYPE
                ENTERPRISE errorClear
                VARIABLES { evtTimestamp,
                        evtDir,
                        evtSensor,
                        evtDesc }
                DESCRIPTION
                " Websense Alert: 'appliance power supply warning' is cleared"
                ::= 2001

        redundancy        TRAP-TYPE
                ENTERPRISE appliance
                VARIABLES { evtTimestamp,
                        evtDir,
                        evtSensor,
                        evtDesc }
                DESCRIPTION
                        " Websense Alert: appliance redundancy warning"
                ::= 2002

        redundancyClear       TRAP-TYPE
                ENTERPRISE errorClear
                VARIABLES { evtTimestamp,
                        evtDir,
                        evtSensor,
                        evtDesc }
                DESCRIPTION
                        " Websense Alert: 'appliance redundancy warning' is cleared"
                ::= 2002

        temps        TRAP-TYPE
                ENTERPRISE appliance
                VARIABLES  { evtTimestamp,
                        evtDir,
                        evtSensor,
                        evtDesc,
                        triggerReading,
                        triggerThreshold }        
                DESCRIPTION
                        " Websense Alert: appliance temperatures warning"
                ::= 2003

        tempsClear        TRAP-TYPE
                ENTERPRISE errorClear
                VARIABLES  { evtTimestamp,
                        evtDir,
                        evtSensor,
                        evtDesc,
                        triggerReading,
                        triggerThreshold }        
                DESCRIPTION
                        " Websense Alert: 'appliance temperatures warning' is cleared"
                ::= 2003

        fans        TRAP-TYPE
                ENTERPRISE appliance
                VARIABLES  { evtTimestamp,
                        evtDir,
                        evtSensor,
                        evtDesc,      
                        triggerReading,
                        triggerThreshold }        
                DESCRIPTION
                        " Websense Alert: appliance fans warning"
                ::= 2004

        fansClear        TRAP-TYPE
                ENTERPRISE errorClear
                VARIABLES  { evtTimestamp,
                        evtDir,
                        evtSensor,
                        evtDesc,      
                        triggerReading,
                        triggerThreshold }        
                DESCRIPTION
                        " Websense Alert: 'appliance fans warning' is cleared"
                ::= 2004

        volt        TRAP-TYPE
                ENTERPRISE appliance
                VARIABLES  { evtTimestamp,
                        evtDir,
                        evtSensor,
                        evtDesc,     
                        triggerReading,
                        triggerThreshold }        
                DESCRIPTION
                        " Websense Alert: appliance voltages warning"
                ::= 2005

        voltClear        TRAP-TYPE
                ENTERPRISE errorClear
                VARIABLES  { evtTimestamp,
                        evtDir,
                        evtSensor,
                        evtDesc,     
                        triggerReading,
                        triggerThreshold }        
                DESCRIPTION
                        " Websense Alert: 'appliance voltages warning' is cleared"
                ::= 2005

        logs        TRAP-TYPE
                ENTERPRISE appliance
                VARIABLES  { evtTimestamp,
                        evtDir,
                        evtSensor,
                        evtDesc }        
                DESCRIPTION
                        " Websense Alert: appliance logs warning"
                ::= 2006

        logsClear        TRAP-TYPE
                ENTERPRISE errorClear
                VARIABLES  { evtTimestamp,
                        evtDir,
                        evtSensor,
                        evtDesc }        
                DESCRIPTION
                        " Websense Alert: 'appliance logs warning' is cleared"
                ::= 2006

        mem        TRAP-TYPE
                ENTERPRISE appliance
                VARIABLES  { evtTimestamp,
                        evtDir,
                        evtSensor,
                        evtDesc }        
                DESCRIPTION
                        " Websense Alert: appliance memory warning"
                ::= 2007

        memClear        TRAP-TYPE
                ENTERPRISE errorClear
                VARIABLES  { evtTimestamp,
                        evtDir,
                        evtSensor,
                        evtDesc }        
                DESCRIPTION
                        " Websense Alert: 'appliance memory warning' is cleared"
                ::= 2007

        intrusion        TRAP-TYPE
                ENTERPRISE appliance
                VARIABLES  { evtTimestamp,
                        evtDir,
                        evtSensor,
                        evtDesc }        
                DESCRIPTION
                        " Websense Alert: appliance chassis intrusion detected"
                ::= 2008

        intrusionClear        TRAP-TYPE
                ENTERPRISE errorClear
                VARIABLES  { evtTimestamp,
                        evtDir,
                        evtSensor,
                        evtDesc }        
                DESCRIPTION
                        " Websense Alert: 'appliance chassis intrusion detected' is cleared"
                ::= 2008

        battery        TRAP-TYPE
                ENTERPRISE appliance
                VARIABLES  { evtTimestamp,
                        evtDir,
                        evtSensor,
                        evtDesc }        
                DESCRIPTION
                        " Websense Alert: appliance battery warning"
                ::= 2009

        batteryClear       TRAP-TYPE
                ENTERPRISE errorClear
                VARIABLES  { evtTimestamp,
                        evtDir,
                        evtSensor,
                        evtDesc }        
                DESCRIPTION
                        " Websense Alert: 'appliance battery warning' is cleared"
                ::= 2009

        raid        TRAP-TYPE
                ENTERPRISE appliance
                VARIABLES  { dskPhysicalNr,
                        dskCriticalNr,
                        dskFailedNr,
                        dskPhysErrMsg,
                        dskVirtualNr,
                        dskDegradedNr,
                        dskOfflineNr }        
                DESCRIPTION
                        " Websense Alert: appliance RAID controller warning"
                ::= 2010

        raidClear        TRAP-TYPE
                ENTERPRISE errorClear
                VARIABLES  { dskPhysicalNr,
                        dskCriticalNr,
                        dskFailedNr,
                        dskPhysErrMsg,
                        dskVirtualNr,
                        dskDegradedNr,
                        dskOfflineNr }        
                DESCRIPTION
                        " Websense Alert: 'appliance RAID controller warning' is cleared"
                ::= 2010


END
