WebGraph-Thermo-Hygrometer-US-MIB DEFINITIONS ::= BEGIN
----------------------------------------------------------------
-- Revison: 1.27
----------------------------------------------------------------
-- 17.04.2008 	wtWebGraphThermHygroHTML corrected
--              wtWebGraphThermHygroDiag added
--	
----------------------------------------------------------------
-- Revison: 1.26
----------------------------------------------------------------
-- 03.08.2006 	wtWebGraphThermHygroSensorNo corrected
--	
----------------------------------------------------------------
-- Revison: 1.25
----------------------------------------------------------------
-- 28.06.2006 	New: Community String Trap
--		
----------------------------------------------------------------
-- Revison: 1.24
----------------------------------------------------------------
-- 26.07.2005 	#57606, WebGraph Thermo-Hygrometer
--		CRON timer function
----------------------------------------------------------------
-- Revison: 1.23
----------------------------------------------------------------
-- 14.07.2005 	#57606, WebGraph Thermo-Hygrometer
--		FTP functions
----------------------------------------------------------------
-- Revison: 1.22
----------------------------------------------------------------
-- 17.05.2005 	#57606, WebGraph Thermo-Hygrometer
--		Trap NMS annotations
----------------------------------------------------------------
-- Revison: 1.21
----------------------------------------------------------------
-- 19.04.2005 	#57606, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                			OBJECT IDENTIFIER ::= { enterprises 5040 }
    wtComServer        			OBJECT IDENTIFIER ::= { wut 1 }
    wtWebio            			OBJECT IDENTIFIER ::= { wtComServer 2 }

--  wtWebGraph Tree

    wtWebGraphThermHygro  		OBJECT IDENTIFIER ::= { wtWebio 9 }
    
--  wtWebGraphThermHygro Tree

    wtWebGraphThermHygroTemp      	OBJECT IDENTIFIER ::= { wtWebGraphThermHygro 1 }
    wtWebGraphThermHygroSessCntrl 	OBJECT IDENTIFIER ::= { wtWebGraphThermHygro 2 }
    wtWebGraphThermHygroConfig    	OBJECT IDENTIFIER ::= { wtWebGraphThermHygro 3 }
    wtWebGraphThermHygroDiag    	OBJECT IDENTIFIER ::= { wtWebGraphThermHygro 4 }
    
--  wtWebGraphThermHygroConfig Tree

    wtWebGraphThermHygroDevice    	OBJECT IDENTIFIER ::= { wtWebGraphThermHygroConfig 1 }
    wtWebGraphThermHygroPorts     	OBJECT IDENTIFIER ::= { wtWebGraphThermHygroConfig 2 }	
    wtWebGraphThermHygroManufact  	OBJECT IDENTIFIER ::= { wtWebGraphThermHygroConfig 3 }	

--  wtWebGraphThermHygroDevice Tree

    wtWebGraphThermHygroText		OBJECT IDENTIFIER ::= { wtWebGraphThermHygroDevice 1 }	
    wtWebGraphThermHygroTimeDate 	OBJECT IDENTIFIER ::= { wtWebGraphThermHygroDevice 2 }
    wtWebGraphThermHygroBasic		OBJECT IDENTIFIER ::= { wtWebGraphThermHygroDevice 3 }	
    wtWebGraphThermHygroDatalogger	OBJECT IDENTIFIER ::= { wtWebGraphThermHygroDevice 4 }	
    wtWebGraphThermHygroAlarm		OBJECT IDENTIFIER ::= { wtWebGraphThermHygroDevice 5 }
    
--  wtWebGraphThermHygroTimeDate Tree

    wtWebGraphThermHygroTimeZone	OBJECT IDENTIFIER ::= { wtWebGraphThermHygroTimeDate 1 }
    wtWebGraphThermHygroTimeServer	OBJECT IDENTIFIER ::= { wtWebGraphThermHygroTimeDate 2 }	
    wtWebGraphThermHygroDeviceClock	OBJECT IDENTIFIER ::= { wtWebGraphThermHygroTimeDate 3 }

--  wtWebGraphThermHygroBasic Tree
    
    wtWebGraphThermHygroNetwork		OBJECT IDENTIFIER ::= { wtWebGraphThermHygroBasic 1 }
    wtWebGraphThermHygroHTTP		OBJECT IDENTIFIER ::= { wtWebGraphThermHygroBasic 2 }
    wtWebGraphThermHygroMail		OBJECT IDENTIFIER ::= { wtWebGraphThermHygroBasic 3 }	
    wtWebGraphThermHygroSNMP		OBJECT IDENTIFIER ::= { wtWebGraphThermHygroBasic 4 }
    wtWebGraphThermHygroUDP		OBJECT IDENTIFIER ::= { wtWebGraphThermHygroBasic 5 }
    wtWebGraphThermHygroSyslog		OBJECT IDENTIFIER ::= { wtWebGraphThermHygroBasic 6 }    
    wtWebGraphThermHygroFTP		OBJECT IDENTIFIER ::= { wtWebGraphThermHygroBasic 7 }
    
       
-- wtWebGraphThermHygroTemp Group
------------------------

wtWebGraphThermHygroSensors OBJECT-TYPE
    SYNTAX INTEGER (1..2)
    ACCESS read-only
    STATUS mandatory
    DESCRIPTION
        "Number of sensors"
    ::= { wtWebGraphThermHygroTemp 1 }

-- Interface Table

wtWebGraphThermHygroSensorTable OBJECT-TYPE
    SYNTAX SEQUENCE OF WtWebGraphThermHygroSensorEntry
    ACCESS not-accessible
    STATUS mandatory
    DESCRIPTION
        "List of sensors."
    ::= { wtWebGraphThermHygroTemp 2 }

wtWebGraphThermHygroSensorEntry OBJECT-TYPE
    SYNTAX WtWebGraphThermHygroSensorEntry
    ACCESS not-accessible
    STATUS mandatory
    DESCRIPTION
        "List of sensor numbers."
    INDEX  { wtWebGraphThermHygroSensorNo }
    ::= { wtWebGraphThermHygroSensorTable 1 }

WtWebGraphThermHygroSensorEntry ::= SEQUENCE {
    wtWebGraphThermHygroSensorNo INTEGER
}

wtWebGraphThermHygroSensorNo OBJECT-TYPE
    SYNTAX INTEGER (1..2)
    ACCESS read-only
    STATUS mandatory
    DESCRIPTION
        "Sensor number."
    ::= { wtWebGraphThermHygroSensorEntry 1 }


-- wtWebGraphThermHygroTempValue Table

wtWebGraphThermHygroTempValueTable OBJECT-TYPE
    SYNTAX SEQUENCE OF WtWebGraphThermHygroTempValueEntry
    ACCESS not-accessible
    STATUS mandatory
    DESCRIPTION
        "List of measurement values corresponding to the channel numbers."
    ::= { wtWebGraphThermHygroTemp 3 }

wtWebGraphThermHygroTempValueEntry OBJECT-TYPE
    SYNTAX WtWebGraphThermHygroTempValueEntry
    ACCESS not-accessible
    STATUS mandatory
    DESCRIPTION
        "Measurement values of the sensors."
    INDEX  { wtWebGraphThermHygroSensorNo }
    ::= { wtWebGraphThermHygroTempValueTable 1 }

WtWebGraphThermHygroTempValueEntry ::= SEQUENCE{
    wtWebGraphThermHygroTempValue OCTET STRING
}

wtWebGraphThermHygroTempValue OBJECT-TYPE
    SYNTAX OCTET STRING (SIZE (5))
    ACCESS read-only
    STATUS mandatory
    DESCRIPTION
        "Measurement value of the sensor, ASCII, 5 characters in length."
    ::= { wtWebGraphThermHygroTempValueEntry 1 }

-- wtWebGraphThermHygroBinaryTempValue Table

wtWebGraphThermHygroBinaryTempValueTable OBJECT-TYPE
    SYNTAX SEQUENCE OF WtWebGraphThermHygroBinaryTempValueEntry
    ACCESS not-accessible
    STATUS mandatory
    DESCRIPTION
        "List of binary measurement values corresponding to the channel numbers."
    ::= { wtWebGraphThermHygroTemp 4 }

wtWebGraphThermHygroBinaryTempValueEntry OBJECT-TYPE
    SYNTAX WtWebGraphThermHygroBinaryTempValueEntry
    ACCESS not-accessible
    STATUS mandatory
    DESCRIPTION
        "Binary measurement values of the sensors."
    INDEX  { wtWebGraphThermHygroSensorNo }
    ::= { wtWebGraphThermHygroBinaryTempValueTable 1 }

WtWebGraphThermHygroBinaryTempValueEntry ::= SEQUENCE{
    wtWebGraphThermHygroBinaryTempValue INTEGER
}    

wtWebGraphThermHygroBinaryTempValue OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphThermHygroBinaryTempValueEntry 1 }

-- wtWebGraphThermHygroSessCntrl Group
--------------------------------

wtWebGraphThermHygroSessCntrlPassword OBJECT-TYPE
    SYNTAX OCTET STRING 
    ACCESS read-write
    STATUS mandatory
    DESCRIPTION
        "Entering this password opens a session which is ended by writing a 1 to 
        wtWebGraphThermHygroSessCntrlLogout. When read this variable provides a string of
        length zero."
    ::= { wtWebGraphThermHygroSessCntrl 1 }

wtWebGraphThermHygroSessCntrlConfigMode OBJECT-TYPE
    SYNTAX INTEGER {
    wtWebGraphThermHygroSessCntrl-NoSession(0),
    wtWebGraphThermHygroSessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphThermHygroSessCntrl 2 }

wtWebGraphThermHygroSessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphThermHygroSessCntrl 3 }

wtWebGraphThermHygroSessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphThermHygroSessCntrl 4 }

wtWebGraphThermHygroSessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphThermHygroSessCntrl 5 }
    

-- wtWebGraphThermHygroText Group
------------------------

wtWebGraphThermHygroDeviceName OBJECT-TYPE
    SYNTAX OCTET STRING 
    ACCESS read-write
    STATUS mandatory
    DESCRIPTION
        "Name of the Webio, which is user definable."
    ::= { wtWebGraphThermHygroText 1 }

wtWebGraphThermHygroDeviceText OBJECT-TYPE
    SYNTAX OCTET STRING 
    ACCESS read-write
    STATUS mandatory
    DESCRIPTION
        "Description of the Webio, which is user definable."
    ::= { wtWebGraphThermHygroText 2 }

wtWebGraphThermHygroDeviceLocation OBJECT-TYPE
    SYNTAX OCTET STRING 
    ACCESS read-write
    STATUS mandatory
    DESCRIPTION
        "Description of the location of the Webio, which is user definable."
    ::= { wtWebGraphThermHygroText 3 }

wtWebGraphThermHygroDeviceContact OBJECT-TYPE
    SYNTAX OCTET STRING 
    ACCESS read-write
    STATUS mandatory
    DESCRIPTION
        "Contact address of the system operator of the Webio, which is user definable."
    ::= { wtWebGraphThermHygroText 4 }

-- wtWebGraphThermHygroTimeZone Group
----------------------------

wtWebGraphThermHygroTzOffsetHrs OBJECT-TYPE
    SYNTAX INTEGER 
    ACCESS read-write
    STATUS mandatory
    DESCRIPTION
        "Offset hours for the time zone (winter time) with respect to UTC."
    ::= { wtWebGraphThermHygroTimeZone 1 }

wtWebGraphThermHygroTzOffsetMin OBJECT-TYPE
    SYNTAX INTEGER 
    ACCESS read-write
    STATUS mandatory
    DESCRIPTION
        "Offset minutes for the time zone (winter time) with respect to UTC."
    ::= { wtWebGraphThermHygroTimeZone 2 }

wtWebGraphThermHygroTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphThermHygroTimeZone 3 }    
    
wtWebGraphThermHygroStTzOffsetHrs OBJECT-TYPE
    SYNTAX INTEGER 
    ACCESS read-write
    STATUS mandatory
    DESCRIPTION
        "Offset hours of the time zone (summer time) with respect to UTC."
    ::= { wtWebGraphThermHygroTimeZone 4 }

wtWebGraphThermHygroStTzOffsetMin OBJECT-TYPE
    SYNTAX INTEGER 
    ACCESS read-write
    STATUS mandatory
    DESCRIPTION
        "Offset minutes of the time zone (summer time) with respect to UTC."
    ::= { wtWebGraphThermHygroTimeZone 5 }
    
wtWebGraphThermHygroStTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphThermHygroTimeZone 6 }       
    
wtWebGraphThermHygroStTzStartMonth OBJECT-TYPE
    SYNTAX INTEGER {
    	wtWebGraphThermHygroStartMonth-January(1),
    	wtWebGraphThermHygroStartMonth-February(2),
    	wtWebGraphThermHygroStartMonth-March(3),
    	wtWebGraphThermHygroStartMonth-April(4),
    	wtWebGraphThermHygroStartMonth-May(5),
    	wtWebGraphThermHygroStartMonth-June(6),
    	wtWebGraphThermHygroStartMonth-July(7),
    	wtWebGraphThermHygroStartMonth-August(8),
    	wtWebGraphThermHygroStartMonth-September(9),
    	wtWebGraphThermHygroStartMonth-October(10),
    	wtWebGraphThermHygroStartMonth-November(11),
    	wtWebGraphThermHygroStartMonth-December(12)
    	}
    	
    ACCESS read-write
    STATUS mandatory
    DESCRIPTION
        "Month in which the change is made from winter time to summer time."
    ::= { wtWebGraphThermHygroTimeZone 7 }

wtWebGraphThermHygroStTzStartMode OBJECT-TYPE
    SYNTAX INTEGER {
    	wtWebGraphThermHygroStartMode-first(1),
    	wtWebGraphThermHygroStartMode-second(2),
    	wtWebGraphThermHygroStartMode-third(3),
    	wtWebGraphThermHygroStartMode-fourth(4),
    	wtWebGraphThermHygroStartMode-last(5)
    	}
    	
    ACCESS read-write
    STATUS mandatory
    DESCRIPTION
        "Mode of the day of the week for which the change is made from winter time to summer time."
    ::= { wtWebGraphThermHygroTimeZone 8 }

wtWebGraphThermHygroStTzStartWday OBJECT-TYPE
    SYNTAX INTEGER {
    	wtWebGraphThermHygroStartWday-Sunday(1),
    	wtWebGraphThermHygroStartWday-Monday(2),
    	wtWebGraphThermHygroStartWday-Tuesday(3),
    	wtWebGraphThermHygroStartWday-Thursday(4),
    	wtWebGraphThermHygroStartWday-Wednesday(5),
    	wtWebGraphThermHygroStartWday-Friday(6),
    	wtWebGraphThermHygroStartWday-Saturday(7)
    	}
    	
    ACCESS read-write
    STATUS mandatory
    DESCRIPTION
        "Day of the week on which the change is made from winter time to summer time"
    ::= { wtWebGraphThermHygroTimeZone 9 }
    
wtWebGraphThermHygroStTzStartHrs OBJECT-TYPE
    SYNTAX INTEGER 
    ACCESS read-write
    STATUS mandatory
    DESCRIPTION
        "Hour in which the time zone is changed from winter to summer time with
        respect to UTC."
    ::= { wtWebGraphThermHygroTimeZone 10 }

wtWebGraphThermHygroStTzStartMin OBJECT-TYPE
    SYNTAX INTEGER 
    ACCESS read-write
    STATUS mandatory
    DESCRIPTION
        "Minute in which the time zone is changed from winter to summer time with
        respect to UTC."
    ::= { wtWebGraphThermHygroTimeZone 11 }
 
wtWebGraphThermHygroStTzStopMonth OBJECT-TYPE
    SYNTAX INTEGER {
    	wtWebGraphThermHygroStopMonth-January(1),
    	wtWebGraphThermHygroStopMonth-February(2),
    	wtWebGraphThermHygroStopMonth-March(3),
    	wtWebGraphThermHygroStopMonth-April(4),
    	wtWebGraphThermHygroStopMonth-May(5),
    	wtWebGraphThermHygroStopMonth-June(6),
    	wtWebGraphThermHygroStopMonth-July(7),
    	wtWebGraphThermHygroStopMonth-August(8),
    	wtWebGraphThermHygroStopMonth-September(9),
    	wtWebGraphThermHygroStopMonth-October(10),
    	wtWebGraphThermHygroStopMonth-November(11),
    	wtWebGraphThermHygroStopMonth-December(12)
    	}
    ACCESS read-write
    STATUS mandatory
    DESCRIPTION
        "Month in which the change is made from summer time to winter time."
   ::= { wtWebGraphThermHygroTimeZone 12 }

wtWebGraphThermHygroStTzStopMode OBJECT-TYPE
    SYNTAX INTEGER {
    	wtWebGraphThermHygroStopMode-first(1),
    	wtWebGraphThermHygroStopMode-second(2),
    	wtWebGraphThermHygroStopMode-third(3),
    	wtWebGraphThermHygroStopMode-fourth(4),
    	wtWebGraphThermHygroStopMode-last(5)
    	}
    ACCESS read-write
    STATUS mandatory
    DESCRIPTION
        "Mode of the week day on which the change is made from summer time to winter time."
    ::= { wtWebGraphThermHygroTimeZone 13 }

wtWebGraphThermHygroStTzStopWday OBJECT-TYPE
    SYNTAX INTEGER {
    	wtWebGraphThermHygroStopWday-Sunday(1),
    	wtWebGraphThermHygroStopWday-Monday(2),
    	wtWebGraphThermHygroStopWday-Tuesday(3),
    	wtWebGraphThermHygroStopWday-Thursday(4),
    	wtWebGraphThermHygroStopWday-Wednesday(5),
    	wtWebGraphThermHygroStopWday-Friday(6),
    	wtWebGraphThermHygroStopWday-Saturday(7)
    	}
    ACCESS read-write
    STATUS mandatory
    DESCRIPTION
        "Day of the week on which the change is made from summer time to winter time."
    ::= { wtWebGraphThermHygroTimeZone 14 }
    
wtWebGraphThermHygroStTzStopHrs OBJECT-TYPE
    SYNTAX INTEGER 
    ACCESS read-write
    STATUS mandatory
    DESCRIPTION
        "Hour at which the time zone is changed from summer to winter time with
        respect to UTC."
    ::= { wtWebGraphThermHygroTimeZone 15 }

wtWebGraphThermHygroStTzStopMin OBJECT-TYPE
    SYNTAX INTEGER 
    ACCESS read-write
    STATUS mandatory
    DESCRIPTION
        "Minute at which the time zone is changed from summer to winter time with
        respect to UTC."
    ::= { wtWebGraphThermHygroTimeZone 16 }

-- wtWebGraphThermHygroTimeServer Group
----------------------------

wtWebGraphThermHygroTimeServer1 OBJECT-TYPE
    SYNTAX OCTET STRING 
    ACCESS read-write
    STATUS mandatory
    DESCRIPTION
        "IP address or name of the 1st time server in ASCII"
    ::= { wtWebGraphThermHygroTimeServer 1 }

wtWebGraphThermHygroTimeServer2 OBJECT-TYPE
    SYNTAX OCTET STRING 
    ACCESS read-write
    STATUS mandatory
    DESCRIPTION
        "IP address or name of the 2nd time server in ASCII"
    ::= { wtWebGraphThermHygroTimeServer 2 }
    
wtWebGraphThermHygroTsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphThermHygroTimeServer 3 }
    
wtWebGraphThermHygroTsSyncTime OBJECT-TYPE
    SYNTAX INTEGER 
    ACCESS read-write
    STATUS mandatory
    DESCRIPTION
        "Daily synchronisation time with the time server (hour: 0-23)."
    ::= { wtWebGraphThermHygroTimeServer 4 } 
    
-- wtWebGraphThermHygroDeviceClock Group
----------------------------

wtWebGraphThermHygroClockHrs OBJECT-TYPE
    SYNTAX INTEGER (0..23)
    ACCESS read-write
    STATUS mandatory
    DESCRIPTION
        "Clock hours taking into account the time zone settings."
    ::= { wtWebGraphThermHygroDeviceClock 1 }

wtWebGraphThermHygroClockMin OBJECT-TYPE
    SYNTAX INTEGER (0..59)
    ACCESS read-write
    STATUS mandatory
    DESCRIPTION
        "Clock minutes taking into account the time zone settings."
    ::= { wtWebGraphThermHygroDeviceClock 2 }

wtWebGraphThermHygroClockDay OBJECT-TYPE
    SYNTAX INTEGER (1..31)
    ACCESS read-write
    STATUS mandatory
    DESCRIPTION
        "Date: Day of the month, taking into account the time zone settings."
    ::= { wtWebGraphThermHygroDeviceClock 3 }

wtWebGraphThermHygroClockMonth OBJECT-TYPE
   SYNTAX INTEGER {
    	wtWebGraphThermHygroClockMonth-January(1),
    	wtWebGraphThermHygroClockMonth-February(2),
    	wtWebGraphThermHygroClockMonth-March(3),
    	wtWebGraphThermHygroClockMonth-April(4),
    	wtWebGraphThermHygroClockMonth-May(5),
    	wtWebGraphThermHygroClockMonth-June(6),
    	wtWebGraphThermHygroClockMonth-July(7),
    	wtWebGraphThermHygroClockMonth-August(8),
    	wtWebGraphThermHygroClockMonth-September(9),
    	wtWebGraphThermHygroClockMonth-October(10),
    	wtWebGraphThermHygroClockMonth-November(11),
    	wtWebGraphThermHygroClockMonth-December(12)
    	}
    ACCESS read-write
    STATUS mandatory
    DESCRIPTION
        "Date: Month, taking into account the time zone settings."
    ::= { wtWebGraphThermHygroDeviceClock 4 }

wtWebGraphThermHygroClockYear OBJECT-TYPE
    SYNTAX INTEGER (0..65535)
    ACCESS read-write
    STATUS mandatory
    DESCRIPTION
        "Date: Year, taking into account the time zone settings."
    ::= { wtWebGraphThermHygroDeviceClock 5 }
    

-- wtWebGraphThermHygroNetwork Group
------------------------

wtWebGraphThermHygroIpAddress OBJECT-TYPE
    SYNTAX IpAddress
    ACCESS read-write
    STATUS mandatory
    DESCRIPTION
        "IP address of the Webio"
    ::= { wtWebGraphThermHygroNetwork 1 }

wtWebGraphThermHygroSubnetMask OBJECT-TYPE
    SYNTAX IpAddress
    ACCESS read-write
    STATUS mandatory
    DESCRIPTION
        "Subnet mask of the Webio"
    ::= { wtWebGraphThermHygroNetwork 2 }

wtWebGraphThermHygroGateway OBJECT-TYPE
    SYNTAX IpAddress
    ACCESS read-write
    STATUS mandatory
    DESCRIPTION
        "Gateway of the Webio"
    ::= { wtWebGraphThermHygroNetwork 3 }

wtWebGraphThermHygroDnsServer1 OBJECT-TYPE
    SYNTAX OCTET STRING 
    ACCESS read-write
    STATUS mandatory
    DESCRIPTION
        "IP address of the 1st DNS server in ASCII"
    ::= { wtWebGraphThermHygroNetwork 4 }

wtWebGraphThermHygroDnsServer2 OBJECT-TYPE
    SYNTAX OCTET STRING 
    ACCESS read-write
    STATUS mandatory
    DESCRIPTION
        "IP address of the 2nd DNS server in ASCII"
    ::= { wtWebGraphThermHygroNetwork 5 }

wtWebGraphThermHygroAddConfig OBJECT-TYPE
    SYNTAX OCTET STRING 
    ACCESS read-write
    STATUS mandatory
    DESCRIPTION
        "Additional configuration (1=ON):
        Octet 1: unused
        Octet 2: unused
        Octet 3: unused
        Octet 4:
	        Bit 0: BOOTP disable
	        "
    ::= { wtWebGraphThermHygroNetwork 6 }

--  wtWebGraphThermHygroHTTP Group
--------------------------------

wtWebGraphThermHygroStartup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphThermHygroHTTP 1 }

wtWebGraphThermHygroGetHeaderEnable OBJECT-TYPE
    SYNTAX OCTET STRING 
    ACCESS read-write
    STATUS mandatory
    DESCRIPTION
        "If this bit is set, every answer of a short form GET question will be lead
        by the IP-address and name of the device:
        Octet 1: unused
        Octet 2: unused
        Octet 3: unused
        Octet 4:
        	Bit 1-7: unused
                Bit 0  : GET Header enable"
    ::= { wtWebGraphThermHygroHTTP 2 }  
    
wtWebGraphThermHygroHttpPort OBJECT-TYPE
    SYNTAX INTEGER (1..65535)
    ACCESS read-write
    STATUS mandatory
    DESCRIPTION
        "Definition of the standard HTML port (Default: 80)."
    ::= { wtWebGraphThermHygroHTTP 3 }    


-- wtWebGraphThermHygroMail Group
--------------------------------

wtWebGraphThermHygroMailAdName OBJECT-TYPE
    SYNTAX OCTET STRING 
    ACCESS read-write
    STATUS mandatory
    DESCRIPTION
        "Device name for mail administration."
    ::= { wtWebGraphThermHygroMail 1 }
    
wtWebGraphThermHygroMailReply OBJECT-TYPE
    SYNTAX OCTET STRING 
    ACCESS read-write
    STATUS mandatory
    DESCRIPTION
        "Reply address for the mail server."
    ::= { wtWebGraphThermHygroMail 2 }
    
wtWebGraphThermHygroMailServer OBJECT-TYPE
    SYNTAX OCTET STRING 
    ACCESS read-write
    STATUS mandatory
    DESCRIPTION
        "Name or IP address of the mail server."
    ::= { wtWebGraphThermHygroMail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphThermHygroMail 4 }
    
wtWebGraphThermHygroMailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphThermHygroMail 5 }
    
wtWebGraphThermHygroMailAuthUser OBJECT-TYPE
    SYNTAX OCTET STRING 
    ACCESS read-write
    STATUS mandatory
    DESCRIPTION
        "Name of the user to be authenticated."
    ::= { wtWebGraphThermHygroMail 6 }    
    
wtWebGraphThermHygroMailAuthPassword OBJECT-TYPE
    SYNTAX OCTET STRING 
    ACCESS read-write
    STATUS mandatory
    DESCRIPTION
        "Authentication password."
    ::= { wtWebGraphThermHygroMail 7 }    
    
wtWebGraphThermHygroMailPop3Server OBJECT-TYPE
    SYNTAX OCTET STRING 
    ACCESS read-write
    STATUS mandatory
    DESCRIPTION
        "Name or Ip-address of the POP3 Servers."
    ::= { wtWebGraphThermHygroMail 8 }            

-- wtWebGraphThermHygroSNMP Group
--------------------------------

wtWebGraphThermHygroSnmpCommunityStringRead OBJECT-TYPE
    SYNTAX OCTET STRING
    ACCESS read-write
    STATUS mandatory
    DESCRIPTION
        "Community string read only"
    ::= { wtWebGraphThermHygroSNMP 1 }

wtWebGraphThermHygroSnmpCommunityStringReadWrite OBJECT-TYPE
    SYNTAX OCTET STRING
    ACCESS read-write
    STATUS mandatory
    DESCRIPTION
        "Community string read / write"
    ::= { wtWebGraphThermHygroSNMP 2 }

wtWebGraphThermHygroSystemTrapManagerIP OBJECT-TYPE
    SYNTAX OCTET STRING 
    ACCESS read-write
    STATUS mandatory
    DESCRIPTION
        "Name or IP address of the TCP server which accepts the system trap."
    ::= { wtWebGraphThermHygroSNMP 3 }
    
wtWebGraphThermHygroSystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphThermHygroSNMP 4 }
    
wtWebGraphThermHygroSnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphThermHygroSNMP 5 }
    
wtWebGraphThermHygroSnmpCommunityStringTrap OBJECT-TYPE
    SYNTAX OCTET STRING
    ACCESS read-write
    STATUS mandatory
    DESCRIPTION
        "Community string send within traps."
    ::= { wtWebGraphThermHygroSNMP 6 }    
            
    
-- wtWebGraphThermHygroUDP Group
--------------------------------
    
wtWebGraphThermHygroUdpPort OBJECT-TYPE
    SYNTAX INTEGER (1..65535)
    ACCESS read-write
    STATUS mandatory
    DESCRIPTION
        "Udp port to which the Udp queries ( short form GET requests) can be sent. This
        port number must be unique within the device."
    ::= { wtWebGraphThermHygroUDP 1 }
    
wtWebGraphThermHygroUdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphThermHygroUDP 2 }
    
--  wtWebGraphThermHygroSyslog Group
--------------------------------
    
wtWebGraphThermHygroSyslogServerIP OBJECT-TYPE
    SYNTAX OCTET STRING 
    ACCESS read-write
    STATUS mandatory
    DESCRIPTION
        "Name or IP address of the Syslog server, which accepts the Syslog messgaes."
    ::= { wtWebGraphThermHygroSyslog 1 }
    
wtWebGraphThermHygroSyslogServerPort OBJECT-TYPE
    SYNTAX INTEGER
    ACCESS read-write
    STATUS mandatory
    DESCRIPTION
        "Portnumber of the Syslog servers, default 514."
    ::= { wtWebGraphThermHygroSyslog 2 }

wtWebGraphThermHygroSyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphThermHygroSyslog 3 }    

wtWebGraphThermHygroSyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphThermHygroSyslog 4 }
    
--  wtWebGraphThermHygroFTP Group
--------------------------------

wtWebGraphThermHygroFTPServerIP OBJECT-TYPE
    SYNTAX OCTET STRING 
    ACCESS read-write
    STATUS mandatory
    DESCRIPTION
        "Name or IP address of the FTP server, which accepts the FTP messages."
    ::= { wtWebGraphThermHygroFTP 1 }
    
wtWebGraphThermHygroFTPServerControlPort OBJECT-TYPE
    SYNTAX INTEGER
    ACCESS read-write
    STATUS mandatory
    DESCRIPTION
        "Portnumber of the control port of the FTP server, default 21."
    ::= { wtWebGraphThermHygroFTP 2 }
    
wtWebGraphThermHygroFTPUserName OBJECT-TYPE
    SYNTAX OCTET STRING 
    ACCESS read-write
    STATUS mandatory
    DESCRIPTION
        "FTP Loggin: user name."
    ::= { wtWebGraphThermHygroFTP 3 }
    
wtWebGraphThermHygroFTPPassword OBJECT-TYPE
    SYNTAX OCTET STRING 
    ACCESS read-write
    STATUS mandatory
    DESCRIPTION
        "FTP Loggin: user password."
    ::= { wtWebGraphThermHygroFTP 4 }

wtWebGraphThermHygroFTPAccount OBJECT-TYPE
    SYNTAX OCTET STRING 
    ACCESS read-write
    STATUS mandatory
    DESCRIPTION
        "FTP Loggin: name of account."
    ::= { wtWebGraphThermHygroFTP 5 }

wtWebGraphThermHygroFTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphThermHygroFTP 6 }
    
wtWebGraphThermHygroFTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphThermHygroFTP 7 }
    
    
-- wtWebGraphThermHygroDatalogger Group
--------------------------------

wtWebGraphThermHygroLoggerTimebase OBJECT-TYPE
    SYNTAX INTEGER {
    wtWebGraphThermHygroDatalogger-1Min(1),
    wtWebGraphThermHygroDatalogger-5Min(2),
    wtWebGraphThermHygroDatalogger-15Min(3),
    wtWebGraphThermHygroDatalogger-60Min(4)
    }
    ACCESS read-write
    STATUS mandatory
    DESCRIPTION
        "Time base of the data logger"
    ::= { wtWebGraphThermHygroDatalogger 1 }

wtWebGraphThermHygroLoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphThermHygroDatalogger 2 }

wtWebGraphThermHygroDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphThermHygroDatalogger 3 }    
    
-- Graph Sensor Color Table

wtWebGraphThermHygroSensorColorTable OBJECT-TYPE
    SYNTAX SEQUENCE OF WtWebGraphThermHygroSensorColorEntry
    ACCESS not-accessible
    STATUS mandatory
    DESCRIPTION
        "List of sensor colors for the praphical presentation."
    ::= { wtWebGraphThermHygroDatalogger 4 }

wtWebGraphThermHygroSensorColorEntry OBJECT-TYPE
    SYNTAX WtWebGraphThermHygroSensorColorEntry
    ACCESS not-accessible
    STATUS mandatory
    DESCRIPTION
        "Index numbers of the sensors."
    INDEX  { wtWebGraphThermHygroSensorNo }
    ::= { wtWebGraphThermHygroSensorColorTable 1 }

WtWebGraphThermHygroSensorColorEntry ::= SEQUENCE {
    wtWebGraphThermHygroSensorColor OCTET STRING
}

wtWebGraphThermHygroSensorColor OBJECT-TYPE
    SYNTAX OCTET STRING (SIZE(3))
    ACCESS read-write
    STATUS mandatory
    DESCRIPTION
        "Color of the sensors at the praphical presention."
    ::= { wtWebGraphThermHygroSensorColorEntry 1 }
    
wtWebGraphThermHygroAutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphThermHygroDatalogger 5 }
    
wtWebGraphThermHygroVerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphThermHygroDatalogger 6 }

wtWebGraphThermHygroVerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphThermHygroDatalogger 7 }
    
wtWebGraphThermHygroHorizontalZoom OBJECT-TYPE
    SYNTAX INTEGER {
    wtWebGraphThermHygroZoom-25min(1),
    wtWebGraphThermHygroZoom-75min(2),
    wtWebGraphThermHygroZoom-5hrs(3),
    wtWebGraphThermHygroZoom-30hrs(4),
    wtWebGraphThermHygroZoom-5days(5),
    wtWebGraphThermHygroZoom-25days(6)
    }
    ACCESS read-write
    STATUS mandatory
    DESCRIPTION
        "Defines the default zoom stage, if no auto scaling is selected."
    ::= { wtWebGraphThermHygroDatalogger 8 }    

-- wtWebGraphThermHygroAlarm Group
----------------------------

wtWebGraphThermHygroAlarmCount OBJECT-TYPE
    SYNTAX INTEGER (1..8)
    ACCESS read-only
    STATUS mandatory
    DESCRIPTION
        "Number of independent alarms."
    ::= { wtWebGraphThermHygroAlarm 1 }
    
-- Alarm Interface Table

wtWebGraphThermHygroAlarmIfTable OBJECT-TYPE
    SYNTAX SEQUENCE OF WtWebGraphThermHygroAlarmIfEntry
    ACCESS not-accessible
    STATUS mandatory
    DESCRIPTION
        "List of alarm indices."
    ::= { wtWebGraphThermHygroAlarm 2 }

wtWebGraphThermHygroAlarmIfEntry OBJECT-TYPE
    SYNTAX WtWebGraphThermHygroAlarmIfEntry
    ACCESS not-accessible
    STATUS mandatory
    DESCRIPTION
        "Numbers of the alarms."
    INDEX  { wtWebGraphThermHygroAlarmNo }
    ::= { wtWebGraphThermHygroAlarmIfTable 1 }

WtWebGraphThermHygroAlarmIfEntry ::= SEQUENCE {
    wtWebGraphThermHygroAlarmNo INTEGER
}

wtWebGraphThermHygroAlarmNo OBJECT-TYPE
    SYNTAX INTEGER (1..8)
    ACCESS read-only
    STATUS mandatory
    DESCRIPTION
        "Alarm number."
    ::= { wtWebGraphThermHygroAlarmIfEntry 1 }

-- Alarm Table

wtWebGraphThermHygroAlarmTable OBJECT-TYPE
    SYNTAX SEQUENCE OF WtWebGraphThermHygroAlarmEntry
    ACCESS not-accessible
    STATUS mandatory
    DESCRIPTION
        "List of settings depending on the alarm number."
    ::= { wtWebGraphThermHygroAlarm 3 }

wtWebGraphThermHygroAlarmEntry OBJECT-TYPE
    SYNTAX WtWebGraphThermHygroAlarmEntry
    ACCESS not-accessible
    STATUS mandatory
    DESCRIPTION
        "Alarm parameters of the individual alarms."
    INDEX  { wtWebGraphThermHygroAlarmNo }
    ::= { wtWebGraphThermHygroAlarmTable 1 }

WtWebGraphThermHygroAlarmEntry ::= SEQUENCE {
    wtWebGraphThermHygroAlarmTrigger		OCTET STRING,
    wtWebGraphThermHygroAlarmMin		OCTET STRING,
    wtWebGraphThermHygroAlarmMax		OCTET STRING,
    wtWebGraphThermHygroAlarmHysteresis		OCTET STRING,
    wtWebGraphThermHygroAlarmDelay		OCTET STRING,
    wtWebGraphThermHygroAlarmInterval		OCTET STRING,
    wtWebGraphThermHygroAlarmEnable		OCTET STRING,
    wtWebGraphThermHygroAlarmEMailAddr		OCTET STRING,
    wtWebGraphThermHygroAlarmMailSubject	OCTET STRING,
    wtWebGraphThermHygroAlarmMailText		OCTET STRING,
    wtWebGraphThermHygroAlarmManagerIP		OCTET STRING,
    wtWebGraphThermHygroAlarmTrapText		OCTET STRING,
    wtWebGraphThermHygroAlarmMailOptions	OCTET STRING,
    wtWebGraphThermHygroAlarmTcpIpAddr		OCTET STRING,
    wtWebGraphThermHygroAlarmTcpPort		INTEGER,
    wtWebGraphThermHygroAlarmTcpText		OCTET STRING,
    wtWebGraphThermHygroAlarmClearMailSubject	OCTET STRING,
    wtWebGraphThermHygroAlarmClearMailText	OCTET STRING,
    wtWebGraphThermHygroAlarmClearTrapText	OCTET STRING,
    wtWebGraphThermHygroAlarmClearTcpText	OCTET STRING,
    wtWebGraphThermHygroAlarmDeltaTemp		OCTET STRING,
    wtWebGraphThermHygroAlarmRHMin		OCTET STRING,
    wtWebGraphThermHygroAlarmRHMax		OCTET STRING,
    wtWebGraphThermHygroAlarmRHHysteresis	OCTET STRING,
    wtWebGraphThermHygroAlarmAHMin		OCTET STRING,
    wtWebGraphThermHygroAlarmAHMax		OCTET STRING,    
    wtWebGraphThermHygroAlarmSyslogIpAddr	OCTET STRING,
    wtWebGraphThermHygroAlarmSyslogPort		INTEGER,
    wtWebGraphThermHygroAlarmSyslogText		OCTET STRING,
    wtWebGraphThermHygroAlarmSyslogClearText	OCTET STRING,
    wtWebGraphThermHygroAlarmFtpDataPort	OCTET STRING,
    wtWebGraphThermHygroAlarmFtpFileName	OCTET STRING,
    wtWebGraphThermHygroAlarmFtpText		OCTET STRING,
    wtWebGraphThermHygroAlarmFtpClearText	OCTET STRING,
    wtWebGraphThermHygroAlarmFtpOption		OCTET STRING,
    wtWebGraphThermHygroAlarmTimerCron		OCTET STRING
}

wtWebGraphThermHygroAlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphThermHygroAlarmEntry 1 }

wtWebGraphThermHygroAlarmMin OBJECT-TYPE
    SYNTAX OCTET STRING 
    ACCESS read-write
    STATUS mandatory
    DESCRIPTION
        "Minimum temperature in degrees with maximum 2 decimal places."
    ::= { wtWebGraphThermHygroAlarmEntry 2 }

wtWebGraphThermHygroAlarmMax OBJECT-TYPE
    SYNTAX OCTET STRING 
    ACCESS read-write
    STATUS mandatory
    DESCRIPTION
        "Maximum temperature in degrees with maximum 2 decimal places."
    ::= { wtWebGraphThermHygroAlarmEntry 3 }
    
wtWebGraphThermHygroAlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphThermHygroAlarmEntry 4 }

wtWebGraphThermHygroAlarmDelay OBJECT-TYPE
    SYNTAX OCTET STRING 
    ACCESS read-write
    STATUS mandatory
    DESCRIPTION
        "Alarm will be delayed by setting this time while stable alarm 
        condition occur (time in minutes)."
    ::= { wtWebGraphThermHygroAlarmEntry 5 }
        

wtWebGraphThermHygroAlarmInterval OBJECT-TYPE
    SYNTAX OCTET STRING 
    ACCESS read-write
    STATUS mandatory
    DESCRIPTION
        "Send interval for alarm messages."
    ::= { wtWebGraphThermHygroAlarmEntry 6 }

wtWebGraphThermHygroAlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphThermHygroAlarmEntry 7 }

wtWebGraphThermHygroAlarmEMailAddr OBJECT-TYPE
    SYNTAX OCTET STRING 
    ACCESS read-write
    STATUS mandatory
    DESCRIPTION
        "E-Mail address for sending the alarm mail to."
    ::= { wtWebGraphThermHygroAlarmEntry 8 }

wtWebGraphThermHygroAlarmMailSubject OBJECT-TYPE
    SYNTAX OCTET STRING 
    ACCESS read-write
    STATUS mandatory
    DESCRIPTION
        "Subject line for alarm mail."
    ::= { wtWebGraphThermHygroAlarmEntry 9 }

wtWebGraphThermHygroAlarmMailText OBJECT-TYPE
    SYNTAX OCTET STRING 
    ACCESS read-write
    STATUS mandatory
    DESCRIPTION
        "Alarm mail text: <Tn> provides the current temperature; n = 1..8.
        <Z> provides the current time."
    ::= { wtWebGraphThermHygroAlarmEntry 10 }

wtWebGraphThermHygroAlarmManagerIP OBJECT-TYPE
    SYNTAX OCTET STRING 
    ACCESS read-write
    STATUS mandatory
    DESCRIPTION
        "Name or IP address of the SNMP Manager which accepts the trap."
    ::= { wtWebGraphThermHygroAlarmEntry 11 }

wtWebGraphThermHygroAlarmTrapText OBJECT-TYPE
    SYNTAX OCTET STRING 
    ACCESS read-write
    STATUS mandatory
    DESCRIPTION
        "This text is sent in the trap body."
    ::= { wtWebGraphThermHygroAlarmEntry 12 }
    
wtWebGraphThermHygroAlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphThermHygroAlarmEntry 13 }    
    
wtWebGraphThermHygroAlarmTcpIpAddr OBJECT-TYPE
    SYNTAX OCTET STRING 
    ACCESS read-write
    STATUS mandatory
    DESCRIPTION
        "Name or IP address of the TCP server which accepts the trap."
    ::= { wtWebGraphThermHygroAlarmEntry 14 }    

wtWebGraphThermHygroAlarmTcpPort OBJECT-TYPE
    SYNTAX INTEGER (1..65535) 
    ACCESS read-write
    STATUS mandatory
    DESCRIPTION
        "Port number of the TCP server which accepts the trap."
    ::= { wtWebGraphThermHygroAlarmEntry 15 }    

wtWebGraphThermHygroAlarmTcpText OBJECT-TYPE
    SYNTAX OCTET STRING 
    ACCESS read-write
    STATUS mandatory
    DESCRIPTION
        "This text is sent in the TCP trap body."
    ::= { wtWebGraphThermHygroAlarmEntry 16 }

wtWebGraphThermHygroAlarmClearMailSubject OBJECT-TYPE
    SYNTAX OCTET STRING 
    ACCESS read-write
    STATUS mandatory
    DESCRIPTION
        "Subject line for alarm clear mail."
    ::= { wtWebGraphThermHygroAlarmEntry 17 }

wtWebGraphThermHygroAlarmClearMailText OBJECT-TYPE
    SYNTAX OCTET STRING 
    ACCESS read-write
    STATUS mandatory
    DESCRIPTION
        "Alarm clear mail text: <Tn> provides the current temperature; n = 1..8.
        <Z> provides the current time."
    ::= { wtWebGraphThermHygroAlarmEntry 18 }

wtWebGraphThermHygroAlarmClearTrapText OBJECT-TYPE
    SYNTAX OCTET STRING 
    ACCESS read-write
    STATUS mandatory
    DESCRIPTION
        "This text is sent in the trap body."
    ::= { wtWebGraphThermHygroAlarmEntry 19 }

wtWebGraphThermHygroAlarmClearTcpText OBJECT-TYPE
    SYNTAX OCTET STRING 
    ACCESS read-write
    STATUS mandatory
    DESCRIPTION
        "This text is sent in the TCP trap body."
    ::= { wtWebGraphThermHygroAlarmEntry 20 }
    
wtWebGraphThermHygroAlarmDeltaTemp OBJECT-TYPE
    SYNTAX OCTET STRING 
    ACCESS read-write
    STATUS mandatory
    DESCRIPTION
        "Maximum rate of change  degrees/min with maximum 2 decimal places.
        Compared with the average of a period of 5 minutes."
    ::= { wtWebGraphThermHygroAlarmEntry 21 }

wtWebGraphThermHygroAlarmRHMin OBJECT-TYPE
    SYNTAX OCTET STRING 
    ACCESS read-write
    STATUS mandatory
    DESCRIPTION
        "Minimum rel. Humidity in percent with maximum 2 decimal places."
    ::= { wtWebGraphThermHygroAlarmEntry 22 }

wtWebGraphThermHygroAlarmRHMax OBJECT-TYPE
    SYNTAX OCTET STRING 
    ACCESS read-write
    STATUS mandatory
    DESCRIPTION
        "Maximum rel.Humidity in percent with maximum 2 decimal places."
    ::= { wtWebGraphThermHygroAlarmEntry 23 }

wtWebGraphThermHygroAlarmRHHysteresis OBJECT-TYPE
    SYNTAX OCTET STRING 
    ACCESS read-write
    STATUS mandatory
    DESCRIPTION
        "Hysterese rel. Humidity in percent with maximum 2 decimal places."
    ::= { wtWebGraphThermHygroAlarmEntry 24 }

wtWebGraphThermHygroAlarmAHMin OBJECT-TYPE
    SYNTAX OCTET STRING 
    ACCESS read-write
    STATUS mandatory
    DESCRIPTION
        "Minimum abs. Humidity in g/(m*m*m) with maximum 2 decimal places."
    ::= { wtWebGraphThermHygroAlarmEntry 25 }

wtWebGraphThermHygroAlarmAHMax OBJECT-TYPE
    SYNTAX OCTET STRING 
    ACCESS read-write
    STATUS mandatory
    DESCRIPTION
        "Maximum abs. Humidity in g/(m*m*m) with maximum 2 decimal places."
    ::= { wtWebGraphThermHygroAlarmEntry 26 }

wtWebGraphThermHygroAlarmSyslogIpAddr OBJECT-TYPE
    SYNTAX IpAddress 
    ACCESS read-write
    STATUS mandatory
    DESCRIPTION
        "IP address of the syslog server to which the Webio device should send syslog messages."
    ::= { wtWebGraphThermHygroAlarmEntry 27 }    

wtWebGraphThermHygroAlarmSyslogPort OBJECT-TYPE
    SYNTAX INTEGER (1..65535) 
    ACCESS read-write
    STATUS mandatory
    DESCRIPTION
        "Port number of the syslog server to which the Webio device should send syslog messages."
    ::= { wtWebGraphThermHygroAlarmEntry 28 }    

wtWebGraphThermHygroAlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphThermHygroAlarmEntry 29 }
    
wtWebGraphThermHygroAlarmSyslogClearText OBJECT-TYPE
    SYNTAX OCTET STRING 
    ACCESS read-write
    STATUS mandatory
    DESCRIPTION
        "Every message starts with the priority key, a time stamp and the host ip address, according RFC3164.
        This text appears in the following syslog message body."
    ::= { wtWebGraphThermHygroAlarmEntry 30 } 
    
wtWebGraphThermHygroAlarmFtpDataPort OBJECT-TYPE
    SYNTAX OCTET STRING 
    ACCESS read-write
    STATUS mandatory
    DESCRIPTION
        "Local data port: 1..65535 or AUTO: the next free port will be assigned."
    ::= { wtWebGraphThermHygroAlarmEntry 31 }
    
wtWebGraphThermHygroAlarmFtpFileName OBJECT-TYPE
    SYNTAX OCTET STRING 
    ACCESS read-write
    STATUS mandatory
    DESCRIPTION
        "Name of the file including path informations."
    ::= { wtWebGraphThermHygroAlarmEntry 32 }
    
wtWebGraphThermHygroAlarmFtpText OBJECT-TYPE
    SYNTAX OCTET STRING 
    ACCESS read-write
    STATUS mandatory
    DESCRIPTION
        "Message text to store on the FTP server."
    ::= { wtWebGraphThermHygroAlarmEntry 33 }

wtWebGraphThermHygroAlarmFtpClearText OBJECT-TYPE
    SYNTAX OCTET STRING 
    ACCESS read-write
    STATUS mandatory
    DESCRIPTION
        "Alarm clear message to store on the FTP server."
    ::= { wtWebGraphThermHygroAlarmEntry 34 }
    
wtWebGraphThermHygroAlarmFtpOptions OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphThermHygroAlarmEntry 35 }
    
wtWebGraphThermHygroAlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphThermHygroAlarmEntry 36 }      
    
    
-- wtWebGraphThermHygroPorts Group
----------------------------

-- Table

wtWebGraphThermHygroPortTable OBJECT-TYPE
    SYNTAX SEQUENCE OF WtWebGraphThermHygroPortEntry
    ACCESS not-accessible
    STATUS mandatory
    DESCRIPTION
        "List of settings depending on the sensor number."
    ::= { wtWebGraphThermHygroPorts 1 }

wtWebGraphThermHygroPortEntry OBJECT-TYPE
    SYNTAX WtWebGraphThermHygroPortEntry
    ACCESS not-accessible
    STATUS mandatory
    DESCRIPTION
        "Sensor parameters for the individual sensors."
    INDEX  { wtWebGraphThermHygroSensorNo }
    ::= { wtWebGraphThermHygroPortTable 1 }

WtWebGraphThermHygroPortEntry ::= SEQUENCE {
    wtWebGraphThermHygroPortName		OCTET STRING,
    wtWebGraphThermHygroPortText		OCTET STRING,
    wtWebGraphThermHygroPortOffset1		OCTET STRING,
    wtWebGraphThermHygroPortTemperature1	OCTET STRING,
    wtWebGraphThermHygroPortOffset2		OCTET STRING,
    wtWebGraphThermHygroPortTemperature2	OCTET STRING,
    wtWebGraphThermHygroPortComment		OCTET STRING
    
}

wtWebGraphThermHygroPortName OBJECT-TYPE
    SYNTAX OCTET STRING 
    ACCESS read-write
    STATUS mandatory
    DESCRIPTION
        "Name of the sensor."
    ::= { wtWebGraphThermHygroPortEntry 1 }

wtWebGraphThermHygroPortText OBJECT-TYPE
    SYNTAX OCTET STRING 
    ACCESS read-write
    STATUS mandatory
    DESCRIPTION
        "Description of the sensor."
    ::= { wtWebGraphThermHygroPortEntry 2 }

wtWebGraphThermHygroPortOffset1 OBJECT-TYPE
    SYNTAX OCTET STRING 
    ACCESS read-write
    STATUS mandatory
    DESCRIPTION
        "Offset calibration: Offset in degrees with maximum 2 decimal places at temperature 1."
    ::= { wtWebGraphThermHygroPortEntry 3 }

wtWebGraphThermHygroPortTemperature1 OBJECT-TYPE
    SYNTAX OCTET STRING 
    ACCESS read-write
    STATUS mandatory
    DESCRIPTION
        "Offset calibration: Reference temperature 1 in degrees with maximum 2 decimal places."
    ::= { wtWebGraphThermHygroPortEntry 4 }

wtWebGraphThermHygroPortOffset2 OBJECT-TYPE
    SYNTAX OCTET STRING 
    ACCESS read-write
    STATUS mandatory
    DESCRIPTION
        "Offset calibration: Offset in degrees with maximum 2 decimal places at temperature 2."
    ::= { wtWebGraphThermHygroPortEntry 5 }

wtWebGraphThermHygroPortTemperature2 OBJECT-TYPE
    SYNTAX OCTET STRING 
    ACCESS read-write
    STATUS mandatory
    DESCRIPTION
        "Offset calibration: Reference temperature 1 in degrees with maximum 2 decimal places."
    ::= { wtWebGraphThermHygroPortEntry 6 }

wtWebGraphThermHygroPortComment OBJECT-TYPE
    SYNTAX OCTET STRING 
    ACCESS read-write
    STATUS mandatory
    DESCRIPTION
        "Offset calibration: informations of date, name of operator, reference devices."
    ::= { wtWebGraphThermHygroPortEntry 7 }   

wtWebGraphThermHygroPortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	PT100
		Bit 1  :	PT1000 (default)
        	Bit 2-7:	unused
        
        Binary coded options for sensor 2:
	Octet 1: unused
	Octet 2: unused
	Octet 3: unused
	Octet 4:
		Bit 0  :	W&T Sensor rel. humidity (default)
		Bit 1  :	Skalar 0-2.5V
		Bit 2  :	Disconnect
        	Bit 3-7:	unused"
    ::= { wtWebGraphThermHygroPortEntry 8 }    
    
    
-- wtWebGraphThermHygroManufact Group
----------------------------

wtWebGraphThermHygroMfName OBJECT-TYPE
    SYNTAX OCTET STRING 
    ACCESS read-write
    STATUS mandatory
    DESCRIPTION
        "Manufacturer company name"
    ::= { wtWebGraphThermHygroManufact 1 }

wtWebGraphThermHygroMfAddr OBJECT-TYPE
    SYNTAX OCTET STRING 
    ACCESS read-write
    STATUS mandatory
    DESCRIPTION
        "Manufacturer address."
    ::= { wtWebGraphThermHygroManufact 2 }

wtWebGraphThermHygroMfHotline OBJECT-TYPE
    SYNTAX OCTET STRING 
    ACCESS read-write
    STATUS mandatory
    DESCRIPTION
        "Manufacturer hotline."
    ::= { wtWebGraphThermHygroManufact 3 }

wtWebGraphThermHygroMfInternet OBJECT-TYPE
    SYNTAX OCTET STRING 
    ACCESS read-write
    STATUS mandatory
    DESCRIPTION
        "Manufacturer Internet address."
    ::= { wtWebGraphThermHygroManufact 4 }

wtWebGraphThermHygroMfDeviceTyp OBJECT-TYPE
    SYNTAX OCTET STRING 
    ACCESS read-write
    STATUS mandatory
    DESCRIPTION
        "Manufacturer device name (model number)."
    ::= { wtWebGraphThermHygroManufact 5 }

wtWebGraphThermHygroMfOrderNo OBJECT-TYPE
    SYNTAX OCTET STRING 
    ACCESS read-write
    STATUS mandatory
    DESCRIPTION
        "Manufacturer part number."
    ::= { wtWebGraphThermHygroManufact 6 }

-- wtWebGraphThermHygroDiag Group
----------------------------

wtWebGraphThermHygroDiagErrorCount OBJECT-TYPE
    SYNTAX INTEGER
    ACCESS read-only
    STATUS mandatory
    DESCRIPTION
        "Number of entries in the error memory."
    ::= { wtWebGraphThermHygroDiag 1 }

wtWebGraphThermHygroDiagBinaryError OBJECT-TYPE
    SYNTAX OCTET STRING 
    ACCESS read-only
    STATUS mandatory
    DESCRIPTION
        "Error causes coded bit-by-bit."
    ::= { wtWebGraphThermHygroDiag 2 }

wtWebGraphThermHygroDiagErrorIndex OBJECT-TYPE
    SYNTAX INTEGER
    ACCESS read-write
    STATUS mandatory
    DESCRIPTION
        "The value of this variable is used as an index to read 
        an error massege from wtWebGraphThermHygroDiagErrorMessage.
        Errors are numbered from 1 to wtWebGraphThermHygroDiagErrorCount.
        Writing a valid value into this variable, making the appropriate 
        message readable from wtWebGraphThermHygroDiagErrorMessage."
    ::= { wtWebGraphThermHygroDiag 3 }

wtWebGraphThermHygroDiagErrorMessage OBJECT-TYPE
    SYNTAX OCTET STRING 
    ACCESS read-only
    STATUS mandatory
    DESCRIPTION
        "Using wtWebGraphThermHygroDiagErrorIndex as an index, the appropriate message is available."
    ::= { wtWebGraphThermHygroDiag 4 }
    
wtWebGraphThermHygroDiagErrorClear OBJECT-TYPE
    SYNTAX INTEGER
    ACCESS write-only
    STATUS mandatory
    DESCRIPTION
        "Writing 1 into this variable clears all diagnosis messages."
    ::= { wtWebGraphThermHygroDiag 5 }

-- TRAP DEFINITIONS

-- Diese SNMP-Traps werden gesendet, wenn die Alarmtriggerbedingungen zutreffen 

wtWebGraphThermHygroAlert1 TRAP-TYPE
    ENTERPRISE  wtWebGraphThermHygro
    VARIABLES   { wtWebGraphThermHygroAlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphThermHygroAlert2 TRAP-TYPE
    ENTERPRISE  wtWebGraphThermHygro
    VARIABLES   { wtWebGraphThermHygroAlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphThermHygroAlert3 TRAP-TYPE
    ENTERPRISE  wtWebGraphThermHygro
    VARIABLES   { wtWebGraphThermHygroAlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphThermHygroAlert4 TRAP-TYPE
    ENTERPRISE  wtWebGraphThermHygro
    VARIABLES   { wtWebGraphThermHygroAlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphThermHygroAlert5 TRAP-TYPE
    ENTERPRISE  wtWebGraphThermHygro
    VARIABLES   { wtWebGraphThermHygroAlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphThermHygroAlert6 TRAP-TYPE
    ENTERPRISE  wtWebGraphThermHygro
    VARIABLES   { wtWebGraphThermHygroAlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphThermHygroAlert7 TRAP-TYPE
    ENTERPRISE  wtWebGraphThermHygro
    VARIABLES   { wtWebGraphThermHygroAlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphThermHygroAlert8 TRAP-TYPE
    ENTERPRISE  wtWebGraphThermHygro
    VARIABLES   { wtWebGraphThermHygroAlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphThermHygroAlert9 TRAP-TYPE
    ENTERPRISE  wtWebGraphThermHygro
    VARIABLES   { wtWebGraphThermHygroAlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphThermHygroAlert10 TRAP-TYPE
    ENTERPRISE  wtWebGraphThermHygro
    VARIABLES   { wtWebGraphThermHygroAlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphThermHygroAlert11 TRAP-TYPE
    ENTERPRISE  wtWebGraphThermHygro
    VARIABLES   { wtWebGraphThermHygroAlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphThermHygroAlert12 TRAP-TYPE
    ENTERPRISE  wtWebGraphThermHygro
    VARIABLES   { wtWebGraphThermHygroAlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphThermHygroAlert13 TRAP-TYPE
    ENTERPRISE  wtWebGraphThermHygro
    VARIABLES   { wtWebGraphThermHygroAlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphThermHygroAlert14 TRAP-TYPE
    ENTERPRISE  wtWebGraphThermHygro
    VARIABLES   { wtWebGraphThermHygroAlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphThermHygroAlert15 TRAP-TYPE
    ENTERPRISE  wtWebGraphThermHygro
    VARIABLES   { wtWebGraphThermHygroAlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphThermHygroAlert16 TRAP-TYPE
    ENTERPRISE  wtWebGraphThermHygro
    VARIABLES   { wtWebGraphThermHygroAlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphThermHygroAlertDiag TRAP-TYPE
    ENTERPRISE  wtWebGraphThermHygro
    VARIABLES   { 	
    		wtWebGraphThermHygroDiagErrorIndex,
    	  	wtWebGraphThermHygroDiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END
