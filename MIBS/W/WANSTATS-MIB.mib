WANSTATS-MIB DEFINITIONS ::= BEGIN

-- Agilent Technologies WAN and ATM statistics MIB
--
-- Copyright (C)  1997-1999 Agilent Technologies. All rights reserved.
-- Author:        Agilent Technologies Netmetrix Division
-- Last updated:  18 November 1999
-- Purpose:       Defines objects to collect ATM and WAN statistics for data
--                collection.
--
-- Change History:
--   12/20/97 map Original version.
--   01/21/98 map Integrate HLA 11 changes.
--   01/23/98 map Bring up to HLA 11B level.
--   01/28/98 map Bring up to HLA 11C level.
--   02/10/98 map Formatting.
--   05/19/99 map Modify definitions to conform to RFC 1406 and RFC 1407
--   10/28/99 map Fix CLP1 in ATM AAL-5 Counters.  Obsolete Hssi tables
--   11/18/99 map Fix syntax errors

IMPORTS
       MODULE-IDENTITY, OBJECT-TYPE          FROM SNMPv2-SMI
       Counter64, TimeTicks, enterprises     FROM SNMPv2-SMI
       DisplayString, RowStatus              FROM SNMPv2-TC
       OwnerString                           FROM RMON-MIB;

hp                            OBJECT IDENTIFIER ::= {enterprises 11 }
nm                            OBJECT IDENTIFIER ::= { hp 2 }
system                        OBJECT IDENTIFIER ::= { nm 3 }
netElement                    OBJECT IDENTIFIER ::= { system 7 }
lanprobe                      OBJECT IDENTIFIER ::= { netElement 6 }
general                       OBJECT IDENTIFIER ::= { lanprobe 1 }
rmonExtension                 OBJECT IDENTIFIER ::= { general 5 }
statsExtension                OBJECT IDENTIFIER ::= { rmonExtension 1 }

wanStatsMIB MODULE-IDENTITY
       LAST-UPDATED "9911180000Z"
       ORGANIZATION "Agilent Technologies NetMetrix Division"
       CONTACT-INFO
              "Agilent Technologies
               NetMetrix Division
               5070 Centennial Blvd
               Colorado Springs, CO 80919"
       DESCRIPTION
              "The MIB containing RMON media statistics for WAN links."
::= { statsExtension 8 }

wanStatsMIBObjects            OBJECT IDENTIFIER ::= { wanStatsMIB 1 }
wanSignalingStats             OBJECT IDENTIFIER ::= { wanStatsMIBObjects 1 }
wanProtocolStats              OBJECT IDENTIFIER ::= { wanStatsMIBObjects 2 }
wanPvcStats                   OBJECT IDENTIFIER ::= { wanStatsMIBObjects 3 }

wanHistoryMIBObjects          OBJECT IDENTIFIER ::= { wanStatsMIB 2 }
wanSignalingHistory           OBJECT IDENTIFIER ::= { wanHistoryMIBObjects 1 }
wanProtocolHistory            OBJECT IDENTIFIER ::= { wanHistoryMIBObjects 2 }
wanPvcHistory                 OBJECT IDENTIFIER ::= { wanHistoryMIBObjects 3 }

wanT1E1StatsTable OBJECT-TYPE
       SYNTAX       SEQUENCE OF WanT1E1StatsEntry
       MAX-ACCESS   not-accessible
       STATUS       current
       DESCRIPTION
              "T1/E1 signaling statistics."
::= { wanSignalingStats 1 }

wanT1E1StatsEntry OBJECT-TYPE
       SYNTAX       WanT1E1StatsEntry
       MAX-ACCESS   not-accessible
       STATUS       current
       DESCRIPTION
              "Statistics for a T1/E1 interface.  The near end of the link
               refers to the side of the link that the probe is monitoring.
               The far end is the side the probe is not on."
       INDEX { wanT1E1StatsIndex }
::= { wanT1E1StatsTable 1 }

WanT1E1StatsEntry ::= SEQUENCE {
       wanT1E1StatsIndex                   INTEGER (1..65535),
       wanT1E1StatsDataSource              OBJECT IDENTIFIER,
       wanT1E1StatsDropEvents              Counter64,
       wanT1E1StatsInFrames                Counter64,
       wanT1E1StatsOutFrames               Counter64,
       wanT1E1StatsInOctets                Counter64,
       wanT1E1StatsOutOctets               Counter64,
       wanT1E1StatsESs                     Counter64,
       wanT1E1StatsSESs                    Counter64,
       wanT1E1StatsSEFSs                   Counter64,
       wanT1E1StatsOOFs                    Counter64,
       wanT1E1StatsUASs                    Counter64,
       wanT1E1StatsCSSs                    Counter64,
       wanT1E1StatsPCVs                    Counter64,
       wanT1E1StatsLESs                    Counter64,
       wanT1E1StatsBESs                    Counter64,
       wanT1E1StatsDMs                     Counter64,
       wanT1E1StatsLCVs                    Counter64,
       wanT1E1StatsLOFs                    Counter64,
       wanT1E1StatsLOSs                    Counter64,
       wanT1E1StatsRAIs                    Counter64,
       wanT1E1StatsAISs                    Counter64,
       wanT1E1StatsTS16AISs                Counter64,
       wanT1E1StatsLOMFs                   Counter64,
       wanT1E1StatsFarLOMFs                Counter64,
       wanT1E1StatsOwner                   OwnerString,
       wanT1E1StatsStatus                  RowStatus
}

wanT1E1StatsIndex OBJECT-TYPE
       SYNTAX       INTEGER (1..65535)
       MAX-ACCESS   not-accessible
       STATUS       current
       DESCRIPTION
              "The value of this object uniquely identifies this
               wanT1E1StatsTable entry."
::= { wanT1E1StatsEntry 1 }

wanT1E1StatsDataSource OBJECT-TYPE
       SYNTAX       OBJECT IDENTIFIER
       MAX-ACCESS   read-create
       STATUS       current
       DESCRIPTION
              "This object identifies the source of the data that this
               wanT1E1StatsEntry analyzes.  This source can be any DS1 or E1
               interface on this device.  In order to identify a particular
               interface, this object shall identify the instance of the 
               ifIndex object, defined in MIB-II [RFC 1573] for the desired
               interface.  The ifType value associated with the ifIndex can
               only be ds1(18)."
::= { wanT1E1StatsEntry 2 }

wanT1E1StatsDropEvents OBJECT-TYPE
       SYNTAX       Counter64
       MAX-ACCESS   read-only
       STATUS       current
       DESCRIPTION
              "The total number of events in which frames were dropped by
               the probe due to lack of resources.  Note that this number is
               not necessarily the number of frames dropped; it is just the
               number of times this condition has been detected."
::= { wanT1E1StatsEntry 3 }

wanT1E1StatsInFrames OBJECT-TYPE
       SYNTAX       Counter64
       MAX-ACCESS   read-only
       STATUS       current
       DESCRIPTION
              "The total number of frames seen originating from the far end
               of the link including errored frames."
::= { wanT1E1StatsEntry 4 }

wanT1E1StatsOutFrames OBJECT-TYPE
       SYNTAX       Counter64
       MAX-ACCESS   read-only
       STATUS       current
       DESCRIPTION
              "The total number of frames seen originating from the near end
               of the link including errored frames."
::= { wanT1E1StatsEntry 5 }

wanT1E1StatsInOctets OBJECT-TYPE
       SYNTAX       Counter64
       MAX-ACCESS   read-only
       STATUS       current
       DESCRIPTION
              "The sum of octets from all frames seen originating from the far
               end of the link including errored frames."
::= { wanT1E1StatsEntry 6 }

wanT1E1StatsOutOctets OBJECT-TYPE
       SYNTAX       Counter64
       MAX-ACCESS   read-only
       STATUS       current
       DESCRIPTION
              "The sum of octets from all frames seen originating from the
               near end of the link including errored frames."
::= { wanT1E1StatsEntry 7 }

wanT1E1StatsESs OBJECT-TYPE
       SYNTAX       Counter64
       MAX-ACCESS   read-only
       STATUS       current
       DESCRIPTION
              "For ESF and E1-CRC links an Errored Second is a second
                with one or more Path Code Violations OR one or more Out
                of Frame defects OR one or more Controlled Slip events OR
                a detected AIS defect.

                For D4 and E1-noCRC links, the presence of Bipolar

                Violations also triggers an Errored Second.

                This is not incremented during an Unavailable Second."
::= { wanT1E1StatsEntry 8 }

wanT1E1StatsSESs OBJECT-TYPE
       SYNTAX       Counter64
       MAX-ACCESS   read-only
       STATUS       current
       DESCRIPTION
              " A Severely Errored Second for ESF signals is a second
                with 320 or more Path Code Violation Error Events OR one
                or more Out of Frame defects OR a detected AIS defect.

                For E1-CRC signals, a Severely Errored Second is a second
                with 832 or more Path Code Violation error events OR one
                or more Out of Frame defects.

                For E1-noCRC signals, a Severely Errored Second is a 2048
                LCVs or more.
    
                For D4 signals, a Severely Errored Second is a count of
                one-second intervals with Framing Error events, or an OOF
                defect, or 1544 LCVs or more.

                Controlled slips are not included in this parameter.

                This is not incremented during an Unavailable Second."
::= { wanT1E1StatsEntry 9 }

wanT1E1StatsSEFSs OBJECT-TYPE
       SYNTAX       Counter64
       MAX-ACCESS   read-only
       STATUS       current
       DESCRIPTION
              "An Severely Errored Framing Second is a second with one
               or more Out of Frame defects OR a detected AIS defect."
::= {wanT1E1StatsEntry 10 }

wanT1E1StatsOOFs OBJECT-TYPE
       SYNTAX       Counter64
       MAX-ACCESS   read-only
       STATUS       current
       DESCRIPTION
              "An OOF defect is the occurrence of a particular density
               of Framing Error events.

               For T1 links, an Out of Frame defect is declared when the
               receiver detects two or more framing errors within a 3
               msec period for ESF signals and 0.75 msec for D4 signals,
               or two or more errors out of five or fewer consecutive
               framing-bits.

               For E1 links, an Out Of Frame defect is declared when
               three consecutive frame alignment signals have been
               received with an error (see G.706 Section 4.1 [17]).

               Once an Out Of Frame Defect is declared, the framer
               starts searching for a correct framing pattern.  The Out
               of Frame defect ends when the signal is in frame.

               In-frame occurs when there are fewer than two frame bit
               errors within 3 msec period for ESF signals and 0.75 msec
               for D4 signals.

               For E1 links, in-frame occurs when a) in frame N the
               frame alignment signal is correct and b) in frame N+1 the
               frame alignment signal is absent (i.e., bit 2 in TS0 is a
               one) and c) in frame N+2 the frame alignment signal is
               present and correct."
::= { wanT1E1StatsEntry 11 }

wanT1E1StatsUASs OBJECT-TYPE
       SYNTAX       Counter64
       MAX-ACCESS   read-only
       STATUS       current
       DESCRIPTION
              "Unavailable Seconds (UAS) are calculated by counting the
               number of seconds that the interface is unavailable.  The
               DS1 interface is said to be unavailable from the onset of
               10 contiguous SESs, or the onset of the condition leading
               to a failure (see Failure States).  If the condition
               leading to the failure was immediately preceded by one or
               more contiguous SESs, then the DS1 interface
               unavailability starts from the onset of these SESs.  Once
               unavailable, and if no failure is present, the DS1
               interface becomes available at the onset of 10 contiguous
               seconds with no SESs.  Once unavailable, and if a failure
               is present, the DS1 interface becomes available at the
               onset of 10 contiguous seconds with no SESs, if the
               failure clearing time is less than or equal to 10
               seconds.  If the failure clearing time is more than 10
               seconds, the DS1 interface becomes available at the onset
               of 10 contiguous seconds with no SESs, or the onset
               period leading to the successful clearing condition,
               whichever occurs later.  With respect to the DS1 error
               counts, all counters are incremented while the DS1
               interface is deemed available.  While the interface is
               deemed unavailable, the only count that is incremented is
               UASs."
::= { wanT1E1StatsEntry 12 }

wanT1E1StatsCSSs OBJECT-TYPE
       SYNTAX       Counter64
       MAX-ACCESS   read-only
       STATUS       current
       DESCRIPTION
              "A Controlled Slip Second is a one-second interval
               containing one or more controlled slips."
::= { wanT1E1StatsEntry 13 }

wanT1E1StatsPCVs OBJECT-TYPE
       SYNTAX       Counter64
       MAX-ACCESS   read-only
       STATUS       current
       DESCRIPTION
              "A Path Coding Violation error event is a frame
               synchronization bit error in the D4 and E1-noCRC formats,
               or a CRC error in the ESF and E1-CRC formats."
::= { wanT1E1StatsEntry 14 }

wanT1E1StatsLESs OBJECT-TYPE
       SYNTAX       Counter64
       MAX-ACCESS   read-only
       STATUS       current
       DESCRIPTION
              "A Line Errored Second, according to T1M1.3, is a second
               in which one or more Line Code Violation error events
               were detected.

               While many implementations are currently unable to detect
               the zero strings, it is expected that interface
               manufacturers will add this capability in deference to
               ANSI; therefore, it will become available in time.

               In the T1M1.3 specification, near end Line Code
               Violations and far end Line Errored Seconds are counted.
               For consistency, we count Line Errored Seconds at both
               ends."
::= {wanT1E1StatsEntry 15 }

wanT1E1StatsBESs OBJECT-TYPE
       SYNTAX       Counter64
       MAX-ACCESS   read-only
       STATUS       current
       DESCRIPTION
              "A Bursty Errored Second (also known as Errored Second
               type B) is a second with fewer than 320 and more than 1
               Path Coding Violation error events, no Severely Errored
               Frame defects and no detected incoming AIS defects.
               Controlled slips are not included in this parameter.

               This is not incremented during an Unavailable Second."
::= { wanT1E1StatsEntry 16 }

wanT1E1StatsDMs OBJECT-TYPE
       SYNTAX       Counter64
       MAX-ACCESS   read-only
       STATUS       current
       DESCRIPTION
              "A Degraded Minute is one in which the estimated error
               rate exceeds 1E-6 but does not exceed 1E-3 (see G.821
               [15]).

               Degraded Minutes are determined by collecting all of the
               Available Seconds, removing any Severely Errored Seconds
               grouping the result in 60-second long groups and counting
               a 60-second long group (a.k.a., minute) as degraded if the
               cumulative errors during the seconds present in the group
               exceed 1E-6.  Available seconds are merely those seconds
               which are not Unavailable as described below."
::= { wanT1E1StatsEntry 17 }

wanT1E1StatsLCVs OBJECT-TYPE
       SYNTAX       Counter64
       MAX-ACCESS   read-only
       STATUS       current
       DESCRIPTION
              "A Line Coding Violation (LCV) is the occurrence of either
               a Bipolar Violation (BPV) or Excessive Zeroes (EXZ) Error
               Event."
::= {wanT1E1StatsEntry 18 }
              
wanT1E1StatsLOFs OBJECT-TYPE
       SYNTAX       Counter64
       MAX-ACCESS   read-only
       STATUS       current
       DESCRIPTION
              "For T1 links, the Loss Of Frame failure is declared when
               an OOF or LOS  defect has persisted for T seconds, where
               2 <= T <= 10.  The Loss Of Frame failure is cleared when
               there have been no OOF or LOS defects during a period T
               where 0 <= T <= 20.  Many systems will perform 'hit
               integration'  within the period T before declaring or
               clearing the failure e.g., see TR 62411 [16].

               For E1 links, the Loss Of Frame Failure is declared when
               an OOF defect is detected."
::= { wanT1E1StatsEntry 19 }

wanT1E1StatsLOSs OBJECT-TYPE
       SYNTAX       Counter64
       MAX-ACCESS   read-only
       STATUS       current
       DESCRIPTION
              "For T1, the Loss Of Signal failure is declared upon
               observing 175 +/- 75 contiguous pulse positions with no
               pulses of either positive or negative polarity.  The LOS
               failure is cleared upon observing an average pulse
               density of at least 12.5% over a period of 175 +/- 75
               contiguous pulse positions starting with the receipt of a
               pulse.

               For E1 links, the Loss Of Signal failure is declared when
               greater than 10 consecutive zeroes are detected (see
               O.162 Section 3.4.4)."
::= { wanT1E1StatsEntry 20 }

wanT1E1StatsRAIs OBJECT-TYPE
       SYNTAX       Counter64
       MAX-ACCESS   read-only
       STATUS       current
       DESCRIPTION
              "The Far End Alarm failure is also known as 'Yellow Alarm'
               in the T1 case and 'Distant Alarm' in the E1 case.

               For D4 links, the Far End Alarm failure is declared when
               bit 6 of all channels has been zero for at least 335 ms
               and is cleared when bit 6 of at least one channel is
               non-zero for a period T, where T is usually less than one
               second and always less than 5 seconds.  The Far End Alarm
               failure is not declared for D4 links when a Loss of
               Signal is detected.

               For ESF links, the Far End Alarm failure is declared if
               the Yellow Alarm signal pattern occurs in at least seven
               out of ten contiguous 16-bit pattern intervals and is
               cleared if the Yellow Alarm signal pattern does not occur
               in ten contiguous 16-bit signal pattern intervals.

               For E1 links, the Far End Alarm failure is declared when
               bit 3 of time-slot zero is received set to one on two
               consecutive occasions.  The Far End Alarm failure is
               cleared when bit 3 of time-slot zero is received set to
               zero."
::= { wanT1E1StatsEntry 21 }

wanT1E1StatsAISs OBJECT-TYPE
       SYNTAX       Counter64
       MAX-ACCESS   read-only
       STATUS       current
       DESCRIPTION
              "The Alarm Indication Signal failure is declared when an
               AIS defect is detected at the input and the  AIS defect
               still exists after the Loss Of Frame failure (which is
               caused by the unframed nature of the 'all-ones' signal)
               is declared. The AIS failure is cleared when the Loss Of
               Frame failure is cleared."
::= { wanT1E1StatsEntry 22 }

wanT1E1StatsTS16AISs OBJECT-TYPE
       SYNTAX       Counter64
       MAX-ACCESS   read-only
       STATUS       current
       DESCRIPTION
              "For E1 links, the TS16 Alarm Indication Signal failure is
               declared when time-slot 16 is received as all ones for
               all frames of two consecutive multiframes (see G.732
               Section 4.2.6).  This condition is never declared for T1."
::= { wanT1E1StatsEntry 23 }

wanT1E1StatsLOMFs OBJECT-TYPE
       SYNTAX       Counter64
       MAX-ACCESS   read-only
       STATUS       current
       DESCRIPTION
              "The Loss Of MultiFrame failure is declared when two
               consecutive multiframe alignment signals (bits 4 through
               7 of TS16 of frame 0) have been received with an error.
               The Loss Of Multiframe failure is cleared when the first
               correct multiframe alignment signal is received.  The
               Loss Of Multiframe failure can only be declared for E1
               links operating with G.732 [18] framing (sometimes called
               'Channel Associated Signalling' mode)."
::= { wanT1E1StatsEntry 24 }

wanT1E1StatsFarLOMFs OBJECT-TYPE
       SYNTAX       Counter64
       MAX-ACCESS   read-only
       STATUS       current
       DESCRIPTION
              "The Far End Loss Of Multiframe failure is declared when
               bit 2 of TS16 of frame 0 is received set to one on two
               consecutive occasions.  The Far End Loss Of Multiframe
               failure is cleared when bit 2 of TS16 of frame 0 is
               received set to zero.  The Far End Loss Of Multiframe
               failure can only be declared for E1 links operating in
               'Channel Associated Signalling' mode."
::= { wanT1E1StatsEntry 25 }

wanT1E1StatsOwner OBJECT-TYPE
       SYNTAX       OwnerString
       MAX-ACCESS   read-create
       STATUS       current
       DESCRIPTION
              "The entity that configured this entry."
::= { wanT1E1StatsEntry 26 }

wanT1E1StatsStatus OBJECT-TYPE
       SYNTAX       RowStatus
--     MAX-ACCESS   read-write
       MAX-ACCESS   read-create
       STATUS       current
       DESCRIPTION
              "The status of this wanT1E1StatsTable entry."
::= { wanT1E1StatsEntry 27 }

wanT1E1HistoryTable OBJECT-TYPE
       SYNTAX       SEQUENCE OF WanT1E1HistoryEntry
       MAX-ACCESS   not-accessible
       STATUS       current
       DESCRIPTION
              "T1/E1 signaling statistics."
::= { wanSignalingHistory 1 }

wanT1E1HistoryEntry OBJECT-TYPE
       SYNTAX       WanT1E1HistoryEntry
       MAX-ACCESS   not-accessible
       STATUS       current
       DESCRIPTION
              "Statistics for a particular T1/E1 interface.  The near end of
               the link refers to the side of the link that the probe is
               monitoring.  The far end is the side the probe is not on."
       INDEX { wanT1E1HistoryIndex, wanT1E1HistorySampleIndex }
::= {wanT1E1HistoryTable 1 }

WanT1E1HistoryEntry ::= SEQUENCE {
       wanT1E1HistoryIndex                 INTEGER (1..65535),
       wanT1E1HistorySampleIndex           INTEGER (1..2147483647),
       wanT1E1HistoryIntervalStart         TimeTicks,
       wanT1E1HistoryDropEvents            Counter64,
       wanT1E1HistoryInFrames              Counter64,
       wanT1E1HistoryOutFrames             Counter64,
       wanT1E1HistoryInOctets              Counter64,
       wanT1E1HistoryOutOctets             Counter64,
       wanT1E1HistoryESs                   Counter64,
       wanT1E1HistorySESs                  Counter64,
       wanT1E1HistorySEFSs                 Counter64,
       wanT1E1HistoryOOFs                  Counter64,
       wanT1E1HistoryUASs                  Counter64,
       wanT1E1HistoryCSSs                  Counter64,
       wanT1E1HistoryPCVs                  Counter64,
       wanT1E1HistoryLESs                  Counter64,
       wanT1E1HistoryBESs                  Counter64,
       wanT1E1HistoryDMs                   Counter64,
       wanT1E1HistoryLCVs                  Counter64,
       wanT1E1HistoryLOFs                  Counter64,
       wanT1E1HistoryLOSs                  Counter64,
       wanT1E1HistoryAISs                  Counter64,
       wanT1E1HistoryRAIs                  Counter64,
       wanT1E1HistoryTS16AISs              Counter64,
       wanT1E1HistoryLOMFs                 Counter64,
       wanT1E1HistoryFarLOMFs              Counter64,
       wanT1E1HistoryInUtilization         INTEGER (0..10000),
       wanT1E1HistoryOutUtilization        INTEGER (0..10000)
}

wanT1E1HistoryIndex OBJECT-TYPE
       SYNTAX       INTEGER (1..65535)
       MAX-ACCESS   not-accessible
       STATUS       current
       DESCRIPTION
              "The history of which this entry is a port.  The history
               identified by a particular value of this index is the same
               history as identified by the same value of historyControlIndex."
::= { wanT1E1HistoryEntry 1 }

wanT1E1HistorySampleIndex OBJECT-TYPE
--     SYNTAX       OBJECT IDENTIFIER
       SYNTAX       INTEGER (1..2147483647)
       MAX-ACCESS   not-accessible
       STATUS       current
       DESCRIPTION
              "An index that uniquely identifies the particular sample this
               entry represents among all samples associated with the same
               historyControlEntry.  This index starts at 1 and increases by
               one as each new sample is taken."
::= {wanT1E1HistoryEntry 2 }

wanT1E1HistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample 
               is started at that instant.  Note that following this rule may
               require the probe to delay collection the first sample of the
               history, as each sample must be of the same interval.  Also
               note that the sample which is currently being collected is not
               accessible in this table until the end of its interval."
::= { wanT1E1HistoryEntry 3 } 

wanT1E1HistoryDropEvents OBJECT-TYPE
       SYNTAX       Counter64
       MAX-ACCESS   read-only
       STATUS       current
       DESCRIPTION
              "The change in value of wanT1E1StatsDropEvents during the
               interval."
::= { wanT1E1HistoryEntry 4 }

wanT1E1HistoryInFrames OBJECT-TYPE
       SYNTAX       Counter64
       MAX-ACCESS   read-only
       STATUS       current
       DESCRIPTION
              "The change in value of wanT1E1StatsInFrames during the
               interval."
::= { wanT1E1HistoryEntry 5 }

wanT1E1HistoryOutFrames OBJECT-TYPE
       SYNTAX       Counter64
       MAX-ACCESS   read-only
       STATUS       current
       DESCRIPTION
              "The change in value of wanT1E1StatsOutFrames during the
               interval."
::= { wanT1E1HistoryEntry 6 }

wanT1E1HistoryInOctets OBJECT-TYPE
       SYNTAX       Counter64
       MAX-ACCESS   read-only
       STATUS       current
       DESCRIPTION
              "The change in value of wanT1E1StatsInOctets during the
               interval."
::= { wanT1E1HistoryEntry 7 }

wanT1E1HistoryOutOctets OBJECT-TYPE
       SYNTAX       Counter64
       MAX-ACCESS   read-only
       STATUS       current
       DESCRIPTION
              "The change in value of wanT1E1StatsOutOctets during the
               interval."
::= { wanT1E1HistoryEntry 8 }

wanT1E1HistoryESs OBJECT-TYPE
       SYNTAX       Counter64
       MAX-ACCESS   read-only
       STATUS       current
       DESCRIPTION
              "The change in value of wanT1E1StatsESs during the interval."
::= { wanT1E1HistoryEntry 9 }

wanT1E1HistorySESs OBJECT-TYPE
       SYNTAX       Counter64
       MAX-ACCESS   read-only
       STATUS       current
       DESCRIPTION
              "The change in value of wanT1E1StatsSESs during the interval."
::= { wanT1E1HistoryEntry 10 }

wanT1E1HistorySEFSs OBJECT-TYPE
       SYNTAX       Counter64
       MAX-ACCESS   read-only
       STATUS       current
       DESCRIPTION
              "The change in value of wanT1E1StatsSEFSs during the interval."
::= { wanT1E1HistoryEntry 11 }

wanT1E1HistoryOOFs OBJECT-TYPE
       SYNTAX       Counter64
       MAX-ACCESS   read-only
       STATUS       current
       DESCRIPTION
              "The change in value of wanT1E1StatsOOFs during the interval."
::= { wanT1E1HistoryEntry 12 }

wanT1E1HistoryUASs OBJECT-TYPE
       SYNTAX       Counter64
       MAX-ACCESS   read-only
       STATUS       current
       DESCRIPTION
              "The change in value of wanT1E1StatsUASs during the interval."
::= { wanT1E1HistoryEntry 13 }

wanT1E1HistoryCSSs OBJECT-TYPE
       SYNTAX       Counter64
       MAX-ACCESS   read-only
       STATUS       current
       DESCRIPTION
              "The change in value of wanT1E1StatsCSSs during the interval."
::= { wanT1E1HistoryEntry 14 }

wanT1E1HistoryPCVs OBJECT-TYPE
       SYNTAX       Counter64
       MAX-ACCESS   read-only
       STATUS       current
       DESCRIPTION
              "The change in value of wanT1E1StatsPCVs during the interval."
::= { wanT1E1HistoryEntry 15 }

wanT1E1HistoryLESs OBJECT-TYPE
       SYNTAX       Counter64
       MAX-ACCESS   read-only
       STATUS       current
       DESCRIPTION
              "The change in value of wanT1E1StatsLESs during the interval."
::= { wanT1E1HistoryEntry 16 }

wanT1E1HistoryBESs OBJECT-TYPE
       SYNTAX       Counter64
       MAX-ACCESS   read-only
       STATUS       current
       DESCRIPTION
              "The change in value of wanT1E1StatsBESs during the interval."
::= { wanT1E1HistoryEntry 17 }

wanT1E1HistoryDMs OBJECT-TYPE
       SYNTAX       Counter64
       MAX-ACCESS   read-only
       STATUS       current
       DESCRIPTION
              "The change in value of wanT1E1StatsDMs during the interval."
::= { wanT1E1HistoryEntry 18 }

wanT1E1HistoryLCVs OBJECT-TYPE
       SYNTAX       Counter64
       MAX-ACCESS   read-only
       STATUS       current
       DESCRIPTION
              "The change in value of wanT1E1StatsLCVs during the interval."
::= { wanT1E1HistoryEntry 19 }

wanT1E1HistoryLOFs OBJECT-TYPE
       SYNTAX       Counter64
       MAX-ACCESS   read-only
       STATUS       current
       DESCRIPTION
              "The change in value of wanT1E1StatsLOFSs during the interval."
::= { wanT1E1HistoryEntry 20 }

wanT1E1HistoryLOSs OBJECT-TYPE
       SYNTAX       Counter64
       MAX-ACCESS   read-only
       STATUS       current
       DESCRIPTION
              "The change in value of wanT1E1StatsLOSs during the interval."
::= { wanT1E1HistoryEntry 21 }

wanT1E1HistoryRAIs OBJECT-TYPE
       SYNTAX       Counter64
       MAX-ACCESS   read-only
       STATUS       current
       DESCRIPTION
              "The change in value of wanT1E1StatsRAIs during the interval."
::= { wanT1E1HistoryEntry 22 }

wanT1E1HistoryAISs OBJECT-TYPE
       SYNTAX       Counter64
       MAX-ACCESS   read-only
       STATUS       current
       DESCRIPTION
              "The change in value of wanT1E1StatsAISs during the interval."
::= { wanT1E1HistoryEntry 23 }

wanT1E1HistoryTS16AISs OBJECT-TYPE
       SYNTAX       Counter64
       MAX-ACCESS   read-only
       STATUS       current
       DESCRIPTION
              "The change in value of wanT1E1StatsTS16AISs during the interval."
::= { wanT1E1HistoryEntry 24 }

wanT1E1HistoryLOMFs OBJECT-TYPE
       SYNTAX       Counter64
       MAX-ACCESS   read-only
       STATUS       current
       DESCRIPTION
              "The change in value of wanT1E1StatsLOMFs during the interval."
::= { wanT1E1HistoryEntry 25 }

wanT1E1HistoryFarLOMFs OBJECT-TYPE
       SYNTAX       Counter64
       MAX-ACCESS   read-only
       STATUS       current
       DESCRIPTION
              "The change in value of wanT1E1StatsFarLOMFs during the interval."
::= { wanT1E1HistoryEntry 26 }

wanT1E1HistoryInUtilization OBJECT-TYPE
       SYNTAX       INTEGER (0..10000)
       MAX-ACCESS   read-only
       STATUS       current
       DESCRIPTION
              "The best estimated of the mean physical layer network
               utilization of traffic coming from the far end of the link in
               hundreds of a percent."
::= { wanT1E1HistoryEntry 27 }

wanT1E1HistoryOutUtilization OBJECT-TYPE
       SYNTAX       INTEGER (0..10000)
       MAX-ACCESS   read-only
       STATUS       current
       DESCRIPTION
              "The best estimated of the mean physical layer network
               utilization of traffic coming from the near end of the link in
               hundreds of a percent."
::= { wanT1E1HistoryEntry 28 }

wanVSeriesStatsTable OBJECT-TYPE
       SYNTAX       SEQUENCE OF WanVSeriesStatsEntry
       MAX-ACCESS   not-accessible
       STATUS       current
       DESCRIPTION
              "V-series interface statistics."
::= { wanSignalingStats 2 }

wanVSeriesStatsEntry OBJECT-TYPE
       SYNTAX       WanVSeriesStatsEntry
       MAX-ACCESS   not-accessible
       STATUS       current
       DESCRIPTION
              "The statistics for a V-series interface. The near end of the
               link refers to the side of the link that the probe is
               monitoring.  The far end is the side the probe is not on."
       INDEX {  wanVSeriesStatsIndex }
::= { wanVSeriesStatsTable 1 }

       WanVSeriesStatsEntry ::= SEQUENCE {
       wanVSeriesStatsIndex                INTEGER (1..65535),
       wanVSeriesStatsDataSource           OBJECT IDENTIFIER,
       wanVSeriesStatsDropEvents           Counter64,
       wanVSeriesStatsInFrames             Counter64,
       wanVSeriesStatsOutFrames            Counter64,
       wanVSeriesStatsInOctets             Counter64,
       wanVSeriesStatsOutOctets            Counter64,
       wanVSeriesStatsInFCSs               Counter64,
       wanVSeriesStatsOutFCSs              Counter64,
       wanVSeriesStatsInOverruns           Counter64,
       wanVSeriesStatsOutOverruns          Counter64,
       wanVSeriesStatsInterruptedFrames    Counter64,
       wanVSeriesStatsInAbortedFrames      Counter64,
       wanVSeriesStatsOutAbortedFrames     Counter64,
       wanVSeriesStatsOwner                OwnerString,
       wanVSeriesStatsStatus               RowStatus
}

wanVSeriesStatsIndex OBJECT-TYPE
       SYNTAX       INTEGER (1..65535)
       MAX-ACCESS   not-accessible
       STATUS       current
       DESCRIPTION
              "The value of this object uniquely identifies this
               wanVSeriesStatsTable entry."
::= { wanVSeriesStatsEntry 1 }

wanVSeriesStatsDataSource OBJECT-TYPE
       SYNTAX       OBJECT IDENTIFIER
       MAX-ACCESS   read-create
       STATUS       current
       DESCRIPTION
              "This object identifies the source of the data that this
               wanVSeriesStatsEntry analyzes.  This source can be and V-series
               interface on this device.  In order to identify a particular
               interface, this object shall identify the instance of the 
               ifIndex object, defined in MIB-II [RFC 1573] for the desired
               interface.  The ifType value associated with the ifIndex can
               only be rs232(33) , v35(45), v11(64), or v36(65)."
::= { wanVSeriesStatsEntry 2 }

wanVSeriesStatsDropEvents OBJECT-TYPE
       SYNTAX       Counter64
       MAX-ACCESS   read-only
       STATUS       current
       DESCRIPTION
              "The total number of events in which frames were dropped by the
               probe due to lack of resources.  Note that this number is not
               necessarily the number of frames dropped; it is just the number
               of times this condition has been detected."
::= { wanVSeriesStatsEntry 3 }

wanVSeriesStatsInFrames OBJECT-TYPE
       SYNTAX       Counter64
       MAX-ACCESS   read-only
       STATUS       current
       DESCRIPTION
              "The total number of frames seen originating from the far end
               of the link including errored."
::= { wanVSeriesStatsEntry 4 }

wanVSeriesStatsOutFrames OBJECT-TYPE
       SYNTAX       Counter64
       MAX-ACCESS   read-only
       STATUS       current
       DESCRIPTION
              "The total number of frames seen originating from the near end
               of the link including errored frames."
::= { wanVSeriesStatsEntry 5}

wanVSeriesStatsInOctets OBJECT-TYPE
       SYNTAX       Counter64
       MAX-ACCESS   read-only
       STATUS       current
       DESCRIPTION
              "The sum of octets from all frames seen originating from the
               far end of the link including errored frames."
::= { wanVSeriesStatsEntry 6 }

wanVSeriesStatsOutOctets OBJECT-TYPE
       SYNTAX       Counter64
       MAX-ACCESS   read-only
       STATUS       current
       DESCRIPTION
              "The sum of octets from all frames seen originating from the
               near end of the link including errored frames."
::= { wanVSeriesStatsEntry 7 }

wanVSeriesStatsInFCSs OBJECT-TYPE
       SYNTAX        Counter64
       MAX-ACCESS    read-only
       STATUS        current
       DESCRIPTION
              "Total number of frames with an invalid frame check from the
               far end of the link."
::= { wanVSeriesStatsEntry 8 }

wanVSeriesStatsOutFCSs OBJECT-TYPE
       SYNTAX        Counter64
       MAX-ACCESS    read-only
       STATUS        current
       DESCRIPTION
              "Total number of frames with an invalid frame check from the
               near end of the link."
::= { wanVSeriesStatsEntry 9 }

wanVSeriesStatsInOverruns OBJECT-TYPE
       SYNTAX        Counter64
       MAX-ACCESS    read-only
       STATUS        current
       DESCRIPTION
              "Total number of frames from the far end of the link that
               failed to be received because the receiver did not accept the
               data in time."
::= { wanVSeriesStatsEntry 10 }

wanVSeriesStatsOutOverruns OBJECT-TYPE
       SYNTAX        Counter64
       MAX-ACCESS    read-only
       STATUS        current
       DESCRIPTION
              "Total number of frames from the near end of the link that
               failed to be received because the receiver did not accept the
               data in time."
::= { wanVSeriesStatsEntry 11 }

wanVSeriesStatsInterruptedFrames OBJECT-TYPE
       SYNTAX        Counter64
       MAX-ACCESS    read-only
       STATUS        current
       DESCRIPTION
              "Total number of frames that failed to be received or
               transmitted on the port due to loss of modem signals."
::= { wanVSeriesStatsEntry 12 }

wanVSeriesStatsInAbortedFrames OBJECT-TYPE
       SYNTAX        Counter64
       MAX-ACCESS    read-only
       STATUS        current
       DESCRIPTION
              "Number of frames from the far end of the link aborted on the
               port due to receiving an abort sequence."
::= { wanVSeriesStatsEntry 13 }

wanVSeriesStatsOutAbortedFrames OBJECT-TYPE
       SYNTAX        Counter64
       MAX-ACCESS    read-only
       STATUS        current
       DESCRIPTION
              "Number of frames from the near end of the link aborted on the
               port due to receiving an abort sequence."
::= { wanVSeriesStatsEntry 14 }

wanVSeriesStatsOwner OBJECT-TYPE
       SYNTAX       OwnerString
       MAX-ACCESS   read-create
       STATUS       current
       DESCRIPTION
              "The entity that configured this entry."
::= { wanVSeriesStatsEntry 15 }

wanVSeriesStatsStatus OBJECT-TYPE
       SYNTAX       RowStatus
--     MAX-ACCESS   read-write
       MAX-ACCESS   read-create
       STATUS       current
       DESCRIPTION
              "The status of this wanVSeriesStatsTable entry."
::= { wanVSeriesStatsEntry 16 }

wanVSeriesHistoryTable OBJECT-TYPE
       SYNTAX       SEQUENCE OF WanVSeriesHistoryEntry
       MAX-ACCESS   not-accessible
       STATUS       current
       DESCRIPTION
              "The history of which this entry is a port.  The history
               identified by a particular value of this index is the same
               history as identified by the same value of historyControlIndex."
::= { wanSignalingHistory 2 }

wanVSeriesHistoryEntry OBJECT-TYPE
       SYNTAX       WanVSeriesHistoryEntry
       MAX-ACCESS   not-accessible
       STATUS       current
       DESCRIPTION
              "The statistics for a V-series interface. The near end of the
               link refers to the side of the link that the probe is
               monitoring.  The far end is the side the probe is not on."
       INDEX { wanVSeriesHistoryIndex, wanVSeriesHistorySampleIndex }
::= { wanVSeriesHistoryTable 1 }

WanVSeriesHistoryEntry ::= SEQUENCE {
       wanVSeriesHistoryIndex              INTEGER (1..65535),
       wanVSeriesHistorySampleIndex        INTEGER (1..2147483647),
       wanVSeriesHistoryIntervalStart      TimeTicks,
       wanVSeriesHistoryDropEvents         Counter64,
       wanVSeriesHistoryInFrames           Counter64,
       wanVSeriesHistoryOutFrames          Counter64,
       wanVSeriesHistoryInOctets           Counter64,
       wanVSeriesHistoryOutOctets          Counter64,
       wanVSeriesHistoryInFCSs             Counter64,
       wanVSeriesHistoryOutFCSs            Counter64,
       wanVSeriesHistoryInOverruns         Counter64,
       wanVSeriesHistoryOutOverruns        Counter64,
       wanVSeriesHistoryInterruptedFrames  Counter64,
       wanVSeriesHistoryInAbortedFrames    Counter64,
       wanVSeriesHistoryOutAbortedFrames   Counter64,
       wanVSeriesHistoryInUtilization      INTEGER (0..10000),
       wanVSeriesHistoryOutUtilization     INTEGER (0..10000)
}

wanVSeriesHistoryIndex OBJECT-TYPE
       SYNTAX       INTEGER (1..65535)
       MAX-ACCESS   not-accessible
       STATUS       current
       DESCRIPTION
              "The history of which this entry is a port.  The history
               identified by a particular value of this index is the same
               history as identified by the same value of historyControlIndex."
::= { wanVSeriesHistoryEntry 1 }

wanVSeriesHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases by
               one as each new sample is taken."
::= {wanVSeriesHistoryEntry 2 }

wanVSeriesHistoryIntervalStart OBJECT-TYPE
       SYNTAX       TimeTicks
       MAX-ACCESS   read-only
       STATUS       current
       DESCRIPTION
              "The value of sysUpTime at the start of the interval over
               which this sample was measured.  If the probe keeps track of
               time of day, it should start the first sample of the history at
               a time such that when the next hour of the day begins, a sample
               is started at that instant.  Note that following this rule may
               require the probe to delay collection the first sample of the
               history, as each sample must be of the same interval.  Also
               note that the sample which is currently being collected is 
               not accessible in this table until the end of its interval."
::= { wanVSeriesHistoryEntry 3 } 

wanVSeriesHistoryDropEvents OBJECT-TYPE
       SYNTAX       Counter64
       MAX-ACCESS   read-only
       STATUS       current
       DESCRIPTION
              "The change in value of wanVSeriesStatsDropEvents during the
               interval."
::= { wanVSeriesHistoryEntry 4 }

wanVSeriesHistoryInFrames OBJECT-TYPE
       SYNTAX       Counter64
       MAX-ACCESS   read-only
       STATUS       current
       DESCRIPTION
              "The change in value of wanVSeriesStatsInFrames during the
               interval."
::= { wanVSeriesHistoryEntry 5 }

wanVSeriesHistoryOutFrames OBJECT-TYPE
       SYNTAX       Counter64
       MAX-ACCESS   read-only
       STATUS       current
       DESCRIPTION
              "The change in value of wanVSeriesStatsOutFrames during the
               interval."
::= { wanVSeriesHistoryEntry 6 }

wanVSeriesHistoryInOctets OBJECT-TYPE
       SYNTAX       Counter64
       MAX-ACCESS   read-only
       STATUS       current
       DESCRIPTION
              "The change in value of wanVSeriesStatsInOctets during the
               interval."
::= { wanVSeriesHistoryEntry 7 }

wanVSeriesHistoryOutOctets OBJECT-TYPE
       SYNTAX       Counter64
       MAX-ACCESS   read-only
       STATUS       current
       DESCRIPTION
              "The change in value of wanVSeriesStatsOutOctets during the
               interval."
::= { wanVSeriesHistoryEntry 8 }

wanVSeriesHistoryInFCSs OBJECT-TYPE
       SYNTAX        Counter64
       MAX-ACCESS    read-only
       STATUS        current
       DESCRIPTION
              "The change in value of wanVSeriesStatsInFCSs during the
               interval."
::= { wanVSeriesHistoryEntry 9 }

wanVSeriesHistoryOutFCSs OBJECT-TYPE
       SYNTAX        Counter64
       MAX-ACCESS    read-only
       STATUS        current
       DESCRIPTION
              "The change in value of wanVSeriesStatsOutFCSs during the
               interval."
::= { wanVSeriesHistoryEntry 10 }

wanVSeriesHistoryInOverruns OBJECT-TYPE
       SYNTAX        Counter64
       MAX-ACCESS    read-only
       STATUS        current
       DESCRIPTION
              "The change in value of wanVSeriesStatsInOverruns during the
               interval."
::= { wanVSeriesHistoryEntry 11 }

wanVSeriesHistoryOutOverruns OBJECT-TYPE
       SYNTAX        Counter64
       MAX-ACCESS    read-only
       STATUS        current
       DESCRIPTION
              "The change in value of wanVSeriesStatsOutOverruns during the
               interval."
::= { wanVSeriesHistoryEntry 12 }

wanVSeriesHistoryInterruptedFrames OBJECT-TYPE
       SYNTAX        Counter64
       MAX-ACCESS    read-only
       STATUS        current
       DESCRIPTION
              "The change in value of wanVSeriesStatsInterruptedFrames
               during the interval."
::= { wanVSeriesHistoryEntry 13 }

wanVSeriesHistoryInAbortedFrames OBJECT-TYPE
       SYNTAX        Counter64
       MAX-ACCESS    read-only
       STATUS        current
       DESCRIPTION
              "The change in value of wanVSeriesStatsInAbortedFrames
               during the interval."
::= { wanVSeriesHistoryEntry 14 }

wanVSeriesHistoryOutAbortedFrames OBJECT-TYPE
       SYNTAX        Counter64
       MAX-ACCESS    read-only
       STATUS        current
       DESCRIPTION
              "The change in value of wanVSeriesStatsOutAbortedFrames
               during the interval."
::= { wanVSeriesHistoryEntry 15 }

wanVSeriesHistoryInUtilization OBJECT-TYPE
       SYNTAX       INTEGER (0..10000)
       MAX-ACCESS   read-only
       STATUS       current
       DESCRIPTION
              "The best estimated of the mean physical layer network
               utilization of traffic coming from the far end of the link in
               hundreds of a percent."
::= { wanVSeriesHistoryEntry 16 }

wanVSeriesHistoryOutUtilization OBJECT-TYPE
       SYNTAX       INTEGER (0..10000)
       MAX-ACCESS   read-only
       STATUS       current
       DESCRIPTION
              "The best estimated of the mean physical layer network
               utilization of traffic coming from the near end of the link in
               hundreds of a percent."
::= { wanVSeriesHistoryEntry 17 }

wanHssiStatsTable OBJECT-TYPE
       SYNTAX       SEQUENCE OF WanHssiStatsEntry
       MAX-ACCESS   not-accessible
       STATUS       deprecated
       DESCRIPTION
              "HSSI interface statistics."
::= { wanSignalingStats 3 }

wanHssiStatsEntry OBJECT-TYPE
       SYNTAX       WanHssiStatsEntry
       MAX-ACCESS   not-accessible
       STATUS       deprecated
       DESCRIPTION
              "The statistics for a HSSI interface. The near end of the link
               refers to the side of the link that the probe is monitoring.
               The far end is the side the probe is not on."
       INDEX { wanHssiStatsIndex }
::= { wanHssiStatsTable 1 }

WanHssiStatsEntry ::= SEQUENCE {
       wanHssiStatsIndex                   INTEGER (1..65535),
       wanHssiStatsDataSource              OBJECT IDENTIFIER,
       wanHssiStatsDropEvents              Counter64,
       wanHssiStatsInFrames                Counter64,
       wanHssiStatsOutFrames               Counter64,
       wanHssiStatsInOctets                Counter64,
       wanHssiStatsOutOctets               Counter64,
       wanHssiStatsRxLongFrames            Counter64,
       wanHssiStatsRxCrcErrors             Counter64,
       wanHssiStatsRxOverruns              Counter64,
       wanHssiStatsRxAborts                Counter64,
       wanHssiStatsTxAborts                Counter64,
       wanHssiStatsTxUnderruns             Counter64,
       wanHssiStatsRxRingErrors            Counter64,
       wanHssiStatsRxRingOverruns          Counter64,
       wanHssiStatsTxRingErrors            Counter64,
       wanHssiStatsPortOpErrors            Counter64,
       wanHssiStatsTxCmplProcessings       Counter64,
       wanHssiStatsOwner                   OwnerString,
       wanHssiStatsStatus                  RowStatus
}

wanHssiStatsIndex OBJECT-TYPE
       SYNTAX       INTEGER (1..65535)
       MAX-ACCESS   not-accessible
       STATUS       deprecated
       DESCRIPTION
              "The value of this object uniquely identifies this
               wanHssiStatsTable entry."
::= { wanHssiStatsEntry 1 }

wanHssiStatsDataSource OBJECT-TYPE
       SYNTAX       OBJECT IDENTIFIER
       MAX-ACCESS   read-create
       STATUS       deprecated
       DESCRIPTION
              "This object identifies the source of the data that this
               wanT1E1StatsEntry analyzes.  This source can be any HSSI
               interface on this device.  In order to identify a particular
               interface, this object shall identify the instance of the 
               ifIndex object, defined in MIB-II [RFC 1573] for the desired
               interface.  The ifType value associated with the ifIndex can
               only be hssi(46)."
::= { wanHssiStatsEntry 2 }

wanHssiStatsDropEvents OBJECT-TYPE
       SYNTAX       Counter64
       MAX-ACCESS   read-only
       STATUS       deprecated
       DESCRIPTION
              "The total number of events in which frames were dropped by
               the probe due to lack of resources.  Note that this number is
               not necessarily the number of frames dropped; it is just the
               number of times this condition has been detected."
::= { wanHssiStatsEntry 3 }

wanHssiStatsInFrames OBJECT-TYPE
       SYNTAX       Counter64
       MAX-ACCESS   read-only
       STATUS       deprecated
       DESCRIPTION
              "The total number of frames seen originating from the far end
               of the link including errored frames."
::= { wanHssiStatsEntry 4 }

wanHssiStatsOutFrames OBJECT-TYPE
       SYNTAX       Counter64
       MAX-ACCESS   read-only
       STATUS       deprecated
       DESCRIPTION
              "The total number of frames seen originating from the near end
               of the link including errored frames."
::= { wanHssiStatsEntry 5 }
              
wanHssiStatsInOctets OBJECT-TYPE
       SYNTAX       Counter64
       MAX-ACCESS   read-only
       STATUS       deprecated
       DESCRIPTION
              "The sum of octets from all frames seen originating from the
               far end of the link including errored frames."
::= {wanHssiStatsEntry 6 }
              
wanHssiStatsOutOctets OBJECT-TYPE
       SYNTAX       Counter64
       MAX-ACCESS   read-only
       STATUS       deprecated
       DESCRIPTION
              "The sum of octets from all frames seen originating from the
               near end of the link including errored frames."
::= { wanHssiStatsEntry 7 }
              
wanHssiStatsRxLongFrames OBJECT-TYPE
       SYNTAX       Counter64
       MAX-ACCESS   read-only
       STATUS       deprecated
       DESCRIPTION
              "Number of long frames from the far end of the link."
::= { wanHssiStatsEntry 8 }

wanHssiStatsRxCrcErrors OBJECT-TYPE
       SYNTAX       Counter64
       MAX-ACCESS   read-only
       STATUS       deprecated
       DESCRIPTION
              "Number of frames from far end of link with CRC errors."
::= { wanHssiStatsEntry 9 }

wanHssiStatsRxOverruns OBJECT-TYPE
       SYNTAX       Counter64
       MAX-ACCESS   read-only
       STATUS       deprecated
       DESCRIPTION
              "Number of frames from far end of link with FIFO overrun errors."
::= { wanHssiStatsEntry 10 }

wanHssiStatsRxAborts OBJECT-TYPE
       SYNTAX       Counter64
       MAX-ACCESS   read-only
       STATUS       deprecated
       DESCRIPTION
              "Number of frames from far end of link with abort status."
::= { wanHssiStatsEntry 11 }

wanHssiStatsTxAborts OBJECT-TYPE
       SYNTAX       Counter64
       MAX-ACCESS   read-only
       STATUS       deprecated
       DESCRIPTION
              "Number of frames from near end of link with internal abort
               errors."
::= { wanHssiStatsEntry 12 }

wanHssiStatsTxUnderruns OBJECT-TYPE
       SYNTAX       Counter64
       MAX-ACCESS   read-only
       STATUS       deprecated
       DESCRIPTION
              "Number of frames from near end of link aborted with underrun
               errors."
::= { wanHssiStatsEntry 13 }

wanHssiStatsRxRingErrors OBJECT-TYPE
       SYNTAX       Counter64
       MAX-ACCESS   read-only
       STATUS       deprecated
       DESCRIPTION
              "Number of receive ring error events."
::= { wanHssiStatsEntry 14 }

wanHssiStatsRxRingOverruns OBJECT-TYPE
       SYNTAX       Counter64
       MAX-ACCESS   read-only
       STATUS       deprecated
       DESCRIPTION
              "Number of receive ring overrun events."
::= { wanHssiStatsEntry 15 }

wanHssiStatsTxRingErrors OBJECT-TYPE
       SYNTAX       Counter64
       MAX-ACCESS   read-only
       STATUS       deprecated
       DESCRIPTION
              "Number of transmit ring error events."
::= { wanHssiStatsEntry 16 }

wanHssiStatsPortOpErrors OBJECT-TYPE
       SYNTAX       Counter64
       MAX-ACCESS   read-only
       STATUS       deprecated
       DESCRIPTION
              "Number of port operation error events."
::= { wanHssiStatsEntry 17 }

wanHssiStatsTxCmplProcessings OBJECT-TYPE
       SYNTAX       Counter64
       MAX-ACCESS   read-only
       STATUS       deprecated
       DESCRIPTION
              "Number of transmit complete processings (TINT)."
::= { wanHssiStatsEntry 18 }

wanHssiStatsOwner OBJECT-TYPE
       SYNTAX       OwnerString
       MAX-ACCESS   read-create
       STATUS       deprecated
       DESCRIPTION
              "The entity that configured this entry."
::= { wanHssiStatsEntry 19 }

wanHssiStatsStatus OBJECT-TYPE
       SYNTAX       RowStatus
       MAX-ACCESS   read-create
       STATUS       deprecated
       DESCRIPTION
              "The status of this wanHssiStatsTable entry."
::= { wanHssiStatsEntry 20 }

wanHssiHistoryTable OBJECT-TYPE
       SYNTAX       SEQUENCE OF WanHssiHistoryEntry
       MAX-ACCESS   not-accessible
       STATUS       deprecated
       DESCRIPTION
              "HSSI interface statistics."
::= { wanSignalingHistory 3 }

wanHssiHistoryEntry OBJECT-TYPE
       SYNTAX       WanHssiHistoryEntry
       MAX-ACCESS   not-accessible
       STATUS       deprecated
       DESCRIPTION
              "The statistics for a HSSI interface. The near end of the link
               refers to the side of the link that the probe is monitoring.
               The far end is the side the probe is not on."
       INDEX { wanHssiHistoryIndex, wanHssiHistorySampleIndex }
::= { wanHssiHistoryTable 1 }

WanHssiHistoryEntry ::= SEQUENCE {
       wanHssiHistoryIndex                 INTEGER (1..65535),
       wanHssiHistorySampleIndex           INTEGER (1..2147483647),
       wanHssiHistoryIntervalStart         TimeTicks,
       wanHssiHistoryDropEvents            Counter64,
       wanHssiHistoryInFrames              Counter64,
       wanHssiHistoryOutFrames             Counter64,
       wanHssiHistoryInOctets              Counter64,
       wanHssiHistoryOutOctets             Counter64,
       wanHssiHistoryRxLongFrames          Counter64,
       wanHssiHistoryRxCrcErrors           Counter64,
       wanHssiHistoryRxOverruns            Counter64,
       wanHssiHistoryRxAborts              Counter64,
       wanHssiHistoryTxAborts              Counter64,
       wanHssiHistoryTxUnderruns           Counter64,
       wanHssiHistoryRxRingErrors          Counter64,
       wanHssiHistoryRxRingOverruns        Counter64,
       wanHssiHistoryTxRingErrors          Counter64,
       wanHssiHistoryPortOpErrors          Counter64,
       wanHssiHistoryTxCmplProcessings     Counter64,
       wanHssiHistoryInUtilization         INTEGER (0..10000),
       wanHssiHistoryOutUtilization        INTEGER (0..10000)
}

wanHssiHistoryIndex OBJECT-TYPE
       SYNTAX       INTEGER (1..65535)
       MAX-ACCESS   not-accessible
       STATUS       deprecated
       DESCRIPTION
              "The history of which this entry is a port.  The history
               identified by a particular value of this index is the same
               history as identified by the same value of historyControlIndex."
::= { wanHssiHistoryEntry 1 }

wanHssiHistorySampleIndex OBJECT-TYPE
       SYNTAX       INTEGER (1..2147483647)
       MAX-ACCESS   not-accessible
       STATUS       deprecated
       DESCRIPTION
              "An index that uniquely identifies the particular sample this
               entry represents among all samples associated with the same
               historyControlEntry.  This index starts at 1 and increases by
               one as each new sample is taken."
::= { wanHssiHistoryEntry 2 }

wanHssiHistoryIntervalStart OBJECT-TYPE
       SYNTAX       TimeTicks
       MAX-ACCESS   read-only
       STATUS       deprecated
       DESCRIPTION
              "The value of sysUpTime at the start of the interval over
               which this sample was measured.  If the probe keeps track of
               time of day, it should start the first sample of the history
               at a time such that when the next hour of the day begins, a
               sample is started at that instant.  Note that following this
               rule may require the probe to delay collection the first sample
               of the history, as each sample must be of the same interval.
               Also note that the sample which is currently being collected is 
               not accessible in this table until the end of its interval."
::= { wanHssiHistoryEntry 3 } 

wanHssiHistoryDropEvents OBJECT-TYPE
       SYNTAX       Counter64
       MAX-ACCESS   read-only
       STATUS       deprecated
       DESCRIPTION
              "The change in value of wanHssiStatsDropEvents during the
               interval."
::= { wanHssiHistoryEntry 4 }

wanHssiHistoryInFrames OBJECT-TYPE
       SYNTAX       Counter64
       MAX-ACCESS   read-only
       STATUS       deprecated
       DESCRIPTION
              "The change in value of wanHssiStatsInFrames during the
               interval."
::= { wanHssiHistoryEntry 5 }

wanHssiHistoryOutFrames OBJECT-TYPE
       SYNTAX       Counter64
       MAX-ACCESS   read-only
       STATUS       deprecated
       DESCRIPTION
              "The change in value of wanHssiStatsOutFrames during the
               interval."
::= { wanHssiHistoryEntry 6 }

wanHssiHistoryInOctets OBJECT-TYPE
       SYNTAX       Counter64
       MAX-ACCESS   read-only
       STATUS       deprecated
       DESCRIPTION
              "The change in value of wanHssiStatsInOctets during the
               interval."
::= { wanHssiHistoryEntry 7 }

wanHssiHistoryOutOctets OBJECT-TYPE
       SYNTAX       Counter64
       MAX-ACCESS   read-only
       STATUS       deprecated
       DESCRIPTION
              "The change in value of wanHssiStatsOutOctets during the
               interval."
::= { wanHssiHistoryEntry 8 }

wanHssiHistoryRxLongFrames OBJECT-TYPE
       SYNTAX       Counter64
       MAX-ACCESS   read-only
       STATUS       deprecated
       DESCRIPTION
              "The change in value of wanHssiStatsRxLongFrames during the
               interval."
::= { wanHssiHistoryEntry 9 }

wanHssiHistoryRxCrcErrors OBJECT-TYPE
       SYNTAX       Counter64
       MAX-ACCESS   read-only
       STATUS       deprecated
       DESCRIPTION
              "The change in value of wanHssiStatsRxCrcErrors during the
               interval."
::= { wanHssiHistoryEntry 10 }

wanHssiHistoryRxOverruns OBJECT-TYPE
       SYNTAX       Counter64
       MAX-ACCESS   read-only
       STATUS       deprecated
       DESCRIPTION
              "The change in value of wanHssiStatsRxOverruns during the
               interval."
::= { wanHssiHistoryEntry 11}

wanHssiHistoryRxAborts OBJECT-TYPE
       SYNTAX       Counter64
       MAX-ACCESS   read-only
       STATUS       deprecated
       DESCRIPTION
              "The change in value of wanHssiStatsRxAborts during the
               interval."
::= { wanHssiHistoryEntry 12 }

wanHssiHistoryTxAborts OBJECT-TYPE
       SYNTAX       Counter64
       MAX-ACCESS   read-only
       STATUS       deprecated
       DESCRIPTION
              "The change in value of wanHssiStatsTxAborts during the
               interval."
::= { wanHssiHistoryEntry 13 }

wanHssiHistoryTxUnderruns OBJECT-TYPE
       SYNTAX       Counter64
       MAX-ACCESS   read-only
       STATUS       deprecated
       DESCRIPTION
              "The change in value of wanHssiStatsTxUnderruns during the
               interval."
::= { wanHssiHistoryEntry 14 }

wanHssiHistoryRxRingErrors OBJECT-TYPE
       SYNTAX       Counter64
       MAX-ACCESS   read-only
       STATUS       deprecated
       DESCRIPTION
              "The change in value of wanHssiStatsTxRingErrors during the
               interval."
::= { wanHssiHistoryEntry 15 }

wanHssiHistoryRxRingOverruns OBJECT-TYPE
       SYNTAX       Counter64
       MAX-ACCESS   read-only
       STATUS       deprecated
       DESCRIPTION
              "The change in value of wanHssiStatsRxRingOverruns during the
               interval."
::= { wanHssiHistoryEntry 16 }

wanHssiHistoryTxRingErrors OBJECT-TYPE
       SYNTAX       Counter64
       MAX-ACCESS   read-only
       STATUS       deprecated
       DESCRIPTION
              "The change in value of wanHssiStatsTxRingErrors during the
               interval."
::= { wanHssiHistoryEntry 17 }

wanHssiHistoryPortOpErrors OBJECT-TYPE
       SYNTAX       Counter64
       MAX-ACCESS   read-only
       STATUS       deprecated
       DESCRIPTION
              "The change in value of wanHssiStatsPortOpErrors during the
               interval."
::= { wanHssiHistoryEntry 18 }

wanHssiHistoryTxCmplProcessings OBJECT-TYPE
       SYNTAX       Counter64
       MAX-ACCESS   read-only
       STATUS       deprecated
       DESCRIPTION
              "The change in value of wanHssiStatsTxCmplProcessings during
               the interval."
::= { wanHssiHistoryEntry 19 }

wanHssiHistoryInUtilization OBJECT-TYPE
       SYNTAX       INTEGER (0..10000)
       MAX-ACCESS   read-only
       STATUS       deprecated
       DESCRIPTION
              "The best estimated of the mean physical layer network
               utilization of traffic coming from the far end of the link in
               hundreds of a percent."
::= { wanHssiHistoryEntry 20 }

wanHssiHistoryOutUtilization OBJECT-TYPE
       SYNTAX       INTEGER (0..10000)
       MAX-ACCESS   read-only
       STATUS       deprecated
       DESCRIPTION
              "The best estimated of the mean physical layer network
               utilization of traffic coming from the near end of the link in
               hundreds of a percent."
::= { wanHssiHistoryEntry 21 }

wanT3E3StatsTable OBJECT-TYPE
       SYNTAX       SEQUENCE OF WanT3E3StatsEntry
       MAX-ACCESS   not-accessible
       STATUS       current
       DESCRIPTION
              "T3/E3 signaling statistics"
::= { wanSignalingStats 4 }

wanT3E3StatsEntry OBJECT-TYPE
       SYNTAX       WanT3E3StatsEntry
       MAX-ACCESS   not-accessible
       STATUS       current
       DESCRIPTION
              "Statistics for a T3/E3 interface. The near end of the link
               refers to the side of the link that the probe is monitoring.
               The far end is the side the probe is not on."
       INDEX {wanT3E3StatsIndex }
::= { wanT3E3StatsTable 1 }

WanT3E3StatsEntry ::= SEQUENCE {
       wanT3E3StatsIndex                   INTEGER (1..65535),
       wanT3E3StatsDataSource              OBJECT IDENTIFIER,
       wanT3E3StatsDropEvents              Counter64,
       wanT3E3StatsInFrames                Counter64,
       wanT3E3StatsOutFrames               Counter64,
       wanT3E3StatsInOctets                Counter64,
       wanT3E3StatsOutOctets               Counter64,
       wanT3E3StatsPESs                    Counter64,
       wanT3E3StatsPSESs                   Counter64,
       wanT3E3StatsOOFs                    Counter64,
       wanT3E3StatsSEFSs                   Counter64,
       wanT3E3StatsUASs                    Counter64,
       wanT3E3StatsLCVs                    Counter64,
       wanT3E3StatsPCVs                    Counter64,
       wanT3E3StatsLESs                    Counter64,
       wanT3E3StatsCCVs                    Counter64,
       wanT3E3StatsCESs                    Counter64,
       wanT3E3StatsCSESs                   Counter64,
       wanT3E3StatsRAIs                    Counter64,
       wanT3E3StatsAISs                    Counter64,
       wanT3E3StatsLOFs                    Counter64,
       wanT3E3StatsLOSs                    Counter64,
       wanT3E3StatsOwner                   OwnerString,
       wanT3E3StatsStatus                  RowStatus
}

wanT3E3StatsIndex OBJECT-TYPE
       SYNTAX       INTEGER (1..65535)
       MAX-ACCESS   not-accessible
       STATUS       current
       DESCRIPTION
              "The value of this object uniquely identifies this
               wanT3E3StatsTable entry."
::= { wanT3E3StatsEntry 1 }

wanT3E3StatsDataSource OBJECT-TYPE
       SYNTAX       OBJECT IDENTIFIER
       MAX-ACCESS   read-create
       STATUS       current
       DESCRIPTION
              "This object identifies the source of the data that this
               wanT3E3StatsEntry analyzes.  This source can be any DS3 or E3
               interface on this device.  In order to identify a particular
               interface, this object shall identify the instance of the 
               ifIndex object, defined in MIB-II [RFC 1573] for the desired
               interface.  The ifType value of the associated ifIndex can
               only be ds3(30)."
::= { wanT3E3StatsEntry 2 }

wanT3E3StatsDropEvents OBJECT-TYPE
       SYNTAX       Counter64
       MAX-ACCESS   read-only
       STATUS       current
       DESCRIPTION
              "The total number of events in which frames were dropped by
               the probe due to lack of resources.  Note that this number is
               not necessarily the number of frames dropped; it is just the
               number of times this condition has been detected."
::= { wanT3E3StatsEntry 3 }

wanT3E3StatsInFrames OBJECT-TYPE
       SYNTAX       Counter64
       MAX-ACCESS   read-only
       STATUS       current
       DESCRIPTION
              "The total number of frames seen originating from the far end
               of the link including errored frames."
::= { wanT3E3StatsEntry 4 }

wanT3E3StatsOutFrames OBJECT-TYPE
       SYNTAX       Counter64
       MAX-ACCESS   read-only
       STATUS       current
       DESCRIPTION
              "The total number of frames seen originating from the near end
               of the link including errored frames."
::= { wanT3E3StatsEntry 5 }

wanT3E3StatsInOctets OBJECT-TYPE
       SYNTAX       Counter64
       MAX-ACCESS   read-only 
       STATUS       current
       DESCRIPTION
              "The sum of octets from all frames seen originating from the
               far end of the link including errored frames."
::= { wanT3E3StatsEntry 6 }

wanT3E3StatsOutOctets OBJECT-TYPE
       SYNTAX       Counter64
       MAX-ACCESS   read-only
       STATUS       current
       DESCRIPTION
              "The sum of octets from all frames seen originating from the
               near end of the link including errored frames."
::= { wanT3E3StatsEntry 7 }

wanT3E3StatsPESs OBJECT-TYPE
       SYNTAX       Counter64
       MAX-ACCESS   read-only
       STATUS       current
       DESCRIPTION
              "A PES is a second with one or more PCVs OR
               one or more Out of Frame defects OR a detected incoming AIS.
               This gauge is not incremented when UASs are counted."
::= { wanT3E3StatsEntry 8 }

wanT3E3StatsPSESs OBJECT-TYPE
       SYNTAX       Counter64
       MAX-ACCESS   read-only
       STATUS       current
       DESCRIPTION
              "A PSES is a second with 44 or more PCVs OR 
               one or more Out of Frame defects OR a detected incoming AIS.
               This gauge is not incremented when UASs are counted."
::= { wanT3E3StatsEntry 9 }

wanT3E3StatsOOFs OBJECT-TYPE
       SYNTAX       Counter64
       MAX-ACCESS   read-only
       STATUS       current
       DESCRIPTION
              "A DS3 OOF defect is detected when any three or more errors
               in sixteen or fewer consecutive F-bits occur within a DS3
               M-frame.  An OOF defect may also be called a Severely
               Errored Frame (SEF) defect.  An OOF defect is cleared when
               reframe occurs.  A DS3 Loss of Frame (LOF) failure is
               declared when the DS3 OOF defect is consistent for 2 to 10
               seconds.  The DS3 OOF defect ends when reframe occurs.
               The DS3 LOF failure is cleared when the DS3 OOF
               defect is absent for 10 to 20 seconds.

               An E3 OOF defect is detected when four consecutive frame
               alignment signals have been incorrectly received in there
               predicted positions in an E3 signal. E3 frame alignment
               occurs when the presence of three consecutive frame
               alignment signals have been detected."
::= { wanT3E3StatsEntry 10 }

wanT3E3StatsSEFSs OBJECT-TYPE
       SYNTAX       Counter64
       MAX-ACCESS   read-only
       STATUS       current
       DESCRIPTION
              "A SEFS is a second with one or more Out of Frame defects
               OR a detected incoming AIS."
::= { wanT3E3StatsEntry 11 }

wanT3E3StatsUASs OBJECT-TYPE
       SYNTAX       Counter64
       MAX-ACCESS   read-only
       STATUS       current
       DESCRIPTION
              "UAS are calculated by counting the number of seconds that
               the interface is unavailable.  The DS3 interface is said
               to be unavailable from the onset of 10 contiguous PSESs, or
               the onset of the condition leading to a failure (see Failure
               States).  If the condition leading to the failure was
               immediately preceded by one or more contiguous PSESs, then
               the DS3 interface unavailability starts from the onset of
               these PSESs.  Once unavailable, and if no failure is
               present, the DS3 interface becomes available at the onset
               of 10 contiguous seconds with no PSESs.  Once unavailable,
               and if a failure is present, the DS3 interface becomes
               available at the onset of 10 contiguous seconds with no
               PSESs, if the failure clearing time is less than
               or equal to 10 seconds.  If the failure clearing time is
               more than 10 seconds, the DS3 interface becomes available
               at the onset of 10 contiguous seconds with no PSESs, or
               the onset period leading to the successful clearing
               condition, whichever occurs later.  With respect to the
               DS3 error counts, all counters are incremented
               while the DS3 interface is deemed available.  While the
               interface is deemed unavailable, the only count that is
               incremented is UASs."
::= { wanT3E3StatsEntry 12 }

wanT3E3StatsLCVs OBJECT-TYPE
       SYNTAX       Counter64
       MAX-ACCESS   read-only
       STATUS       current
       DESCRIPTION
              "This parameter is a count of both BPVs and EXZs
               occurring over the accumulation period.  An EXZ
               increments the LCV by one regardless of the length
               of the zero string."
::= { wanT3E3StatsEntry 13 }

wanT3E3StatsPCVs OBJECT-TYPE
       SYNTAX       Counter64
       MAX-ACCESS   read-only
       STATUS       current
       DESCRIPTION
              "For all DS3 applications, a coding violation error event is
               a P-bit Parity Error event.  A P-bit Parity Error event is
               the occurrence of a received P-bit code on the DS3 M-frame
               that is not identical to the corresponding locally-
               calculated code."
::= { wanT3E3StatsEntry 14 }

wanT3E3StatsLESs OBJECT-TYPE
       SYNTAX       Counter64
       MAX-ACCESS   read-only
       STATUS       current
       DESCRIPTION
              "A Line Errored Second is a second in
               which one or more CVs occurred OR one or more LOS defects."
::= { wanT3E3StatsEntry 15 }

wanT3E3StatsCCVs OBJECT-TYPE
       SYNTAX       Counter64
       MAX-ACCESS   read-only
       STATUS       current
       DESCRIPTION
              "For C-bit Parity and SYNTRAN DS3 applications, this is
               the count of coding violations reported via the C-bits.
               For C-bit Parity, it is a count of CP-bit parity errors
               occurring in the accumulation interval.  For SYNTRAN, it
               is a count of CRC-9 errors occurring in the accumulation
               interval."
::= { wanT3E3StatsEntry 16 }

wanT3E3StatsCESs OBJECT-TYPE
       SYNTAX       Counter64
       MAX-ACCESS   read-only
       STATUS       current
       DESCRIPTION
              "An CES is a second with one or more CCVs OR
               one or more Out of Frame defects OR a detected incoming AIS.
               This count is only for the SYNTRAN and C-bit Parity DS3
               applications.  This gauge is not incremented when UASs are
               counted."
::= { wanT3E3StatsEntry 17 }

wanT3E3StatsCSESs OBJECT-TYPE
       SYNTAX       Counter64
       MAX-ACCESS   read-only
       STATUS       current
       DESCRIPTION
              "A CSES is a second with 44 or more CCVs OR
               one or more Out of Frame defects OR a detected incoming AIS.
               This count is only for the SYNTRAN and C-bit Parity DS3
               applications.  This gauge is not incremented when UASs
               are counted."
::= { wanT3E3StatsEntry 18 }

wanT3E3StatsRAIs OBJECT-TYPE
       SYNTAX       Counter64
       MAX-ACCESS   read-only
       STATUS       current
       DESCRIPTION
              "The Remote Alarm Indication (RAI) failure, in SYNTRAN
               applications, is declared after detecting
               the Yellow Alarm Signal on the alarm channel.  See ANSI
               T1.107a-1990 [10].  The Remote Alarm Indication failure,
               in C-bit Parity DS3 applications, is declared
               as soon as the preqsence of either one or two alarm signals
               are detected on then Far End Alarm Channel.  See [10].
               The Remote Alarm Indication failure may also be declared
               after detecting the far-end SEF/AIS defect (aka yellow).
               The Remote Alarm Indication failure is cleared as soon as
               the presence of the any of the above alarms are removed.

               Also, the incoming failure state is declared when a defect
               persists for at least 2-10 seconds.  The defects are
               the following:  Loss of Signal (LOS), an Out of Frame (OOF)
               or an incoming Alarm Indication Signal (AIS).
               The Failure State is cleared when the defect is absent
               for less than or equal to 20 seconds."
::= { wanT3E3StatsEntry 19 }

wanT3E3StatsAISs OBJECT-TYPE
       SYNTAX       Counter64
       MAX-ACCESS   read-only
       STATUS       current
       DESCRIPTION
              "The DS3 AIS is framed with 'stuck stuffing.'  This implies
               that it has a valid M-subframe alignments bits, M-frame
               alignment bits, and P bits.  The information bits are set
               to a 1010... sequence, starting with a one (1) after each
               M-subframe alignment bit, M-frame alignment bit, X bit, P
               bit, and C bit.  The C bits are all set to zero giving
               what is called 'stuck stuffing.'  The X bits are set to
               one.  The DS3 AIS defect is declared after DS3 AIS is
               present in contiguous M-frames for a time equal to or
               greater than T, where 0.2 ms <= T <= 100 ms.
               The DS3 AIS defect is terminated after AIS is absent in
               contiguous M-frames for a time equal to or greater than T.

               The E3 binary content of the AIS is nominally a continuous
               stream of ones.  AIS detection and the application of
               consequent actions, should be completed within a time
               limit of 1 ms."
::= { wanT3E3StatsEntry 20 }

wanT3E3StatsLOFs OBJECT-TYPE
       SYNTAX       Counter64
       MAX-ACCESS   read-only
       STATUS       current
       DESCRIPTION
              "A DS3 Loss of Frame (LOF) failure is declared when the DS3 OOF
              defect is consistent for 2 to 10 seconds.  The DS3 OOF defect
              ends when reframe occurs.  The DS3 LOF failure is cleared when
              the DS3 OOF defect is absent for 10 to 20 seconds. (See T1.231
              section 7.1.2.2.1)"
::= { wanT3E3StatsEntry 21 }

wanT3E3StatsLOSs OBJECT-TYPE
       SYNTAX       Counter64
       MAX-ACCESS   read-only
       STATUS       current
       DESCRIPTION
              "The DS3 LOS defect is declared upon observing 175 +/- 75
               contiguous pulse positions with no pulses of either
               positive or negative polarity.
               The DS3 LOS defect is terminated upon observing an average
               pulse density of at least 33% over a period of 175 +/- 75
               contiguous pulse positions starting with the receipt of a
               pulse."
::= { wanT3E3StatsEntry 22 }

wanT3E3StatsOwner OBJECT-TYPE
       SYNTAX       OwnerString
       MAX-ACCESS   read-create
       STATUS       current
       DESCRIPTION
              "The entity that configured this entry."
::= { wanT3E3StatsEntry 23 }

wanT3E3StatsStatus OBJECT-TYPE
       SYNTAX       RowStatus
--     MAX-ACCESS   read-write
       MAX-ACCESS   read-create
       STATUS       current
       DESCRIPTION
              "The status of this wanT3E3StatsTable entry."
::= { wanT3E3StatsEntry 24 }

wanT3E3HistoryTable OBJECT-TYPE
       SYNTAX       SEQUENCE OF WanT3E3HistoryEntry
       MAX-ACCESS   not-accessible
       STATUS       current
       DESCRIPTION
              "T3/E3 signaling statistics"
::= { wanSignalingHistory 4 }

wanT3E3HistoryEntry OBJECT-TYPE
       SYNTAX       WanT3E3HistoryEntry
       MAX-ACCESS   not-accessible
       STATUS       current
       DESCRIPTION
              "Statistics for a T3/E3 interface. The near end of the link
               refers to the side of the link that the probe is monitoring.
               The far end is the side the probe is not on."
       INDEX {wanT3E3HistoryIndex, wanT3E3HistorySampleIndex }
::= { wanT3E3HistoryTable 1 }

WanT3E3HistoryEntry ::= SEQUENCE {
       wanT3E3HistoryIndex                 INTEGER (1..65535),
       wanT3E3HistorySampleIndex           INTEGER (1..2147483647),
       wanT3E3HistoryIntervalStart         TimeTicks,
       wanT3E3HistoryDropEvents            Counter64,
       wanT3E3HistoryInFrames              Counter64,
       wanT3E3HistoryOutFrames             Counter64,
       wanT3E3HistoryInOctets              Counter64,
       wanT3E3HistoryOutOctets             Counter64,
       wanT3E3HistoryPESs                  Counter64,
       wanT3E3HistoryPSESs                 Counter64,
       wanT3E3HistoryOOFs                  Counter64,
       wanT3E3HistorySEFSs                 Counter64,
       wanT3E3HistoryUASs                  Counter64,
       wanT3E3HistoryLCVs                  Counter64,
       wanT3E3HistoryPCVs                  Counter64,
       wanT3E3HistoryLESs                  Counter64,
       wanT3E3HistoryCCVs                  Counter64,
       wanT3E3HistoryCESs                  Counter64,
       wanT3E3HistoryCSESs                 Counter64,
       wanT3E3HistoryRAIs                  Counter64,
       wanT3E3HistoryAISs                  Counter64,
       wanT3E3HistoryLOFs                  Counter64,
       wanT3E3HistoryLOSs                  Counter64,
       wanT3E3HistoryInUtilization         INTEGER (0..10000),
       wanT3E3HistoryOutUtilization        INTEGER (0..10000)
}

wanT3E3HistoryIndex OBJECT-TYPE
       SYNTAX       INTEGER (1..65535)
       MAX-ACCESS   not-accessible
       STATUS       current
       DESCRIPTION
              "The history of which this entry is a port.  The history
               identified by a particular value of this index is the same
               history as identified by the same value of historyControlIndex."
::= { wanT3E3HistoryEntry 1 }

wanT3E3HistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases by
               one as each new sample is taken."
::= { wanT3E3HistoryEntry 2 }

wanT3E3HistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample is
               started at that instant.  Note that following this rule may
               require the probe to delay collection the first sample of the
               history, as each sample must be of the same interval.  Also
               note that the sample which is currently being collected is 
               not accessible in this table until the end of its interval."
::= { wanT3E3HistoryEntry 3 } 

wanT3E3HistoryDropEvents OBJECT-TYPE
       SYNTAX       Counter64
       MAX-ACCESS   read-only
       STATUS       current
       DESCRIPTION
              "The change in value of wanT3E3StatsDropEvents during the
               interval."
::= { wanT3E3HistoryEntry 4 }

wanT3E3HistoryInFrames OBJECT-TYPE
       SYNTAX       Counter64
       MAX-ACCESS   read-only
       STATUS       current
       DESCRIPTION
              "The change in value of wanT3E3StatsInFrames during the
               interval."
::= { wanT3E3HistoryEntry 5 }

wanT3E3HistoryOutFrames OBJECT-TYPE
       SYNTAX       Counter64
       MAX-ACCESS   read-only
       STATUS       current
       DESCRIPTION
              "The change in value of wanT3E3StatsOutFrames during the
               interval."
::= { wanT3E3HistoryEntry 6 }

wanT3E3HistoryInOctets OBJECT-TYPE
       SYNTAX       Counter64
       MAX-ACCESS   read-only
       STATUS       current
       DESCRIPTION
              "The change in value of wanT3E3StatsInOctets during the
               interval."
::= { wanT3E3HistoryEntry 7 }

wanT3E3HistoryOutOctets OBJECT-TYPE
       SYNTAX       Counter64
       MAX-ACCESS   read-only
       STATUS       current
       DESCRIPTION
              "The change in value of wanT3E3StatsOutOctets during the
               interval."
::= { wanT3E3HistoryEntry 8 }

wanT3E3HistoryPESs OBJECT-TYPE
       SYNTAX       Counter64
       MAX-ACCESS   read-only
       STATUS       current
       DESCRIPTION
              "The change in value of wanT3E3StatsPESs during the interval."
::= { wanT3E3HistoryEntry 9 }

wanT3E3HistoryPSESs OBJECT-TYPE
       SYNTAX       Counter64
       MAX-ACCESS   read-only
       STATUS       current
       DESCRIPTION
              "The change in value of wanT3E3StatsPSESs during the interval."
::= { wanT3E3HistoryEntry 10 }

wanT3E3HistoryOOFs OBJECT-TYPE
       SYNTAX       Counter64
       MAX-ACCESS   read-only
       STATUS       current
       DESCRIPTION
              "The change in value of wanT3E3StatsOOFs during the interval."
::= { wanT3E3HistoryEntry 11 }

wanT3E3HistorySEFSs OBJECT-TYPE
       SYNTAX       Counter64
       MAX-ACCESS   read-only
       STATUS       current
       DESCRIPTION
              "The change in value of wanT3E3StatsSEFs during the interval."
::= { wanT3E3HistoryEntry 12 }

wanT3E3HistoryUASs OBJECT-TYPE
       SYNTAX       Counter64
       MAX-ACCESS   read-only
       STATUS       current
       DESCRIPTION
              "The change in value of wanT3E3StatsUASs during the interval."
::= { wanT3E3HistoryEntry 13 }

wanT3E3HistoryLCVs OBJECT-TYPE
       SYNTAX       Counter64
       MAX-ACCESS   read-only
       STATUS       current
       DESCRIPTION
              "The change in value of wanT3E3StatsLCVs during the interval."
::= { wanT3E3HistoryEntry 14 }

wanT3E3HistoryPCVs OBJECT-TYPE
       SYNTAX       Counter64
       MAX-ACCESS   read-only
       STATUS       current
       DESCRIPTION
              "The change in value of wanT3E3StatsPCVs during the interval."
::= { wanT3E3HistoryEntry 15 }

wanT3E3HistoryLESs OBJECT-TYPE
       SYNTAX       Counter64
       MAX-ACCESS   read-only
       STATUS       current
       DESCRIPTION
              "The change in value of wanT3E3StatsLESs during the interval."
::= { wanT3E3HistoryEntry 16 }

wanT3E3HistoryCCVs OBJECT-TYPE
       SYNTAX       Counter64
       MAX-ACCESS   read-only
       STATUS       current
       DESCRIPTION
              "The change in value of wanT3E3StatsCCVs during the interval."
::= { wanT3E3HistoryEntry 17 }

wanT3E3HistoryCESs OBJECT-TYPE
       SYNTAX       Counter64
       MAX-ACCESS   read-only
       STATUS       current
       DESCRIPTION
              "The change in value of wanT3E3StatsCESs during the interval."
::= { wanT3E3HistoryEntry 18 }

wanT3E3HistoryCSESs OBJECT-TYPE
       SYNTAX       Counter64
       MAX-ACCESS   read-only
       STATUS       current
       DESCRIPTION
              "The change in value of wanT3E3StatsCSESs during the interval."
::= { wanT3E3HistoryEntry 19 }

wanT3E3HistoryRAIs OBJECT-TYPE
       SYNTAX       Counter64
       MAX-ACCESS   read-only
       STATUS       current
       DESCRIPTION
              "The change in value of wanT3E3StatsRAIs during the interval."
::= { wanT3E3HistoryEntry 20 }

wanT3E3HistoryAISs OBJECT-TYPE
       SYNTAX       Counter64
       MAX-ACCESS   read-only
       STATUS       current
       DESCRIPTION
              "The change in value of wanT3E3StatsAISs during the interval."
::= { wanT3E3HistoryEntry 21 }

wanT3E3HistoryLOFs OBJECT-TYPE
       SYNTAX       Counter64
       MAX-ACCESS   read-only
       STATUS       current
       DESCRIPTION
              "The change in value of wanT3E3StatsLOFs during the interval."
::= { wanT3E3HistoryEntry 22 }

wanT3E3HistoryLOSs OBJECT-TYPE
       SYNTAX       Counter64
       MAX-ACCESS   read-only
       STATUS       current
       DESCRIPTION
              "The change in value of wanT3E3StatsLOSs during the interval."
::= { wanT3E3HistoryEntry 23 }

wanT3E3HistoryInUtilization OBJECT-TYPE
       SYNTAX       INTEGER (0..10000)
       MAX-ACCESS   read-only
       STATUS       current
       DESCRIPTION
              "The best estimated of the mean physical layer network
               utilization of traffic coming from the far end of the link
               in hundreds of a percent."
::= { wanT3E3HistoryEntry 24 }

wanT3E3HistoryOutUtilization OBJECT-TYPE
       SYNTAX       INTEGER (0..10000)
       MAX-ACCESS   read-only
       STATUS       current
       DESCRIPTION
              "The best estimated of the mean physical layer network
               utilization of traffic coming from the near end of the link
               in hundreds of a percent."
::= { wanT3E3HistoryEntry 25 }

wanAtmStatsTable OBJECT-TYPE
       SYNTAX       SEQUENCE OF WanAtmStatsEntry
       MAX-ACCESS   not-accessible
       STATUS       current
       DESCRIPTION
              "ATM signaling statistics."
::= { wanSignalingStats 5 }

wanAtmStatsEntry OBJECT-TYPE
       SYNTAX       WanAtmStatsEntry
       MAX-ACCESS   not-accessible
       STATUS       current
       DESCRIPTION
              "The statistics for an ATM interface. The near end of the link
               refers to the side of the link that the probe is monitoring.
               The far end is the side the probe is not on.  In an ATM network,
               there are many far ends of the link, but they shall be logically
               grouped into one end in this table."
       INDEX { wanAtmStatsIndex }
::= { wanAtmStatsTable 1 }

WanAtmStatsEntry ::= SEQUENCE {
       wanAtmStatsIndex                    INTEGER (1..65535),
       wanAtmStatsDataSource               OBJECT IDENTIFIER,
       wanAtmStatsDropEvents               Counter64,
       wanAtmStatsInCells                  Counter64,
       wanAtmStatsOutCells                 Counter64,
       wanAtmStatsInCLP1                   Counter64,
       wanAtmStatsOutCLP1                  Counter64,
       wanAtmStatsConnectionEvents         Counter64,
       wanAtmStatsErroredPDUs              Counter64,
       wanAtmStatsSetupAttempts            Counter64,
       wanAtmStatsInRoutesUnavailable      Counter64,
       wanAtmStatsOutRoutesUnavailable     Counter64,
       wanAtmStatsInResourcesUnavailable   Counter64,
       wanAtmStatsOutResourcesUnavailable  Counter64,
       wanAtmStatsInUnsuccessfulCalls      Counter64,
       wanAtmStatsOutUnsuccessfulCalls     Counter64,
       wanAtmStatsInIncorrectMsgs          Counter64,
       wanAtmStatsOutIncorrectMsgs         Counter64,
       wanAtmStatsInPartyEvents            Counter64,
       wanAtmStatsOutPartyEvents           Counter64,
       wanAtmStatsInExpiries               Counter64,
       wanAtmStatsOutExpiries              Counter64,
       wanAtmStatsInRestartErrors          Counter64,
       wanAtmStatsOutRestartErrors         Counter64,
       wanAtmStatsInSVCs                   Counter64,
       wanAtmStatsOutSVCs                  Counter64,
       wanAtmStatsInOCDs                   Counter64,
       wanAtmStatsOutOCDs                  Counter64,
       wanAtmStatsInLOCs                   Counter64,
       wanAtmStatsOutLOCs                  Counter64,
       wanAtmStatsInLOFs                   Counter64,
       wanAtmStatsOutLOFs                  Counter64,
       wanAtmStatsInLOPs                   Counter64,
       wanAtmStatsOutLOPs                  Counter64,
       wanAtmStatsInLOSs                   Counter64,
       wanAtmStatsOutLOSs                  Counter64,
       wanAtmStatsOwner                    OwnerString,
       wanAtmStatsStatus                   RowStatus
}

wanAtmStatsIndex OBJECT-TYPE
       SYNTAX       INTEGER (1..65535)
       MAX-ACCESS   not-accessible
       STATUS       current
       DESCRIPTION
              "The value of this object uniquely identifies this wanAtmStatsTable entry."
::= { wanAtmStatsEntry 1 }

wanAtmStatsDataSource OBJECT-TYPE
       SYNTAX       OBJECT IDENTIFIER
       MAX-ACCESS   read-create
       STATUS       current
       DESCRIPTION
              "This object identifies the source of the data that this
               wanAtmStatsEntry analyzes.  This source can be any interface on
               this device.  in order to identify a particular interface, this
               object shall identify the instance of the ifIndex object, defined
               in MIB-II [RFC 1573] for the desired interface.  The ifType value
               associated with the ifIndex can only be atm(37)."
::= { wanAtmStatsEntry 2 }

wanAtmStatsDropEvents OBJECT-TYPE
       SYNTAX       Counter64
       MAX-ACCESS   read-only
       STATUS       current
       DESCRIPTION
              "The total number of events in which frames were dropped by the
               probe due to lack of resources.  Note that this number is not
               necessarily the number of frames dropped; it is just the number
               of times this condition has been detected."
::= { wanAtmStatsEntry 3 }

wanAtmStatsInCells OBJECT-TYPE
       SYNTAX       Counter64
       MAX-ACCESS   read-only
       STATUS       current
       DESCRIPTION
              "The total number of cells seen coming from the far end of the
               link including errored cells."
::= { wanAtmStatsEntry 4 }

wanAtmStatsOutCells OBJECT-TYPE
       SYNTAX       Counter64
       MAX-ACCESS   read-only
       STATUS       current
       DESCRIPTION
              "The total number of cells seen coming from the near end of the
               link including errored cells."
::= { wanAtmStatsEntry 5 }

wanAtmStatsInCLP1 OBJECT-TYPE
       SYNTAX       Counter64
       MAX-ACCESS   read-only
       STATUS       current
       DESCRIPTION
              "The total number of cells with the CLP bit set seen coming from
               the far end of the link."
::= { wanAtmStatsEntry 6 }

wanAtmStatsOutCLP1 OBJECT-TYPE
       SYNTAX       Counter64
       MAX-ACCESS   read-only
       STATUS       current
       DESCRIPTION
              "The total number of cells with the CLP bit set seen coming from
               the near end of the link."
::= { wanAtmStatsEntry 7 }

wanAtmStatsConnectionEvents OBJECT-TYPE
       SYNTAX       Counter64
       MAX-ACCESS   read-only
       STATUS       current
       DESCRIPTION
              "This counter counts the sum of the following errors:
               1) SSCOP Connection Disconnect Counter
                  The abnormal occurrence of this event is characterized by the 
                  expiry of Timer_NO_RESPONSE. (This event is 
                  communicated to the layer management with MAA-ERROR 
                  code P.  See ITU-T Q.2110.)
               2) SSCOP Connection Initiation Failure
                  This condition indicates the inability to establish an SSCOP 
                  connection.  This event occurs whenever the number of 
                  expiries of the connection control timer (Timer_CC) exceeds 
                  the MaxCC or upon receipt of a connection reject message 
                  BGREJ PDU.  (This event is communicated to layer 
                  management with MAA-ERROR code O.  See ITU-T 
                  Q.2110.)
              3) SSCOP Connection Re-Establ/Resynch
                 This event occurs upon receipt of a BGN PDU or RESYNC 
                 PDU."
::= { wanAtmStatsEntry 8 }

wanAtmStatsErroredPDUs OBJECT-TYPE
       SYNTAX       Counter64
       MAX-ACCESS   read-only
       STATUS       current
       DESCRIPTION
              "This counter counts the sum of the following errors:
              1) Invalid PDUs.
                 These are defined in SSCOP and consist of PDUs with 
                 incorrect length (MAA-ERROR code U), undefined PDU type 
                 code or not 32-bit aligned.
              2) PDUs that result in MAA error codes and are discarded
                 See Errors A-M and Q-T defined in ITU-T Q.2110."
::= { wanAtmStatsEntry 9 }

wanAtmStatsSetupAttempts OBJECT-TYPE
       SYNTAX       Counter64
       MAX-ACCESS   read-only
       STATUS       current
       DESCRIPTION
              "This counter counts the number of call setup attempts (both
               successful and unsuccessful) detected on this interface."
::= { wanAtmStatsEntry 10 }

wanAtmStatsInRoutesUnavailable OBJECT-TYPE
       SYNTAX       Counter64
       MAX-ACCESS   read-only
       STATUS       current
       DESCRIPTION
              "This counter is incremented when a RELEASE, RELEASE COMPLETE
               (only when not preceded by a RELEASE mesg for the same call),
               ADD PARTY REJECT, or STATUS message that contains one of the
               following cause code values is received (Note: These cause
               values apply to both UNI3.0 and UNI3.1):
                  Cause Value          Meaning
                  1                   unallocated (unassigned) number
                  2                   no route to specified transit
                                      network
                  3                   no route to destination
                 88                   incompatible destination
              
              NOTE:  For this counter, RELEASE COMPLETE messages that are
              a reply to a previous RELEASE message and contain the same
              cause value, are redundant (for counting purposes) and should
              not be counted."
::= { wanAtmStatsEntry 11 }

wanAtmStatsOutRoutesUnavailable OBJECT-TYPE
       SYNTAX       Counter64
       MAX-ACCESS   read-only
       STATUS       current
       DESCRIPTION
              "This counter is incremented when a RELEASE, RELEASE COMPLETE
               (only when not preceded by a RELEASE mesg for the same call),
               ADD PARTY REJECT, or STATUS message that contains one of the
               following cause code values is transmitted (Note: These cause
               values apply to both UNI3.0 and UNI3.1):
                  Cause Value          Meaning
                  1                   unallocated (unassigned) number
                  2                   no route to specified transit
                                      network
                  3                   no route to destination
              
              NOTE:  For this counter, RELEASE COMPLETE messages that are a
              reply to a previous RELEASE  message and contain the same cause
              value, are redundant(for counting purposes) and should not be
              counted."
::= { wanAtmStatsEntry 12 }

wanAtmStatsInResourcesUnavailable OBJECT-TYPE
       SYNTAX       Counter64
       MAX-ACCESS   read-only
       STATUS       current
       DESCRIPTION
              "This counter is incremented when a RELEASE, RELEASE COMPLETE
               (only when not preceded by a RELEASE mesg for the same call),
               ADD PARTY REJECT, or STATUS message that contains one of the
               following cause code values is received (Note: These cause
               values apply to both UNI3.0 and UNI3.1 unless otherwise
               stated):
                  Cause Value          Meaning
                  35                 requested VPCI/VCI not available
                  37                 user cell rate not available
                                     (UNI3.1 only)
                  38                 network out of order
                  41                 temporary failure
                  45                 no VPCI/VCI available
                  47                 resource unavailable, unspecified
                  49                 Quality of Service unavailable
                  51                 user cell rate not available
                                     (UNI3.0 only)
                  58                 bearer capability not presently
                                     available
                  63                 Service or option not available,
                                     unspecified
                  92                 too many pending add party requests
              
              NOTE:  For this counter, RELEASE COMPLETE messages that are a
              reply to a previous RELEASE message and contain the same cause
              value, are redundant (for counting purposes) and should not be
              counted."
::= { wanAtmStatsEntry 13 }

wanAtmStatsOutResourcesUnavailable OBJECT-TYPE
       SYNTAX       Counter64
       MAX-ACCESS   read-only
       STATUS       current
       DESCRIPTION
              "This counter is incremented when a RELEASE, RELEASE COMPLETE
               (only when not preceded by a RELEASE mesg for the same call),
               ADD PARTY REJECT, or STATUS message that contains one of the
               following cause code values is transmitted (Note: These cause
               values apply to both UNI3.0 and UNI3.1 unless otherwise stated):
                  Cause Value          Meaning
                  35                 requested VPCI/VCI not available
                  37                 user cell rate not available
                                     (UNI3.1 only)
                  38                 network out of order
                  41                 temporary failure
                  45                 no VPCI/VCI available
                  47                 resource unavailable, unspecified
                  49                 Quality of Service unavailable
                  51                 user cell rate not available
                                     (UNI3.0 only)
                  58                 bearer capability not presently
                                     available
                  63                 Service or option not available,
                                     unspecified
                  92                 too many pending add party requests
              
              NOTE:  For this counter, RELEASE COMPLETE messages that are a
              reply to a previous RELEASE message and contain the same cause
              value, are redundant (for counting purposes) and should not be
              counted."
::= { wanAtmStatsEntry 14 }

wanAtmStatsInUnsuccessfulCalls OBJECT-TYPE
       SYNTAX       Counter64
       MAX-ACCESS   read-only
       STATUS       current
       DESCRIPTION       
              "This counter is incremented when a RELEASE, RELEASE COMPLETE
               (only when not preceded by a RELEASE mesg for the same call),
               ADD PARTY REJECT, or STATUS message that contains one of the
               following cause code values is received (Note: These cause
               values apply to both UNI3.0 and UNI3.1):
                  Cause Value         Meaning
                  17                  user busy
                  18                  no user responding
                  21                  call rejected
                  22                  number changed
                  23                  user rejects all calls with
                                      calling line id restriction 
                  27                  destination out of order
                  31                  normal, unspecified
                  88                  incompatible destination
              
              NOTE:  For this counter, RELEASE COMPLETE messages that are a
              reply to a previous RELEASE message and contain the same cause
              value, are redundant (for counting purposes) and should not be
              counted.
              
              Note: Cause Value #30 'response to STATUS ENQUIRY' was not
              included in this memo since it did not apply to a hard failure."
::= { wanAtmStatsEntry 15 }

wanAtmStatsOutUnsuccessfulCalls OBJECT-TYPE
       SYNTAX       Counter64
       MAX-ACCESS   read-only
       STATUS       current
       DESCRIPTION
              "This counter is incremented when a RELEASE, RELEASE COMPLETE
               (only when not preceded by a RELEASE mesg for the same call),
               ADD PARTY REJECT, or STATUS message that contains one of the
               following cause code values is transmitted (Note: These cause
               values apply to both UNI3.0 and UNI3.1):
                  Cause Value         Meaning
                  17                  user busy
                  18                  no user responding
                  21                  call rejected
                  22                  number changed
                  23                  user rejects all calls with
                                      calling line id restriction (CLIR)
                  27                  destination out of order
                  31                  normal, unspecified
                  88                  incompatible destination
              
              NOTE:  For this counter, RELEASE COMPLETE messages that are a
              reply to a previous RELEASE message and contain the same cause
              value, are redundant(for counting purposes) and should not be
              counted.
              
              Note: Cause Value #30 'response to STATUS ENQUIRY' was not
              included in this memo since it did not apply to a hard failure."
::= { wanAtmStatsEntry 16 }

wanAtmStatsInIncorrectMsgs OBJECT-TYPE
       SYNTAX       Counter64
       MAX-ACCESS   read-only
       STATUS       current
       DESCRIPTION
              "The Incorrect Messages Counter reflects any sort of incorrect
              information in a message.  This includes:

              ? RELEASE, RELEASE COMPLETE, ADD PARTY REJECT, and 
                STATUS messages transmitted or received, that contain any of
                the Cause values listed below.
              ? Ignored messages.  These messages are dropped because the
                message was so damaged that it could not be further processed.
                A list of dropped messages is compiled below:
                Message with invalid protocol discriminator
                Message with errors in the call reference I.E.
              ? Bits 5-8 of the first octet not equal to '0000'
              ? Bits 1-4 of the first octet indicating a length other than
                3 octets
              ? RELEASE COMPLETE message received with a call 
                reference that does not relate to a call active or in progress
              ? SETUP message received with call reference flag incorrectly 
                set to 1
              ? SETUP message received with a call reference for a call that is 
                already active or in progress.
                Message too short
              
              The following cause values are monitored by this counter
              (Note: These cause values apply to both UNI3.0 and UNI3.1 unless
              otherwise stated)
                 Cause Value          Meaning
                 10            VPCI/VCI unacceptable (UNI3.0 only)
                 36            VPCI/VCI assignment failure (UNI3.1 only)
                 81            invalid call reference value
                 82            identified channel does not exist
                 89            invalid endpoint reference
                 96            mandatory information element is missing
                 97            message type non-existent or not
                               implemented
                 99            information element non-existent or not
                               implemented
                 100           invalid information element contents
                 101           message not compatible with call state
                 104           incorrect message length
                 111           protocol error, unspecified
              
              NOTE:  For this counter, RELEASE COMPLETE messages that are a
              reply to a previous RELEASE message and contain the same cause
              value, are redundant (for counting purposes) and should not be
              counted."
::= { wanAtmStatsEntry 17 }

wanAtmStatsOutIncorrectMsgs OBJECT-TYPE
       SYNTAX       Counter64
       MAX-ACCESS   read-only
       STATUS       current
       DESCRIPTION
              "The Incorrect Messages Counter reflects any sort of incorrect
               information in a message.  This includes:

              ? RELEASE, RELEASE COMPLETE, ADD PARTY REJECT, and 
                STATUS messages transmitted or received, that contain any of
                the Cause values listed below.
              ? Ignored messages.  These messages are dropped because the
                message was so damaged that it could not be further processed.
                A list of dropped messages is compiled below:
                  Message with invalid protocol discriminator
                  Message with errors in the call reference I.E.
              ? Bits 5-8 of the first octet not equal to '0000'
              ? Bits 1-4 of the first octet indicating a length other than
                3 octets
              ? RELEASE COMPLETE message received with a call reference that
                does not relate to a call active or in progress
              ? SETUP message received with call reference flag incorrectly
                set to 1
              ? SETUP message received with a call reference for a call that is 
                already active or in progress.
                Message too short
              
              The following cause values are monitored by this counter
              Note: These cause values apply to both UNI3.0 and UNI3.1 unless
              otherwise stated)
                 Cause Value     Meaning
                 10            VPCI/VCI unacceptable (UNI3.0 only)
                 36            VPCI/VCI assignment failure (UNI3.1 only)
                 81            invalid call reference value
                 82            identified channel does not exist
                 89            invalid endpoint reference
                 96            mandatory information element is missing
                 97            message type non-existent or not
                               implemented
                 99            information element non-existent or not
                               implemented
                100            invalid information element contents
                101            message not compatible with call state
                104            incorrect message length
                111            protocol error, unspecified
              
              NOTE:  For this counter, RELEASE COMPLETE messages that are
              a reply to a previous RELEASE message and contain the same
              cause value, are redundant (for counting purposes) and should
              not be counted."
::= { wanAtmStatsEntry 18 }

wanAtmStatsInPartyEvents OBJECT-TYPE
       SYNTAX       Counter64
       MAX-ACCESS   read-only
       STATUS       current
       DESCRIPTION
              "This counter monitors error events that occur due to the
               originating user doing something wrong. This counter is
               incremented when a RELEASE, RELEASE COMPLETE (only when not
               preceded by a RELEASE mesg for the same call), ADD PARTY REJECT,
               or STATUS message that contains one of the following cause code
               values is received (Note: These cause values apply to both
               UNI3.0 and UNI3.1):
                  Cause Value          Meaning
                  28            invalid number format (address incomplete)
                  43            access information discarded
                  57            bearer capability not authorized
                  65            bearer capability not implemented
                  73            unsupported combination of traffic
                                parameters
                  78            AAL parameters cannot be supported
                                (UNI3.1 only)
                  91            invalid transit network selection
                  93            AAL parameters cannot be supported
                                (UNI3.0 only)
              
              NOTE:  For this counter, RELEASE COMPLETE messages that are
              a reply to a previous RELEASE message and contain the same cause
              value, are redundant(for counting purposes) and should not be
              counted."
::= { wanAtmStatsEntry 19 }

wanAtmStatsOutPartyEvents OBJECT-TYPE
       SYNTAX       Counter64
       MAX-ACCESS   read-only
       STATUS       current
       DESCRIPTION
              "This counter monitors error events that occur due to the
               originating user doing something wrong. This counter is
               incremented when a RELEASE, RELEASE COMPLETE (only when not
               preceded by a RELEASE mesg for the same call), ADD PARTY
               REJECT, or STATUS message that contains one of the following
               cause code values is transmitted (Note: These cause values
               apply to both UNI3.0 and UNI3.1):
                  Cause Value          Meaning
                  28            invalid number format (address incomplete)
                  43            access information discarded
                  57            bearer capability not authorized
                  65            bearer capability not implemented
                  73            unsupported combination of traffic
                                parameters
                  78            AAL parameters cannot be supported
                                (UNI3.1 only)
                  91            invalid transit network selection
                  93            AAL parameters cannot be supported
                                (UNI3.0 only)
              
              NOTE:  For this counter, RELEASE COMPLETE messages that are
              a reply to a previous RELEASE message and contain the same
              cause value, are redundant (for counting purposes) and should
              not be counted."
::= { wanAtmStatsEntry 20 }

wanAtmStatsInExpiries OBJECT-TYPE
       SYNTAX       Counter64
       MAX-ACCESS   read-only
       STATUS       current
       DESCRIPTION
              "The Timer Expiries Counter provides a count of network timer
               expiries, and to some extent, host or switch timer expiries.
               The conditions for incrementing this counter are:
              ? Expiry of any network timer
              ? Receipt of a RELEASE or RELEASE COMPLETE message with 
                Cause #102, 'recovery on timer expiry'.
              
              NOTE:  For this counter, RELEASE COMPLETE messages that are a
              reply to a previous RELEASE message and contain the same cause
              value, are redundant (for counting purposes) and should not be
              counted."
::= { wanAtmStatsEntry 21 }

wanAtmStatsOutExpiries OBJECT-TYPE
       SYNTAX       Counter64
       MAX-ACCESS   read-only
       STATUS       current
       DESCRIPTION
              "The Timer Expiries Counter provides a count of network timer
               expiries, and to some extent, host or switch timer expiries.
               The conditions for incrementing this counter are:

              ? Expiry of any network timer
              ? Receipt of a RELEASE or RELEASE COMPLETE message with 
                Cause #102, 'recovery on timer expiry'.
              
              NOTE:  For this counter, RELEASE COMPLETE messages that are a
              reply to a previous RELEASE message and contain the same cause
              value, are redundant (for counting purposes) and should not be
              counted."
::= { wanAtmStatsEntry 22 }

wanAtmStatsInRestartErrors OBJECT-TYPE
       SYNTAX       Counter64
       MAX-ACCESS   read-only
       STATUS       current
       DESCRIPTION
              "The Restart Activity Counter provides a count of host, switch,
               or network restart activity. This counter is incremented when
               receiving a RESTART message."
::= { wanAtmStatsEntry 23 }

wanAtmStatsOutRestartErrors OBJECT-TYPE
       SYNTAX       Counter64
       MAX-ACCESS   read-only
       STATUS       current
       DESCRIPTION
              "The Restart Activity Counter provides a count of host, switch,
               or network restart activity. This counter is incremented when
               transmitting a RESTART message."
::= { wanAtmStatsEntry 24 }

wanAtmStatsInSVCs OBJECT-TYPE
       SYNTAX       Counter64
       MAX-ACCESS   read-only
       STATUS       current
       DESCRIPTION
              "SVC VCCs established at this signaling entity for incoming
               connections."
::= { wanAtmStatsEntry 25 }

wanAtmStatsOutSVCs OBJECT-TYPE
       SYNTAX       Counter64
       MAX-ACCESS   read-only
       STATUS       current
       DESCRIPTION
              "SVC VCCs established at this signaling entity for outgoing
               connections."
::= { wanAtmStatsEntry 26 }

wanAtmStatsInOCDs OBJECT-TYPE
       SYNTAX       Counter64
       MAX-ACCESS   read-only
       STATUS       current
       DESCRIPTION
              "An out of cell delineation from far end of the link."
::= { wanAtmStatsEntry 27 }

wanAtmStatsOutOCDs OBJECT-TYPE
       SYNTAX       Counter64
       MAX-ACCESS   read-only
       STATUS       current
       DESCRIPTION
              "An out of cell delineation from near end of the link."
::= { wanAtmStatsEntry 28 }

wanAtmStatsInLOCs OBJECT-TYPE
       SYNTAX       Counter64
       MAX-ACCESS   read-only
       STATUS       current
       DESCRIPTION
              "A loss of cell delineation error from far end of the link.
               This is a persistent OCD condition."
::= { wanAtmStatsEntry 29 }

wanAtmStatsOutLOCs OBJECT-TYPE
       SYNTAX       Counter64
       MAX-ACCESS   read-only
       STATUS       current
       DESCRIPTION
              "A loss of cell delineation error from near end of link.
               This is a persistent OCD condition."
::= { wanAtmStatsEntry 30 }

wanAtmStatsInLOFs OBJECT-TYPE
       SYNTAX       Counter64
       MAX-ACCESS   read-only
       STATUS       current
       DESCRIPTION
              "A loss of frame error from far end of link."
::= { wanAtmStatsEntry 31 }

wanAtmStatsOutLOFs OBJECT-TYPE
       SYNTAX       Counter64
       MAX-ACCESS   read-only
       STATUS       current
       DESCRIPTION
              "A loss of frame error from near end of link."
::= { wanAtmStatsEntry 32 }

wanAtmStatsInLOPs OBJECT-TYPE
       SYNTAX       Counter64
       MAX-ACCESS   read-only
       STATUS       current
       DESCRIPTION
              "A loss of pointer error from far end of link."
::= { wanAtmStatsEntry 33 }

wanAtmStatsOutLOPs OBJECT-TYPE
       SYNTAX       Counter64
       MAX-ACCESS   read-only
       STATUS       current
       DESCRIPTION
              "A loss of pointer error from near end of link."
::= { wanAtmStatsEntry 34 }

wanAtmStatsInLOSs OBJECT-TYPE
       SYNTAX       Counter64
       MAX-ACCESS   read-only
       STATUS       current
       DESCRIPTION
              "A loss of signal error from far end of link."
::= { wanAtmStatsEntry 35 }

wanAtmStatsOutLOSs OBJECT-TYPE
       SYNTAX       Counter64
       MAX-ACCESS   read-only
       STATUS       current
       DESCRIPTION
              "A loss of signal error from near end of link."
::= { wanAtmStatsEntry 36 }

wanAtmStatsOwner OBJECT-TYPE
       SYNTAX       OwnerString
       MAX-ACCESS   read-create
       STATUS       current
       DESCRIPTION
              "The entity that configured this entry."
::= { wanAtmStatsEntry 37 }

wanAtmStatsStatus OBJECT-TYPE
       SYNTAX       RowStatus
--     MAX-ACCESS   read-write
       MAX-ACCESS   read-create
       STATUS       current
       DESCRIPTION
              "The status of this wanAtmStatsTable entry."
::= { wanAtmStatsEntry 38 }

wanAtmHistoryTable OBJECT-TYPE
       SYNTAX       SEQUENCE OF WanAtmHistoryEntry
       MAX-ACCESS   not-accessible
       STATUS       current
       DESCRIPTION
              "ATM signaling statistics."
::= { wanSignalingHistory 5 }

wanAtmHistoryEntry OBJECT-TYPE
       SYNTAX       WanAtmHistoryEntry
       MAX-ACCESS   not-accessible
       STATUS       current
       DESCRIPTION
              "The statistics for an ATM interface. The near end of the link
               refers to the side of the link that the probe is monitoring.
               The far end is the side the probe is not on.  In an ATM network,
               there are many far ends of the link, but they shall be logically
               grouped into one end in this table."
       INDEX { wanAtmHistoryIndex, wanAtmHistorySampleIndex }
::= { wanAtmHistoryTable 1 }


WanAtmHistoryEntry ::= SEQUENCE {
       wanAtmHistoryIndex                   INTEGER (1..65535),
       wanAtmHistorySampleIndex             INTEGER (1..2147483647),
       wanAtmHistoryIntervalStart           TimeTicks,
       wanAtmHistoryDropEvents              Counter64,
       wanAtmHistoryInCells                 Counter64,
       wanAtmHistoryOutCells                Counter64,
       wanAtmHistoryInCLP1                  Counter64,
       wanAtmHistoryOutCLP1                 Counter64,
       wanAtmHistoryConnectionEvents        Counter64,
       wanAtmHistoryErroredPDUs             Counter64,
       wanAtmHistorySetupAttempts           Counter64,
       wanAtmHistoryInRoutesUnavailable     Counter64,
       wanAtmHistoryOutRoutesUnavailable    Counter64,
       wanAtmHistoryInResourcesUnavailable  Counter64,
       wanAtmHistoryOutResourcesUnavailable Counter64,
       wanAtmHistoryInUnsuccessfulCalls     Counter64, 
       wanAtmHistoryOutUnsuccessfulCalls    Counter64,
       wanAtmHistoryInIncorrectMsgs         Counter64,
       wanAtmHistoryOutIncorrectMsgs        Counter64,
       wanAtmHistoryInPartyEvents           Counter64,
       wanAtmHistoryOutPartyEvents          Counter64,
       wanAtmHistoryInExpiries              Counter64,
       wanAtmHistoryOutExpiries             Counter64,
       wanAtmHistoryInRestartErrors         Counter64,
       wanAtmHistoryOutRestartErrors        Counter64,
       wanAtmHistoryInSVCs                  Counter64,
       wanAtmHistoryOutSVCs                 Counter64,
       wanAtmHistoryInOCDs                  Counter64,
       wanAtmHistoryOutOCDs                 Counter64,
       wanAtmHistoryInLOCs                  Counter64,
       wanAtmHistoryOutLOCs                 Counter64,
       wanAtmHistoryInLOFs                  Counter64,
       wanAtmHistoryOutLOFs                 Counter64,
       wanAtmHistoryInLOPs                  Counter64,
       wanAtmHistoryOutLOPs                 Counter64,
       wanAtmHistoryInLOSs                  Counter64,
       wanAtmHistoryOutLOSs                 Counter64,
       wanAtmHistoryInUtilization           INTEGER (0..10000),
       wanAtmHistoryOutUtilization          INTEGER (0..10000)
}

wanAtmHistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanAtmHistoryEntry 1 }

wanAtmHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases
               by one as each new sample is taken."
::= { wanAtmHistoryEntry 2 }

wanAtmHistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample is 
               started at that instant.  Note that following this rule may 
               require the probe to delay collection the first sample of the
               history, as each sample must be of the same interval.  Also
               note that the sample which is currently being collected is not
               accessible in this table until the end of its interval."
::= { wanAtmHistoryEntry 3 } 

wanAtmHistoryDropEvents OBJECT-TYPE
       SYNTAX       Counter64
       MAX-ACCESS   read-only
       STATUS       current
       DESCRIPTION
              "The change in value of wanAtmStatsDropEvents during the
               interval."
::= { wanAtmHistoryEntry 4 }

wanAtmHistoryInCells OBJECT-TYPE
       SYNTAX       Counter64
       MAX-ACCESS   read-only
       STATUS       current
       DESCRIPTION
              "The change in value of wanAtmStatsInCells during the
               interval."
::= { wanAtmHistoryEntry 5 }

wanAtmHistoryOutCells OBJECT-TYPE
       SYNTAX       Counter64
       MAX-ACCESS   read-only
       STATUS       current
       DESCRIPTION
              "The change in value of wanAtmStatsOutCells during the
               interval."
::= { wanAtmHistoryEntry 6 }

wanAtmHistoryInCLP1 OBJECT-TYPE
       SYNTAX       Counter64
       MAX-ACCESS   read-only
       STATUS       current
       DESCRIPTION
              "The change in value of wanAtmStatsInCLP1 during the
               interval."
::= { wanAtmHistoryEntry 7 }

wanAtmHistoryOutCLP1 OBJECT-TYPE
       SYNTAX       Counter64
       MAX-ACCESS   read-only
       STATUS       current
       DESCRIPTION
              "The change in value of wanAtmStatsOutCLP1 during the
               interval."
::= { wanAtmHistoryEntry 8 }

wanAtmHistoryConnectionEvents OBJECT-TYPE
       SYNTAX       Counter64
       MAX-ACCESS   read-only
       STATUS       current
       DESCRIPTION
              "The change in value of wanAtmStatsConnectionEvents during the
               interval."
::= { wanAtmHistoryEntry 9 }

wanAtmHistoryErroredPDUs OBJECT-TYPE
       SYNTAX       Counter64
       MAX-ACCESS   read-only
       STATUS       current
       DESCRIPTION
              "The change in value of wanAtmStatsErroredPDUs during the
               interval."
::= { wanAtmHistoryEntry 10 }

wanAtmHistorySetupAttempts OBJECT-TYPE
       SYNTAX       Counter64
       MAX-ACCESS   read-only
       STATUS       current
       DESCRIPTION
              "The change in value of wanAtmStatsSetupAttempts during the
               interval."
::= { wanAtmHistoryEntry 11 }

wanAtmHistoryInRoutesUnavailable OBJECT-TYPE
       SYNTAX       Counter64
       MAX-ACCESS   read-only
       STATUS       current
       DESCRIPTION
              "The change in value of wanAtmStatsInRoutesUnavailable
               during the interval."
::= { wanAtmHistoryEntry 12 }

wanAtmHistoryOutRoutesUnavailable OBJECT-TYPE
       SYNTAX       Counter64
       MAX-ACCESS   read-only
       STATUS       current
       DESCRIPTION
              "The change in value of wanAtmStatsOutRoutesUnavailable
               during the interval."
::= { wanAtmHistoryEntry 13 }

wanAtmHistoryInResourcesUnavailable OBJECT-TYPE
       SYNTAX       Counter64
       MAX-ACCESS   read-only
       STATUS       current
       DESCRIPTION
              "The change in value of wanAtmStatsInResourcesUnavailable
               during the interval."
::= { wanAtmHistoryEntry 14 }

wanAtmHistoryOutResourcesUnavailable OBJECT-TYPE
       SYNTAX       Counter64
       MAX-ACCESS   read-only
       STATUS       current
       DESCRIPTION
              "The change in value of wanAtmStatsOutResourcesUnavailable
               during the interval."
::= { wanAtmHistoryEntry 15 }

wanAtmHistoryInUnsuccessfulCalls OBJECT-TYPE
       SYNTAX       Counter64
       MAX-ACCESS   read-only
       STATUS       current
       DESCRIPTION
              "The change in value of wanAtmStatsInUnsuccessfulCalls
               during the interval."
::= { wanAtmHistoryEntry 16 }

wanAtmHistoryOutUnsuccessfulCalls OBJECT-TYPE
       SYNTAX       Counter64
       MAX-ACCESS   read-only
       STATUS       current
       DESCRIPTION
              "The change in value of wanAtmStatsOutUnsuccessfulCalls
               during the interval."
::= { wanAtmHistoryEntry 17 }

wanAtmHistoryInIncorrectMsgs OBJECT-TYPE
       SYNTAX       Counter64
       MAX-ACCESS   read-only
       STATUS       current
       DESCRIPTION
              "The change in value of wanAtmStatsInIncorrectMsgs
               during the interval."
::= { wanAtmHistoryEntry 18 }
              
wanAtmHistoryOutIncorrectMsgs OBJECT-TYPE
       SYNTAX       Counter64
       MAX-ACCESS   read-only
       STATUS       current
       DESCRIPTION
              "The change in value of wanAtmStatsOutIncorrectMsgs
               during the interval."
::= { wanAtmHistoryEntry 19 }

wanAtmHistoryInPartyEvents OBJECT-TYPE
       SYNTAX       Counter64
       MAX-ACCESS   read-only
       STATUS       current
       DESCRIPTION
              "The change in value of wanAtmStatsInPartyEvents
               during the interval."
::= { wanAtmHistoryEntry 20 }

wanAtmHistoryOutPartyEvents OBJECT-TYPE
       SYNTAX       Counter64
       MAX-ACCESS   read-only
       STATUS       current
       DESCRIPTION
              "The change in value of wanAtmStatsOutPartyEvents
               during the interval."
::= { wanAtmHistoryEntry 21 }

wanAtmHistoryInExpiries OBJECT-TYPE
       SYNTAX       Counter64
       MAX-ACCESS   read-only
       STATUS       current
       DESCRIPTION
              "The change in value of wanAtmStatsInExpiries
               during the interval."
::= { wanAtmHistoryEntry 22 }

wanAtmHistoryOutExpiries OBJECT-TYPE
       SYNTAX       Counter64
       MAX-ACCESS   read-only
       STATUS       current
       DESCRIPTION
              "The change in value of wanAtmStatsOutExpiries
               during the interval."
::= { wanAtmHistoryEntry 23 }

wanAtmHistoryInRestartErrors OBJECT-TYPE
       SYNTAX       Counter64
       MAX-ACCESS   read-only
       STATUS       current
       DESCRIPTION
              "The change in value of wanAtmStatsInRestartErrors
               during the interval."
::= { wanAtmHistoryEntry 24 }

wanAtmHistoryOutRestartErrors OBJECT-TYPE
       SYNTAX       Counter64
       MAX-ACCESS   read-only
       STATUS       current
       DESCRIPTION
              "The change in value of wanAtmStatsOutRestartErrors
               during the interval."
::= { wanAtmHistoryEntry 25 }

wanAtmHistoryInSVCs OBJECT-TYPE
       SYNTAX       Counter64
       MAX-ACCESS   read-only
       STATUS       current
       DESCRIPTION
              "The change in value of wanAtmStatsInSVCs during the
               interval."
::= { wanAtmHistoryEntry 26 }

wanAtmHistoryOutSVCs OBJECT-TYPE
       SYNTAX       Counter64
       MAX-ACCESS   read-only
       STATUS       current
       DESCRIPTION
              "The change in value of wanAtmStatsOutSVCs during the
               interval."
::= { wanAtmHistoryEntry 27 }

wanAtmHistoryInOCDs OBJECT-TYPE
       SYNTAX       Counter64
       MAX-ACCESS   read-only
       STATUS       current
       DESCRIPTION
              "The change in value of wanAtmStatsInOCDs during the
               interval."
::= { wanAtmHistoryEntry 28 }

wanAtmHistoryOutOCDs OBJECT-TYPE
       SYNTAX       Counter64
       MAX-ACCESS   read-only
       STATUS       current
       DESCRIPTION
              "The change in value of wanAtmStatsOutOCDs during the
               interval."
::= { wanAtmHistoryEntry 29 }

wanAtmHistoryInLOCs OBJECT-TYPE
       SYNTAX       Counter64
       MAX-ACCESS   read-only
       STATUS       current
       DESCRIPTION
              "The change in value of wanAtmStatsInLOCs during the
               interval."
::= { wanAtmHistoryEntry 30 }

wanAtmHistoryOutLOCs OBJECT-TYPE
       SYNTAX       Counter64
       MAX-ACCESS   read-only
       STATUS       current
       DESCRIPTION
              "The change in value of wanAtmStatsOutLOCs during the
               interval."
::= { wanAtmHistoryEntry 31 }

wanAtmHistoryInLOFs OBJECT-TYPE
       SYNTAX       Counter64
       MAX-ACCESS   read-only
       STATUS       current
       DESCRIPTION
              "The change in value of wanAtmStatsInLOFs during the
               interval."
::= { wanAtmHistoryEntry 32 }

wanAtmHistoryOutLOFs OBJECT-TYPE
       SYNTAX       Counter64
       MAX-ACCESS   read-only
       STATUS       current
       DESCRIPTION
              "The change in value of wanAtmStatsOutLOFs during the
               interval."
::= { wanAtmHistoryEntry 33 }

wanAtmHistoryInLOPs OBJECT-TYPE
       SYNTAX       Counter64
       MAX-ACCESS   read-only
       STATUS       current
       DESCRIPTION
              "The change in value of wanAtmStatsInLOPs during the
               interval."
::= { wanAtmHistoryEntry 34 }

wanAtmHistoryOutLOPs OBJECT-TYPE
       SYNTAX       Counter64
       MAX-ACCESS   read-only
       STATUS       current
       DESCRIPTION
              "The change in value of wanAtmStatsOutLOPs during the
               interval."
::= { wanAtmHistoryEntry 35 }

wanAtmHistoryInLOSs OBJECT-TYPE
       SYNTAX       Counter64
       MAX-ACCESS   read-only
       STATUS       current
       DESCRIPTION
              "The change in value of wanAtmStatsInLOSs during the
               interval."
::= { wanAtmHistoryEntry 36 }

wanAtmHistoryOutLOSs OBJECT-TYPE
       SYNTAX       Counter64
       MAX-ACCESS   read-only
       STATUS       current
       DESCRIPTION
              "The change in value of wanAtmStatsOutLOSs during the
               interval."
::= { wanAtmHistoryEntry 37 }

wanAtmHistoryInUtilization OBJECT-TYPE
       SYNTAX       INTEGER (0..10000)
       MAX-ACCESS   read-only
       STATUS       current
       DESCRIPTION
              "The best estimated of the mean physical layer network
               utilization of traffic coming from the far end of the link
               in hundreds of a percent."
::= { wanAtmHistoryEntry 38 }

wanAtmHistoryOutUtilization OBJECT-TYPE
       SYNTAX       INTEGER (0..10000)
       MAX-ACCESS   read-only
       STATUS       current
       DESCRIPTION
              "The best estimated of the mean physical layer network
               utilization of traffic coming from the near end of the
               link in hundreds of a percent."
::= { wanAtmHistoryEntry 39 }

wanX25StatsTable OBJECT-TYPE
       SYNTAX       SEQUENCE OF WanX25StatsEntry
       MAX-ACCESS   not-accessible
       STATUS       current
       DESCRIPTION
              "X.25 Packet layer statistics."
::= { wanProtocolStats 1 }

wanX25StatsEntry OBJECT-TYPE
       SYNTAX       WanX25StatsEntry
       MAX-ACCESS   not-accessible
       STATUS       current
       DESCRIPTION
              "The statistics for an X.25 interface across all LCIs. The near
               end of the link refers to the side of the link that the probe is
               monitoring.  The far end is the side the probe is not on.  In an
               X.25 network, there are many far ends of the link, but they
               shall be logically grouped into one end in this table."
       INDEX { wanX25StatsIndex }
::= { wanX25StatsTable 1 }

WanX25StatsEntry ::= SEQUENCE {
       wanX25StatsIndex                    INTEGER (1..65535),
       wanX25StatsDataSource               OBJECT IDENTIFIER,
       wanX25StatsDropEvents               Counter64,
       wanX25StatsInFrames                 Counter64,
       wanX25StatsOutFrames                Counter64,
       wanX25StatsInOctets                 Counter64,
       wanX25StatsOutOctets                Counter64,
       wanX25StatsInRejects                Counter64,
       wanX25StatsOutRejects               Counter64,
       wanX25StatsInAttempts               Counter64,
       wanX25StatsOutAttempts              Counter64,
       wanX25StatsInFailures               Counter64,
       wanX25StatsOutFailures              Counter64, 
       wanX25StatsProviderClears           Counter64,
       wanX25StatsInResets                 Counter64,
       wanX25StatsOutResets                Counter64,
       wanX25StatsProviderResets           Counter64,
       wanX25StatsInAccusedErrors          Counter64,
       wanX25StatsOutAccusedErrors         Counter64,
       wanX25StatsInInterrupts             Counter64,
       wanX25StatsOutInterrupts            Counter64,
       wanX25StatsOwner                    OwnerString,
       wanX25StatsStatus                   RowStatus
}

wanX25StatsIndex OBJECT-TYPE
       SYNTAX       INTEGER (1..65535)
       MAX-ACCESS   not-accessible
       STATUS       current
       DESCRIPTION
              "The value of this object uniquely identifies this wanX25StatsTable entry."
::= { wanX25StatsEntry 1 }

wanX25StatsDataSource OBJECT-TYPE
       SYNTAX       OBJECT IDENTIFIER
       MAX-ACCESS   read-create
       STATUS       current
       DESCRIPTION
              "This object identifies the source of the data that this
               wanX25StatsEntry analyzes.  This source can be any interface
               on this device.  In order to identify a particular interface,
               this object shall identify the instance of the ifIndex object,
               defined in MIB-II [RFC 1573] for the desired interface.  The
               ifType value associated with the ifIndex can only be
               rfc887-x25(5)."
::= { wanX25StatsEntry 2 }

wanX25StatsDropEvents OBJECT-TYPE
       SYNTAX       Counter64
       MAX-ACCESS   read-only
       STATUS       current
       DESCRIPTION
              "The total number of events in which frames were dropped by
               the probe due to lack of resources.  Note that this number is
               not necessarily the number of frames dropped; it is just the
               number of times this condition has been detected."
::= { wanX25StatsEntry 3 }

wanX25StatsInFrames OBJECT-TYPE
       SYNTAX       Counter64
       MAX-ACCESS   read-only
       STATUS       current
       DESCRIPTION
              "The total number of frames seen coming from the far end of
               the link including error packets."
::= { wanX25StatsEntry 4 }

wanX25StatsOutFrames OBJECT-TYPE
       SYNTAX       Counter64
       MAX-ACCESS   read-only
       STATUS       current
       DESCRIPTION
              "The total number of frames seen coming from the near end of
               the link including error packets."
::= { wanX25StatsEntry 5 }

wanX25StatsInOctets OBJECT-TYPE
       SYNTAX       Counter64
       MAX-ACCESS   read-only
       STATUS       current
       DESCRIPTION
              "The sum of octets from all frames seen originating from the
               far end of the link including errored frames."
::= { wanX25StatsEntry 6 }

wanX25StatsOutOctets OBJECT-TYPE
       SYNTAX       Counter64
       MAX-ACCESS   read-only
       STATUS       current
       DESCRIPTION
              "The sum of octets from all frames seen originating from the
               near end of the link including errored frames."
::= { wanX25StatsEntry 7 }

wanX25StatsInRejects OBJECT-TYPE
       SYNTAX       Counter64
       MAX-ACCESS   read-only
       STATUS       current
       DESCRIPTION
              "The number of REJ or SREJ frames see coming from the far end
               of the link."
::= { wanX25StatsEntry 8 }

wanX25StatsOutRejects OBJECT-TYPE
       SYNTAX       Counter64
       MAX-ACCESS   read-only
       STATUS       current
       DESCRIPTION
              "The number of REJ or SREJ frames see coming from the near end
               of the link."
::= { wanX25StatsEntry 9 }

wanX25StatsInAttempts OBJECT-TYPE
       SYNTAX       Counter64
       MAX-ACCESS   read-only
       STATUS       current
       DESCRIPTION
              "The number of call setup attempts initiated from the far end
               of the link."
::= { wanX25StatsEntry 10 }

wanX25StatsOutAttempts OBJECT-TYPE
       SYNTAX       Counter64
       MAX-ACCESS   read-only
       STATUS       current
       DESCRIPTION
              "The number of call setup attempts initiated from the near end
               of the link."
::= { wanX25StatsEntry 11 }

wanX25StatsInFailures OBJECT-TYPE
       SYNTAX       Counter64
       MAX-ACCESS   read-only
       STATUS       current
       DESCRIPTION
              "The number call setup attempt failures seen coming from the
               far end of the link."
::= { wanX25StatsEntry 12 }

wanX25StatsOutFailures OBJECT-TYPE
       SYNTAX       Counter64
       MAX-ACCESS   read-only
       STATUS       current
       DESCRIPTION
              "The number call setup attempt failures seen coming from the
               near end of the link."
::= { wanX25StatsEntry 13 }

wanX25StatsProviderClears OBJECT-TYPE
       SYNTAX       Counter64
       MAX-ACCESS   read-only
       STATUS       current
       DESCRIPTION
              "The number of clear request seen with a cause code other than DTE
              initiated."
::= { wanX25StatsEntry 14 }

wanX25StatsInResets OBJECT-TYPE
       SYNTAX       Counter64
       MAX-ACCESS   read-only
       STATUS       current
       DESCRIPTION
              "The number of reset requests seen from the far end of the link
               with cause code DTE initiated."
::= { wanX25StatsEntry 15 }

wanX25StatsOutResets OBJECT-TYPE
       SYNTAX       Counter64
       MAX-ACCESS   read-only
       STATUS       current
       DESCRIPTION
              "The number of reset requests seen from the near end of the link
               with cause code DTE initiated."
::= { wanX25StatsEntry 16 }

wanX25StatsProviderResets OBJECT-TYPE
       SYNTAX       Counter64
       MAX-ACCESS   read-only
       STATUS       current
       DESCRIPTION
              "The number of reset requests seen with cause code other than DTE
              initiated."
::= { wanX25StatsEntry 17 }

wanX25StatsInAccusedErrors OBJECT-TYPE
       SYNTAX       Counter64
       MAX-ACCESS   read-only
       STATUS       current
       DESCRIPTION
              "The numbers of packets seen from the far end of the link
               containing a procedure error cause code.  These include clear,
               reset, restart, or diagnostic packets."
::= { wanX25StatsEntry 18 }

wanX25StatsOutAccusedErrors OBJECT-TYPE
       SYNTAX       Counter64
       MAX-ACCESS   read-only
       STATUS       current
       DESCRIPTION
              "The numbers of packets seen from the near end of the link
               containing a procedure error cause code.  These include clear,
               reset, restart, or diagnostic packets."
::= { wanX25StatsEntry 19 }

wanX25StatsInInterrupts OBJECT-TYPE
       SYNTAX       Counter64
       MAX-ACCESS   read-only
       STATUS       current
       DESCRIPTION
              "The number of interrupts packets seen coming from the far end
               of the link over all VCs."
::= { wanX25StatsEntry 20 }

wanX25StatsOutInterrupts OBJECT-TYPE
       SYNTAX       Counter64
       MAX-ACCESS   read-only
       STATUS       current
       DESCRIPTION
              "The number of interrupts packets seen coming from the near end
               of the link over all VCs."
::= { wanX25StatsEntry 21 }

wanX25StatsOwner OBJECT-TYPE
       SYNTAX       OwnerString
       MAX-ACCESS   read-create
       STATUS       current
       DESCRIPTION
              "The entity that configured this entry."
::= { wanX25StatsEntry 22 }

wanX25StatsStatus OBJECT-TYPE
       SYNTAX       RowStatus
--     MAX-ACCESS   read-write
       MAX-ACCESS   read-create
       STATUS       current
       DESCRIPTION
              "The status of this wanX25StatsTable entry."
::= { wanX25StatsEntry 23 }

wanX25HistoryTable OBJECT-TYPE
       SYNTAX       SEQUENCE OF WanX25HistoryEntry
       MAX-ACCESS   not-accessible
       STATUS       current
       DESCRIPTION
              "X.25 Packet layer statistics."
::= { wanProtocolHistory 1 }

wanX25HistoryEntry OBJECT-TYPE
       SYNTAX       WanX25HistoryEntry
       MAX-ACCESS   not-accessible
       STATUS       current
       DESCRIPTION
              "The statistics for an X.25 interface across all LCIs. The near
               end of the link refers to the side of the link that the probe
               is monitoring.  The far end is the side the probe is not on.
               In a X.25 network, there are many far ends of the link, but
               they shall be logically grouped into one end in this table."
       INDEX { wanX25HistoryIndex, wanX25HistorySampleIndex }
::= { wanX25HistoryTable 1 }

WanX25HistoryEntry ::= SEQUENCE {
       wanX25HistoryIndex                  INTEGER(1..65535),
       wanX25HistorySampleIndex            INTEGER (1..2147483647),
       wanX25HistoryIntervalStart          TimeTicks,
       wanX25HistoryDropEvents             Counter64,
       wanX25HistoryInFrames               Counter64,
       wanX25HistoryOutFrames              Counter64,
       wanX25HistoryInOctets               Counter64,
       wanX25HistoryOutOctets              Counter64,
       wanX25HistoryInRejects              Counter64,
       wanX25HistoryOutRejects             Counter64,
       wanX25HistoryInAttempts             Counter64,
       wanX25HistoryOutAttempts            Counter64,
       wanX25HistoryInFailures             Counter64,
       wanX25HistoryOutFailures            Counter64,
       wanX25HistoryProviderClears         Counter64,
       wanX25HistoryInResets               Counter64,
       wanX25HistoryOutResets              Counter64,
       wanX25HistoryProviderResets         Counter64,
       wanX25HistoryInAccusedErrors        Counter64,
       wanX25HistoryOutAccusedErrors       Counter64,
       wanX25HistoryInInterrupts           Counter64,
       wanX25HistoryOutInterrupts          Counter64,
       wanX25HistoryInUtilization          INTEGER (0..10000),
       wanX25HistoryOutUtilization         INTEGER (0..10000)
}

wanX25HistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanX25HistoryEntry 1 }

wanX25HistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases
               by one as each new sample is taken."
::= { wanX25HistoryEntry 2 }

wanX25HistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample is
               started at that instant.  Note that following this rule may
               require the probe to delay collection the first sample of the
               history, as each sample must be of the same interval.  Also
               note that the sample which is currently being collected is not
               accessible in this table until the end of its interval."
::= { wanX25HistoryEntry 3 } 

wanX25HistoryDropEvents OBJECT-TYPE
       SYNTAX       Counter64
       MAX-ACCESS   read-only
       STATUS       current
       DESCRIPTION
              "The change in value of wanX25StatsDropEvents during the
               interval."
::= { wanX25HistoryEntry 4  }

wanX25HistoryInFrames OBJECT-TYPE
       SYNTAX       Counter64
       MAX-ACCESS   read-only
       STATUS       current
       DESCRIPTION
              "The change in value of wanX25StatsInFrames during the
               interval."
::= { wanX25HistoryEntry 5 }

wanX25HistoryOutFrames OBJECT-TYPE
       SYNTAX       Counter64
       MAX-ACCESS   read-only
       STATUS       current
       DESCRIPTION
              "The change in value of wanX25StatsOutFrames during the
               interval."
::= { wanX25HistoryEntry 6 }

wanX25HistoryInOctets OBJECT-TYPE
       SYNTAX       Counter64
       MAX-ACCESS   read-only
       STATUS       current
       DESCRIPTION
              "The change in value of wanX25StatsInOctets during the
               interval."
::= { wanX25HistoryEntry 7 }

wanX25HistoryOutOctets OBJECT-TYPE
       SYNTAX       Counter64
       MAX-ACCESS   read-only
       STATUS       current
       DESCRIPTION
              "The change in value of wanX25StatsOutOctets during the
               interval."
::= { wanX25HistoryEntry 8 }

wanX25HistoryInRejects OBJECT-TYPE
       SYNTAX       Counter64
       MAX-ACCESS   read-only
       STATUS       current
       DESCRIPTION
              "The change in value of wanX25StatsInRejects during the
               interval."
::= { wanX25HistoryEntry 9 }

wanX25HistoryOutRejects OBJECT-TYPE
       SYNTAX       Counter64
       MAX-ACCESS   read-only
       STATUS       current
       DESCRIPTION
              "The change in value of wanX25StatsOutRejects during the
               interval."
::= { wanX25HistoryEntry 10 }

wanX25HistoryInAttempts OBJECT-TYPE
       SYNTAX       Counter64
       MAX-ACCESS   read-only
       STATUS       current
       DESCRIPTION
              "The change in value of wanX25StatsInAttempts during the
               interval."
::= { wanX25HistoryEntry 11 }

wanX25HistoryOutAttempts OBJECT-TYPE
       SYNTAX       Counter64
       MAX-ACCESS   read-only
       STATUS       current
       DESCRIPTION
              "The change in value of wanX25StatsOutAttempts during the
               interval."
::= { wanX25HistoryEntry 12 }

wanX25HistoryInFailures OBJECT-TYPE
       SYNTAX       Counter64
       MAX-ACCESS   read-only
       STATUS       current
       DESCRIPTION
              "The change in value of wanX25StatsInFailures during the
               interval."
::= { wanX25HistoryEntry 13 }

wanX25HistoryOutFailures OBJECT-TYPE
       SYNTAX       Counter64
       MAX-ACCESS   read-only
       STATUS       current
       DESCRIPTION
              "The change in value of wanX25StatsOutFailures during the
               interval."
::= { wanX25HistoryEntry 14 }

wanX25HistoryProviderClears OBJECT-TYPE
       SYNTAX       Counter64
       MAX-ACCESS   read-only
       STATUS       current
       DESCRIPTION
              "The change in value of wanX25StatsProviderClears during the
               interval."
::= { wanX25HistoryEntry 15 }

wanX25HistoryInResets OBJECT-TYPE
       SYNTAX       Counter64
       MAX-ACCESS   read-only
       STATUS       current
       DESCRIPTION
              "The change in value of wanX25StatsInResets during the
               interval."
::= { wanX25HistoryEntry 16 }

wanX25HistoryOutResets OBJECT-TYPE
       SYNTAX       Counter64
       MAX-ACCESS   read-only
       STATUS       current
       DESCRIPTION
              "The change in value of wanX25StatsOutResets during the
               interval."
::= { wanX25HistoryEntry 17 }

wanX25HistoryProviderResets OBJECT-TYPE
       SYNTAX       Counter64
       MAX-ACCESS   read-only
       STATUS       current
       DESCRIPTION
              "The change in value of wanX25StatsProviderResets during the
               interval."
::= { wanX25HistoryEntry 18 }

wanX25HistoryInAccusedErrors OBJECT-TYPE
       SYNTAX       Counter64
       MAX-ACCESS   read-only
       STATUS       current
       DESCRIPTION
              "The change in value of wanX25StatsInAccusedErrors during the
               interval."
::= { wanX25HistoryEntry 19 }

wanX25HistoryOutAccusedErrors OBJECT-TYPE
       SYNTAX       Counter64
       MAX-ACCESS   read-only
       STATUS       current
       DESCRIPTION
              "The change in value of wanX25StatsOutAccusedErrors during the
               interval."
::= { wanX25HistoryEntry 20 }

wanX25HistoryInInterrupts OBJECT-TYPE
       SYNTAX       Counter64
       MAX-ACCESS   read-only
       STATUS       current
       DESCRIPTION
              "The change in value of wanX25StatsInInterrupts during the
               interval."
::= { wanX25HistoryEntry 21 }

wanX25HistoryOutInterrupts OBJECT-TYPE
       SYNTAX       Counter64
       MAX-ACCESS   read-only
       STATUS       current
       DESCRIPTION
              "The change in value of wanX25StatsOutInterrupts during the
               interval."
::= { wanX25HistoryEntry 22 }

wanX25HistoryInUtilization OBJECT-TYPE
       SYNTAX       INTEGER (0..10000)
       MAX-ACCESS   read-only
       STATUS       current
       DESCRIPTION
              "The best estimated of the mean physical layer network
               utilization of traffic coming from the far end of the link
               in hundreds of a percent."
::= { wanX25HistoryEntry 23 }

wanX25HistoryOutUtilization OBJECT-TYPE
       SYNTAX       INTEGER (0..10000)
       MAX-ACCESS   read-only
       STATUS       current
       DESCRIPTION
              "The best estimated of the mean physical layer network
               utilization of traffic coming from the near end of the link
               in hundreds of a percent."
::= { wanX25HistoryEntry 24 }

wanFrStatsTable OBJECT-TYPE
       SYNTAX       SEQUENCE OF WanFrStatsEntry
       MAX-ACCESS   not-accessible
       STATUS       current
       DESCRIPTION
              "Frame Relay statistics."
::= { wanProtocolStats 2 }

wanFrStatsEntry OBJECT-TYPE
       SYNTAX       WanFrStatsEntry
       MAX-ACCESS   not-accessible
       STATUS       current
       DESCRIPTION
              "The statistics for a frame relay interface across all DLCIs.
               The near end of the link refers to the side of the link that the
               probe is monitoring.  The far end is the side the probe is not
               on.  In a frame relay network, there are many far ends of the
               link, but they shall be logically grouped into one end in this
               table."
       INDEX { wanFrStatsIndex }
::= { wanFrStatsTable 1 }

WanFrStatsEntry ::= SEQUENCE {
       wanFrStatsIndex                     INTEGER (1..65535),
       wanFrStatsDataSource                OBJECT IDENTIFIER,
       wanFrStatsDropEvents                Counter64,
       wanFrStatsInFrames                  Counter64,
       wanFrStatsOutFrames                 Counter64,
       wanFrStatsInOctets                  Counter64,
       wanFrStatsOutOctets                 Counter64,
       wanFrStatsInFECNs                   Counter64,
       wanFrStatsOutFECNs                  Counter64,
       wanFrStatsInBECNs                   Counter64,
       wanFrStatsOutBECNs                  Counter64,
       wanFrStatsInDEs                     Counter64,
       wanFrStatsOutDEs                    Counter64,
       wanFrStatsOwner                     OwnerString,
       wanFrStatsStatus                    RowStatus
}

wanFrStatsIndex OBJECT-TYPE
       SYNTAX       INTEGER (1..65535)
       MAX-ACCESS   not-accessible
       STATUS       current
       DESCRIPTION
              "The value of this object uniquely identifies this
               wanFrStatsTable entry."
::= { wanFrStatsEntry 1 }

wanFrStatsDataSource OBJECT-TYPE
       SYNTAX       OBJECT IDENTIFIER
       MAX-ACCESS   read-create
       STATUS       current
       DESCRIPTION
              "This object identifies the source of the data that this
               wanFrStatsEntry analyzes.  This source can be any frame relay
               interface on this device.  In order to identify a particular
               interface, this object shall identify the instance of the
               ifIndex object, defined in MIB-II [RFC 1573] for the desired
               interface.  The ifType value associated with the ifIndex can
               only be frameRelay(32)."
::= { wanFrStatsEntry 2 }

wanFrStatsDropEvents OBJECT-TYPE
       SYNTAX       Counter64
       MAX-ACCESS   read-only
       STATUS       current
       DESCRIPTION
              "The total number of events in which frames were dropped by the
               probe due to lack of resources.  Note that this number is not
               necessarily the number of frames dropped; it is just the number
               of times this condition has been detected."
::= { wanFrStatsEntry 3 }

wanFrStatsInFrames OBJECT-TYPE
       SYNTAX       Counter64
       MAX-ACCESS   read-only
       STATUS       current
       DESCRIPTION
              "The total number of frames seen coming from the far end of
               the link including error packets."
::= { wanFrStatsEntry 4 }

wanFrStatsOutFrames OBJECT-TYPE
       SYNTAX       Counter64
       MAX-ACCESS   read-only
       STATUS       current
       DESCRIPTION
              "The total number of frames seen coming from the near end of
               the link including error packets."
::= { wanFrStatsEntry 5 }

wanFrStatsInOctets OBJECT-TYPE
       SYNTAX       Counter64
       MAX-ACCESS   read-only
       STATUS       current
       DESCRIPTION
              "The sum of octets from all frames seen originating from the
               far end of the link including errored frames."
::= { wanFrStatsEntry 6 }

wanFrStatsOutOctets OBJECT-TYPE
       SYNTAX       Counter64
       MAX-ACCESS   read-only
       STATUS       current
       DESCRIPTION
              "The sum of octets from all frames seen originating from the
               near end of the link including errored frames."
::= { wanFrStatsEntry 7 }

wanFrStatsInFECNs OBJECT-TYPE
       SYNTAX       Counter64
       MAX-ACCESS   read-only
       STATUS       current
       DESCRIPTION
              "The number of frames see coming form the far end of the link
               with the FECN bit set."
::= { wanFrStatsEntry 8 }

wanFrStatsOutFECNs OBJECT-TYPE
       SYNTAX       Counter64
       MAX-ACCESS   read-only
       STATUS       current
       DESCRIPTION
              "The number of frames see coming form the near end of the link
               with the FECN bit set."
::= { wanFrStatsEntry 9 }

wanFrStatsInBECNs OBJECT-TYPE
       SYNTAX       Counter64
       MAX-ACCESS   read-only
       STATUS       current
       DESCRIPTION
              "The number of frames seen coming from the far end of the link
               with the BECN bit set."
::= { wanFrStatsEntry 10 }

wanFrStatsOutBECNs OBJECT-TYPE
       SYNTAX       Counter64
       MAX-ACCESS   read-only
       STATUS       current
       DESCRIPTION
              "The number of frames seen coming from the near end of the link
               with the BECN bit set."
::= { wanFrStatsEntry 11 }

wanFrStatsInDEs OBJECT-TYPE
       SYNTAX       Counter64
       MAX-ACCESS   read-only
       STATUS       current
       DESCRIPTION
              "The number of frames seen coming from the far end of the link
               with the DE bit set."
::= { wanFrStatsEntry 12 }

wanFrStatsOutDEs OBJECT-TYPE
       SYNTAX       Counter64
       MAX-ACCESS   read-only
       STATUS       current
       DESCRIPTION
              "The number of frames seen coming from the near end of the link
               with the DE bit set."
::= { wanFrStatsEntry 13 }

wanFrStatsOwner OBJECT-TYPE
       SYNTAX       OwnerString
       MAX-ACCESS   read-create
       STATUS       current
       DESCRIPTION
              "The entity that configured this entry."
::= { wanFrStatsEntry 14 }

wanFrStatsStatus OBJECT-TYPE
       SYNTAX       RowStatus
 --    MAX-ACCESS   read-write
       MAX-ACCESS   read-create
       STATUS       current
       DESCRIPTION
              "The status of this wanFrStatsTable entry."
::= { wanFrStatsEntry 15 }

wanFrHistoryTable OBJECT-TYPE
       SYNTAX       SEQUENCE OF WanFrHistoryEntry
       MAX-ACCESS   not-accessible
       STATUS       current
       DESCRIPTION
              "Frame Relay statistics."
::= { wanProtocolHistory 2 }

wanFrHistoryEntry OBJECT-TYPE
       SYNTAX       WanFrHistoryEntry
       MAX-ACCESS   not-accessible
       STATUS       current
       DESCRIPTION
              "The statistics for a frame relay interface across all DLCIs. The
               near end of the link refers to the side of the link that the
               probe is monitoring.  The far end is the side the probe is not
               on.  In a frame relay network, there are many far ends of the
               link, but they shall be logically grouped into one end in this
               table."
       INDEX { wanFrHistoryIndex, wanFrHistorySampleIndex }
::= { wanFrHistoryTable 1 }

WanFrHistoryEntry ::= SEQUENCE {
       wanFrHistoryIndex                   INTEGER (1..65535),
       wanFrHistorySampleIndex             INTEGER (1..2147483647),
       wanFrHistoryIntervalStart           TimeTicks,
       wanFrHistoryDropEvents              Counter64,
       wanFrHistoryInFrames                Counter64,
       wanFrHistoryOutFrames               Counter64,
       wanFrHistoryInOctets                Counter64,
       wanFrHistoryOutOctets               Counter64,
       wanFrHistoryInFECNs                 Counter64,
       wanFrHistoryOutFECNs                Counter64,
       wanFrHistoryInBECNs                 Counter64,
       wanFrHistoryOutBECNs                Counter64,
       wanFrHistoryInDEs                   Counter64,
       wanFrHistoryOutDEs                  Counter64,
       wanFrHistoryInUtilization           INTEGER (0..10000),
       wanFrHistoryOutUtilization          INTEGER (0..10000)
}

wanFrHistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanFrHistoryEntry 1 }

wanFrHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases by
               one as each new sample is taken."
::= { wanFrHistoryEntry 2 }

wanFrHistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample is
               started at that instant.  Note that following this rule may
               require the probe to delay collection the first sample of the
               history, as each sample must be of the same interval.  Also
               note that the sample which is currently being collected is not
               accessible in this table until the end of its interval."
::= { wanFrHistoryEntry 3 } 

wanFrHistoryDropEvents OBJECT-TYPE
       SYNTAX       Counter64
       MAX-ACCESS   read-only
       STATUS       current
       DESCRIPTION
              "The change in value of wanFrStatsDropEvents during the
               interval."
::= { wanFrHistoryEntry 4 }

wanFrHistoryInFrames OBJECT-TYPE
       SYNTAX       Counter64
       MAX-ACCESS   read-only
       STATUS       current
       DESCRIPTION
              "The change in value of wanFrStatsInFrames during the
               interval."
::= { wanFrHistoryEntry 5 }

wanFrHistoryOutFrames OBJECT-TYPE
       SYNTAX       Counter64
       MAX-ACCESS   read-only
       STATUS       current
       DESCRIPTION
              "The change in value of wanFrStatsOutFrames during the
               interval."
::= { wanFrHistoryEntry 6 }

wanFrHistoryInOctets OBJECT-TYPE
       SYNTAX       Counter64
       MAX-ACCESS   read-only
       STATUS       current
       DESCRIPTION
              "The change in value of wanFrStatsInOctets during the
               interval."
::= { wanFrHistoryEntry 7 }

wanFrHistoryOutOctets OBJECT-TYPE
       SYNTAX       Counter64
       MAX-ACCESS   read-only
       STATUS       current
       DESCRIPTION
              "The change in value of wanFrStatsOutOctets during the
               interval."
::= { wanFrHistoryEntry 8 }

wanFrHistoryInFECNs OBJECT-TYPE
       SYNTAX       Counter64
       MAX-ACCESS   read-only
       STATUS       current
       DESCRIPTION
              "The change in value of wanFrStatsInFECSs during the
               interval."
::= { wanFrHistoryEntry 9 }

wanFrHistoryOutFECNs OBJECT-TYPE
       SYNTAX       Counter64
       MAX-ACCESS   read-only
       STATUS       current
       DESCRIPTION
              "The change in value of wanFrStatsOutFECNs during the
               interval."
::= { wanFrHistoryEntry 10 }

wanFrHistoryInBECNs OBJECT-TYPE
       SYNTAX       Counter64
       MAX-ACCESS   read-only
       STATUS       current
       DESCRIPTION
              "The change in value of wanFrStatsInBECNs during the
               interval."
::= { wanFrHistoryEntry 11 }

wanFrHistoryOutBECNs OBJECT-TYPE
       SYNTAX       Counter64
       MAX-ACCESS   read-only
       STATUS       current
       DESCRIPTION
              "The change in value of wanFrStatsOutBECNs during the
               interval."
::= { wanFrHistoryEntry 12 }

wanFrHistoryInDEs OBJECT-TYPE
       SYNTAX       Counter64
       MAX-ACCESS   read-only
       STATUS       current
       DESCRIPTION
              "The change in value of wanFrStatsInDEs during the interval."
::= { wanFrHistoryEntry 13 }

wanFrHistoryOutDEs OBJECT-TYPE
       SYNTAX       Counter64
       MAX-ACCESS   read-only
       STATUS       current
       DESCRIPTION
              "The change in value of wanFrStatsDOutDEs during the interval."
::= { wanFrHistoryEntry 14 }

wanFrHistoryInUtilization OBJECT-TYPE
       SYNTAX       INTEGER (0..10000)
       MAX-ACCESS   read-only
       STATUS       current
       DESCRIPTION
              "The best estimated of the mean physical layer network
               utilization of traffic coming from the far end of the link
               in hundreds of a percent."
::= { wanFrHistoryEntry 15 }

wanFrHistoryOutUtilization OBJECT-TYPE
       SYNTAX       INTEGER (0..10000)
       MAX-ACCESS   read-only
       STATUS       current
       DESCRIPTION
              "The best estimated of the mean physical layer network
               utilization of traffic coming from the near end of the link
               in hundreds of a percent."
::= { wanFrHistoryEntry 16 }

wanAal5StatsTable OBJECT-TYPE
       SYNTAX       SEQUENCE OF WanAal5StatsEntry
       MAX-ACCESS   not-accessible
       STATUS       current
       DESCRIPTION
              "AAL/5 statistics."
::= { wanProtocolStats 3 }

wanAal5StatsEntry OBJECT-TYPE
       SYNTAX       WanAal5StatsEntry
       MAX-ACCESS   not-accessible
       STATUS       current
       DESCRIPTION
              "The statistics for a AAL/5 interface. The near end of the link
               refers to the side of the link that the probe is monitoring.
               The far end is the side the probe is not on.  In an ATM network,
               there are many far ends of the link, but they shall be logically
               grouped into one end in this table."
       INDEX { wanAal5StatsIndex }
::= { wanAal5StatsTable 1 }

WanAal5StatsEntry ::= SEQUENCE {
       wanAal5StatsIndex                   INTEGER (1..65535),
       wanAal5StatsDataSource              OBJECT IDENTIFIER,
       wanAal5StatsDropEvents              Counter64,
       wanAal5StatsInCells                 Counter64,
       wanAal5StatsOutCells                Counter64,
       wanAal5StatsInPDUs                  Counter64,
       wanAal5StatsOutPDUs                 Counter64,
       wanAal5StatsInOctets                Counter64,
       wanAal5StatsOutOctets               Counter64,
       wanAal5StatsInCLP1                  Counter64,
       wanAal5StatsOutCLP1                 Counter64,
       wanAal5StatsInCRCs                  Counter64,
       wanAal5StatsOutCRCs                 Counter64,
       wanAal5StatsInOversizedSDUs         Counter64,
       wanAal5StatsOutOversizedSDUs        Counter64,
       wanAal5StatsInSVCs                  Counter64,
       wanAal5StatsOutSVCs                 Counter64,
       wanAal5StatsOwner                   OwnerString,
       wanAal5StatsStatus                  RowStatus
}

wanAal5StatsIndex OBJECT-TYPE
       SYNTAX       INTEGER (1..65535)
       MAX-ACCESS   not-accessible
       STATUS       current
       DESCRIPTION
              "The value of this object uniquely identifies this wanAal5StatsTable entry."
::= { wanAal5StatsEntry 1 }

wanAal5StatsDataSource OBJECT-TYPE
       SYNTAX       OBJECT IDENTIFIER
       MAX-ACCESS   read-create
       STATUS       current
       DESCRIPTION
              "This object identifies the source of the data that this
               wanAal5StatsEntry analyzes.  This source can be any interface
               on this device.  In order to identify a particular interface,
               this object shall identify the instance of the ifIndex object,
               defined in MIB-II [RFC 1573] for the desired interface.  The
               ifType value associated with the ifIndex can only be aal5(49)."
::= { wanAal5StatsEntry 2 }

wanAal5StatsDropEvents OBJECT-TYPE
       SYNTAX       Counter64
       MAX-ACCESS   read-only
       STATUS       current
       DESCRIPTION
              "The total number of events in which frames were dropped by the
               probe due to lack of resources.  Note that this number is not
               necessarily the number of frames dropped; it is just the
               number of times this condition has been detected."
::= { wanAal5StatsEntry 3 }

wanAal5StatsInCells OBJECT-TYPE
       SYNTAX       Counter64
       MAX-ACCESS   read-only
       STATUS       current
       DESCRIPTION
              "The total number of cells for any AAL-5 connection seen
               coming from the far end of the link."
::= { wanAal5StatsEntry 4 }

wanAal5StatsOutCells OBJECT-TYPE
       SYNTAX       Counter64
       MAX-ACCESS   read-only
       STATUS       current
       DESCRIPTION
              "The total number of cells for any AAL-5 connection seen
               coming from the near end of the link."
::= { wanAal5StatsEntry 5 }

wanAal5StatsInPDUs OBJECT-TYPE
       SYNTAX       Counter64
       MAX-ACCESS   read-only
       STATUS       current
       DESCRIPTION
              "The total number of AAL-5 PDUs seen coming from the far end
               of the link including error PDUs."
::= { wanAal5StatsEntry 6 }

wanAal5StatsOutPDUs OBJECT-TYPE
       SYNTAX       Counter64
       MAX-ACCESS   read-only
       STATUS       current
       DESCRIPTION
              "The total number of AAL-5 PDUs seen coming from the near end
               of the link including error PDUs."
::= { wanAal5StatsEntry 7 }

wanAal5StatsInOctets OBJECT-TYPE
       SYNTAX       Counter64
       MAX-ACCESS   read-only
       STATUS       current
       DESCRIPTION
              "The sum of octets from all AAL-5 PDUs seen originating from
               the far end of the link including errored PDUs."
::= { wanAal5StatsEntry 8 }

wanAal5StatsOutOctets OBJECT-TYPE
       SYNTAX       Counter64
       MAX-ACCESS   read-only
       STATUS       current
       DESCRIPTION
              "The sum of octets from all AAL-5 PDUs seen originating from
               the near end of the link including errored PDUs."
::= { wanAal5StatsEntry 9 }

wanAal5StatsInCLP1 OBJECT-TYPE
       SYNTAX       Counter64
       MAX-ACCESS   read-only
       STATUS       current
       DESCRIPTION
              "The total number of cells for any AAL-5 connection with the
               CLP bit set seen coming from the far end of the link."
::= { wanAal5StatsEntry 10 }

wanAal5StatsOutCLP1 OBJECT-TYPE
       SYNTAX       Counter64
       MAX-ACCESS   read-only
       STATUS       current
       DESCRIPTION
              "The total number of cells for any AAL-5 connection with the
               CLP bit set seen coming from the near end of the link."
::= { wanAal5StatsEntry 11 }

wanAal5StatsInCRCs OBJECT-TYPE
       SYNTAX       Counter64
       MAX-ACCESS   read-only
       STATUS       current
       DESCRIPTION
              "The total number of AAL-5 PDUs with CRC errors from the far
               end of the link."
::= { wanAal5StatsEntry 12 }

wanAal5StatsOutCRCs OBJECT-TYPE
       SYNTAX       Counter64
       MAX-ACCESS   read-only
       STATUS       current
       DESCRIPTION
              "The total number of AAL-5 PDUs with CRC errors from the
               near end of the link."
::= { wanAal5StatsEntry 13 }

wanAal5StatsInOversizedSDUs OBJECT-TYPE
       SYNTAX       Counter64
       MAX-ACCESS   read-only
       STATUS       current
       DESCRIPTION
              "The total number of AAL-5 SDUs from the far end of the link
               that were too large."
::= { wanAal5StatsEntry 14 }

wanAal5StatsOutOversizedSDUs OBJECT-TYPE
       SYNTAX       Counter64
       MAX-ACCESS   read-only
       STATUS       current
       DESCRIPTION
              "The total number of AAL-5 SDUs from the near end of the link
               that were too large."
::= { wanAal5StatsEntry 15 }

wanAal5StatsInSVCs OBJECT-TYPE
       SYNTAX       Counter64
       MAX-ACCESS   read-only
       STATUS       current
       DESCRIPTION
              "The total number of AAL/5 connections seen initiated from the
               far end of the link."
::= { wanAal5StatsEntry 16 }

wanAal5StatsOutSVCs OBJECT-TYPE
       SYNTAX       Counter64
       MAX-ACCESS   read-only
       STATUS       current
       DESCRIPTION
              "The total number of AAL-5 connections seen initiated from
               the near end of the link."
::= { wanAal5StatsEntry 17 }

wanAal5StatsOwner OBJECT-TYPE
       SYNTAX       OwnerString
       MAX-ACCESS   read-create
       STATUS       current
       DESCRIPTION
              "The entity that configured this entry."
::= { wanAal5StatsEntry 18 }

wanAal5StatsStatus OBJECT-TYPE
       SYNTAX       RowStatus
--     MAX-ACCESS   read-write
       MAX-ACCESS   read-create
       STATUS       current
       DESCRIPTION
              "The status of this wanAal5StatsTable entry."
::= { wanAal5StatsEntry 19 }

wanAal5HistoryTable OBJECT-TYPE
       SYNTAX       SEQUENCE OF WanAal5HistoryEntry
       MAX-ACCESS   not-accessible
       STATUS       current
       DESCRIPTION
              "AAL/5 statistics."
::= { wanProtocolHistory 3 }

wanAal5HistoryEntry OBJECT-TYPE
       SYNTAX       WanAal5HistoryEntry
       MAX-ACCESS   not-accessible
       STATUS       current
       DESCRIPTION
              "The statistics for a AAL/5 interface. The near end of the link
               refers to the side of the link that the probe is monitoring.
               The far end is the side the probe is not on.  In an ATM network,
               there are many far ends of the link, but they shall be logically
               grouped into one end in this table."
       INDEX { wanAal5HistoryIndex, wanAal5HistorySampleIndex }
::= { wanAal5HistoryTable 1 }

WanAal5HistoryEntry ::= SEQUENCE {
       wanAal5HistoryIndex                 INTEGER (1..65535),
       wanAal5HistorySampleIndex           INTEGER (1..2147483647),
       wanAal5HistoryIntervalStart         TimeTicks,
       wanAal5HistoryDropEvents            Counter64,
       wanAal5HistoryInCells               Counter64,
       wanAal5HistoryOutCells              Counter64,
       wanAal5HistoryInPDUs                Counter64,
       wanAal5HistoryOutPDUs               Counter64,
       wanAal5HistoryInOctets              Counter64,
       wanAal5HistoryOutOctets             Counter64,
       wanAal5HistoryInCLP1                Counter64,
       wanAal5HistoryOutCLP1               Counter64,
       wanAal5HistoryInCRCs                Counter64,
       wanAal5HistoryOutCRCs               Counter64,
       wanAal5HistoryInOversizedSDUs       Counter64,
       wanAal5HistoryOutOversizedSDUs      Counter64,
       wanAal5HistoryInSVCs                Counter64,
       wanAal5HistoryOutSVCs               Counter64,
       wanAal5HistoryInUtilization         INTEGER (0..10000),
       wanAal5HistoryOutUtilization        INTEGER (0..10000)
}

wanAal5HistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanAal5HistoryEntry 1 }

wanAal5HistorySampleIndex OBJECT-TYPE
       SYNTAX       INTEGER (1..2147483647)
       MAX-ACCESS   not-accessible 
       STATUS       current
       DESCRIPTION
              "An index that uniquely identifies the particular sample
               this entry represents among all samples associated with the
               same historyControlEntry.  This index starts at 1 and
               increases by one as each new sample is taken."
::= { wanAal5HistoryEntry 2 }

wanAal5HistoryIntervalStart OBJECT-TYPE
       SYNTAX       TimeTicks
       MAX-ACCESS   read-only
       STATUS       current
       DESCRIPTION
              "The value of sysUpTime at the start of the interval over
               which this sample was measured.  If the probe keeps track of
               time of day, it should start the first sample of the history
               at a time such that when the next hour of the day begins, a
               sample is started at that instant.  Note that following this
               rule may require the probe to delay collection the first
               sample of the history, as each sample must be of the same
               interval.  Also note that the sample which is currently being
               collected is not accessible in this table until the end of its
               interval."
::= { wanAal5HistoryEntry 3 } 

wanAal5HistoryDropEvents OBJECT-TYPE
       SYNTAX       Counter64
       MAX-ACCESS   read-only
       STATUS       current
       DESCRIPTION
              "The change in value of wanAal5StatsDropEvents during the
               interval."
::= { wanAal5HistoryEntry 4 }

wanAal5HistoryInCells OBJECT-TYPE
       SYNTAX       Counter64
       MAX-ACCESS   read-only
       STATUS       current
       DESCRIPTION
              "The change in value of wanAal5StatsInCells during the
               interval."
::= { wanAal5HistoryEntry 5 }

wanAal5HistoryOutCells OBJECT-TYPE
       SYNTAX       Counter64
       MAX-ACCESS   read-only
       STATUS       current
       DESCRIPTION
              "The change in value of wanAal5StatsOutCells during the
               interval."
::= { wanAal5HistoryEntry 6 }

wanAal5HistoryInPDUs OBJECT-TYPE
       SYNTAX       Counter64
       MAX-ACCESS   read-only
       STATUS       current
       DESCRIPTION
              "The change in value of wanAal5StatsInPDUs during the
               interval."
::= { wanAal5HistoryEntry 7 }

wanAal5HistoryOutPDUs OBJECT-TYPE
       SYNTAX       Counter64
       MAX-ACCESS   read-only
       STATUS       current
       DESCRIPTION
              "The change in value of wanAal5StatsOutPDUs during the
               interval."
::= { wanAal5HistoryEntry 8 }

wanAal5HistoryInOctets OBJECT-TYPE
       SYNTAX       Counter64
       MAX-ACCESS   read-only
       STATUS       current
       DESCRIPTION
              "The change in value of wanAal5StatsInOctets during the
               interval."
::= { wanAal5HistoryEntry 9 }

wanAal5HistoryOutOctets OBJECT-TYPE
       SYNTAX       Counter64
       MAX-ACCESS   read-only
       STATUS       current
       DESCRIPTION
              "The change in value of wanAal5StatsOutOctets during the
               interval."
::= { wanAal5HistoryEntry 10 }

wanAal5HistoryInCLP1 OBJECT-TYPE
       SYNTAX       Counter64
       MAX-ACCESS   read-only
       STATUS       current
       DESCRIPTION
              "The change in value of wanAal5StatsInCLP1 the
               interval."
::= { wanAal5HistoryEntry 11 }

wanAal5HistoryOutCLP1 OBJECT-TYPE
       SYNTAX       Counter64
       MAX-ACCESS   read-only
       STATUS       current
       DESCRIPTION
              "The change in value of wanAal5StatsOutCLP1 during the
               interval."
::= { wanAal5HistoryEntry 12 }

wanAal5HistoryInCRCs OBJECT-TYPE
       SYNTAX       Counter64
       MAX-ACCESS   read-only
       STATUS       current
       DESCRIPTION
              "The change in value of wanAal5StatsInCRCs during the
               interval."
::= { wanAal5HistoryEntry 13 }

wanAal5HistoryOutCRCs OBJECT-TYPE
       SYNTAX       Counter64
       MAX-ACCESS   read-only
       STATUS       current
       DESCRIPTION
              "The change in value of wanAal5StatsOutCRCs during the
               interval."
::= { wanAal5HistoryEntry 14 }

wanAal5HistoryInOversizedSDUs OBJECT-TYPE
       SYNTAX       Counter64
       MAX-ACCESS   read-only
       STATUS       current
       DESCRIPTION
              "The change in value of wanAal5StatsInOversizedSDUs during the
               interval."
::= { wanAal5HistoryEntry 15 }

wanAal5HistoryOutOversizedSDUs OBJECT-TYPE
       SYNTAX       Counter64
       MAX-ACCESS   read-only
       STATUS       current
       DESCRIPTION
              "The change in value of wanAal5StatsOutOversizedSDUs during the
               interval."
::= { wanAal5HistoryEntry 16 }

wanAal5HistoryInSVCs OBJECT-TYPE
       SYNTAX       Counter64
       MAX-ACCESS   read-only
       STATUS       current
       DESCRIPTION
              "The change in value of wanAal5StatsInSVCs during the
               interval."
::= { wanAal5HistoryEntry 17 }

wanAal5HistoryOutSVCs OBJECT-TYPE
       SYNTAX       Counter64
       MAX-ACCESS   read-only
       STATUS       current
       DESCRIPTION
              "The change in value of wanAal5StatsOutSVCs during the
               interval."
::= { wanAal5HistoryEntry 18 }

wanAal5HistoryInUtilization OBJECT-TYPE
       SYNTAX       INTEGER (0..10000)
       MAX-ACCESS   read-only
       STATUS       current
       DESCRIPTION
              "The best estimated of the mean AAL-5 layer network
               utilization of traffic coming from the far end of the
               link in hundreds of a percent."
::= { wanAal5HistoryEntry 19 }

wanAal5HistoryOutUtilization OBJECT-TYPE
       SYNTAX       INTEGER (0..10000)
       MAX-ACCESS   read-only
       STATUS       current
       DESCRIPTION
              "The best estimated of the mean AAL-5 layer network
               utilization of traffic coming from the near end of the
               link in hundreds of a percent."
::= { wanAal5HistoryEntry 20 }

wanPppStatsTable OBJECT-TYPE
       SYNTAX       SEQUENCE OF WanPppStatsEntry
       MAX-ACCESS   not-accessible
       STATUS       current
       DESCRIPTION
              "PPP in HDLC service statistics."
::= { wanProtocolStats 4 }

wanPppStatsEntry OBJECT-TYPE
       SYNTAX       WanPppStatsEntry
       MAX-ACCESS   not-accessible
       STATUS       current
       DESCRIPTION
              "The statistics for a PPP in HDLC service. The near end of
               the link refers to the side of the link that the probe is
               monitoring.  The far end is the side the probe is not on."
       INDEX { wanPppStatsIndex }
::= { wanPppStatsTable 1 }

WanPppStatsEntry ::= SEQUENCE {
       wanPppStatsIndex                    INTEGER (1..65535),
       wanPppStatsDataSource               OBJECT IDENTIFIER,
       wanPppStatsDropEvents               Counter64,
       wanPppStatsInFrames                 Counter64,
       wanPppStatsOutFrames                Counter64,
       wanPppStatsInOctets                 Counter64,
       wanPppStatsOutOctets                Counter64,
       wanPppStatsInBadAddresses           Counter64,
       wanPppStatsOutBadAddresses          Counter64,
       wanPppStatsInBadControls            Counter64,
       wanPppStatsOutBadControls           Counter64,
       wanPppStatsInLongFrames             Counter64,
       wanPppStatsOutLongFrames            Counter64,
       wanPppStatsInBadFCSs                Counter64,
       wanPppStatsOutBadFCSs               Counter64,
       wanPppStatsOwner                    OwnerString,
       wanPppStatsStatus                   RowStatus
}

wanPppStatsIndex OBJECT-TYPE
       SYNTAX       INTEGER (1..65535)
       MAX-ACCESS   not-accessible
       STATUS       current
       DESCRIPTION
              "The value of this object uniquely identifies this wanPppStatsTable entry."
::= { wanPppStatsEntry 1 }

wanPppStatsDataSource OBJECT-TYPE
       SYNTAX       OBJECT IDENTIFIER
       MAX-ACCESS   read-create
       STATUS       current
       DESCRIPTION
              "This object identifies the source of the data that this
               wanPppStatsEntry analyzes.  This source can be any interface
               on this device.  In order to identify a particular interface,
               this object shall identify the instance of the ifIndex object,
               defined in MIB-II [RFC 1573] for the desired interface.  The
               ifType value associated with the ifIndex can only be ppp(22)."
::= {wanPppStatsEntry 2 }

wanPppStatsDropEvents OBJECT-TYPE
       SYNTAX       Counter64
       MAX-ACCESS   read-only
       STATUS       current
       DESCRIPTION
              "The total number of events in which frames were dropped by
               the probe due to lack of resources.  Note that this number
               is not necessarily the number of frames dropped; it is just
               the number of times this condition has been detected."
::= { wanPppStatsEntry 3 }

wanPppStatsInFrames OBJECT-TYPE
       SYNTAX       Counter64
       MAX-ACCESS   read-only
       STATUS       current
       DESCRIPTION
              "The total number of frames seen coming from the far end
               of the link including error frames."
::= { wanPppStatsEntry 4 }

wanPppStatsOutFrames OBJECT-TYPE
       SYNTAX       Counter64
       MAX-ACCESS   read-only
       STATUS       current
       DESCRIPTION
              "The total number of frames seen coming from the near end
               of the link including error frames."
::= { wanPppStatsEntry 5 }

wanPppStatsInOctets OBJECT-TYPE
       SYNTAX       Counter64
       MAX-ACCESS   read-only
       STATUS       current
       DESCRIPTION
              "The sum of octets from all frames seen coming from the far
               end of the link including errored frames."
::= { wanPppStatsEntry 6 }

wanPppStatsOutOctets OBJECT-TYPE
       SYNTAX       Counter64
       MAX-ACCESS   read-only
       STATUS       current
       DESCRIPTION
              "The sum of octets from all frames seen coming from the near
               end of the link including errored frames."
::= { wanPppStatsEntry 7 }

wanPppStatsInBadAddresses OBJECT-TYPE
       SYNTAX       Counter64
       MAX-ACCESS   read-only
       STATUS       current
       DESCRIPTION
              "The number of frames seen from the far end of the link with
               an incorrect address field."
::= { wanPppStatsEntry 8 }

wanPppStatsOutBadAddresses OBJECT-TYPE
       SYNTAX       Counter64
       MAX-ACCESS   read-only
       STATUS       current
       DESCRIPTION
              "The number of frames seen from the near end of the link with
               an incorrect address field"
::= { wanPppStatsEntry 9 }

wanPppStatsInBadControls OBJECT-TYPE
       SYNTAX       Counter64
       MAX-ACCESS   read-only
       STATUS       current
       DESCRIPTION
              "The number of frames seen from the far end of the link with
               an incorrect control field."
::= { wanPppStatsEntry 10 }

wanPppStatsOutBadControls OBJECT-TYPE
       SYNTAX       Counter64
       MAX-ACCESS   read-only
       STATUS       current
       DESCRIPTION
              "The number of frames seen from the near end of the link with
               an incorrect control field."
::= { wanPppStatsEntry 11 }

wanPppStatsInLongFrames OBJECT-TYPE
       SYNTAX       Counter64
       MAX-ACCESS   read-only
       STATUS       current
       DESCRIPTION
              "The number of frames seen from the far end of the link that
               exceed the MRU."
::= { wanPppStatsEntry 12 }

wanPppStatsOutLongFrames OBJECT-TYPE
       SYNTAX       Counter64
       MAX-ACCESS   read-only
       STATUS       current
       DESCRIPTION
              "The number of frames seen from the near end of the link that
               exceed the MRU."
::= { wanPppStatsEntry 13 }

wanPppStatsInBadFCSs OBJECT-TYPE
       SYNTAX       Counter64
       MAX-ACCESS   read-only
       STATUS       current
       DESCRIPTION
              "The number of packets seen from the far end of the link with
               incorrect FCSs."
::= { wanPppStatsEntry 14 }

wanPppStatsOutBadFCSs OBJECT-TYPE
       SYNTAX       Counter64
       MAX-ACCESS   read-only
       STATUS       current
       DESCRIPTION
              "The number of packets seen from the near end of the link with
               incorrect FCSs."
::= { wanPppStatsEntry 15 }

wanPppStatsOwner OBJECT-TYPE
       SYNTAX       OwnerString
       MAX-ACCESS   read-create
       STATUS       current
       DESCRIPTION
              "The entity that configured this entry."
::= { wanPppStatsEntry 16 }

wanPppStatsStatus OBJECT-TYPE
       SYNTAX       RowStatus
--     MAX-ACCESS   read-write
       MAX-ACCESS   read-create
       STATUS       current
       DESCRIPTION
              "The status of this wanPppStatsTable entry."
::= { wanPppStatsEntry 17 }

wanPppHistoryTable OBJECT-TYPE
       SYNTAX       SEQUENCE OF WanPppHistoryEntry
       MAX-ACCESS   not-accessible
       STATUS       current
       DESCRIPTION
              "PPP in HDLC service statistics."
::= { wanProtocolHistory 4 }

wanPppHistoryEntry OBJECT-TYPE
       SYNTAX       WanPppHistoryEntry
       MAX-ACCESS   not-accessible
       STATUS       current
       DESCRIPTION
              "The statistics for a PPP in HDLC service. The near end of the
               link refers to the side of the link that the probe is
               monitoring.  The far end is the side the probe is not on."
       INDEX { wanPppHistoryIndex, wanPppHistorySampleIndex }
::= { wanPppHistoryTable 1 }

WanPppHistoryEntry ::= SEQUENCE {
       wanPppHistoryIndex                  INTEGER (1..65535),
       wanPppHistorySampleIndex            INTEGER (1..2147483647),
       wanPppHistoryIntervalStart          TimeTicks,
       wanPppHistoryDropEvents             Counter64,
       wanPppHistoryInFrames               Counter64,
       wanPppHistoryOutFrames              Counter64,
       wanPppHistoryInOctets               Counter64,
       wanPppHistoryOutOctets              Counter64,
       wanPppHistoryInBadAddresses         Counter64,
       wanPppHistoryOutBadAddresses        Counter64,
       wanPppHistoryInBadControls          Counter64,
       wanPppHistoryOutBadControls         Counter64,
       wanPppHistoryInLongFrames           Counter64,
       wanPppHistoryOutLongFrames          Counter64,
       wanPppHistoryInBadFCSs              Counter64,
       wanPppHistoryOutBadFCSs             Counter64,
       wanPppHistoryInUtilization          INTEGER (0..10000),
       wanPppHistoryOutUtilization         INTEGER (0..10000)
}

wanPppHistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanPppHistoryEntry 1 }

wanPppHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases
               by one as each new sample is taken."
::= {wanPppHistoryEntry 2 }

wanPppHistoryIntervalStart OBJECT-TYPE
       SYNTAX       TimeTicks
       MAX-ACCESS   read-only
       STATUS       current
       DESCRIPTION
              "The value of sysUpTime at the start of the interval over which
               this sample was measured.  If the probe keeps track of time of
               day, it should start the first sample of the history at a time
               such that when the next hour of the day begins, a sample is 
               started at that instant.  Note that following this rule may 
               require the probe to delay collection the first sample of the
               history, as each sample must be of the same interval.  Also
               note that the sample which is currently being collected is not
               accessible in this table until the end of its interval."
::= { wanPppHistoryEntry 3 } 

wanPppHistoryDropEvents OBJECT-TYPE
       SYNTAX       Counter64
       MAX-ACCESS   read-only
       STATUS       current
       DESCRIPTION
              "The change in value of wanPppStatsDropEvents during the
               interval."
::= { wanPppHistoryEntry 4 }

wanPppHistoryInFrames OBJECT-TYPE
       SYNTAX       Counter64
       MAX-ACCESS   read-only
       STATUS       current
       DESCRIPTION
              "The change in value of wanPppStatsInFrames during the
               interval."
::= { wanPppHistoryEntry 5 }

wanPppHistoryOutFrames OBJECT-TYPE
       SYNTAX       Counter64
       MAX-ACCESS   read-only
       STATUS       current
       DESCRIPTION
              "The change in value of wanPppStatsOutFrames during the
               interval."
::= { wanPppHistoryEntry 6 }

wanPppHistoryInOctets OBJECT-TYPE
       SYNTAX       Counter64
       MAX-ACCESS   read-only
       STATUS       current
       DESCRIPTION
              "The change in value of wanPppStatsInOctets during the
               interval."
::= { wanPppHistoryEntry 7 }

wanPppHistoryOutOctets OBJECT-TYPE
       SYNTAX       Counter64
       MAX-ACCESS   read-only
       STATUS       current
       DESCRIPTION
               "The change in value of wanPppStatsOutOctets during the
               interval."
::= { wanPppHistoryEntry 8 }

wanPppHistoryInBadAddresses OBJECT-TYPE
       SYNTAX       Counter64
       MAX-ACCESS   read-only
       STATUS       current
       DESCRIPTION
              "The change in value of wanPppStatsInBadAddresses during the
               interval."
::= { wanPppHistoryEntry 9 }

wanPppHistoryOutBadAddresses OBJECT-TYPE
       SYNTAX       Counter64
       MAX-ACCESS   read-only
       STATUS       current
       DESCRIPTION
              "The change in value of wanPppStatsOutBadAddresses during the
               interval."
::= { wanPppHistoryEntry 10 }

wanPppHistoryInBadControls OBJECT-TYPE
       SYNTAX       Counter64
       MAX-ACCESS   read-only
       STATUS       current
       DESCRIPTION
              "The change in value of wanPppStatsInBadControls during the
               interval."
::= { wanPppHistoryEntry 11 }

wanPppHistoryOutBadControls OBJECT-TYPE
       SYNTAX       Counter64
       MAX-ACCESS   read-only
       STATUS       current
       DESCRIPTION
              "The change in value of wanPppStatsOutBadControls during the
               interval."
::= { wanPppHistoryEntry 12 }

wanPppHistoryInLongFrames OBJECT-TYPE
       SYNTAX       Counter64
       MAX-ACCESS   read-only
       STATUS       current
       DESCRIPTION
              "The change in value of wanPppStatsInLongFrames during the
               interval."
::= { wanPppHistoryEntry 13 }

wanPppHistoryOutLongFrames OBJECT-TYPE
       SYNTAX       Counter64
       MAX-ACCESS   read-only
       STATUS       current
       DESCRIPTION
              "The change in value of wanPppStatsOutLongFrames during the
               interval."
::= { wanPppHistoryEntry 14 }

wanPppHistoryInBadFCSs OBJECT-TYPE
       SYNTAX       Counter64
       MAX-ACCESS   read-only
       STATUS       current
       DESCRIPTION
              "The change in value of wanPppStatsInBadFCSs during the
               interval."
::= { wanPppHistoryEntry 15 }

wanPppHistoryOutBadFCSs OBJECT-TYPE
       SYNTAX       Counter64
       MAX-ACCESS   read-only
       STATUS       current
       DESCRIPTION
              "The change in value of wanPppStatsOutBadFCSs during the
               interval."
::= { wanPppHistoryEntry 16 }

wanPppHistoryInUtilization OBJECT-TYPE
       SYNTAX       INTEGER (0..10000)
       MAX-ACCESS   read-only
       STATUS       current
       DESCRIPTION
              "The best estimated of the mean physical layer network
               utilization of traffic coming from the far end of the
               link in hundreds of a percent."
::= { wanPppHistoryEntry 17 }

wanPppHistoryOutUtilization OBJECT-TYPE
       SYNTAX       INTEGER (0..10000)
       MAX-ACCESS   read-only
       STATUS       current
       DESCRIPTION
              "The best estimated of the mean physical layer network
               utilization of traffic coming from the near end of the
               link in hundreds of a percent."
::= { wanPppHistoryEntry 18 }

wanX25PvcStatsTable OBJECT-TYPE
       SYNTAX       SEQUENCE OF WanX25PvcStatsEntry
       MAX-ACCESS   not-accessible
       STATUS       current
       DESCRIPTION
              "X.25 per-LCI statistics for a PVC."
::= { wanPvcStats 1 }

wanX25PvcStatsEntry OBJECT-TYPE
       SYNTAX       WanX25PvcStatsEntry
       MAX-ACCESS   not-accessible
       STATUS       current
       DESCRIPTION
              "The statistics for a X.25 PVC. The near end of the link
               refers to the side of the link that the probe is
               monitoring.  The far end is the sides the probe is not on."
       INDEX { wanX25StatsIndex }
::= { wanX25PvcStatsTable 1 }

WanX25PvcStatsEntry ::= SEQUENCE {
       wanX25PvcStatsIndex                 INTEGER (1..65535),
       wanX25PvcStatsDataSource            OBJECT IDENTIFIER,
       wanX25PvcStatsDropEvents            Counter64,
       wanX25PvcStatsInFrames              Counter64,
       wanX25PvcStatsOutFrames             Counter64,
       wanX25PvcStatsInOctets              Counter64,
       wanX25PvcStatsOutOctets             Counter64,
       wanX25PvcStatsInResets              Counter64,
       wanX25PvcStatsOutResets             Counter64,
       wanX25PvcStatsProviderResets        Counter64,
       wanX25PvcStatsInAccusedErrors       Counter64,
       wanX25PvcStatsOutAccusedErrors      Counter64,
       wanX25PvcStatsInInterrupts          Counter64,
       wanX25PvcStatsOutInterrupts         Counter64,
       wanX25PvcStatsUpTime                TimeTicks,
       wanX25PvcStatsDownTime              TimeTicks,
       wanX25PvcStatsState                 INTEGER,
       wanX25PvcStatsStateChanges          Counter64,
       wanX25PvcStatsOwner                 OwnerString,
       wanX25PvcStatsStatus                RowStatus
}

wanX25PvcStatsIndex OBJECT-TYPE
       SYNTAX       INTEGER (1..65535)
       MAX-ACCESS   not-accessible
       STATUS       current
       DESCRIPTION
              "The value of this object uniquely identifies this
               wanX25PvcStatsTable entry."
::= { wanX25PvcStatsEntry 1 }

wanX25PvcStatsDataSource OBJECT-TYPE
       SYNTAX       OBJECT IDENTIFIER
       MAX-ACCESS   read-create
       STATUS       current
       DESCRIPTION
              "This object identifies the source of the data that this
               wanX25PvcStatsEntry analyzes.  This source can be any
               pvcEntry associated with an X.25 interface.  In order to
               identify a particular LCI to monitor, this object shall
               identify the instance of the pvcIndex object that
               corresponds to a X.25 PVC, defined above for the desired
               interface."
::= { wanX25PvcStatsEntry 2 }

wanX25PvcStatsDropEvents OBJECT-TYPE
       SYNTAX       Counter64
       MAX-ACCESS   read-only
       STATUS       current
       DESCRIPTION
              "The total number of events in which frames were dropped by
               the probe due to lack of resources.  Note that this number
               is not necessarily the number of frames dropped; it is just
               the number of times this condition has been detected."
::= { wanX25PvcStatsEntry 3 }

wanX25PvcStatsInFrames OBJECT-TYPE
       SYNTAX       Counter64
       MAX-ACCESS   read-only
       STATUS       current
       DESCRIPTION
              "The total number of frames seen coming from the far end
               of the link on this LCI."
::= { wanX25PvcStatsEntry 4 }

wanX25PvcStatsOutFrames OBJECT-TYPE
       SYNTAX       Counter64
       MAX-ACCESS   read-only
       STATUS       current
       DESCRIPTION
              "The total number of frames seen coming from the near end
               of the link on this LCI."
::= { wanX25PvcStatsEntry 5 }

wanX25PvcStatsInOctets OBJECT-TYPE
       SYNTAX       Counter64
       MAX-ACCESS   read-only
       STATUS       current
       DESCRIPTION
              "The sum of octets from all frames seen originating from
               the far end of the link on this LCI."
::= { wanX25PvcStatsEntry 6 }

wanX25PvcStatsOutOctets OBJECT-TYPE
       SYNTAX       Counter64
       MAX-ACCESS   read-only
       STATUS       current
       DESCRIPTION
              "The sum of octets from all frames seen originating from
               the near end of the link on this LCI."
::= { wanX25PvcStatsEntry 7 }

wanX25PvcStatsInResets OBJECT-TYPE
       SYNTAX       Counter64
       MAX-ACCESS   read-only
       STATUS       current
       DESCRIPTION
              "The number of reset requests seen from the far end of the
               link with cause code DTE initiated for this LCI."
::= { wanX25PvcStatsEntry 8 }

wanX25PvcStatsOutResets OBJECT-TYPE
       SYNTAX       Counter64
       MAX-ACCESS   read-only
       STATUS       current
       DESCRIPTION
              "The number of reset requests seen from the far end of the
               link with cause code DTE initiated for this LCI."
::= { wanX25PvcStatsEntry 9 }

wanX25PvcStatsProviderResets OBJECT-TYPE
       SYNTAX       Counter64
       MAX-ACCESS   read-only
       STATUS       current
       DESCRIPTION
              "The number of reset requests seen with cause code other
               than DTE initiated for this LCI."
::= { wanX25PvcStatsEntry 10 }

wanX25PvcStatsInAccusedErrors OBJECT-TYPE
       SYNTAX       Counter64
       MAX-ACCESS   read-only
       STATUS       current
       DESCRIPTION
              "The numbers of frames seen from the far end of the link
               containing a procedure error cause code on this LCI.
               These include clear, reset, restart, or diagnostic
               packets."
::= { wanX25PvcStatsEntry 11 }

wanX25PvcStatsOutAccusedErrors OBJECT-TYPE
       SYNTAX       Counter64
       MAX-ACCESS   read-only
       STATUS       current
       DESCRIPTION
              "The numbers of frames seen from the near end of the link
               containing a procedure error cause code on this LCI.
               These include clear, reset, restart, or diagnostic packets."
::= { wanX25PvcStatsEntry 12 }

wanX25PvcStatsInInterrupts OBJECT-TYPE
       SYNTAX       Counter64
       MAX-ACCESS   read-only
       STATUS       current
       DESCRIPTION
              "The number of interrupts frames seen coming from the far
               end of the link on this LCI."
::= { wanX25PvcStatsEntry 13 }

wanX25PvcStatsOutInterrupts OBJECT-TYPE
       SYNTAX       Counter64
       MAX-ACCESS   read-only
       STATUS       current
       DESCRIPTION
              "The number of interrupts frames seen coming from the far
               end of the link on this LCI."
::= { wanX25PvcStatsEntry 14 }

wanX25PvcStatsUpTime OBJECT-TYPE
       SYNTAX       TimeTicks
       MAX-ACCESS   read-only
       STATUS       current
       DESCRIPTION
              "The total amount of time in one-hundreds of a second that the
               probe is sure this LCI was active, i.e., the total time the
               value of wanX25PvcStatsState was equal to up(1).  A value of
               less than the age of this entry does not necessarily mean that
               this LCI was down.  It only means the probe was not certain it
               was up.
              
               Note: the sum of wanX25PvcStatsUpTime and wanX25PvcStatsDownTime 
               may be less than the age of this entry.  In this case, the
               unaccounted for time is the time the probe was uncertain of the
               state of this LCI, i.e., the total time the value of
               wanX25PvcStatsState was unknown(3)."
::= { wanX25PvcStatsEntry 15 }

wanX25PvcStatsDownTime OBJECT-TYPE
       SYNTAX       TimeTicks
       MAX-ACCESS   read-only
       STATUS       current
       DESCRIPTION
              "The total amount of time in one-hundreds of a second that the
               probe is sure this LCI was down, i.e., the total time the value
               of wanX25PvcStatsState was equal to down(3).  A value of less
               than the age of this entry does not necessarily mean that this
               LCI was up at some point.  It only means the probe was not
               certain it was down.
              
               Note: the sum of wanX25PvcStatsUpTime and wanX25PvcStatsDownTime
               may be less than the age of this entry.  In this case, the
               unaccounted for time is the time the probe was uncertain of the
               state of this LCI, i.e., the total time the value of
               wanX25PvcStatsState was unknown(3)."
::= { wanX25PvcStatsEntry 16 }

wanX25PvcStatsState OBJECT-TYPE
       SYNTAX       INTEGER {
              up(1),
              down(2),
              unknown(3)
       }
       MAX-ACCESS   read-only
       STATUS       current
       DESCRIPTION
              "The current state of this LCI as inferred by the probe.
               A value of up(2) means the LCI is active.  A value of
               down(2) means the LCI is inactive.  And a value of
               unknown(3) means the probe cannot currently infer the
               state."
::= { wanX25PvcStatsEntry 17 }

wanX25PvcStatsStateChanges OBJECT-TYPE
       SYNTAX       Counter64
       MAX-ACCESS   read-only
       STATUS       current
       DESCRIPTION
              "The count of the number of times the wanX25PvcStatsState
               has gone from up(1) to down(2) or vice versa.  The number
               of times wanX25PvcStatsState goes to unknown(3) is not
               counted.  However, if the value goes from up(1) to unknown(3)
               and then to down(2) should be counted as 1.  Likewise going
               from down(2) to unknown(3) and then to up(3) should be
               counted as 1."
::= { wanX25PvcStatsEntry 18 }

wanX25PvcStatsOwner OBJECT-TYPE
       SYNTAX       OwnerString
       MAX-ACCESS   read-create
       STATUS       current
       DESCRIPTION
              "The entity that configured this entry."
::= { wanX25PvcStatsEntry 19 }

wanX25PvcStatsStatus OBJECT-TYPE
       SYNTAX       RowStatus
--     MAX-ACCESS   read-write
       MAX-ACCESS   read-create
       STATUS       current
       DESCRIPTION
              "The status of this wanX25PvcStatsTable entry."
::= { wanX25PvcStatsEntry 20 }

wanX25PvcHistoryTable OBJECT-TYPE
       SYNTAX       SEQUENCE OF WanX25PvcHistoryEntry
       MAX-ACCESS   not-accessible
       STATUS       current
       DESCRIPTION
              "X.25 per LCI statistics."
::= { wanPvcHistory 1 }

wanX25PvcHistoryEntry OBJECT-TYPE
       SYNTAX       WanX25PvcHistoryEntry
       MAX-ACCESS   not-accessible
       STATUS       current
       DESCRIPTION
             "The statistics for a X.25 LCI. The near end of the link
              refers to the side of the link that the probe is monitoring.
              The far end is the side the probe is not on."
       INDEX { wanX25PvcHistoryIndex, wanX25PvcHistorySampleIndex }
::= { wanX25PvcHistoryTable 1 }

WanX25PvcHistoryEntry ::= SEQUENCE {
       wanX25PvcHistoryIndex               INTEGER (1..65535),
       wanX25PvcHistorySampleIndex         INTEGER (1..2147483647),
       wanX25PvcHistoryIntervalStart       TimeTicks,
       wanX25PvcHistoryDropEvents          Counter64,
       wanX25PvcHistoryInFrames            Counter64,
       wanX25PvcHistoryOutFrames           Counter64,
       wanX25PvcHistoryInOctets            Counter64,
       wanX25PvcHistoryOutOctets           Counter64,
       wanX25PvcHistoryInResets            Counter64,
       wanX25PvcHistoryOutResets           Counter64,
       wanX25PvcHistoryProviderResets      Counter64,
       wanX25PvcHistoryInAccusedErrors     Counter64,
       wanX25PvcHistoryOutAccusedErrors    Counter64,
       wanX25PvcHistoryInInterrupts        Counter64,
       wanX25PvcHistoryOutInterrupts       Counter64,
       wanX25PvcHistoryUpTime              TimeTicks,
       wanX25PvcHistoryDownTime            TimeTicks,
       wanX25PvcHistoryStateChanges        Counter64,
       wanX25PvcHistoryInUtilization       INTEGER (0..10000),
       wanX25PvcHistoryOutUtilization      INTEGER (0..10000)
}

wanX25PvcHistoryIndex OBJECT-TYPE
       SYNTAX       INTEGER (1..65535)
       MAX-ACCESS   not-accessible
       STATUS       current
       DESCRIPTION
              "The history of which this entry is a port.  The history
               identified by a particular value of this index is the
               same history as identified by the same value of
               historyControlIndex."
::= { wanX25PvcHistoryEntry 1 }

wanX25PvcHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases by
               one as each new sample is taken."
::= {wanX25PvcHistoryEntry 2 }

wanX25PvcHistoryIntervalStart OBJECT-TYPE
       SYNTAX       TimeTicks
       MAX-ACCESS   read-only
       STATUS       current
       DESCRIPTION
              "The value of sysUpTime at the start of the interval over
               which this sample was measured.  If the probe keeps track
               of time of day, it should start the first sample of the
               history at a time such that when the next hour of the day
               begins, a sample is started at that instant.  Note that
               following this rule may require the probe to delay collection
               the first sample of the history, as each sample must be of the
               same interval.  Also note that the sample which is currently
               being collected is not accessible in this table until the end
               of its interval."
::= { wanX25PvcHistoryEntry 3 } 

wanX25PvcHistoryDropEvents OBJECT-TYPE
       SYNTAX       Counter64
       MAX-ACCESS   read-only
       STATUS       current
       DESCRIPTION
              "The change in value of wanX25PvcStatsDropEvents during the
               interval."
::= { wanX25PvcHistoryEntry 4 }

wanX25PvcHistoryInFrames OBJECT-TYPE
       SYNTAX       Counter64
       MAX-ACCESS   read-only
       STATUS       current
       DESCRIPTION
              "The change in value of wanX25PvcStatsInFrames during the
               interval."
::= { wanX25PvcHistoryEntry 5 }

wanX25PvcHistoryOutFrames OBJECT-TYPE
       SYNTAX       Counter64
       MAX-ACCESS   read-only
       STATUS       current
       DESCRIPTION
              "The change in value of wanX25PvcStatsOutFrames during the
               interval."
::= { wanX25PvcHistoryEntry 6 }

wanX25PvcHistoryInOctets OBJECT-TYPE
       SYNTAX       Counter64
       MAX-ACCESS   read-only
       STATUS       current
       DESCRIPTION
              "The change in value of wanX25PvcStatsInOctets during the
               interval."
::= { wanX25PvcHistoryEntry 7 }

wanX25PvcHistoryOutOctets OBJECT-TYPE
       SYNTAX       Counter64
       MAX-ACCESS   read-only
       STATUS       current
       DESCRIPTION
              "The change in value of wanX25PvcStatsOutOctets during the
               interval."
::= { wanX25PvcHistoryEntry 8 }

wanX25PvcHistoryInResets OBJECT-TYPE
       SYNTAX       Counter64
       MAX-ACCESS   read-only
       STATUS       current
       DESCRIPTION
              "The change in value of wanX25PvcStatsInResets during the
               interval."
::= { wanX25PvcHistoryEntry 9 }

wanX25PvcHistoryOutResets OBJECT-TYPE
       SYNTAX       Counter64
       MAX-ACCESS   read-only
       STATUS       current
       DESCRIPTION
              "The change in value of wanX25PvcStatsOutResets during the
               interval."
::= { wanX25PvcHistoryEntry 10 }

wanX25PvcHistoryProviderResets OBJECT-TYPE
       SYNTAX       Counter64
       MAX-ACCESS   read-only
       STATUS       current
       DESCRIPTION
              "The change in value of wanX25PvcStatsProviderResets during the
               interval."
::= { wanX25PvcHistoryEntry 11 }

wanX25PvcHistoryInAccusedErrors OBJECT-TYPE
       SYNTAX       Counter64
       MAX-ACCESS   read-only
       STATUS       current
       DESCRIPTION
              "The change in value of wanX25PvcStatsInAccusedErrors during the
               interval."
::= { wanX25PvcHistoryEntry 12 }

wanX25PvcHistoryOutAccusedErrors OBJECT-TYPE
       SYNTAX       Counter64
       MAX-ACCESS   read-only
       STATUS       current
       DESCRIPTION
              "The change in value of wanX25PvcStatsOutAccusedErrors during the
               interval."
::= { wanX25PvcHistoryEntry 13 }

wanX25PvcHistoryInInterrupts OBJECT-TYPE
       SYNTAX       Counter64
       MAX-ACCESS   read-only
       STATUS       current
       DESCRIPTION
              "The change in value of wanX25PvcStatsInInterrupts during the
               interval."
::= { wanX25PvcHistoryEntry 14 }

wanX25PvcHistoryOutInterrupts OBJECT-TYPE
       SYNTAX       Counter64
       MAX-ACCESS   read-only
       STATUS       current
       DESCRIPTION
              "The change in value of wanX25PvcStatsOutInterrupts during the
               interval."
::= { wanX25PvcHistoryEntry 15 }

wanX25PvcHistoryUpTime OBJECT-TYPE
       SYNTAX       TimeTicks
       MAX-ACCESS   read-only
       STATUS       current
       DESCRIPTION
              "The change in value of wanX25PvcStatsUpTime during the
               interval."
::= { wanX25PvcHistoryEntry 16 }

wanX25PvcHistoryDownTime OBJECT-TYPE
       SYNTAX       TimeTicks
       MAX-ACCESS   read-only
       STATUS       current
       DESCRIPTION
              "The change in value of wanX25PvcStatsDownTime during the
               interval."
::= { wanX25PvcHistoryEntry 17 }

wanX25PvcHistoryStateChanges OBJECT-TYPE
       SYNTAX       Counter64
       MAX-ACCESS   read-only
       STATUS       current
       DESCRIPTION
              "The change in value of wanX25PvcStatsStateChanges during the
               interval."
::= { wanX25PvcHistoryEntry 18 }

wanX25PvcHistoryInUtilization OBJECT-TYPE
       SYNTAX       INTEGER (0..10000)
       MAX-ACCESS   read-only
       STATUS       current
       DESCRIPTION
              "The best estimated of the mean utilization of traffic on this
               LCI coming from the far end of the link in hundreds of percent
               of the CIR."
::= { wanX25PvcHistoryEntry 19 }

wanX25PvcHistoryOutUtilization OBJECT-TYPE
       SYNTAX       INTEGER (0..10000)
       MAX-ACCESS   read-only
       STATUS       current
       DESCRIPTION
              "The best estimated of the mean utilization of traffic on this
               LCI coming from the near end of the link in hundreds of percent
               of CIR."
::= { wanX25PvcHistoryEntry 20 }

wanFrPvcStatsTable OBJECT-TYPE
       SYNTAX       SEQUENCE OF WanFrPvcStatsEntry
       MAX-ACCESS   not-accessible
       STATUS       current
       DESCRIPTION
              "Frame Relay per-DLCI statistics."
::= { wanPvcStats 2 }

wanFrPvcStatsEntry OBJECT-TYPE
       SYNTAX       WanFrPvcStatsEntry
       MAX-ACCESS   not-accessible
       STATUS       current
       DESCRIPTION
              "The statistics for a frame relay DLCI. The near end of the
               link refers to the side of the link that the probe is
               monitoring.  The far end is the side the probe is not on."
       INDEX { wanFrPvcStatsIndex }
::= { wanFrPvcStatsTable 1 }

WanFrPvcStatsEntry ::= SEQUENCE {
       wanFrPvcStatsIndex                  INTEGER (1..65535),
       wanFrPvcStatsDataSource             OBJECT IDENTIFIER,
       wanFrPvcStatsDropEvents             Counter64,
       wanFrPvcStatsInFrames               Counter64,
       wanFrPvcStatsOutFrames              Counter64,
       wanFrPvcStatsInOctets               Counter64,
       wanFrPvcStatsOutOctets              Counter64,
       wanFrPvcStatsInFECNs                Counter64,
       wanFrPvcStatsOutFECNs               Counter64,
       wanFrPvcStatsInBECNs                Counter64,
       wanFrPvcStatsOutBECNs               Counter64,
       wanFrPvcStatsInDEs                  Counter64,
       wanFrPvcStatsOutDEs                 Counter64,
       wanFrPvcStatsUpTime                 TimeTicks,
       wanFrPvcStatsDownTime               TimeTicks,
       wanFrPvcStatsState                  INTEGER,
       wanFrPvcStatsStateChanges           Counter64,
       wanFrPvcStatsOwner                  OwnerString,
       wanFrPvcStatsStatus                 RowStatus
}

wanFrPvcStatsIndex OBJECT-TYPE
       SYNTAX       INTEGER (1..65535)
       MAX-ACCESS   not-accessible
       STATUS       current
       DESCRIPTION
              "The value of this object uniquely identifies this
               wanFrPvcStatsTable entry."
::= { wanFrPvcStatsEntry 1 }

wanFrPvcStatsDataSource OBJECT-TYPE
       SYNTAX       OBJECT IDENTIFIER
       MAX-ACCESS   read-create
       STATUS       current
       DESCRIPTION
              "This object identifies the source of the data that this
               wanFrPvcStatsEntry analyzes.  This source can be any
               pvcEntry associated with a frame relay interface on this
               device.  In order to identify a particular DLCI, this object
               shall identify the instance of the frame relay pvcIndex
               object, defined in the PVCCONFIG-MIB."
::= {wanFrPvcStatsEntry 2 }

wanFrPvcStatsDropEvents OBJECT-TYPE
       SYNTAX       Counter64
       MAX-ACCESS   read-only
       STATUS       current
       DESCRIPTION
              "The total number of events in which frames were dropped by
               the probe due to lack of resources.  Note that this number is
               not necessarily the number of frames dropped; it is just the
               number of times this condition has been detected."
::= { wanFrPvcStatsEntry 3 }

wanFrPvcStatsInFrames OBJECT-TYPE
       SYNTAX       Counter64
       MAX-ACCESS   read-only
       STATUS       current
       DESCRIPTION
              "The total number of frames seen coming from the far end of
               the link on this DLCI."
::= { wanFrPvcStatsEntry 4 }

wanFrPvcStatsOutFrames OBJECT-TYPE
       SYNTAX       Counter64
       MAX-ACCESS   read-only
       STATUS       current
       DESCRIPTION
              "The total number of frames seen coming from the near end of
               the link on this DLCI."
::= { wanFrPvcStatsEntry 5 }

wanFrPvcStatsInOctets OBJECT-TYPE
       SYNTAX       Counter64
       MAX-ACCESS   read-only
       STATUS       current
       DESCRIPTION
              "The sum of octets from all frames seen originating from the
               far end of the link on this DLCI."
::= { wanFrPvcStatsEntry 6 }

wanFrPvcStatsOutOctets OBJECT-TYPE
       SYNTAX       Counter64
       MAX-ACCESS   read-only
       STATUS       current
       DESCRIPTION
              "The sum of octets from all frames seen originating from the
               near end of the link on this DLCI."
::= { wanFrPvcStatsEntry 7 }

wanFrPvcStatsInFECNs OBJECT-TYPE
       SYNTAX       Counter64
       MAX-ACCESS   read-only
       STATUS       current
       DESCRIPTION
              "The number of frames see coming form the far end of the link
               with the FECN bit set on this DLCI."
::= { wanFrPvcStatsEntry 8 }

wanFrPvcStatsOutFECNs OBJECT-TYPE
       SYNTAX       Counter64
       MAX-ACCESS   read-only
       STATUS       current
       DESCRIPTION
              "The number of frames seen coming from the far end of the
               link with the BECN bit set on this DLCI."
::= { wanFrPvcStatsEntry 9 }

wanFrPvcStatsInBECNs OBJECT-TYPE
       SYNTAX       Counter64
       MAX-ACCESS   read-only
       STATUS       current
       DESCRIPTION
              "The number of frames see coming form the near end of the
               link with the FECN bit set."
::= { wanFrPvcStatsEntry 10 }

wanFrPvcStatsOutBECNs OBJECT-TYPE
       SYNTAX       Counter64
       MAX-ACCESS   read-only
       STATUS       current
       DESCRIPTION
              "The number of frames seen coming from the near end of the
               link with the BECN bit set on this DLCI."
::= { wanFrPvcStatsEntry 11 }

wanFrPvcStatsInDEs OBJECT-TYPE
       SYNTAX       Counter64
       MAX-ACCESS   read-only
       STATUS       current
       DESCRIPTION
              "The number of frames seen coming from the far end of the
               link with the DE bit set on this DCLI."
::= { wanFrPvcStatsEntry 12 }

wanFrPvcStatsOutDEs OBJECT-TYPE
       SYNTAX       Counter64
       MAX-ACCESS   read-only
       STATUS       current
       DESCRIPTION
              "The number of frames seen coming from the near end of the
               link with the DE bit set on this DLCI."
::= { wanFrPvcStatsEntry 13 }

wanFrPvcStatsUpTime OBJECT-TYPE
       SYNTAX       TimeTicks
       MAX-ACCESS   read-only
       STATUS       current
       DESCRIPTION
              "The total amount of time in one-hundreds of a second that
               the probe is sure this LCI was active, i.e., the total time
               the value of wanFrPvcStatsState was equal to up(1).  A value
               of less than the age of this entry does not necessarily mean
               that this LCI was down.  It only means the probe was not
               certain it was up.
              
               Note: the sum of wanFrPvcStatsUpTime and wanFrPvcStatsDownTime
               may be less than the age of this entry.  In this case, the
               unaccounted for time is the time the probe was uncertain of the
               state of this DLCI, i.e., the total time the value of
               wanFrPvcStatsState was unknown(3)."
::= { wanFrPvcStatsEntry 14 }

wanFrPvcStatsDownTime OBJECT-TYPE
       SYNTAX       TimeTicks
       MAX-ACCESS   read-only
       STATUS       current
       DESCRIPTION
              "The total amount of time in one-hundreds of a second that
               the probe is sure this LCI was down, i.e., the total time
               the value of wanFrPvcStatsState was equal to down(3).  A
               value of less than the age of this entry does not
               necessarily mean that this LCI was up at some point.  It
               only means the probe was not certain it was down.
              
               Note: the sum of wanX25PvcStatsUpTime and wanFrPvcStatsDownTime
               may be less than the age of this entry.  In this case, the
               unaccounted for time is the time the probe was uncertain of the
               state of this DLCI, i.e., the total time the value of
               wanFrPvcStatsState was unknown(3)."
::= { wanFrPvcStatsEntry 15 }

wanFrPvcStatsState OBJECT-TYPE
       SYNTAX       INTEGER {
       up(1),
       down(2),
       unknown(3)
}
MAX-ACCESS   read-only
STATUS       current
DESCRIPTION
              "The current state of this DLCI as inferred by the probe.
               A value of up(2) means the DLCI is active.  A value of down(2)
               means the DLCI is inactive.  And a value of unknown(3) means
               the probe cannot currently infer the state."
::= { wanFrPvcStatsEntry 16 }

wanFrPvcStatsStateChanges OBJECT-TYPE
       SYNTAX       Counter64
       MAX-ACCESS   read-only
       STATUS       current
       DESCRIPTION
              "The count of the number of times the wanFrPvcStatsState has
               gone from up(1) to down(2) or vice versa.  The number of
               times wanFrPvcStatsState goes to unknown(3) is not counted.
               However, if the value goes from up(1) to unknown(3) and then
               to down(2) should be counted as 1.  Likewise going from down(2)
               to unknown(3) and then to up(3) should be counted as 1."
::= { wanFrPvcStatsEntry 17 }

wanFrPvcStatsOwner OBJECT-TYPE
       SYNTAX       OwnerString
       MAX-ACCESS   read-create
       STATUS       current
       DESCRIPTION
              "The entity that configured this entry."
::= { wanFrPvcStatsEntry 18 }

wanFrPvcStatsStatus OBJECT-TYPE
       SYNTAX       RowStatus
--     MAX-ACCESS   read-write
       MAX-ACCESS   read-create
       STATUS       current
       DESCRIPTION
              "The status of this wanFrPvcStatsTable entry."
::= { wanFrPvcStatsEntry 19 }

wanFrPvcHistoryTable OBJECT-TYPE
       SYNTAX       SEQUENCE OF WanFrPvcHistoryEntry
       MAX-ACCESS   not-accessible
       STATUS       current
       DESCRIPTION
              "Frame Relay per-DCLI statistics."
::= { wanPvcHistory 2 }

wanFrPvcHistoryEntry OBJECT-TYPE
       SYNTAX       WanFrPvcHistoryEntry
       MAX-ACCESS   not-accessible
       STATUS       current
       DESCRIPTION
              "The statistics for a frame relay DLCI. The near end of the
               link refers to the side of the link that the probe is
               monitoring.  The far end is the side the probe is not on."
       INDEX { wanFrPvcHistoryIndex, wanFrPvcHistorySampleIndex }
::= { wanFrPvcHistoryTable 1 }

WanFrPvcHistoryEntry ::= SEQUENCE {
       wanFrPvcHistoryIndex                INTEGER (1..65535),
       wanFrPvcHistorySampleIndex          INTEGER (1..2147483647),
       wanFrPvcHistoryIntervalStart        TimeTicks,
       wanFrPvcHistoryDropEvents           Counter64,
       wanFrPvcHistoryInFrames             Counter64,
       wanFrPvcHistoryOutFrames            Counter64,
       wanFrPvcHistoryInOctets             Counter64,
       wanFrPvcHistoryOutOctets            Counter64,
       wanFrPvcHistoryInFECNs              Counter64,
       wanFrPvcHistoryOutFECNs             Counter64,
       wanFrPvcHistoryInBECNs              Counter64,
       wanFrPvcHistoryOutBECNs             Counter64,
       wanFrPvcHistoryInDEs                Counter64,
       wanFrPvcHistoryOutDEs               Counter64,
       wanFrPvcHistoryUpTime               TimeTicks,
       wanFrPvcHistoryDownTime             TimeTicks,
       wanFrPvcHistoryStateChanges         Counter64,
       wanFrPvcHistoryInUtilization        INTEGER (0..10000),
       wanFrPvcHistoryOutUtilization       INTEGER (0..10000)
}

wanFrPvcHistoryIndex OBJECT-TYPE
       SYNTAX       INTEGER (1..65535)
       MAX-ACCESS   not-accessible
       STATUS       current
       DESCRIPTION
              "The history of which this entry is a port.  The history
               identified by a particular value of this index is the same
               history as identified by the same value of historyControlIndex."
::= { wanFrPvcHistoryEntry 1 }

wanFrPvcHistorySampleIndex OBJECT-TYPE
       SYNTAX       INTEGER (1..2147483647)
       MAX-ACCESS   not-accessible 
       STATUS       current
       DESCRIPTION
              "An index that uniquely identifies the particular sample this
               entry represents among all samples associated with the same
               historyControlEntry.  This index starts at 1 and increases by
               one as each new sample is taken."
::= { wanFrPvcHistoryEntry 2 }

wanFrPvcHistoryIntervalStart OBJECT-TYPE
       SYNTAX       TimeTicks
       MAX-ACCESS   read-only
       STATUS       current
       DESCRIPTION
              "The value of sysUpTime at the start of the interval over
               which this sample was measured.  If the probe keeps track
               of time of day, it should start the first sample of the
               history at a time such that when the next hour of the day
               begins, a sample is started at that instant.  Note that
               following this rule may require the probe to delay collection
               the first sample of the history, as each sample must be of the
               same interval.  Also note that the sample which is currently
               being collected is not accessible in this table until the end
               of its interval."
::= { wanFrPvcHistoryEntry 3 } 

wanFrPvcHistoryDropEvents OBJECT-TYPE
       SYNTAX       Counter64
       MAX-ACCESS   read-only
       STATUS       current
       DESCRIPTION
              "The change in value of wanFrPvcStatsDropEvents during the
               interval."
::= { wanFrPvcHistoryEntry 4 }

wanFrPvcHistoryInFrames OBJECT-TYPE
       SYNTAX       Counter64
       MAX-ACCESS   read-only
       STATUS       current
       DESCRIPTION
              "The change in value of wanFrPvcStatsInFrames during the
               interval."
::= { wanFrPvcHistoryEntry 5 }

wanFrPvcHistoryOutFrames OBJECT-TYPE
       SYNTAX       Counter64
       MAX-ACCESS   read-only
       STATUS       current
       DESCRIPTION
              "The change in value of wanFrPvcStatsOutFrames during the
               interval."
::= { wanFrPvcHistoryEntry 6 }

wanFrPvcHistoryInOctets OBJECT-TYPE
       SYNTAX       Counter64
       MAX-ACCESS   read-only
       STATUS       current
       DESCRIPTION
              "The change in value of wanFrPvcStatsInOctets during the
               interval."
::= { wanFrPvcHistoryEntry 7 }

wanFrPvcHistoryOutOctets OBJECT-TYPE
       SYNTAX       Counter64
       MAX-ACCESS   read-only
       STATUS       current
       DESCRIPTION
              "The change in value of wanFrPvcStatsOutOctets during the
               interval."
::= { wanFrPvcHistoryEntry 8 }

wanFrPvcHistoryInFECNs OBJECT-TYPE
       SYNTAX       Counter64
       MAX-ACCESS   read-only
       STATUS       current
       DESCRIPTION
              "The change in value of wanFrPvcStatsInFECNs during the
               interval."
::= { wanFrPvcHistoryEntry 9 }

wanFrPvcHistoryOutFECNs OBJECT-TYPE
       SYNTAX       Counter64
       MAX-ACCESS   read-only
       STATUS       current
       DESCRIPTION
              "The change in value of wanFrPvcStatsOutFECNs during the
               interval."
::= { wanFrPvcHistoryEntry 10 }

wanFrPvcHistoryInBECNs OBJECT-TYPE
       SYNTAX       Counter64
       MAX-ACCESS   read-only
       STATUS       current
       DESCRIPTION
              "The change in value of wanFrPvcStatsInBECNs during the
               interval."
::= { wanFrPvcHistoryEntry 11 }

wanFrPvcHistoryOutBECNs OBJECT-TYPE
       SYNTAX       Counter64
       MAX-ACCESS   read-only
       STATUS       current
       DESCRIPTION
              "The change in value of wanFrPvcStatsOutBECNs during the
               interval."
::= { wanFrPvcHistoryEntry 12 }

wanFrPvcHistoryInDEs OBJECT-TYPE
       SYNTAX       Counter64
       MAX-ACCESS   read-only
       STATUS       current
       DESCRIPTION
              "The change in value of wanFrPvcStatsInDEs during the
               interval."
::= { wanFrPvcHistoryEntry 13 }

wanFrPvcHistoryOutDEs OBJECT-TYPE
       SYNTAX       Counter64
       MAX-ACCESS   read-only
       STATUS       current
       DESCRIPTION
              "The change in value of wanFrPvcStatsOutDEs during the
               interval."
::= { wanFrPvcHistoryEntry 14 }

wanFrPvcHistoryUpTime OBJECT-TYPE
       SYNTAX       TimeTicks
       MAX-ACCESS   read-only
       STATUS       current
       DESCRIPTION
              "The change in value of wanFrPvcStatsUpTime during the
               interval."
::= { wanFrPvcHistoryEntry 15 }

wanFrPvcHistoryDownTime OBJECT-TYPE
       SYNTAX       TimeTicks
       MAX-ACCESS   read-only
       STATUS       current
       DESCRIPTION
              "The change in value of wanFrPvcStatsDownTime during the
               interval."
::= { wanFrPvcHistoryEntry 16 }

wanFrPvcHistoryStateChanges OBJECT-TYPE
       SYNTAX       Counter64
       MAX-ACCESS   read-only
       STATUS       current
       DESCRIPTION
              "The change in value of wanFrPvcStatsStateChanges during the
               interval."
::= { wanFrPvcHistoryEntry 17 }

wanFrPvcHistoryInUtilization OBJECT-TYPE
       SYNTAX       INTEGER (0..10000)
       MAX-ACCESS   read-only
       STATUS       current
       DESCRIPTION
              "The best estimated of the mean utilization of traffic on
               this DLCI coming from the far end of the link in hundreds
               of percent of the CIR."
::= { wanFrPvcHistoryEntry 18 }

wanFrPvcHistoryOutUtilization OBJECT-TYPE
       SYNTAX       INTEGER (0..10000)
       MAX-ACCESS   read-only
       STATUS       current
       DESCRIPTION
              "The best estimated of the mean utilization of traffic on
               this DLCI coming from the near end of the link in hundreds
               of percent of CIR."
::= { wanFrPvcHistoryEntry 19 }

wanAal5PvcStatsTable OBJECT-TYPE
       SYNTAX       SEQUENCE OF WanAal5PvcStatsEntry
       MAX-ACCESS   not-accessible
       STATUS       current
       DESCRIPTION
              "AAL/5 per-VPI/VCI statistics."
::= { wanPvcStats 3 }

wanAal5PvcStatsEntry OBJECT-TYPE
       SYNTAX       WanAal5PvcStatsEntry
       MAX-ACCESS   not-accessible
       STATUS       current
       DESCRIPTION
              "The statistics for a AAL-5 VCI/VPI. The near end of the
               link refers to the side of the link that the probe is
               monitoring.  The far end is the side the probe is not on."
       INDEX { wanAal5PvcStatsIndex }
::= { wanAal5PvcStatsTable 1 }

WanAal5PvcStatsEntry ::= SEQUENCE {
       wanAal5PvcStatsIndex                INTEGER (1..65535),
       wanAal5PvcStatsDataSource           OBJECT IDENTIFIER,
       wanAal5PvcStatsDropEvents           Counter64,
       wanAal5PvcStatsInCells              Counter64,
       wanAal5PvcStatsOutCells             Counter64,
       wanAal5PvcStatsInPDUs               Counter64,
       wanAal5PvcStatsOutPDUs              Counter64,
       wanAal5PvcStatsInOctets             Counter64,
       wanAal5PvcStatsOutOctets            Counter64,
       wanAal5PvcStatsInCLP1               Counter64,
       wanAal5PvcStatsOutCLP1              Counter64,
       wanAal5PvcStatsInCRCs               Counter64,
       wanAal5PvcStatsOutCRCs              Counter64,
       wanAal5PvcStatsInOversizedSDUs      Counter64,
       wanAal5PvcStatsOutOversizedSDUs     Counter64,
       wanAal5PvcStatsUpTime               TimeTicks,
       wanAal5PvcStatsDownTime             TimeTicks,
       wanAal5PvcStatsState                INTEGER,
       wanAal5PvcStatsStateChanges         Counter64,
       wanAal5PvcStatsOwner                OwnerString,
       wanAal5PvcStatsStatus               RowStatus
}

wanAal5PvcStatsIndex OBJECT-TYPE
       SYNTAX       INTEGER (1..65535)
       MAX-ACCESS   not-accessible
       STATUS       current
       DESCRIPTION
              "The value of this object uniquely identifies this
               wanAal5PvcStatsTable entry."
::= { wanAal5PvcStatsEntry 1 }

wanAal5PvcStatsDataSource OBJECT-TYPE
       SYNTAX       OBJECT IDENTIFIER
       MAX-ACCESS   read-create
       STATUS       current
       DESCRIPTION
              "This object identifies the source of the data that this
               wanAal5StatsEntry analyzes.  This source can be any
               pvcEntry that is associated with an ATM interface on this
               device.  In order to identify a particular VPI/VCI, this
               object shall identify the instance of the pvcIndex object,
               defined in the PVCCONFIG-MIB."
::= { wanAal5PvcStatsEntry 2 }

wanAal5PvcStatsDropEvents OBJECT-TYPE
       SYNTAX       Counter64
       MAX-ACCESS   read-only
       STATUS       current
       DESCRIPTION
              "The total number of events in which frames were dropped
               by the probe due to lack of resources.  Note that this
               number is not necessarily the number of frames dropped;
               it is just the number of times this condition has been
               detected."
::= { wanAal5PvcStatsEntry 3 }

wanAal5PvcStatsInCells OBJECT-TYPE
       SYNTAX       Counter64
       MAX-ACCESS   read-only
       STATUS       current
       DESCRIPTION
              "The total number of cells for seen coming from the far
               end of the link on this VPI/VCI."
::= { wanAal5PvcStatsEntry 4 }

wanAal5PvcStatsOutCells OBJECT-TYPE
       SYNTAX       Counter64
       MAX-ACCESS   read-only
       STATUS       current
       DESCRIPTION
              "The total number of cells seen coming from the near end
               of the link on this VPI/VCI."
::= { wanAal5PvcStatsEntry 5 }

wanAal5PvcStatsInPDUs OBJECT-TYPE
       SYNTAX       Counter64
       MAX-ACCESS   read-only
       STATUS       current
       DESCRIPTION
              "The total number of AAL-5 PDUs seen coming from the far
               end of the link on this VPI/VCI."
::= { wanAal5PvcStatsEntry 6 }

wanAal5PvcStatsOutPDUs OBJECT-TYPE
       SYNTAX       Counter64
       MAX-ACCESS   read-only
       STATUS       current
       DESCRIPTION
              "The total number of AAL-5 PDUs seen coming from the near
               end of the link on this VPI/VCI."
::= { wanAal5PvcStatsEntry 7 }

wanAal5PvcStatsInOctets OBJECT-TYPE
       SYNTAX       Counter64
       MAX-ACCESS   read-only
       STATUS       current
       DESCRIPTION
              "The sum of octets from all AAL-5 PDUs seen originating from
               the far end of the link on this VCI/VPI."
::= { wanAal5PvcStatsEntry 8 }

wanAal5PvcStatsOutOctets OBJECT-TYPE
       SYNTAX       Counter64
       MAX-ACCESS   read-only
       STATUS       current
       DESCRIPTION
              "The sum of octets from all AAL-5 PDUs seen originating from
               the near end of the link on this VPI/VCI."
::= { wanAal5PvcStatsEntry 9 }

wanAal5PvcStatsInCLP1 OBJECT-TYPE
       SYNTAX       Counter64
       MAX-ACCESS   read-only
       STATUS       current
       DESCRIPTION
              "The total number of cells with the CLP bit set seen coming
               from the far end of the link on this VCI/VPI."
::= { wanAal5PvcStatsEntry 10 }

wanAal5PvcStatsOutCLP1 OBJECT-TYPE
       SYNTAX       Counter64
       MAX-ACCESS   read-only
       STATUS       current
       DESCRIPTION
              "The total number of cells with the CLP bit set seen coming
               from the near end of the link on this VCI/VPI."
::= { wanAal5PvcStatsEntry 11 }

wanAal5PvcStatsInCRCs OBJECT-TYPE
       SYNTAX       Counter64
       MAX-ACCESS   read-only
       STATUS       current
       DESCRIPTION
              "The total number of AAL-5 PDUs with CRC errors seen coming
               from the far end of the link on this VCI/VPI."
::= { wanAal5PvcStatsEntry 12 }

wanAal5PvcStatsOutCRCs OBJECT-TYPE
       SYNTAX       Counter64
       MAX-ACCESS   read-only
       STATUS       current
       DESCRIPTION
              "The total number of AAL-5 PDUs with CRC errors seen coming
               from the near end of the link on this VPI/VCI."
::= { wanAal5PvcStatsEntry 13 }

wanAal5PvcStatsInOversizedSDUs OBJECT-TYPE
       SYNTAX       Counter64
       MAX-ACCESS   read-only
       STATUS       current
       DESCRIPTION
              "The number of AAL5 SDUs from the far end of the link that
               were too large on this VPI/VCI."
::= { wanAal5PvcStatsEntry 14 }

wanAal5PvcStatsOutOversizedSDUs OBJECT-TYPE
       SYNTAX       Counter64
       MAX-ACCESS   read-only
       STATUS       current
       DESCRIPTION
              "The number of AAL5 SDUs from the near end of the link that
               were too large on this VPI/VCI."
::= { wanAal5PvcStatsEntry 15 }

wanAal5PvcStatsUpTime OBJECT-TYPE
       SYNTAX       TimeTicks
       MAX-ACCESS   read-only
       STATUS       current
       DESCRIPTION
              "The total amount of time in one-hundreds of a second that
               the probe is sure this LCI was active, i.e., the total time
               the value of wanAal5PvcStatsState was equal to up(1).  A value
               of less than the age of this entry does not necessarily mean
               that this VPI/VCI was down.  It only means the probe was not
               certain it was up.
              
               Note: the sum of wanAal5PvcStatsUpTime and
               wanAal5PvcStatsDownTime may be less than the age of this entry.
               In this case, the unaccounted for time is the time the probe was
               uncertain of the state of this VPI/VCI, i.e., the total time the
               value of wanAal5PvcStatsState was unknown(3)."
::= { wanAal5PvcStatsEntry 16 }

wanAal5PvcStatsDownTime OBJECT-TYPE
       SYNTAX       TimeTicks
       MAX-ACCESS   read-only
       STATUS       current
       DESCRIPTION
              "The total amount of time in one-hundreds of a second that the
               probe is sure this LCI was down, i.e., the total time the
               value of wanAal5PvcStatsState was equal to down(3).  A value of
               less than the age of this entry does not necessarily mean that
               this VPI/VCI was up at some point.  It only means the probe was
               not certain it was down.
              
               Note: the sum of wanAal5PvcStatsUpTime and
               wanAal5PvcStatsDownTime may be less than the age of this entry.
               In this case, the unaccounted for time is the time the probe was
               uncertain of the state of this VPI/VCI, i.e., the total time the
               value of wanAal5PvcStatsState was unknown(3)."
::= { wanAal5PvcStatsEntry 17 }

wanAal5PvcStatsState OBJECT-TYPE
       SYNTAX       INTEGER {
              up(1),
              down(2),
              unknown(3)
       }
       MAX-ACCESS   read-only
       STATUS       current
       DESCRIPTION
              "The current state of this VPI/VCI as inferred by the probe.
               A value of up(2) means the LCI is active.  A value of down(2)
               means the VPI/VCI is inactive.  And a value of unknown(3)
               means the probe cannot currently infer the state."
::= { wanAal5PvcStatsEntry 18 }

wanAal5PvcStatsStateChanges OBJECT-TYPE
       SYNTAX       Counter64
       MAX-ACCESS   read-only
       STATUS       current
       DESCRIPTION
              "The count of the number of times the wanAal5PvcStatsState
               has gone from up(1) to down(2) or vice versa.  The number of
               times wanAal5PvcStatsState goes to unknown(3) is not counted.
               However, if the value goes from up(1) to unknown(3) and then
               to down(2) should be counted as 1.  Likewise going from down(2)
               to unknown(3) and then to up(3) should be counted as 1."
::= { wanAal5PvcStatsEntry 19 }

wanAal5PvcStatsOwner OBJECT-TYPE
       SYNTAX       OwnerString
       MAX-ACCESS   read-create
       STATUS       current
       DESCRIPTION
              "The entity that configured this entry."
::= { wanAal5PvcStatsEntry 20 }

wanAal5PvcStatsStatus OBJECT-TYPE
       SYNTAX       RowStatus
--     MAX-ACCESS   read-write
       MAX-ACCESS   read-create
       STATUS       current
       DESCRIPTION
              "The status of this wanAal5PvcStatsTable entry."
::= { wanAal5PvcStatsEntry 21 }

wanAal5PvcHistoryTable OBJECT-TYPE
       SYNTAX       SEQUENCE OF WanAal5PvcHistoryEntry
       MAX-ACCESS   not-accessible
       STATUS       current
       DESCRIPTION
              "AAL-5 per-VPI/VCI statistics."
::= { wanPvcHistory 3 }

wanAal5PvcHistoryEntry OBJECT-TYPE
       SYNTAX       WanAal5PvcHistoryEntry
       MAX-ACCESS   not-accessible
       STATUS       current
       DESCRIPTION
              "The statistics for a AAL-5 VCI/VPI. The near end of the link
               refers to the side of the link that the probe is monitoring.
               The far end is the side the probe is not on."
       INDEX { wanAal5PvcHistoryIndex, wanAal5PvcHistorySampleIndex }
::= { wanAal5PvcHistoryTable 1 }

WanAal5PvcHistoryEntry ::= SEQUENCE {
       wanAal5PvcHistoryIndex              INTEGER (1..65535),
       wanAal5PvcHistorySampleIndex        INTEGER (1..2147483647),
       wanAal5PvcHistoryIntervalStart      TimeTicks,
       wanAal5PvcHistoryDropEvents         Counter64,
       wanAal5PvcHistoryInCells            Counter64,
       wanAal5PvcHistoryOutCells           Counter64,
       wanAal5PvcHistoryInPDUs             Counter64,
       wanAal5PvcHistoryOutPDUs            Counter64,
       wanAal5PvcHistoryInOctets           Counter64,
       wanAal5PvcHistoryOutOctets          Counter64,
       wanAal5PvcHistoryInCLP1             Counter64,
       wanAal5PvcHistoryOutCLP1            Counter64,
       wanAal5PvcHistoryInCRCs             Counter64,
       wanAal5PvcHistoryOutCRCs            Counter64,
       wanAal5PvcHistoryInOversizedSDUs    Counter64,
       wanAal5PvcHistoryOutOversizedSDUs   Counter64,
       wanAal5PvcHistoryUpTime             TimeTicks,
       wanAal5PvcHistoryDownTime           TimeTicks,
       wanAal5PvcHistoryStateChanges       Counter64,
       wanAal5PvcHistoryInUtilization      INTEGER (0..10000),
       wanAal5PvcHistoryOutUtilization     INTEGER (0..10000)
}

wanAal5PvcHistoryIndex OBJECT-TYPE
       SYNTAX       INTEGER (1..65535)
       MAX-ACCESS   not-accessible
       STATUS       current
       DESCRIPTION
              "The history of which this entry is a port.  The history
               identified by a particular value of this index is the same
               history as identified by the same value of
               historyControlIndex."
::= { wanAal5PvcHistoryEntry 1 }

wanAal5PvcHistorySampleIndex OBJECT-TYPE
       SYNTAX       INTEGER (1..2147483647)
       MAX-ACCESS   not-accessible 
       STATUS       current
       DESCRIPTION
              "An index that uniquely identifies the particular sample
               this entry represents among all samples associated with
               the same historyControlEntry.  This index starts at 1 and
               increases by one as each new sample is taken."
::= {wanAal5PvcHistoryEntry 2 }

wanAal5PvcHistoryIntervalStart OBJECT-TYPE
       SYNTAX       TimeTicks
       MAX-ACCESS   read-only
       STATUS       current
       DESCRIPTION
              "The value of sysUpTime at the start of the interval over
               which this sample was measured.  If the probe keeps track
               of time of day, it should start the first sample of the
               history at a time such that when the next hour of the day
               begins, a sample is started at that instant.  Note that
               following this rule may require the probe to delay collection
               the first sample of the history, as each sample must be of the
               same interval.  Also note that the sample which is currently
               being collected is not accessible in this table until the end
               of its interval."
::= { wanAal5PvcHistoryEntry 3 } 

wanAal5PvcHistoryDropEvents OBJECT-TYPE
       SYNTAX       Counter64
       MAX-ACCESS   read-only
       STATUS       current
       DESCRIPTION
              "The change in value of wanAal5PvcStatsDropEvents during the
               interval."
::= { wanAal5PvcHistoryEntry 4 }

wanAal5PvcHistoryInCells OBJECT-TYPE
       SYNTAX       Counter64
       MAX-ACCESS   read-only
       STATUS       current
       DESCRIPTION
              "The change in value of wanAal5PvcStatsInCells during the
               interval."
::= { wanAal5PvcHistoryEntry 5 }

wanAal5PvcHistoryOutCells OBJECT-TYPE
       SYNTAX       Counter64
       MAX-ACCESS   read-only
       STATUS       current
       DESCRIPTION
              "The change in value of wanAal5PvcStatsOutCells during the
               interval."
::= { wanAal5PvcHistoryEntry 6 }

wanAal5PvcHistoryInPDUs OBJECT-TYPE
       SYNTAX       Counter64
       MAX-ACCESS   read-only
       STATUS       current
       DESCRIPTION
              "The change in value of wanAal5PvcStatsInPDUs during the
               interval."
::= { wanAal5PvcHistoryEntry 7 }

wanAal5PvcHistoryOutPDUs OBJECT-TYPE
       SYNTAX       Counter64
       MAX-ACCESS   read-only
       STATUS       current
       DESCRIPTION
              "The change in value of wanAal5PvcStatsOutPDUs during the
               interval."
::= { wanAal5PvcHistoryEntry 8 }

wanAal5PvcHistoryInOctets OBJECT-TYPE
       SYNTAX       Counter64
       MAX-ACCESS   read-only
       STATUS       current
       DESCRIPTION
              "The change in value of wanAal5PvcStatsInOctets during the
               interval."
::= { wanAal5PvcHistoryEntry 9 }

wanAal5PvcHistoryOutOctets OBJECT-TYPE
       SYNTAX       Counter64
       MAX-ACCESS   read-only
       STATUS       current
       DESCRIPTION
              "The change in value of wanAal5PvcStatsOutOctets during the
               interval."
::= { wanAal5PvcHistoryEntry 10 }

wanAal5PvcHistoryInCLP1 OBJECT-TYPE
       SYNTAX       Counter64
       MAX-ACCESS   read-only
       STATUS       current
       DESCRIPTION
              "The change in value of wanAal5PvcStatsInCLP1 during the
               interval."
::= { wanAal5PvcHistoryEntry 11 }

wanAal5PvcHistoryOutCLP1 OBJECT-TYPE
       SYNTAX       Counter64
       MAX-ACCESS   read-only
       STATUS       current
       DESCRIPTION
              "The change in value of wanAal5PvcStatsOutCLP1 during the
               interval."
::= { wanAal5PvcHistoryEntry 12 }

wanAal5PvcHistoryInCRCs OBJECT-TYPE
       SYNTAX       Counter64
       MAX-ACCESS   read-only
       STATUS       current
       DESCRIPTION
              "The change in value of wanAal5PvcStatsInCRCs during the
               interval."
::= { wanAal5PvcHistoryEntry 13 }

wanAal5PvcHistoryOutCRCs OBJECT-TYPE
       SYNTAX       Counter64
       MAX-ACCESS   read-only
       STATUS       current
       DESCRIPTION
              "The change in value of wanAal5PvcStatsOutCRCs during the
               interval."
::= { wanAal5PvcHistoryEntry 14 }

wanAal5PvcHistoryInOversizedSDUs OBJECT-TYPE
       SYNTAX       Counter64
       MAX-ACCESS   read-only
       STATUS       current
       DESCRIPTION
              "The change in value of wanAal5PvcStatsInOversizedSDUs
               during the interval."
::= { wanAal5PvcHistoryEntry 15 }

wanAal5PvcHistoryOutOversizedSDUs OBJECT-TYPE
       SYNTAX       Counter64
       MAX-ACCESS   read-only
       STATUS       current
       DESCRIPTION
              "The change in value of wanAal5PvcStatsOutOversizedSDUs
               during the interval."
::= { wanAal5PvcHistoryEntry 16 }

wanAal5PvcHistoryUpTime OBJECT-TYPE
       SYNTAX       TimeTicks
       MAX-ACCESS   read-only
       STATUS       current
       DESCRIPTION
              "The change in value of wanAal5PvcStatsUpTime
               during the interval."
::= { wanAal5PvcHistoryEntry 17 }

wanAal5PvcHistoryDownTime OBJECT-TYPE
       SYNTAX       TimeTicks
       MAX-ACCESS   read-only
       STATUS       current
       DESCRIPTION
              "The change in value of wanAal5PvcStatsDownTime
               during the interval."
::= { wanAal5PvcHistoryEntry 18 }

wanAal5PvcHistoryStateChanges OBJECT-TYPE
       SYNTAX       Counter64
       MAX-ACCESS   read-only
       STATUS       current
       DESCRIPTION
              "The change in value of wanAal5PvcStatsStateChanges
               during the interval."
::= { wanAal5PvcHistoryEntry 19 }

wanAal5PvcHistoryInUtilization OBJECT-TYPE
       SYNTAX       INTEGER (0..10000)
       MAX-ACCESS   read-only
       STATUS       current
       DESCRIPTION
              "The best estimated of the mean utilization of traffic on
               this VPI/VCI coming from the far end of the link in hundreds
               of percent of the CIR."
::= { wanAal5PvcHistoryEntry 20 }

wanAal5PvcHistoryOutUtilization OBJECT-TYPE
       SYNTAX       INTEGER (0..10000)
       MAX-ACCESS   read-only
       STATUS       current
       DESCRIPTION
              "The best estimated of the mean utilization of traffic on
               this VPI/VCI coming from the near end of the link in hundreds
               of percent of CIR."
::= { wanAal5PvcHistoryEntry 21 }

END
