--
-- WEBMON-EDGE-MATRIX-MIB.my
--

	WEBMON-EDGE-MATRIX-MIB DEFINITIONS ::= BEGIN

		IMPORTS 
			OBJECT-GROUP, NOTIFICATION-GROUP			
				FROM SNMPv2-CONF			
			Unsigned32, Integer32, IpAddress, enterprises, OBJECT-TYPE, MODULE-IDENTITY, OBJECT-IDENTITY, NOTIFICATION-TYPE			
				FROM SNMPv2-SMI			
			TEXTUAL-CONVENTION			
				FROM SNMPv2-TC;
	
	
		moduleIdentity MODULE-IDENTITY
			LAST-UPDATED "201205172218Z"
			ORGANIZATION
				"Dantel, Inc."
			CONTACT-INFO
				"Dantel, Inc.
				P.O. Box 55013
				Fresno, CA 93747-5013
				
				For customer support, call:
				1-800-4-DANTEL"
			DESCRIPTION
				"WebMon Edge-Matrix MIB."
 			REVISION "201205172218Z"
			DESCRIPTION 
				"MIB for WebMon Edge-Matrix version 1.18.3."
			::= { webMon 3 }


--
-- Textual conventions
--
	
		DescriptionString ::= TEXTUAL-CONVENTION
			STATUS current
			DESCRIPTION
				"A character string used for descriptions."
			SYNTAX OCTET STRING (SIZE (0..80))
			
		DigitalState ::= TEXTUAL-CONVENTION
			STATUS current
			DESCRIPTION
				"A type with only two states, used specifically to represent the 
				state of a digital reading."
			SYNTAX INTEGER
				{
					off(0),
					on(1)
				}
			
		Boolean ::= TEXTUAL-CONVENTION
			STATUS current
			DESCRIPTION
				"A type with only two states."
			SYNTAX INTEGER
				{
					false(0),
					true(1)
				}
			
		ConnectivityState ::= TEXTUAL-CONVENTION
			STATUS current
			DESCRIPTION
				"Used for the state of a connection."
			SYNTAX INTEGER
				{
					online(0),
					offline(1)
				}
			
		AnalogState ::= TEXTUAL-CONVENTION
			STATUS current
			DESCRIPTION
				"Defines states for an analog input."
			SYNTAX INTEGER
				{
					highHigh(0),
					high(1),
					medium(2),
					low(3),
					lowLow(4)
				} 
				
		Configured ::= TEXTUAL-CONVENTION
			STATUS current
			DESCRIPTION
				"In use"
			SYNTAX INTEGER
				{
					not-in-use(0),
					always-in-use(1),
					schedule-a(2),
					schedule-b(3),
					schedule-c(4),
					schedule-d(5)
				}
			
		Level ::= TEXTUAL-CONVENTION
			STATUS current
			DESCRIPTION
				"Describes a priority or level."
			SYNTAX INTEGER
				{
					normal(0),
					critical(1),
					major(2),
					minor(3),
					status(4)
				}
			
		SnmpVersion ::= TEXTUAL-CONVENTION
			STATUS current
			DESCRIPTION
				"Defines which version of SNMP is used for traps."
			SYNTAX INTEGER
				{
					snmpv1(0),
					snmpv2c(1),
					snmpv3(2),
					snmpv2c-inform(3),
					snmpv3-inform(4)
				}
			
		CameraStyle ::= TEXTUAL-CONVENTION
			STATUS current
			DESCRIPTION
				"Defines the different types of IP cameras supported."
			SYNTAX INTEGER
				{
					d-link-dcs1000(0),
					sony-snc-rz30n(1),
					axis-2100(2),
					d-link-dcs2000(3),
					d-link-dcs5300(4),
					axis-210(5),
					axis-m1103(6)
				}
			
		ContactStyle ::= TEXTUAL-CONVENTION
			STATUS current
			DESCRIPTION
				"Defines the different types of discrete alarm contacts."
			SYNTAX INTEGER
				{
					dry-contact(0),
					wet-contact(1)
				}
			
		MeasureStyle ::= TEXTUAL-CONVENTION
			STATUS current
			DESCRIPTION
				"Defines state of measurement style English or Metic."
			SYNTAX INTEGER
				{
					english(0),
					metric(1)
				}
			
		OutputMode ::= TEXTUAL-CONVENTION
			STATUS current
			DESCRIPTION
				"Defines the different ways a control point can be activated."
			SYNTAX INTEGER
				{
					manual(0),
					automatic(1)
				}
			
		OutputState ::= TEXTUAL-CONVENTION
			STATUS current
			DESCRIPTION
				"Defines states for an output."
			SYNTAX INTEGER
				{
					open(0),
					closed(1)
				}
			
		BaudRate ::= TEXTUAL-CONVENTION
			STATUS current
			DESCRIPTION
				"Defines baud rates for serial communication."
			SYNTAX INTEGER
				{
					baud-300(300),
					baud-600(600),
					baud-1200(1200),
					baud-2400(2400),
					baud-4800(4800),
					baud-9600(9600),
					baud-19200(19200),
					baud-28800(28800),
					baud-38400(38400)
				}
			
		DataBits ::= TEXTUAL-CONVENTION
			STATUS current
			DESCRIPTION
				"Defines the number of data bits in a byte for serial communication."
			SYNTAX INTEGER
				{
					data-bits-7(7),
					data-bits-8(8)
				}
			
		Parity ::= TEXTUAL-CONVENTION
			STATUS current
			DESCRIPTION
				"Defines the parity for serial communication."
			SYNTAX INTEGER
				{
					none(0),
					even-parity(1),
					odd-parity(2)
				}
			
		StopBits ::= TEXTUAL-CONVENTION
			STATUS current
			DESCRIPTION
				"Defines the number of stop bits in a byte for serial communication."
			SYNTAX INTEGER
				{
					stop-bit-1(1),
					stop-bits-2(2)
				}
			
		Protocol ::= TEXTUAL-CONVENTION
			STATUS current
			DESCRIPTION
				"Defines different protocols used for communication."
			SYNTAX INTEGER
				{
					none(0),
					command-line(1),
					modbus-interrogation(2),
					configuration-transfer(3),
					ip-switchboard(4),
					terminal-server(5),
					user-login(6),
					modem-mode(7),
					ppp-server(8),
					dcm-responder(9),
					ascii-log-single-line(10),
					e2a-host(11),
					gps-reader(12),
					port-redirect(13),
					sensor-reader(14),
					tl1-responder(15),
					dcpf-responder(16),
					lcd-protocol(17),
					tabs-responder(18),
					configuration-menu(19),
					sensor-hub-interrogation(20)
				}
			
		SerialRTS ::= TEXTUAL-CONVENTION
			STATUS current
			DESCRIPTION
				"Defines the different RTS states for serial communication."
			SYNTAX INTEGER
				{
					rts-never-on(0),
					rts-always-on(1),
					rts-on-for-transmit(2)
				}
			
		SerialCTS ::= TEXTUAL-CONVENTION
			STATUS current
			DESCRIPTION
				"Defines the different CTS states for serial communication."
			SYNTAX INTEGER
				{
					cts-ignore(0),
					cts-require(1)
				}
			
		SlotId ::= TEXTUAL-CONVENTION
			STATUS current
			DESCRIPTION
				"Defines the different types of slot types available."
			SYNTAX INTEGER
				{
					empty(0),
					discrete-inputs(1),
					discrete-outputs(2),
					serial-ports(3),
					onboard-sensors(4),
					analog-inputs(5),
					switch-ports(6),
					sensor-inputs(7)
				}
			
		ProductType ::= TEXTUAL-CONVENTION
			STATUS current
			DESCRIPTION
				"Defines the type of device."
			SYNTAX INTEGER
				{
					webmon-edge(0),
					webmon-matrix(1)
				}
			
		VoltageRange ::= TEXTUAL-CONVENTION
			STATUS current
			DESCRIPTION
				"Defines the valid voltage ranges."
			SYNTAX INTEGER
				{
					plus-minus-100-volts(100),
					sensor-port(5)
				}
			
		IOFormat ::= TEXTUAL-CONVENTION
			STATUS current
			DESCRIPTION
				"Defines the physical pin layout of slot cards."
			SYNTAX INTEGER
				{
					single-pin(0),
					single-pin-with-ground(1),
					two-pins(2),
					two-pins-with-ground(3),
					two-pins-right-to-left(4),
					three-pins(5),
					three-pins-right-to-left(6),
					rj(7),
					onboard-built-in(8)
				}
			
		PortType ::= TEXTUAL-CONVENTION
			STATUS current
			DESCRIPTION
				"Defines the type of serial port."
			SYNTAX INTEGER
				{
					not-present(0),
					rs-232(1),
					rs-485(2),
					dialup(3),
					iden(4),
					e2a(5),
					cdma(6),
					gps(7),
					edge(8),
					t202(9)
				}
			
		DiscreteFormula ::= TEXTUAL-CONVENTION
			STATUS current
			DESCRIPTION
				"Defines the type of formula used for derived discretes."
			SYNTAX INTEGER
				{
					a-and-b(0),
					not-a-and-b(1),
					a-and-not-b(2),
					not-a-and-not-b(3),
					a-or-b(4),
					not-a-or-b(5),
					a-or-not-b(6),
					not-a-or-not-b(7),
					a-xor-b(8),
					not-a-xor-b(9),
					a-xor-not-b(10),
					not-a-xor-not-b(11)
				}
			
		DayOfWeek ::= TEXTUAL-CONVENTION
			STATUS current
			DESCRIPTION
				"Day of the week"
			SYNTAX INTEGER
				{
					sunday(0),
					monday(1),
					tuesday(2),
					wednesday(3),
					thursday(4),
					friday(5),
					saturday(6)
				}
			
		ConfiguredState ::= TEXTUAL-CONVENTION
			STATUS current
			DESCRIPTION
				""
			SYNTAX INTEGER
				{
					disabled(0),
					enabled(1)
				}
			
		TL1Srveff ::= TEXTUAL-CONVENTION
			STATUS current
			DESCRIPTION
				"Service Effecting"
			SYNTAX INTEGER
				{
					blank(0),
					sa(1),
					nsa(2)
				}
			
		TL1Locn ::= TEXTUAL-CONVENTION
			STATUS current
			DESCRIPTION
				"Location"
			SYNTAX INTEGER
				{
					blank(0),
					nend(1),
					fend(2),
					line(3)
				}
			
		TL1Dirn ::= TEXTUAL-CONVENTION
			STATUS current
			DESCRIPTION
				"Direction"
			SYNTAX INTEGER
				{
					blank(0),
					trmt(1),
					rcv(2),
					na(3)
				}
			
		TL1Issue ::= TEXTUAL-CONVENTION
			STATUS current
			DESCRIPTION
				"TL1 Issue"
			SYNTAX INTEGER
				{
					issue-3(3),
					issue-5(5)
				}
			
		UseDialout ::= TEXTUAL-CONVENTION
			STATUS current
			DESCRIPTION
				"Use Dialout"
			SYNTAX INTEGER
				{
					never(0),
					always(1),
					as-backup(2)
				}
			
		SensorType ::= TEXTUAL-CONVENTION
			STATUS current
			DESCRIPTION
				"Sensor Type"
			SYNTAX INTEGER
				{
					raw(0),
					temperature(1),
					humidity(2)
				}
			
		SNMPCommandType ::= TEXTUAL-CONVENTION
			STATUS current
			DESCRIPTION
				"Command type"
			SYNTAX INTEGER
				{
					get(160),
					set(163)
				}
			
		SNMPVarbindType ::= TEXTUAL-CONVENTION
			STATUS current
			DESCRIPTION
				"Value type"
			SYNTAX INTEGER
				{
					integer(2),
					string(4)
				}
			
		SNMPAccess ::= TEXTUAL-CONVENTION
			STATUS current
			DESCRIPTION
				"Auth/Priv type"
			SYNTAX INTEGER
				{
					noauthnopriv(0),
					authnopriv-md5(1),
					authpriv-md5(2),
					authnopriv-sha(3),
					authpriv-sha(4)
				}
			
		MODBUSCommand ::= TEXTUAL-CONVENTION
			STATUS current
			DESCRIPTION
				"Function code"
			SYNTAX INTEGER
				{
					read-holding-register(3),
					read-input-register(4)
				}
			


--
-- Node definitions
--
	
		dantel OBJECT IDENTIFIER ::= { enterprises 994 }
		
		dantelProducts OBJECT IDENTIFIER ::= { dantel 3 }
		
		webMon OBJECT-IDENTITY
			STATUS current
			DESCRIPTION
				"The parent node representing the WebMon device."
			::= { dantelProducts 4 }

		-- 1.3.6.1.4.1.994.3.4.7
		configuration OBJECT IDENTIFIER ::= { webMon 7 }

-- triggers folder
		-- 1.3.6.1.4.1.994.3.4.8
		triggers OBJECT IDENTIFIER ::= { webMon 8 }
  
		-- 1.3.6.1.4.1.994.3.4.8.1
		resetDevice OBJECT-TYPE
			SYNTAX Boolean
			MAX-ACCESS read-write
			STATUS current
			DESCRIPTION
				"Setting this item to true will cause a reset of the device.  
				 Setting this item to false will have no effect."
			::= { triggers 1 }

		-- 1.3.6.1.4.1.994.3.4.8.2
		commitAccountChanges OBJECT-TYPE
			SYNTAX Boolean
			MAX-ACCESS read-write
			STATUS current
			DESCRIPTION
				"Setting this item to true will cause any user account changes to go into effect immediatly.  
				 Setting this item to false will have no effect."
			::= { triggers 2 }

		-- 1.3.6.1.4.1.994.3.4.8.3
		resendEvents OBJECT-TYPE
			SYNTAX Boolean
			MAX-ACCESS read-write
			STATUS current
			DESCRIPTION
				"Setting this item to true will cause the device to resend traps for any standing alarms.
				 Setting this item to false will have no effect."
			::= { triggers 3 }

		
-- systemGeneral folder
		
		-- 1.3.6.1.4.1.994.3.4.7.1
		systemGeneral OBJECT IDENTIFIER ::= {configuration 1 }
		
		-- 1.3.6.1.4.1.994.3.4.7.1.2
		systemGeneralLocation OBJECT-TYPE
			SYNTAX DescriptionString
			MAX-ACCESS read-write
			STATUS current
			DESCRIPTION
				"Location on the device."
			::= { systemGeneral 2 }
		
		
		-- 1.3.6.1.4.1.994.3.4.7.1.3
		systemGeneralDescription OBJECT-TYPE
			SYNTAX DescriptionString
			MAX-ACCESS read-write
			STATUS current
			DESCRIPTION
				"Description of the device."
			::= { systemGeneral 3 }
		
		
		-- 1.3.6.1.4.1.994.3.4.7.1.14
		systemGeneralIpAddress OBJECT-TYPE
			SYNTAX IpAddress
			MAX-ACCESS read-write
			STATUS current
			DESCRIPTION
				"IP Address of the device.  If changed, the new IP address 
				will only take effect after a reset."
			::= { systemGeneral 14 }
		
		
		-- 1.3.6.1.4.1.994.3.4.7.1.15
		systemGeneralSubnetMask OBJECT-TYPE
			SYNTAX IpAddress
			MAX-ACCESS read-write
			STATUS current
			DESCRIPTION
				"Subnet Mask of the device.  If changed, the new IP address 
				will only take effect after a reset."
			::= { systemGeneral 15 }
		
		
		-- 1.3.6.1.4.1.994.3.4.7.1.16
		systemGeneralGatewayAddress OBJECT-TYPE
			SYNTAX IpAddress
			MAX-ACCESS read-write
			STATUS current
			DESCRIPTION
				"Gateway Address of the device.  If changed, the new IP address 
				will only take effect after a reset."
			::= { systemGeneral 16 }
		
		
		-- 1.3.6.1.4.1.994.3.4.7.1.45
		systemGeneralMeasureStyle OBJECT-TYPE
			SYNTAX MeasureStyle
			MAX-ACCESS read-write
			STATUS current
			DESCRIPTION
				"Determines if units are displayed in English or Metric."
			::= { systemGeneral 45 }
		
		
		-- 1.3.6.1.4.1.994.3.4.7.1.54
		systemGeneralMacAddress OBJECT-TYPE
			SYNTAX DescriptionString
			MAX-ACCESS read-only
			STATUS current
			DESCRIPTION
				"The MAC address of the device."
			::= { systemGeneral 54 }
		
		
		-- 1.3.6.1.4.1.994.3.4.7.1.70
		systemGeneralProductType OBJECT-TYPE
			SYNTAX ProductType
			MAX-ACCESS read-only
			STATUS current
			DESCRIPTION
				"Describes the type of device."
			::= { systemGeneral 70 }
		
		
		-- 1.3.6.1.4.1.994.3.4.7.1.73
		systemGeneralIPPortNum OBJECT-TYPE
			SYNTAX Integer32
			MAX-ACCESS read-write
			STATUS current
			DESCRIPTION
				"IP port number to use when connecting to the web page (HTTP)."
			::= { systemGeneral 73 }
		
		
		-- 1.3.6.1.4.1.994.3.4.7.1.82
		systemGeneralVersion OBJECT-TYPE
			SYNTAX DescriptionString
			MAX-ACCESS read-only
			STATUS current
			DESCRIPTION
				"The version of the running software."
			::= { systemGeneral 82 }


-- TrapTarget table
		
		-- 1.3.6.1.4.1.994.3.4.7.2
		pTrapTargetTable OBJECT-TYPE
			SYNTAX SEQUENCE OF PTrapTargetEntry
			MAX-ACCESS not-accessible
			STATUS current
			DESCRIPTION
				"Table for configuration of TrapTarget"
			::= { configuration 2 }
		
		
		-- 1.3.6.1.4.1.994.3.4.7.2.1
		pTrapTargetEntry OBJECT-TYPE
			SYNTAX PTrapTargetEntry
			MAX-ACCESS not-accessible
			STATUS current
			DESCRIPTION
				"Entry for configuration table of TrapTarget"
				INDEX { pTrapTargetIndex }
			::= { pTrapTargetTable 1 }
		
		
		PTrapTargetEntry ::= 
			SEQUENCE {
				pTrapTargetDescription
					DescriptionString,
				pTrapTargetConfigured
					Configured,
				pTrapTargetIpAddress
					IpAddress,
				pTrapTargetSnmpVersion
					SnmpVersion,
				pTrapTargetIPPortNum
					Integer32,
				pTrapTargetBackupIPAddress
					IpAddress,
				pTrapTargetUseDialout
					UseDialout,
				pTrapTargetDialoutTarget
					Integer32,
				pTrapTargetAuthKey
					DescriptionString,
				pTrapTargetPrivKey
					DescriptionString,
				pTrapTargetSNMPAccess
					SNMPAccess,
				pTrapTargetEngineID
					DescriptionString,
				pTrapTargetIndex
					Integer32 (1..16)
			}
		
		-- 1.3.6.1.4.1.994.3.4.7.2.1.3
		pTrapTargetDescription OBJECT-TYPE
			SYNTAX DescriptionString
			MAX-ACCESS read-write
			STATUS current
			DESCRIPTION
				"Description of the trap target."
			::= { pTrapTargetEntry 3 }
		
		
		-- 1.3.6.1.4.1.994.3.4.7.2.1.10
		pTrapTargetConfigured OBJECT-TYPE
			SYNTAX Configured
			MAX-ACCESS read-write
			STATUS current
			DESCRIPTION
				"Determines if traps will be sent to trap target with given IP address."
			::= { pTrapTargetEntry 10 }
		
		
		-- 1.3.6.1.4.1.994.3.4.7.2.1.14
		pTrapTargetIpAddress OBJECT-TYPE
			SYNTAX IpAddress
			MAX-ACCESS read-write
			STATUS current
			DESCRIPTION
				"SNMP traps are sent to this IP address."
			::= { pTrapTargetEntry 14 }
		
		
		-- 1.3.6.1.4.1.994.3.4.7.2.1.42
		pTrapTargetSnmpVersion OBJECT-TYPE
			SYNTAX SnmpVersion
			MAX-ACCESS read-write
			STATUS current
			DESCRIPTION
				"Indicates the version of SNMP trap to use."
			::= { pTrapTargetEntry 42 }
		
		
		-- 1.3.6.1.4.1.994.3.4.7.2.1.73
		pTrapTargetIPPortNum OBJECT-TYPE
			SYNTAX Integer32
			MAX-ACCESS read-write
			STATUS current
			DESCRIPTION
				"SNMP traps are sent to this network port."
			::= { pTrapTargetEntry 73 }
		
		
		-- 1.3.6.1.4.1.994.3.4.7.2.1.78
		pTrapTargetBackupIPAddress OBJECT-TYPE
			SYNTAX IpAddress
			MAX-ACCESS read-write
			STATUS current
			DESCRIPTION
				"Used only when dialing out as backup."
			::= { pTrapTargetEntry 78 }
		
		
		-- 1.3.6.1.4.1.994.3.4.7.2.1.125
		pTrapTargetUseDialout OBJECT-TYPE
			SYNTAX UseDialout
			MAX-ACCESS read-write
			STATUS current
			DESCRIPTION
				"Determines if traps will be sent only when dialed out."
			::= { pTrapTargetEntry 125 }
		
		
		-- 1.3.6.1.4.1.994.3.4.7.2.1.126
		pTrapTargetDialoutTarget OBJECT-TYPE
			SYNTAX Integer32
			MAX-ACCESS read-write
			STATUS current
			DESCRIPTION
				"Determines which target to dial out to when sending traps."
			::= { pTrapTargetEntry 126 }
		
		
		-- 1.3.6.1.4.1.994.3.4.7.2.1.140
		pTrapTargetAuthKey OBJECT-TYPE
			SYNTAX DescriptionString
			MAX-ACCESS read-write
			STATUS current
			DESCRIPTION
				""
			::= { pTrapTargetEntry 140 }
		
		
		-- 1.3.6.1.4.1.994.3.4.7.2.1.141
		pTrapTargetPrivKey OBJECT-TYPE
			SYNTAX DescriptionString
			MAX-ACCESS read-write
			STATUS current
			DESCRIPTION
				""
			::= { pTrapTargetEntry 141 }
		
		
		-- 1.3.6.1.4.1.994.3.4.7.2.1.142
		pTrapTargetSNMPAccess OBJECT-TYPE
			SYNTAX SNMPAccess
			MAX-ACCESS read-write
			STATUS current
			DESCRIPTION
				""
			::= { pTrapTargetEntry 142 }
		
		
		-- 1.3.6.1.4.1.994.3.4.7.2.1.143
		pTrapTargetEngineID OBJECT-TYPE
			SYNTAX DescriptionString
			MAX-ACCESS read-write
			STATUS current
			DESCRIPTION
				""
			::= { pTrapTargetEntry 143 }
		
		
		-- 1.3.6.1.4.1.994.3.4.7.2.1.999
		pTrapTargetIndex OBJECT-TYPE
			SYNTAX Integer32 (1..16)
			MAX-ACCESS read-only
			STATUS current
			DESCRIPTION
				"Index."
			::= { pTrapTargetEntry 999 }


-- Email table
		
		-- 1.3.6.1.4.1.994.3.4.7.3
		pEmailTable OBJECT-TYPE
			SYNTAX SEQUENCE OF PEmailEntry
			MAX-ACCESS not-accessible
			STATUS current
			DESCRIPTION
				"Table for configuration of Email"
			::= { configuration 3 }
		
		
		-- 1.3.6.1.4.1.994.3.4.7.3.1
		pEmailEntry OBJECT-TYPE
			SYNTAX PEmailEntry
			MAX-ACCESS not-accessible
			STATUS current
			DESCRIPTION
				"Entry for configuration table of Email"
				INDEX { pEmailIndex }
			::= { pEmailTable 1 }
		
		
		PEmailEntry ::= 
			SEQUENCE {
				pEmailAddress
					DescriptionString,
				pEmailDescription
					DescriptionString,
				pEmailConfigured
					Configured,
				pEmailIndex
					Integer32 (1..16)
			}
		
		-- 1.3.6.1.4.1.994.3.4.7.3.1.1
		pEmailAddress OBJECT-TYPE
			SYNTAX DescriptionString
			MAX-ACCESS read-write
			STATUS current
			DESCRIPTION
				"Email events will be sent to this address."
			::= { pEmailEntry 1 }
		
		
		-- 1.3.6.1.4.1.994.3.4.7.3.1.3
		pEmailDescription OBJECT-TYPE
			SYNTAX DescriptionString
			MAX-ACCESS read-write
			STATUS current
			DESCRIPTION
				"Description of the Email target."
			::= { pEmailEntry 3 }
		
		
		-- 1.3.6.1.4.1.994.3.4.7.3.1.10
		pEmailConfigured OBJECT-TYPE
			SYNTAX Configured
			MAX-ACCESS read-write
			STATUS current
			DESCRIPTION
				"If set to true, email events will be sent to given address.
				If set to false, email will not be sent."
			::= { pEmailEntry 10 }
		
		
		-- 1.3.6.1.4.1.994.3.4.7.3.1.999
		pEmailIndex OBJECT-TYPE
			SYNTAX Integer32 (1..16)
			MAX-ACCESS read-only
			STATUS current
			DESCRIPTION
				"Index."
			::= { pEmailEntry 999 }


-- RemoteSensor table
		
		-- 1.3.6.1.4.1.994.3.4.7.5
		pRemoteSensorTable OBJECT-TYPE
			SYNTAX SEQUENCE OF PRemoteSensorEntry
			MAX-ACCESS not-accessible
			STATUS current
			DESCRIPTION
				"Table for configuration of RemoteSensor"
			::= { configuration 5 }
		
		
		-- 1.3.6.1.4.1.994.3.4.7.5.1
		pRemoteSensorEntry OBJECT-TYPE
			SYNTAX PRemoteSensorEntry
			MAX-ACCESS not-accessible
			STATUS current
			DESCRIPTION
				"Entry for configuration table of RemoteSensor"
				INDEX { pRemoteSensorIndex }
			::= { pRemoteSensorTable 1 }
		
		
		PRemoteSensorEntry ::= 
			SEQUENCE {
				pRemoteSensorDescription
					DescriptionString,
				pRemoteSensorDesc0
					DescriptionString,
				pRemoteSensorDesc1
					DescriptionString,
				pRemoteSensorDesc2
					DescriptionString,
				pRemoteSensorDesc3
					DescriptionString,
				pRemoteSensorDesc4
					DescriptionString,
				pRemoteSensorDesc5
					DescriptionString,
				pRemoteSensorConfigured
					Configured,
				pRemoteSensorSendEmail
					Boolean,
				pRemoteSensorSendSNMPTrap
					Boolean,
				pRemoteSensorLevel0
					Level,
				pRemoteSensorLevel1
					Level,
				pRemoteSensorLevel2
					Level,
				pRemoteSensorLevel3
					Level,
				pRemoteSensorLevel4
					Level,
				pRemoteSensorLevel5
					Level,
				pRemoteSensorThresh0
					DescriptionString,
				pRemoteSensorThresh1
					DescriptionString,
				pRemoteSensorThresh2
					DescriptionString,
				pRemoteSensorThresh3
					DescriptionString,
				pRemoteSensorThresh4
					DescriptionString,
				pRemoteSensorThresh5
					DescriptionString,
				pRemoteSensorUnits
					DescriptionString,
				pRemoteSensorPollAddress
					Integer32,
				pRemoteSensorLiveDescription
					DescriptionString,
				pRemoteSensorLiveLevel
					DescriptionString,
				pRemoteSensorLiveRaw
					DescriptionString,
				pRemoteSensorLiveTime
					DescriptionString,
				pRemoteSensorTL1SID
					DescriptionString,
				pRemoteSensorTL1COND
					DescriptionString,
				pRemoteSensorTL1Eqpt
					DescriptionString,
				pRemoteSensorTL1Env
					Boolean,
				pRemoteSensorTL1Srveff
					TL1Srveff,
				pRemoteSensorTL1Locn
					TL1Locn,
				pRemoteSensorTL1Dirn
					TL1Dirn,
				pRemoteSensorMODBUSCommand
					MODBUSCommand,
				pRemoteSensorStartRegister
					Integer32,
				pRemoteSensorIndex
					Integer32 (1..32)
			}
		
		-- 1.3.6.1.4.1.994.3.4.7.5.1.3
		pRemoteSensorDescription OBJECT-TYPE
			SYNTAX DescriptionString
			MAX-ACCESS read-write
			STATUS current
			DESCRIPTION
				"Description of the Analog device."
			::= { pRemoteSensorEntry 3 }
		
		
		-- 1.3.6.1.4.1.994.3.4.7.5.1.4
		pRemoteSensorDesc0 OBJECT-TYPE
			SYNTAX DescriptionString
			MAX-ACCESS read-write
			STATUS current
			DESCRIPTION
				"The description for values between threshold 0 and threshold 1."
			::= { pRemoteSensorEntry 4 }
		
		
		-- 1.3.6.1.4.1.994.3.4.7.5.1.5
		pRemoteSensorDesc1 OBJECT-TYPE
			SYNTAX DescriptionString
			MAX-ACCESS read-write
			STATUS current
			DESCRIPTION
				"The description for values between threshold 1 and threshold 2."
			::= { pRemoteSensorEntry 5 }
		
		
		-- 1.3.6.1.4.1.994.3.4.7.5.1.6
		pRemoteSensorDesc2 OBJECT-TYPE
			SYNTAX DescriptionString
			MAX-ACCESS read-write
			STATUS current
			DESCRIPTION
				"The description for values between threshold 2 and threshold 3."
			::= { pRemoteSensorEntry 6 }
		
		
		-- 1.3.6.1.4.1.994.3.4.7.5.1.7
		pRemoteSensorDesc3 OBJECT-TYPE
			SYNTAX DescriptionString
			MAX-ACCESS read-write
			STATUS current
			DESCRIPTION
				"The description for values between threshold 3 and threshold 4."
			::= { pRemoteSensorEntry 7 }
		
		
		-- 1.3.6.1.4.1.994.3.4.7.5.1.8
		pRemoteSensorDesc4 OBJECT-TYPE
			SYNTAX DescriptionString
			MAX-ACCESS read-write
			STATUS current
			DESCRIPTION
				"The description for values between threshold 4 and threshold 5."
			::= { pRemoteSensorEntry 8 }
		
		
		-- 1.3.6.1.4.1.994.3.4.7.5.1.9
		pRemoteSensorDesc5 OBJECT-TYPE
			SYNTAX DescriptionString
			MAX-ACCESS read-write
			STATUS current
			DESCRIPTION
				"Description for a communications failure to the remote analog device."
			::= { pRemoteSensorEntry 9 }
		
		
		-- 1.3.6.1.4.1.994.3.4.7.5.1.10
		pRemoteSensorConfigured OBJECT-TYPE
			SYNTAX Configured
			MAX-ACCESS read-write
			STATUS current
			DESCRIPTION
				"If set to true analog values will be monitored. 
				If set to false no values will be monitored."
			::= { pRemoteSensorEntry 10 }
		
		
		-- 1.3.6.1.4.1.994.3.4.7.5.1.11
		pRemoteSensorSendEmail OBJECT-TYPE
			SYNTAX Boolean
			MAX-ACCESS read-write
			STATUS current
			DESCRIPTION
				"If set to true an email event will be set when a threshold is crossed.
				If set to false no email event will be sent."
			::= { pRemoteSensorEntry 11 }
		
		
		-- 1.3.6.1.4.1.994.3.4.7.5.1.12
		pRemoteSensorSendSNMPTrap OBJECT-TYPE
			SYNTAX Boolean
			MAX-ACCESS read-write
			STATUS current
			DESCRIPTION
				"If set to true an SNMP trap will be set when a threshold is crossed.
				If set to false no SNMP trap will be sent."
			::= { pRemoteSensorEntry 12 }
		
		
		-- 1.3.6.1.4.1.994.3.4.7.5.1.17
		pRemoteSensorLevel0 OBJECT-TYPE
			SYNTAX Level
			MAX-ACCESS read-write
			STATUS current
			DESCRIPTION
				"The level for values between threshold 0 and threshold 1."
			::= { pRemoteSensorEntry 17 }
		
		
		-- 1.3.6.1.4.1.994.3.4.7.5.1.18
		pRemoteSensorLevel1 OBJECT-TYPE
			SYNTAX Level
			MAX-ACCESS read-write
			STATUS current
			DESCRIPTION
				"The level for values between threshold 1 and threshold 2."
			::= { pRemoteSensorEntry 18 }
		
		
		-- 1.3.6.1.4.1.994.3.4.7.5.1.19
		pRemoteSensorLevel2 OBJECT-TYPE
			SYNTAX Level
			MAX-ACCESS read-write
			STATUS current
			DESCRIPTION
				"The level for values between threshold 2 and threshold 3."
			::= { pRemoteSensorEntry 19 }
		
		
		-- 1.3.6.1.4.1.994.3.4.7.5.1.20
		pRemoteSensorLevel3 OBJECT-TYPE
			SYNTAX Level
			MAX-ACCESS read-write
			STATUS current
			DESCRIPTION
				"The level for values between threshold 3 and threshold 4."
			::= { pRemoteSensorEntry 20 }
		
		
		-- 1.3.6.1.4.1.994.3.4.7.5.1.21
		pRemoteSensorLevel4 OBJECT-TYPE
			SYNTAX Level
			MAX-ACCESS read-write
			STATUS current
			DESCRIPTION
				"The level for values between threshold 4 and threshold 5."
			::= { pRemoteSensorEntry 21 }
		
		
		-- 1.3.6.1.4.1.994.3.4.7.5.1.22
		pRemoteSensorLevel5 OBJECT-TYPE
			SYNTAX Level
			MAX-ACCESS read-write
			STATUS current
			DESCRIPTION
				"Level of a communications failure to the remote analog device."
			::= { pRemoteSensorEntry 22 }
		
		
		-- 1.3.6.1.4.1.994.3.4.7.5.1.28
		pRemoteSensorThresh0 OBJECT-TYPE
			SYNTAX DescriptionString
			MAX-ACCESS read-write
			STATUS current
			DESCRIPTION
				"This is the maximum analog value."
			::= { pRemoteSensorEntry 28 }
		
		
		-- 1.3.6.1.4.1.994.3.4.7.5.1.29
		pRemoteSensorThresh1 OBJECT-TYPE
			SYNTAX DescriptionString
			MAX-ACCESS read-write
			STATUS current
			DESCRIPTION
				"This is the first threshold value."
			::= { pRemoteSensorEntry 29 }
		
		
		-- 1.3.6.1.4.1.994.3.4.7.5.1.30
		pRemoteSensorThresh2 OBJECT-TYPE
			SYNTAX DescriptionString
			MAX-ACCESS read-write
			STATUS current
			DESCRIPTION
				"This is the second threshold value."
			::= { pRemoteSensorEntry 30 }
		
		
		-- 1.3.6.1.4.1.994.3.4.7.5.1.31
		pRemoteSensorThresh3 OBJECT-TYPE
			SYNTAX DescriptionString
			MAX-ACCESS read-write
			STATUS current
			DESCRIPTION
				"This is the third threshold value."
			::= { pRemoteSensorEntry 31 }
		
		
		-- 1.3.6.1.4.1.994.3.4.7.5.1.32
		pRemoteSensorThresh4 OBJECT-TYPE
			SYNTAX DescriptionString
			MAX-ACCESS read-write
			STATUS current
			DESCRIPTION
				"This is the fourth threshold value."
			::= { pRemoteSensorEntry 32 }
		
		
		-- 1.3.6.1.4.1.994.3.4.7.5.1.33
		pRemoteSensorThresh5 OBJECT-TYPE
			SYNTAX DescriptionString
			MAX-ACCESS read-write
			STATUS current
			DESCRIPTION
				"This is the minimum threshold value."
			::= { pRemoteSensorEntry 33 }
		
		
		-- 1.3.6.1.4.1.994.3.4.7.5.1.46
		pRemoteSensorUnits OBJECT-TYPE
			SYNTAX DescriptionString
			MAX-ACCESS read-write
			STATUS current
			DESCRIPTION
				"Description of the units of measurement."
			::= { pRemoteSensorEntry 46 }
		
		
		-- 1.3.6.1.4.1.994.3.4.7.5.1.56
		pRemoteSensorPollAddress OBJECT-TYPE
			SYNTAX Integer32
			MAX-ACCESS read-write
			STATUS current
			DESCRIPTION
				"The polling address of the analog device."
			::= { pRemoteSensorEntry 56 }
		
		
		-- 1.3.6.1.4.1.994.3.4.7.5.1.64
		pRemoteSensorLiveDescription OBJECT-TYPE
			SYNTAX DescriptionString
			MAX-ACCESS read-only
			STATUS current
			DESCRIPTION
				"The description  of  the current state of the analog device"
			::= { pRemoteSensorEntry 64 }
		
		
		-- 1.3.6.1.4.1.994.3.4.7.5.1.65
		pRemoteSensorLiveLevel OBJECT-TYPE
			SYNTAX DescriptionString
			MAX-ACCESS read-only
			STATUS current
			DESCRIPTION
				"The level of the current state of the analog device."
			::= { pRemoteSensorEntry 65 }
		
		
		-- 1.3.6.1.4.1.994.3.4.7.5.1.66
		pRemoteSensorLiveRaw OBJECT-TYPE
			SYNTAX DescriptionString
			MAX-ACCESS read-only
			STATUS current
			DESCRIPTION
				"The current reading from the analog device.  This value will always
				be between the threshold 0 and threshold 5 values."
			::= { pRemoteSensorEntry 66 }
		
		
		-- 1.3.6.1.4.1.994.3.4.7.5.1.67
		pRemoteSensorLiveTime OBJECT-TYPE
			SYNTAX DescriptionString
			MAX-ACCESS read-only
			STATUS current
			DESCRIPTION
				"The time of the last event."
			::= { pRemoteSensorEntry 67 }
		
		
		-- 1.3.6.1.4.1.994.3.4.7.5.1.116
		pRemoteSensorTL1SID OBJECT-TYPE
			SYNTAX DescriptionString
			MAX-ACCESS read-write
			STATUS current
			DESCRIPTION
				"(TL1) System ID associated with this item."
			::= { pRemoteSensorEntry 116 }
		
		
		-- 1.3.6.1.4.1.994.3.4.7.5.1.117
		pRemoteSensorTL1COND OBJECT-TYPE
			SYNTAX DescriptionString
			MAX-ACCESS read-write
			STATUS current
			DESCRIPTION
				"(TL1) Condition text associated with this item."
			::= { pRemoteSensorEntry 117 }
		
		
		-- 1.3.6.1.4.1.994.3.4.7.5.1.118
		pRemoteSensorTL1Eqpt OBJECT-TYPE
			SYNTAX DescriptionString
			MAX-ACCESS read-write
			STATUS current
			DESCRIPTION
				"(TL1) EQPT field associated with this item."
			::= { pRemoteSensorEntry 118 }
		
		
		-- 1.3.6.1.4.1.994.3.4.7.5.1.119
		pRemoteSensorTL1Env OBJECT-TYPE
			SYNTAX Boolean
			MAX-ACCESS read-write
			STATUS current
			DESCRIPTION
				"(TL1) Environmental field associated with this item."
			::= { pRemoteSensorEntry 119 }
		
		
		-- 1.3.6.1.4.1.994.3.4.7.5.1.120
		pRemoteSensorTL1Srveff OBJECT-TYPE
			SYNTAX TL1Srveff
			MAX-ACCESS read-write
			STATUS current
			DESCRIPTION
				"(TL1) Service Effecting field associated with this item."
			::= { pRemoteSensorEntry 120 }
		
		
		-- 1.3.6.1.4.1.994.3.4.7.5.1.121
		pRemoteSensorTL1Locn OBJECT-TYPE
			SYNTAX TL1Locn
			MAX-ACCESS read-write
			STATUS current
			DESCRIPTION
				"(TL1) Location field associated with this item."
			::= { pRemoteSensorEntry 121 }
		
		
		-- 1.3.6.1.4.1.994.3.4.7.5.1.122
		pRemoteSensorTL1Dirn OBJECT-TYPE
			SYNTAX TL1Dirn
			MAX-ACCESS read-write
			STATUS current
			DESCRIPTION
				"(TL1) Direction field associated with this item."
			::= { pRemoteSensorEntry 122 }
		
		
		-- 1.3.6.1.4.1.994.3.4.7.5.1.144
		pRemoteSensorMODBUSCommand OBJECT-TYPE
			SYNTAX MODBUSCommand
			MAX-ACCESS read-write
			STATUS current
			DESCRIPTION
				"The polling command for the analog device."
			::= { pRemoteSensorEntry 144 }
		
		
		-- 1.3.6.1.4.1.994.3.4.7.5.1.145
		pRemoteSensorStartRegister OBJECT-TYPE
			SYNTAX Integer32
			MAX-ACCESS read-write
			STATUS current
			DESCRIPTION
				"The MODBUS register for the analog device."
			::= { pRemoteSensorEntry 145 }
		
		
		-- 1.3.6.1.4.1.994.3.4.7.5.1.999
		pRemoteSensorIndex OBJECT-TYPE
			SYNTAX Integer32 (1..32)
			MAX-ACCESS read-only
			STATUS current
			DESCRIPTION
				"Index."
			::= { pRemoteSensorEntry 999 }


-- OnboardSensor table
		
		-- 1.3.6.1.4.1.994.3.4.7.6
		pOnboardSensorTable OBJECT-TYPE
			SYNTAX SEQUENCE OF POnboardSensorEntry
			MAX-ACCESS not-accessible
			STATUS current
			DESCRIPTION
				"Table for configuration of OnboardSensor"
			::= { configuration 6 }
		
		
		-- 1.3.6.1.4.1.994.3.4.7.6.1
		pOnboardSensorEntry OBJECT-TYPE
			SYNTAX POnboardSensorEntry
			MAX-ACCESS not-accessible
			STATUS current
			DESCRIPTION
				"Entry for configuration table of OnboardSensor"
				INDEX { pOnboardSensorIndex }
			::= { pOnboardSensorTable 1 }
		
		
		POnboardSensorEntry ::= 
			SEQUENCE {
				pOnboardSensorDescription
					DescriptionString,
				pOnboardSensorDesc0
					DescriptionString,
				pOnboardSensorDesc1
					DescriptionString,
				pOnboardSensorDesc2
					DescriptionString,
				pOnboardSensorDesc3
					DescriptionString,
				pOnboardSensorDesc4
					DescriptionString,
				pOnboardSensorDesc5
					DescriptionString,
				pOnboardSensorConfigured
					Configured,
				pOnboardSensorSendEmail
					Boolean,
				pOnboardSensorSendSNMPTrap
					Boolean,
				pOnboardSensorLevel0
					Level,
				pOnboardSensorLevel1
					Level,
				pOnboardSensorLevel2
					Level,
				pOnboardSensorLevel3
					Level,
				pOnboardSensorLevel4
					Level,
				pOnboardSensorLevel5
					Level,
				pOnboardSensorThresh0
					DescriptionString,
				pOnboardSensorThresh1
					DescriptionString,
				pOnboardSensorThresh2
					DescriptionString,
				pOnboardSensorThresh3
					DescriptionString,
				pOnboardSensorThresh4
					DescriptionString,
				pOnboardSensorThresh5
					DescriptionString,
				pOnboardSensorUnits
					DescriptionString,
				pOnboardSensorLiveDescription
					DescriptionString,
				pOnboardSensorLiveLevel
					DescriptionString,
				pOnboardSensorLiveRaw
					DescriptionString,
				pOnboardSensorLiveTime
					DescriptionString,
				pOnboardSensorTL1SID
					DescriptionString,
				pOnboardSensorTL1COND
					DescriptionString,
				pOnboardSensorTL1Eqpt
					DescriptionString,
				pOnboardSensorTL1Env
					Boolean,
				pOnboardSensorTL1Srveff
					TL1Srveff,
				pOnboardSensorTL1Locn
					TL1Locn,
				pOnboardSensorTL1Dirn
					TL1Dirn,
				pOnboardSensorIndex
					Integer32 (1..2)
			}
		
		-- 1.3.6.1.4.1.994.3.4.7.6.1.3
		pOnboardSensorDescription OBJECT-TYPE
			SYNTAX DescriptionString
			MAX-ACCESS read-only
			STATUS current
			DESCRIPTION
				"Description of the onboard sensor input."
			::= { pOnboardSensorEntry 3 }
		
		
		-- 1.3.6.1.4.1.994.3.4.7.6.1.4
		pOnboardSensorDesc0 OBJECT-TYPE
			SYNTAX DescriptionString
			MAX-ACCESS read-write
			STATUS current
			DESCRIPTION
				"The description for values between threshold 0 and threshold 1."
			::= { pOnboardSensorEntry 4 }
		
		
		-- 1.3.6.1.4.1.994.3.4.7.6.1.5
		pOnboardSensorDesc1 OBJECT-TYPE
			SYNTAX DescriptionString
			MAX-ACCESS read-write
			STATUS current
			DESCRIPTION
				"The description for values between threshold 1 and threshold 2."
			::= { pOnboardSensorEntry 5 }
		
		
		-- 1.3.6.1.4.1.994.3.4.7.6.1.6
		pOnboardSensorDesc2 OBJECT-TYPE
			SYNTAX DescriptionString
			MAX-ACCESS read-write
			STATUS current
			DESCRIPTION
				"The description for values between threshold 2 and threshold 3."
			::= { pOnboardSensorEntry 6 }
		
		
		-- 1.3.6.1.4.1.994.3.4.7.6.1.7
		pOnboardSensorDesc3 OBJECT-TYPE
			SYNTAX DescriptionString
			MAX-ACCESS read-write
			STATUS current
			DESCRIPTION
				"The description for values between threshold 3 and threshold 4."
			::= { pOnboardSensorEntry 7 }
		
		
		-- 1.3.6.1.4.1.994.3.4.7.6.1.8
		pOnboardSensorDesc4 OBJECT-TYPE
			SYNTAX DescriptionString
			MAX-ACCESS read-write
			STATUS current
			DESCRIPTION
				"The description for values between threshold 4 and threshold 5."
			::= { pOnboardSensorEntry 8 }
		
		
		-- 1.3.6.1.4.1.994.3.4.7.6.1.9
		pOnboardSensorDesc5 OBJECT-TYPE
			SYNTAX DescriptionString
			MAX-ACCESS read-write
			STATUS current
			DESCRIPTION
				"Description for a communications failure to the sensor."
			::= { pOnboardSensorEntry 9 }
		
		
		-- 1.3.6.1.4.1.994.3.4.7.6.1.10
		pOnboardSensorConfigured OBJECT-TYPE
			SYNTAX Configured
			MAX-ACCESS read-write
			STATUS current
			DESCRIPTION
				"If set to true, the sensor input will be usable.
				If set to false the sensor input will be ignored."
			::= { pOnboardSensorEntry 10 }
		
		
		-- 1.3.6.1.4.1.994.3.4.7.6.1.11
		pOnboardSensorSendEmail OBJECT-TYPE
			SYNTAX Boolean
			MAX-ACCESS read-write
			STATUS current
			DESCRIPTION
				"If set to true an email event will be set when a threshold is crossed.
				If set to false no email event will be sent."
			::= { pOnboardSensorEntry 11 }
		
		
		-- 1.3.6.1.4.1.994.3.4.7.6.1.12
		pOnboardSensorSendSNMPTrap OBJECT-TYPE
			SYNTAX Boolean
			MAX-ACCESS read-write
			STATUS current
			DESCRIPTION
				"If set to true an SNMP trap will be set when a threshold is crossed.
				If set to false no SNMP trap will be sent."
			::= { pOnboardSensorEntry 12 }
		
		
		-- 1.3.6.1.4.1.994.3.4.7.6.1.17
		pOnboardSensorLevel0 OBJECT-TYPE
			SYNTAX Level
			MAX-ACCESS read-write
			STATUS current
			DESCRIPTION
				"The level for values between threshold 0 and threshold 1."
			::= { pOnboardSensorEntry 17 }
		
		
		-- 1.3.6.1.4.1.994.3.4.7.6.1.18
		pOnboardSensorLevel1 OBJECT-TYPE
			SYNTAX Level
			MAX-ACCESS read-write
			STATUS current
			DESCRIPTION
				"The level for values between threshold 1 and threshold 2."
			::= { pOnboardSensorEntry 18 }
		
		
		-- 1.3.6.1.4.1.994.3.4.7.6.1.19
		pOnboardSensorLevel2 OBJECT-TYPE
			SYNTAX Level
			MAX-ACCESS read-write
			STATUS current
			DESCRIPTION
				"The level for values between threshold 2 and threshold 3."
			::= { pOnboardSensorEntry 19 }
		
		
		-- 1.3.6.1.4.1.994.3.4.7.6.1.20
		pOnboardSensorLevel3 OBJECT-TYPE
			SYNTAX Level
			MAX-ACCESS read-write
			STATUS current
			DESCRIPTION
				"The level for values between threshold 3 and threshold 4."
			::= { pOnboardSensorEntry 20 }
		
		
		-- 1.3.6.1.4.1.994.3.4.7.6.1.21
		pOnboardSensorLevel4 OBJECT-TYPE
			SYNTAX Level
			MAX-ACCESS read-write
			STATUS current
			DESCRIPTION
				"The level for values between threshold 4 and threshold 5."
			::= { pOnboardSensorEntry 21 }
		
		
		-- 1.3.6.1.4.1.994.3.4.7.6.1.22
		pOnboardSensorLevel5 OBJECT-TYPE
			SYNTAX Level
			MAX-ACCESS read-write
			STATUS current
			DESCRIPTION
				"Level of a communications failure to the sensor."
			::= { pOnboardSensorEntry 22 }
		
		
		-- 1.3.6.1.4.1.994.3.4.7.6.1.28
		pOnboardSensorThresh0 OBJECT-TYPE
			SYNTAX DescriptionString
			MAX-ACCESS read-only
			STATUS current
			DESCRIPTION
				"This is the minimun analog value."
			::= { pOnboardSensorEntry 28 }
		
		
		-- 1.3.6.1.4.1.994.3.4.7.6.1.29
		pOnboardSensorThresh1 OBJECT-TYPE
			SYNTAX DescriptionString
			MAX-ACCESS read-write
			STATUS current
			DESCRIPTION
				"This is the first threshold value."
			::= { pOnboardSensorEntry 29 }
		
		
		-- 1.3.6.1.4.1.994.3.4.7.6.1.30
		pOnboardSensorThresh2 OBJECT-TYPE
			SYNTAX DescriptionString
			MAX-ACCESS read-write
			STATUS current
			DESCRIPTION
				"This is the second threshold value."
			::= { pOnboardSensorEntry 30 }
		
		
		-- 1.3.6.1.4.1.994.3.4.7.6.1.31
		pOnboardSensorThresh3 OBJECT-TYPE
			SYNTAX DescriptionString
			MAX-ACCESS read-write
			STATUS current
			DESCRIPTION
				"This is the third threshold value."
			::= { pOnboardSensorEntry 31 }
		
		
		-- 1.3.6.1.4.1.994.3.4.7.6.1.32
		pOnboardSensorThresh4 OBJECT-TYPE
			SYNTAX DescriptionString
			MAX-ACCESS read-write
			STATUS current
			DESCRIPTION
				"This is the fourth threshold value."
			::= { pOnboardSensorEntry 32 }
		
		
		-- 1.3.6.1.4.1.994.3.4.7.6.1.33
		pOnboardSensorThresh5 OBJECT-TYPE
			SYNTAX DescriptionString
			MAX-ACCESS read-only
			STATUS current
			DESCRIPTION
				"This is the maximum threshold value."
			::= { pOnboardSensorEntry 33 }
		
		
		-- 1.3.6.1.4.1.994.3.4.7.6.1.46
		pOnboardSensorUnits OBJECT-TYPE
			SYNTAX DescriptionString
			MAX-ACCESS read-only
			STATUS current
			DESCRIPTION
				"Description of the units of measurement."
			::= { pOnboardSensorEntry 46 }
		
		
		-- 1.3.6.1.4.1.994.3.4.7.6.1.64
		pOnboardSensorLiveDescription OBJECT-TYPE
			SYNTAX DescriptionString
			MAX-ACCESS read-only
			STATUS current
			DESCRIPTION
				"The description of  the current state of the onboard sensor"
			::= { pOnboardSensorEntry 64 }
		
		
		-- 1.3.6.1.4.1.994.3.4.7.6.1.65
		pOnboardSensorLiveLevel OBJECT-TYPE
			SYNTAX DescriptionString
			MAX-ACCESS read-only
			STATUS current
			DESCRIPTION
				"The level of the current state of the onboard sensor."
			::= { pOnboardSensorEntry 65 }
		
		
		-- 1.3.6.1.4.1.994.3.4.7.6.1.66
		pOnboardSensorLiveRaw OBJECT-TYPE
			SYNTAX DescriptionString
			MAX-ACCESS read-only
			STATUS current
			DESCRIPTION
				"The current reading from the onboard sensor.  This value 
				will always be between the threshold 0 and threshold 5 values."
			::= { pOnboardSensorEntry 66 }
		
		
		-- 1.3.6.1.4.1.994.3.4.7.6.1.67
		pOnboardSensorLiveTime OBJECT-TYPE
			SYNTAX DescriptionString
			MAX-ACCESS read-only
			STATUS current
			DESCRIPTION
				"The time of the last event."
			::= { pOnboardSensorEntry 67 }
		
		
		-- 1.3.6.1.4.1.994.3.4.7.6.1.116
		pOnboardSensorTL1SID OBJECT-TYPE
			SYNTAX DescriptionString
			MAX-ACCESS read-write
			STATUS current
			DESCRIPTION
				"(TL1) System ID associated with this item."
			::= { pOnboardSensorEntry 116 }
		
		
		-- 1.3.6.1.4.1.994.3.4.7.6.1.117
		pOnboardSensorTL1COND OBJECT-TYPE
			SYNTAX DescriptionString
			MAX-ACCESS read-write
			STATUS current
			DESCRIPTION
				"(TL1) Condition text associated with this item."
			::= { pOnboardSensorEntry 117 }
		
		
		-- 1.3.6.1.4.1.994.3.4.7.6.1.118
		pOnboardSensorTL1Eqpt OBJECT-TYPE
			SYNTAX DescriptionString
			MAX-ACCESS read-write
			STATUS current
			DESCRIPTION
				"(TL1) EQPT field associated with this item."
			::= { pOnboardSensorEntry 118 }
		
		
		-- 1.3.6.1.4.1.994.3.4.7.6.1.119
		pOnboardSensorTL1Env OBJECT-TYPE
			SYNTAX Boolean
			MAX-ACCESS read-write
			STATUS current
			DESCRIPTION
				"(TL1) Environmental field associated with this item."
			::= { pOnboardSensorEntry 119 }
		
		
		-- 1.3.6.1.4.1.994.3.4.7.6.1.120
		pOnboardSensorTL1Srveff OBJECT-TYPE
			SYNTAX TL1Srveff
			MAX-ACCESS read-write
			STATUS current
			DESCRIPTION
				"(TL1) Service Effecting field associated with this item."
			::= { pOnboardSensorEntry 120 }
		
		
		-- 1.3.6.1.4.1.994.3.4.7.6.1.121
		pOnboardSensorTL1Locn OBJECT-TYPE
			SYNTAX TL1Locn
			MAX-ACCESS read-write
			STATUS current
			DESCRIPTION
				"(TL1) Location field associated with this item."
			::= { pOnboardSensorEntry 121 }
		
		
		-- 1.3.6.1.4.1.994.3.4.7.6.1.122
		pOnboardSensorTL1Dirn OBJECT-TYPE
			SYNTAX TL1Dirn
			MAX-ACCESS read-write
			STATUS current
			DESCRIPTION
				"(TL1) Direction field associated with this item."
			::= { pOnboardSensorEntry 122 }
		
		
		-- 1.3.6.1.4.1.994.3.4.7.6.1.999
		pOnboardSensorIndex OBJECT-TYPE
			SYNTAX Integer32 (1..2)
			MAX-ACCESS read-only
			STATUS current
			DESCRIPTION
				"Index."
			::= { pOnboardSensorEntry 999 }


-- NetDevices table
		
		-- 1.3.6.1.4.1.994.3.4.7.7
		pNetDevicesTable OBJECT-TYPE
			SYNTAX SEQUENCE OF PNetDevicesEntry
			MAX-ACCESS not-accessible
			STATUS current
			DESCRIPTION
				"Table for configuration of NetDevices"
			::= { configuration 7 }
		
		
		-- 1.3.6.1.4.1.994.3.4.7.7.1
		pNetDevicesEntry OBJECT-TYPE
			SYNTAX PNetDevicesEntry
			MAX-ACCESS not-accessible
			STATUS current
			DESCRIPTION
				"Entry for configuration table of NetDevices"
				INDEX { pNetDevicesIndex }
			::= { pNetDevicesTable 1 }
		
		
		PNetDevicesEntry ::= 
			SEQUENCE {
				pNetDevicesDescription
					DescriptionString,
				pNetDevicesDesc0
					DescriptionString,
				pNetDevicesDesc1
					DescriptionString,
				pNetDevicesConfigured
					Configured,
				pNetDevicesSendEmail
					Boolean,
				pNetDevicesSendSNMPTrap
					Boolean,
				pNetDevicesIpAddress
					IpAddress,
				pNetDevicesLevel0
					Level,
				pNetDevicesLevel1
					Level,
				pNetDevicesLiveDescription
					DescriptionString,
				pNetDevicesLiveLevel
					DescriptionString,
				pNetDevicesLiveRaw
					DescriptionString,
				pNetDevicesLiveTime
					DescriptionString,
				pNetDevicesTL1SID
					DescriptionString,
				pNetDevicesTL1COND
					DescriptionString,
				pNetDevicesTL1Eqpt
					DescriptionString,
				pNetDevicesTL1Env
					Boolean,
				pNetDevicesTL1Srveff
					TL1Srveff,
				pNetDevicesTL1Locn
					TL1Locn,
				pNetDevicesTL1Dirn
					TL1Dirn,
				pNetDevicesIndex
					Integer32 (1..32)
			}
		
		-- 1.3.6.1.4.1.994.3.4.7.7.1.3
		pNetDevicesDescription OBJECT-TYPE
			SYNTAX DescriptionString
			MAX-ACCESS read-write
			STATUS current
			DESCRIPTION
				"Description of the network device."
			::= { pNetDevicesEntry 3 }
		
		
		-- 1.3.6.1.4.1.994.3.4.7.7.1.4
		pNetDevicesDesc0 OBJECT-TYPE
			SYNTAX DescriptionString
			MAX-ACCESS read-write
			STATUS current
			DESCRIPTION
				"Text description of online state."
			::= { pNetDevicesEntry 4 }
		
		
		-- 1.3.6.1.4.1.994.3.4.7.7.1.5
		pNetDevicesDesc1 OBJECT-TYPE
			SYNTAX DescriptionString
			MAX-ACCESS read-write
			STATUS current
			DESCRIPTION
				"Text description of offline state."
			::= { pNetDevicesEntry 5 }
		
		
		-- 1.3.6.1.4.1.994.3.4.7.7.1.10
		pNetDevicesConfigured OBJECT-TYPE
			SYNTAX Configured
			MAX-ACCESS read-write
			STATUS current
			DESCRIPTION
				"If set to true, net device will be pinged,
				If set to false, no action will be taken."
			::= { pNetDevicesEntry 10 }
		
		
		-- 1.3.6.1.4.1.994.3.4.7.7.1.11
		pNetDevicesSendEmail OBJECT-TYPE
			SYNTAX Boolean
			MAX-ACCESS read-write
			STATUS current
			DESCRIPTION
				"If set to true, an email will be sent when a change of state is detected.
				If set to false, no email will be sent."
			::= { pNetDevicesEntry 11 }
		
		
		-- 1.3.6.1.4.1.994.3.4.7.7.1.12
		pNetDevicesSendSNMPTrap OBJECT-TYPE
			SYNTAX Boolean
			MAX-ACCESS read-write
			STATUS current
			DESCRIPTION
				"If set to true, an SNMP trap will be sent when a change of state is detected.
				If set to false, no SNMP trap will be sent."
			::= { pNetDevicesEntry 12 }
		
		
		-- 1.3.6.1.4.1.994.3.4.7.7.1.14
		pNetDevicesIpAddress OBJECT-TYPE
			SYNTAX IpAddress
			MAX-ACCESS read-write
			STATUS current
			DESCRIPTION
				"The IP address of the net device to ping."
			::= { pNetDevicesEntry 14 }
		
		
		-- 1.3.6.1.4.1.994.3.4.7.7.1.17
		pNetDevicesLevel0 OBJECT-TYPE
			SYNTAX Level
			MAX-ACCESS read-write
			STATUS current
			DESCRIPTION
				"Alarm level associated with the online state."
			::= { pNetDevicesEntry 17 }
		
		
		-- 1.3.6.1.4.1.994.3.4.7.7.1.18
		pNetDevicesLevel1 OBJECT-TYPE
			SYNTAX Level
			MAX-ACCESS read-write
			STATUS current
			DESCRIPTION
				"Alarm level associated with the offline state."
			::= { pNetDevicesEntry 18 }
		
		
		-- 1.3.6.1.4.1.994.3.4.7.7.1.64
		pNetDevicesLiveDescription OBJECT-TYPE
			SYNTAX DescriptionString
			MAX-ACCESS read-only
			STATUS current
			DESCRIPTION
				"The description of the current state of the net device"
			::= { pNetDevicesEntry 64 }
		
		
		-- 1.3.6.1.4.1.994.3.4.7.7.1.65
		pNetDevicesLiveLevel OBJECT-TYPE
			SYNTAX DescriptionString
			MAX-ACCESS read-only
			STATUS current
			DESCRIPTION
				"The level of the current state of the net device."
			::= { pNetDevicesEntry 65 }
		
		
		-- 1.3.6.1.4.1.994.3.4.7.7.1.66
		pNetDevicesLiveRaw OBJECT-TYPE
			SYNTAX DescriptionString
			MAX-ACCESS read-only
			STATUS current
			DESCRIPTION
				"The current reading from the net device.  This value will always
				be between the threshold 0 and threshold 5 values."
			::= { pNetDevicesEntry 66 }
		
		
		-- 1.3.6.1.4.1.994.3.4.7.7.1.67
		pNetDevicesLiveTime OBJECT-TYPE
			SYNTAX DescriptionString
			MAX-ACCESS read-only
			STATUS current
			DESCRIPTION
				"The time of the last event."
			::= { pNetDevicesEntry 67 }
		
		
		-- 1.3.6.1.4.1.994.3.4.7.7.1.116
		pNetDevicesTL1SID OBJECT-TYPE
			SYNTAX DescriptionString
			MAX-ACCESS read-write
			STATUS current
			DESCRIPTION
				"(TL1) System ID associated with this item."
			::= { pNetDevicesEntry 116 }
		
		
		-- 1.3.6.1.4.1.994.3.4.7.7.1.117
		pNetDevicesTL1COND OBJECT-TYPE
			SYNTAX DescriptionString
			MAX-ACCESS read-write
			STATUS current
			DESCRIPTION
				"(TL1) Condition text associated with this item."
			::= { pNetDevicesEntry 117 }
		
		
		-- 1.3.6.1.4.1.994.3.4.7.7.1.118
		pNetDevicesTL1Eqpt OBJECT-TYPE
			SYNTAX DescriptionString
			MAX-ACCESS read-write
			STATUS current
			DESCRIPTION
				"(TL1) EQPT field associated with this item."
			::= { pNetDevicesEntry 118 }
		
		
		-- 1.3.6.1.4.1.994.3.4.7.7.1.119
		pNetDevicesTL1Env OBJECT-TYPE
			SYNTAX Boolean
			MAX-ACCESS read-write
			STATUS current
			DESCRIPTION
				"(TL1) Environmental field associated with this item."
			::= { pNetDevicesEntry 119 }
		
		
		-- 1.3.6.1.4.1.994.3.4.7.7.1.120
		pNetDevicesTL1Srveff OBJECT-TYPE
			SYNTAX TL1Srveff
			MAX-ACCESS read-write
			STATUS current
			DESCRIPTION
				"(TL1) Service Effecting field associated with this item."
			::= { pNetDevicesEntry 120 }
		
		
		-- 1.3.6.1.4.1.994.3.4.7.7.1.121
		pNetDevicesTL1Locn OBJECT-TYPE
			SYNTAX TL1Locn
			MAX-ACCESS read-write
			STATUS current
			DESCRIPTION
				"(TL1) Location field associated with this item."
			::= { pNetDevicesEntry 121 }
		
		
		-- 1.3.6.1.4.1.994.3.4.7.7.1.122
		pNetDevicesTL1Dirn OBJECT-TYPE
			SYNTAX TL1Dirn
			MAX-ACCESS read-write
			STATUS current
			DESCRIPTION
				"(TL1) Direction field associated with this item."
			::= { pNetDevicesEntry 122 }
		
		
		-- 1.3.6.1.4.1.994.3.4.7.7.1.999
		pNetDevicesIndex OBJECT-TYPE
			SYNTAX Integer32 (1..32)
			MAX-ACCESS read-only
			STATUS current
			DESCRIPTION
				"Index."
			::= { pNetDevicesEntry 999 }


-- Accounts table
		
		-- 1.3.6.1.4.1.994.3.4.7.9
		pAccountsTable OBJECT-TYPE
			SYNTAX SEQUENCE OF PAccountsEntry
			MAX-ACCESS not-accessible
			STATUS current
			DESCRIPTION
				"Table for configuration of Accounts"
			::= { configuration 9 }
		
		
		-- 1.3.6.1.4.1.994.3.4.7.9.1
		pAccountsEntry OBJECT-TYPE
			SYNTAX PAccountsEntry
			MAX-ACCESS not-accessible
			STATUS current
			DESCRIPTION
				"Entry for configuration table of Accounts"
				INDEX { pAccountsIndex }
			::= { pAccountsTable 1 }
		
		
		PAccountsEntry ::= 
			SEQUENCE {
				pAccountsConfigured
					Configured,
				pAccountsName
					DescriptionString,
				pAccountsEncPassword
					DescriptionString,
				pAccountsUserLevel
					Unsigned32,
				pAccountsUnsecured
					Boolean,
				pAccountsAuthKey
					DescriptionString,
				pAccountsPrivKey
					DescriptionString,
				pAccountsSNMPAccess
					SNMPAccess,
				pAccountsIndex
					Integer32 (1..16)
			}
		
		-- 1.3.6.1.4.1.994.3.4.7.9.1.10
		pAccountsConfigured OBJECT-TYPE
			SYNTAX Configured
			MAX-ACCESS read-write
			STATUS current
			DESCRIPTION
				"If set to true, this account can be used to login."
			::= { pAccountsEntry 10 }
		
		
		-- 1.3.6.1.4.1.994.3.4.7.9.1.25
		pAccountsName OBJECT-TYPE
			SYNTAX DescriptionString
			MAX-ACCESS read-write
			STATUS current
			DESCRIPTION
				"Name associated with this account."
			::= { pAccountsEntry 25 }
		
		
		-- 1.3.6.1.4.1.994.3.4.7.9.1.27
		pAccountsEncPassword OBJECT-TYPE
			SYNTAX DescriptionString
			MAX-ACCESS read-write
			STATUS current
			DESCRIPTION
				"Password for this account.  When reading, an encrypted version of password 
				will be displayed.  When writing, use plain text."
			::= { pAccountsEntry 27 }
		
		
		-- 1.3.6.1.4.1.994.3.4.7.9.1.55
		pAccountsUserLevel OBJECT-TYPE
			SYNTAX Unsigned32
			MAX-ACCESS read-write
			STATUS current
			DESCRIPTION
				"The user level for this account.
				One of the following masks from each group are used:
				   No FTP access     0x0000   0
				   FTP read-only     0x0001   1
				   FTP Full access   0x0003   3
				
				   No Web access     0x0000   0
				   Monitor           0x0010  16
				   Config            0x0030  48
				   Config + Accounts 0x00B0 176
				The masks are added together to create a permission value."
			::= { pAccountsEntry 55 }
		
		
		-- 1.3.6.1.4.1.994.3.4.7.9.1.77
		pAccountsUnsecured OBJECT-TYPE
			SYNTAX Boolean
			MAX-ACCESS read-write
			STATUS current
			DESCRIPTION
				"Allow secured configuration for SNMP through this account."
			::= { pAccountsEntry 77 }
		
		
		-- 1.3.6.1.4.1.994.3.4.7.9.1.140
		pAccountsAuthKey OBJECT-TYPE
			SYNTAX DescriptionString
			MAX-ACCESS read-write
			STATUS current
			DESCRIPTION
				""
			::= { pAccountsEntry 140 }
		
		
		-- 1.3.6.1.4.1.994.3.4.7.9.1.141
		pAccountsPrivKey OBJECT-TYPE
			SYNTAX DescriptionString
			MAX-ACCESS read-write
			STATUS current
			DESCRIPTION
				""
			::= { pAccountsEntry 141 }
		
		
		-- 1.3.6.1.4.1.994.3.4.7.9.1.142
		pAccountsSNMPAccess OBJECT-TYPE
			SYNTAX SNMPAccess
			MAX-ACCESS read-write
			STATUS current
			DESCRIPTION
				""
			::= { pAccountsEntry 142 }
		
		
		-- 1.3.6.1.4.1.994.3.4.7.9.1.999
		pAccountsIndex OBJECT-TYPE
			SYNTAX Integer32 (1..16)
			MAX-ACCESS read-only
			STATUS current
			DESCRIPTION
				"Index."
			::= { pAccountsEntry 999 }


-- camera folder
		
		-- 1.3.6.1.4.1.994.3.4.7.10
		camera OBJECT IDENTIFIER ::= {configuration 10 }
		
		-- 1.3.6.1.4.1.994.3.4.7.10.10
		cameraConfigured OBJECT-TYPE
			SYNTAX Configured
			MAX-ACCESS read-write
			STATUS current
			DESCRIPTION
				"If set to true, camera view will be used in main webpage.
				If set to false, camera view will not be used."
			::= { camera 10 }
		
		
		-- 1.3.6.1.4.1.994.3.4.7.10.14
		cameraIpAddress OBJECT-TYPE
			SYNTAX IpAddress
			MAX-ACCESS read-write
			STATUS current
			DESCRIPTION
				"IP address of the camera."
			::= { camera 14 }
		
		
		-- 1.3.6.1.4.1.994.3.4.7.10.43
		cameraCameraStyle OBJECT-TYPE
			SYNTAX CameraStyle
			MAX-ACCESS read-write
			STATUS current
			DESCRIPTION
				"Type of camera used."
			::= { camera 43 }


-- snmpGeneral folder
		
		-- 1.3.6.1.4.1.994.3.4.7.12
		snmpGeneral OBJECT IDENTIFIER ::= {configuration 12 }
		
		-- 1.3.6.1.4.1.994.3.4.7.12.10
		snmpGeneralConfigured OBJECT-TYPE
			SYNTAX Configured
			MAX-ACCESS read-write
			STATUS current
			DESCRIPTION
				"Resend standing alarms at a given interval"
			::= { snmpGeneral 10 }
		
		
		-- 1.3.6.1.4.1.994.3.4.7.12.23
		snmpGeneralReadPeriod OBJECT-TYPE
			SYNTAX Integer32
			MAX-ACCESS read-write
			STATUS current
			DESCRIPTION
				"Period in minutes between resend of standing alarms"
			::= { snmpGeneral 23 }
		
		
		-- 1.3.6.1.4.1.994.3.4.7.12.39
		snmpGeneralGet OBJECT-TYPE
			SYNTAX DescriptionString
			MAX-ACCESS read-write
			STATUS current
			DESCRIPTION
				"Get community name for SNMP."
			::= { snmpGeneral 39 }
		
		
		-- 1.3.6.1.4.1.994.3.4.7.12.40
		snmpGeneralSet OBJECT-TYPE
			SYNTAX DescriptionString
			MAX-ACCESS read-write
			STATUS current
			DESCRIPTION
				"Set community name for SNMP."
			::= { snmpGeneral 40 }
		
		
		-- 1.3.6.1.4.1.994.3.4.7.12.41
		snmpGeneralTrap OBJECT-TYPE
			SYNTAX DescriptionString
			MAX-ACCESS read-write
			STATUS current
			DESCRIPTION
				"Trap community name for SNMP."
			::= { snmpGeneral 41 }
		
		
		-- 1.3.6.1.4.1.994.3.4.7.12.73
		snmpGeneralIPPortNum OBJECT-TYPE
			SYNTAX Integer32
			MAX-ACCESS read-write
			STATUS current
			DESCRIPTION
				"SNMP configuration is done on this network port."
			::= { snmpGeneral 73 }
		
		
		-- 1.3.6.1.4.1.994.3.4.7.12.143
		snmpGeneralEngineID OBJECT-TYPE
			SYNTAX DescriptionString
			MAX-ACCESS read-only
			STATUS current
			DESCRIPTION
				"SNMP v3 engine ID"
			::= { snmpGeneral 143 }


-- emailGeneral folder
		
		-- 1.3.6.1.4.1.994.3.4.7.13
		emailGeneral OBJECT IDENTIFIER ::= {configuration 13 }
		
		-- 1.3.6.1.4.1.994.3.4.7.13.1
		emailGeneralAddress OBJECT-TYPE
			SYNTAX DescriptionString
			MAX-ACCESS read-write
			STATUS current
			DESCRIPTION
				"Login name to use if logging into email server is true."
			::= { emailGeneral 1 }
		
		
		-- 1.3.6.1.4.1.994.3.4.7.13.10
		emailGeneralConfigured OBJECT-TYPE
			SYNTAX Configured
			MAX-ACCESS read-write
			STATUS current
			DESCRIPTION
				"If set to true, the device will log onto the email server before sending 
				and email event.  If set to false, the device will not log onto email server."
			::= { emailGeneral 10 }
		
		
		-- 1.3.6.1.4.1.994.3.4.7.13.14
		emailGeneralIpAddress OBJECT-TYPE
			SYNTAX IpAddress
			MAX-ACCESS read-write
			STATUS current
			DESCRIPTION
				"IP address of email server."
			::= { emailGeneral 14 }
		
		
		-- 1.3.6.1.4.1.994.3.4.7.13.26
		emailGeneralPassword OBJECT-TYPE
			SYNTAX DescriptionString
			MAX-ACCESS read-write
			STATUS current
			DESCRIPTION
				"Password to use if logging into email server is true."
			::= { emailGeneral 26 }
		
		
		-- 1.3.6.1.4.1.994.3.4.7.13.73
		emailGeneralIPPortNum OBJECT-TYPE
			SYNTAX Integer32
			MAX-ACCESS read-write
			STATUS current
			DESCRIPTION
				"Port number address of email server."
			::= { emailGeneral 73 }


-- Serial table
		
		-- 1.3.6.1.4.1.994.3.4.7.14
		pSerialTable OBJECT-TYPE
			SYNTAX SEQUENCE OF PSerialEntry
			MAX-ACCESS not-accessible
			STATUS current
			DESCRIPTION
				"Table for configuration of Serial"
			::= { configuration 14 }
		
		
		-- 1.3.6.1.4.1.994.3.4.7.14.1
		pSerialEntry OBJECT-TYPE
			SYNTAX PSerialEntry
			MAX-ACCESS not-accessible
			STATUS current
			DESCRIPTION
				"Entry for configuration table of Serial"
				INDEX { pSerialIndex }
			::= { pSerialTable 1 }
		
		
		PSerialEntry ::= 
			SEQUENCE {
				pSerialDescription
					DescriptionString,
				pSerialConfigured
					Configured,
				pSerialIpAddress
					IpAddress,
				pSerialReadPeriod
					Integer32,
				pSerialBaudRate
					BaudRate,
				pSerialDataBits
					DataBits,
				pSerialParity
					Parity,
				pSerialStopBits
					StopBits,
				pSerialProtocol
					Protocol,
				pSerialSerialRTS
					SerialRTS,
				pSerialSerialCTS
					SerialCTS,
				pSerialPresent
					Boolean,
				pSerialIPPortNum
					Integer32,
				pSerialPortType
					PortType,
				pSerialIndex
					Integer32 (1..5)
			}
		
		-- 1.3.6.1.4.1.994.3.4.7.14.1.3
		pSerialDescription OBJECT-TYPE
			SYNTAX DescriptionString
			MAX-ACCESS read-only
			STATUS current
			DESCRIPTION
				"Description of the serial port."
			::= { pSerialEntry 3 }
		
		
		-- 1.3.6.1.4.1.994.3.4.7.14.1.10
		pSerialConfigured OBJECT-TYPE
			SYNTAX Configured
			MAX-ACCESS read-write
			STATUS current
			DESCRIPTION
				"If set to true, this serial port will be usable.
				If set to false the port will not be usable."
			::= { pSerialEntry 10 }
		
		
		-- 1.3.6.1.4.1.994.3.4.7.14.1.14
		pSerialIpAddress OBJECT-TYPE
			SYNTAX IpAddress
			MAX-ACCESS read-write
			STATUS current
			DESCRIPTION
				"IP Address of the target device."
			::= { pSerialEntry 14 }
		
		
		-- 1.3.6.1.4.1.994.3.4.7.14.1.23
		pSerialReadPeriod OBJECT-TYPE
			SYNTAX Integer32
			MAX-ACCESS read-write
			STATUS current
			DESCRIPTION
				"Inactivity timeout (in minutes)."
			::= { pSerialEntry 23 }
		
		
		-- 1.3.6.1.4.1.994.3.4.7.14.1.57
		pSerialBaudRate OBJECT-TYPE
			SYNTAX BaudRate
			MAX-ACCESS read-write
			STATUS current
			DESCRIPTION
				"Baud rate of the serial port."
			::= { pSerialEntry 57 }
		
		
		-- 1.3.6.1.4.1.994.3.4.7.14.1.58
		pSerialDataBits OBJECT-TYPE
			SYNTAX DataBits
			MAX-ACCESS read-write
			STATUS current
			DESCRIPTION
				"Number of data bit for the serial port."
			::= { pSerialEntry 58 }
		
		
		-- 1.3.6.1.4.1.994.3.4.7.14.1.59
		pSerialParity OBJECT-TYPE
			SYNTAX Parity
			MAX-ACCESS read-write
			STATUS current
			DESCRIPTION
				"Parity of the serial port."
			::= { pSerialEntry 59 }
		
		
		-- 1.3.6.1.4.1.994.3.4.7.14.1.60
		pSerialStopBits OBJECT-TYPE
			SYNTAX StopBits
			MAX-ACCESS read-write
			STATUS current
			DESCRIPTION
				"Number of stop bits for the serial port."
			::= { pSerialEntry 60 }
		
		
		-- 1.3.6.1.4.1.994.3.4.7.14.1.61
		pSerialProtocol OBJECT-TYPE
			SYNTAX Protocol
			MAX-ACCESS read-write
			STATUS current
			DESCRIPTION
				"Protocol the serial port is speaking."
			::= { pSerialEntry 61 }
		
		
		-- 1.3.6.1.4.1.994.3.4.7.14.1.62
		pSerialSerialRTS OBJECT-TYPE
			SYNTAX SerialRTS
			MAX-ACCESS read-write
			STATUS current
			DESCRIPTION
				"Request To Send (RTS) setting for the serial port."
			::= { pSerialEntry 62 }
		
		
		-- 1.3.6.1.4.1.994.3.4.7.14.1.63
		pSerialSerialCTS OBJECT-TYPE
			SYNTAX SerialCTS
			MAX-ACCESS read-write
			STATUS current
			DESCRIPTION
				"Clear To Send (CTS) setting for the serial port."
			::= { pSerialEntry 63 }
		
		
		-- 1.3.6.1.4.1.994.3.4.7.14.1.68
		pSerialPresent OBJECT-TYPE
			SYNTAX Boolean
			MAX-ACCESS read-only
			STATUS current
			DESCRIPTION
				"If set to true, the serial port exists.
				If set to false the serial port does not exist."
			::= { pSerialEntry 68 }
		
		
		-- 1.3.6.1.4.1.994.3.4.7.14.1.73
		pSerialIPPortNum OBJECT-TYPE
			SYNTAX Integer32
			MAX-ACCESS read-write
			STATUS current
			DESCRIPTION
				"IP port number of the target device."
			::= { pSerialEntry 73 }
		
		
		-- 1.3.6.1.4.1.994.3.4.7.14.1.76
		pSerialPortType OBJECT-TYPE
			SYNTAX PortType
			MAX-ACCESS read-only
			STATUS current
			DESCRIPTION
				"The type of serial port."
			::= { pSerialEntry 76 }
		
		
		-- 1.3.6.1.4.1.994.3.4.7.14.1.999
		pSerialIndex OBJECT-TYPE
			SYNTAX Integer32 (1..5)
			MAX-ACCESS read-only
			STATUS current
			DESCRIPTION
				"Index."
			::= { pSerialEntry 999 }


-- SelfTest table
		
		-- 1.3.6.1.4.1.994.3.4.7.15
		pSelfTestTable OBJECT-TYPE
			SYNTAX SEQUENCE OF PSelfTestEntry
			MAX-ACCESS not-accessible
			STATUS current
			DESCRIPTION
				"Table for configuration of SelfTest"
			::= { configuration 15 }
		
		
		-- 1.3.6.1.4.1.994.3.4.7.15.1
		pSelfTestEntry OBJECT-TYPE
			SYNTAX PSelfTestEntry
			MAX-ACCESS not-accessible
			STATUS current
			DESCRIPTION
				"Entry for configuration table of SelfTest"
				INDEX { pSelfTestIndex }
			::= { pSelfTestTable 1 }
		
		
		PSelfTestEntry ::= 
			SEQUENCE {
				pSelfTestDescription
					DescriptionString,
				pSelfTestConfigured
					Configured,
				pSelfTestIndex
					Integer32 (1..7)
			}
		
		-- 1.3.6.1.4.1.994.3.4.7.15.1.3
		pSelfTestDescription OBJECT-TYPE
			SYNTAX DescriptionString
			MAX-ACCESS read-write
			STATUS current
			DESCRIPTION
				"Description of the Power On Self Test (POST)."
			::= { pSelfTestEntry 3 }
		
		
		-- 1.3.6.1.4.1.994.3.4.7.15.1.10
		pSelfTestConfigured OBJECT-TYPE
			SYNTAX Configured
			MAX-ACCESS read-write
			STATUS current
			DESCRIPTION
				"If set to true, this POST has passed.  If set to false, it has failed."
			::= { pSelfTestEntry 10 }
		
		
		-- 1.3.6.1.4.1.994.3.4.7.15.1.999
		pSelfTestIndex OBJECT-TYPE
			SYNTAX Integer32 (1..7)
			MAX-ACCESS read-only
			STATUS current
			DESCRIPTION
				"Index."
			::= { pSelfTestEntry 999 }


-- InternalFaults table
		
		-- 1.3.6.1.4.1.994.3.4.7.16
		pInternalFaultsTable OBJECT-TYPE
			SYNTAX SEQUENCE OF PInternalFaultsEntry
			MAX-ACCESS not-accessible
			STATUS current
			DESCRIPTION
				"Table for configuration of InternalFaults"
			::= { configuration 16 }
		
		
		-- 1.3.6.1.4.1.994.3.4.7.16.1
		pInternalFaultsEntry OBJECT-TYPE
			SYNTAX PInternalFaultsEntry
			MAX-ACCESS not-accessible
			STATUS current
			DESCRIPTION
				"Entry for configuration table of InternalFaults"
				INDEX { pInternalFaultsIndex }
			::= { pInternalFaultsTable 1 }
		
		
		PInternalFaultsEntry ::= 
			SEQUENCE {
				pInternalFaultsDescription
					DescriptionString,
				pInternalFaultsDesc0
					DescriptionString,
				pInternalFaultsDesc1
					DescriptionString,
				pInternalFaultsDesc2
					DescriptionString,
				pInternalFaultsDesc3
					DescriptionString,
				pInternalFaultsSendEmail
					Boolean,
				pInternalFaultsSendSNMPTrap
					Boolean,
				pInternalFaultsLevel0
					Level,
				pInternalFaultsLevel1
					Level,
				pInternalFaultsLevel2
					Level,
				pInternalFaultsLevel3
					Level,
				pInternalFaultsIgnoreOff
					Boolean,
				pInternalFaultsLiveDescription
					DescriptionString,
				pInternalFaultsLiveLevel
					DescriptionString,
				pInternalFaultsLiveTime
					DescriptionString,
				pInternalFaultsIndex
					Integer32 (1..11)
			}
		
		-- 1.3.6.1.4.1.994.3.4.7.16.1.3
		pInternalFaultsDescription OBJECT-TYPE
			SYNTAX DescriptionString
			MAX-ACCESS read-only
			STATUS current
			DESCRIPTION
				"Description of the internal fault."
			::= { pInternalFaultsEntry 3 }
		
		
		-- 1.3.6.1.4.1.994.3.4.7.16.1.4
		pInternalFaultsDesc0 OBJECT-TYPE
			SYNTAX DescriptionString
			MAX-ACCESS read-only
			STATUS current
			DESCRIPTION
				"Text description of the healthy state."
			::= { pInternalFaultsEntry 4 }
		
		
		-- 1.3.6.1.4.1.994.3.4.7.16.1.5
		pInternalFaultsDesc1 OBJECT-TYPE
			SYNTAX DescriptionString
			MAX-ACCESS read-only
			STATUS current
			DESCRIPTION
				"Text description of a non-normal state."
			::= { pInternalFaultsEntry 5 }
		
		
		-- 1.3.6.1.4.1.994.3.4.7.16.1.6
		pInternalFaultsDesc2 OBJECT-TYPE
			SYNTAX DescriptionString
			MAX-ACCESS read-only
			STATUS current
			DESCRIPTION
				"Text description of a non-normal state."
			::= { pInternalFaultsEntry 6 }
		
		
		-- 1.3.6.1.4.1.994.3.4.7.16.1.7
		pInternalFaultsDesc3 OBJECT-TYPE
			SYNTAX DescriptionString
			MAX-ACCESS read-only
			STATUS current
			DESCRIPTION
				"Text description of a non-normal state."
			::= { pInternalFaultsEntry 7 }
		
		
		-- 1.3.6.1.4.1.994.3.4.7.16.1.11
		pInternalFaultsSendEmail OBJECT-TYPE
			SYNTAX Boolean
			MAX-ACCESS read-write
			STATUS current
			DESCRIPTION
				"If set to true an email event will be set when a change occurs.
				If set to false no email event will be sent."
			::= { pInternalFaultsEntry 11 }
		
		
		-- 1.3.6.1.4.1.994.3.4.7.16.1.12
		pInternalFaultsSendSNMPTrap OBJECT-TYPE
			SYNTAX Boolean
			MAX-ACCESS read-write
			STATUS current
			DESCRIPTION
				"If set to true an SNMP trap will be set when a change occurs.
				If set to false no SNMP trap will be sent."
			::= { pInternalFaultsEntry 12 }
		
		
		-- 1.3.6.1.4.1.994.3.4.7.16.1.17
		pInternalFaultsLevel0 OBJECT-TYPE
			SYNTAX Level
			MAX-ACCESS read-write
			STATUS current
			DESCRIPTION
				"Alarm level associated with the healthy state."
			::= { pInternalFaultsEntry 17 }
		
		
		-- 1.3.6.1.4.1.994.3.4.7.16.1.18
		pInternalFaultsLevel1 OBJECT-TYPE
			SYNTAX Level
			MAX-ACCESS read-write
			STATUS current
			DESCRIPTION
				"Alarm level associated with this non-normal state."
			::= { pInternalFaultsEntry 18 }
		
		
		-- 1.3.6.1.4.1.994.3.4.7.16.1.19
		pInternalFaultsLevel2 OBJECT-TYPE
			SYNTAX Level
			MAX-ACCESS read-write
			STATUS current
			DESCRIPTION
				"Alarm level associated with this non-normal state."
			::= { pInternalFaultsEntry 19 }
		
		
		-- 1.3.6.1.4.1.994.3.4.7.16.1.20
		pInternalFaultsLevel3 OBJECT-TYPE
			SYNTAX Level
			MAX-ACCESS read-write
			STATUS current
			DESCRIPTION
				"Alarm level associated with this non-normal state."
			::= { pInternalFaultsEntry 20 }
		
		
		-- 1.3.6.1.4.1.994.3.4.7.16.1.50
		pInternalFaultsIgnoreOff OBJECT-TYPE
			SYNTAX Boolean
			MAX-ACCESS read-write
			STATUS current
			DESCRIPTION
				"If true, no event is generated for a change to the healty state."
			::= { pInternalFaultsEntry 50 }
		
		
		-- 1.3.6.1.4.1.994.3.4.7.16.1.64
		pInternalFaultsLiveDescription OBJECT-TYPE
			SYNTAX DescriptionString
			MAX-ACCESS read-only
			STATUS current
			DESCRIPTION
				"The current condition of the internal fault."
			::= { pInternalFaultsEntry 64 }
		
		
		-- 1.3.6.1.4.1.994.3.4.7.16.1.65
		pInternalFaultsLiveLevel OBJECT-TYPE
			SYNTAX DescriptionString
			MAX-ACCESS read-only
			STATUS current
			DESCRIPTION
				"The current level of the internal fault."
			::= { pInternalFaultsEntry 65 }
		
		
		-- 1.3.6.1.4.1.994.3.4.7.16.1.67
		pInternalFaultsLiveTime OBJECT-TYPE
			SYNTAX DescriptionString
			MAX-ACCESS read-only
			STATUS current
			DESCRIPTION
				"The time of the fault event."
			::= { pInternalFaultsEntry 67 }
		
		
		-- 1.3.6.1.4.1.994.3.4.7.16.1.999
		pInternalFaultsIndex OBJECT-TYPE
			SYNTAX Integer32 (1..11)
			MAX-ACCESS read-only
			STATUS current
			DESCRIPTION
				"Index."
			::= { pInternalFaultsEntry 999 }


-- SlotInfo table
		
		-- 1.3.6.1.4.1.994.3.4.7.17
		pSlotInfoTable OBJECT-TYPE
			SYNTAX SEQUENCE OF PSlotInfoEntry
			MAX-ACCESS not-accessible
			STATUS current
			DESCRIPTION
				"Table for configuration of SlotInfo"
			::= { configuration 17 }
		
		
		-- 1.3.6.1.4.1.994.3.4.7.17.1
		pSlotInfoEntry OBJECT-TYPE
			SYNTAX PSlotInfoEntry
			MAX-ACCESS not-accessible
			STATUS current
			DESCRIPTION
				"Entry for configuration table of SlotInfo"
				INDEX { pSlotInfoIndex }
			::= { pSlotInfoTable 1 }
		
		
		PSlotInfoEntry ::= 
			SEQUENCE {
				pSlotInfoDescription
					DescriptionString,
				pSlotInfoRecord
					Integer32,
				pSlotInfoPresent
					Boolean,
				pSlotInfoSlotId
					SlotId,
				pSlotInfoIndex
					Integer32 (1..6)
			}
		
		-- 1.3.6.1.4.1.994.3.4.7.17.1.3
		pSlotInfoDescription OBJECT-TYPE
			SYNTAX DescriptionString
			MAX-ACCESS read-only
			STATUS current
			DESCRIPTION
				"Description of the slot contents."
			::= { pSlotInfoEntry 3 }
		
		
		-- 1.3.6.1.4.1.994.3.4.7.17.1.35
		pSlotInfoRecord OBJECT-TYPE
			SYNTAX Integer32
			MAX-ACCESS read-only
			STATUS current
			DESCRIPTION
				"The number of records for this slot."
			::= { pSlotInfoEntry 35 }
		
		
		-- 1.3.6.1.4.1.994.3.4.7.17.1.68
		pSlotInfoPresent OBJECT-TYPE
			SYNTAX Boolean
			MAX-ACCESS read-only
			STATUS current
			DESCRIPTION
				"If true indicates a card is in the slot.
				If false indicates that no card is present in the slot."
			::= { pSlotInfoEntry 68 }
		
		
		-- 1.3.6.1.4.1.994.3.4.7.17.1.69
		pSlotInfoSlotId OBJECT-TYPE
			SYNTAX SlotId
			MAX-ACCESS read-only
			STATUS current
			DESCRIPTION
				"Identifies the type of card in slot."
			::= { pSlotInfoEntry 69 }
		
		
		-- 1.3.6.1.4.1.994.3.4.7.17.1.999
		pSlotInfoIndex OBJECT-TYPE
			SYNTAX Integer32 (1..6)
			MAX-ACCESS read-only
			STATUS current
			DESCRIPTION
				"Index."
			::= { pSlotInfoEntry 999 }


-- NetPorts table
		
		-- 1.3.6.1.4.1.994.3.4.7.24
		pNetPortsTable OBJECT-TYPE
			SYNTAX SEQUENCE OF PNetPortsEntry
			MAX-ACCESS not-accessible
			STATUS current
			DESCRIPTION
				"Table for configuration of NetPorts"
			::= { configuration 24 }
		
		
		-- 1.3.6.1.4.1.994.3.4.7.24.1
		pNetPortsEntry OBJECT-TYPE
			SYNTAX PNetPortsEntry
			MAX-ACCESS not-accessible
			STATUS current
			DESCRIPTION
				"Entry for configuration table of NetPorts"
				INDEX { pNetPortsIndex }
			::= { pNetPortsTable 1 }
		
		
		PNetPortsEntry ::= 
			SEQUENCE {
				pNetPortsDescription
					DescriptionString,
				pNetPortsIPPortNum
					Integer32,
				pNetPortsIndex
					Integer32 (1..5)
			}
		
		-- 1.3.6.1.4.1.994.3.4.7.24.1.3
		pNetPortsDescription OBJECT-TYPE
			SYNTAX DescriptionString
			MAX-ACCESS read-only
			STATUS current
			DESCRIPTION
				"Description of the static network ports."
			::= { pNetPortsEntry 3 }
		
		
		-- 1.3.6.1.4.1.994.3.4.7.24.1.73
		pNetPortsIPPortNum OBJECT-TYPE
			SYNTAX Integer32
			MAX-ACCESS read-write
			STATUS current
			DESCRIPTION
				"IP port number to use when connecting to this network port."
			::= { pNetPortsEntry 73 }
		
		
		-- 1.3.6.1.4.1.994.3.4.7.24.1.999
		pNetPortsIndex OBJECT-TYPE
			SYNTAX Integer32 (1..5)
			MAX-ACCESS read-only
			STATUS current
			DESCRIPTION
				"Index."
			::= { pNetPortsEntry 999 }


-- wirelessModem folder
		
		-- 1.3.6.1.4.1.994.3.4.7.25
		wirelessModem OBJECT IDENTIFIER ::= {configuration 25 }
		
		-- 1.3.6.1.4.1.994.3.4.7.25.78
		wirelessModemBackupIPAddress OBJECT-TYPE
			SYNTAX IpAddress
			MAX-ACCESS read-only
			STATUS current
			DESCRIPTION
				"Wireless Modem IP Address."
			::= { wirelessModem 78 }
		
		
		-- 1.3.6.1.4.1.994.3.4.7.25.81
		wirelessModemTime OBJECT-TYPE
			SYNTAX DescriptionString
			MAX-ACCESS read-write
			STATUS current
			DESCRIPTION
				"Wireless modem 24 hour reset time (hh:mm:ss)"
			::= { wirelessModem 81 }
		
		
		-- 1.3.6.1.4.1.994.3.4.7.25.96
		wirelessModemTransmit OBJECT-TYPE
			SYNTAX DescriptionString
			MAX-ACCESS read-write
			STATUS current
			DESCRIPTION
				"The string that will be sent to the modem."
			::= { wirelessModem 96 }
		
		
		-- 1.3.6.1.4.1.994.3.4.7.25.97
		wirelessModemUseWirelessNetwork OBJECT-TYPE
			SYNTAX Boolean
			MAX-ACCESS read-write
			STATUS current
			DESCRIPTION
				"Determines if modem tries to connect to wireless network."
			::= { wirelessModem 97 }
		
		
		-- 1.3.6.1.4.1.994.3.4.7.25.98
		wirelessModemUseResetTime OBJECT-TYPE
			SYNTAX Boolean
			MAX-ACCESS read-write
			STATUS current
			DESCRIPTION
				"Determines if the modem resets at reset time."
			::= { wirelessModem 98 }
		
		
		-- 1.3.6.1.4.1.994.3.4.7.25.99
		wirelessModemResponseWaitTime OBJECT-TYPE
			SYNTAX DescriptionString
			MAX-ACCESS read-write
			STATUS current
			DESCRIPTION
				"Response Timeout (s)"
			::= { wirelessModem 99 }
		
		
		-- 1.3.6.1.4.1.994.3.4.7.25.115
		wirelessModemSecondary OBJECT-TYPE
			SYNTAX Boolean
			MAX-ACCESS read-write
			STATUS current
			DESCRIPTION
				"Determines if the modem can use accept a dynamic (local) IP."
			::= { wirelessModem 115 }


-- webmonSecurity folder
		
		-- 1.3.6.1.4.1.994.3.4.7.26
		webmonSecurity OBJECT IDENTIFIER ::= {configuration 26 }
		
		-- 1.3.6.1.4.1.994.3.4.7.26.55
		webmonSecurityUserLevel OBJECT-TYPE
			SYNTAX Unsigned32
			MAX-ACCESS read-write
			STATUS current
			DESCRIPTION
				"This is the default user level. Anyone who has access to this 
				device will have these permissions without logging in. 
				One of the following masks from each group are used:
				   No FTP access     0x0000   0
				   FTP read-only     0x0001   1
				   FTP Full access   0x0003   3
				
				   No Web access     0x0000   0
				   Monitor           0x0010  16
				   Config            0x0030  48
				   Config + Accounts 0x00B0 176
				The masks are added together to create a permission value."
			::= { webmonSecurity 55 }
		
		
		-- 1.3.6.1.4.1.994.3.4.7.26.77
		webmonSecurityUnsecured OBJECT-TYPE
			SYNTAX Boolean
			MAX-ACCESS read-write
			STATUS current
			DESCRIPTION
				"Allow unsecured configuration for SNMP."
			::= { webmonSecurity 77 }


-- dateTime folder
		
		-- 1.3.6.1.4.1.994.3.4.7.27
		dateTime OBJECT IDENTIFIER ::= {configuration 27 }
		
		-- 1.3.6.1.4.1.994.3.4.7.27.10
		dateTimeConfigured OBJECT-TYPE
			SYNTAX Configured
			MAX-ACCESS read-write
			STATUS current
			DESCRIPTION
				"Determines whether or not NTP will be used to set system time."
			::= { dateTime 10 }
		
		
		-- 1.3.6.1.4.1.994.3.4.7.27.14
		dateTimeIpAddress OBJECT-TYPE
			SYNTAX IpAddress
			MAX-ACCESS read-write
			STATUS current
			DESCRIPTION
				"Time Server IP Address"
			::= { dateTime 14 }
		
		
		-- 1.3.6.1.4.1.994.3.4.7.27.53
		dateTimeDaylightSaving OBJECT-TYPE
			SYNTAX Boolean
			MAX-ACCESS read-write
			STATUS current
			DESCRIPTION
				"Determines if Daylight Savings is automatically adjusted."
			::= { dateTime 53 }
		
		
		-- 1.3.6.1.4.1.994.3.4.7.27.80
		dateTimeDate OBJECT-TYPE
			SYNTAX DescriptionString
			MAX-ACCESS read-write
			STATUS current
			DESCRIPTION
				"This is the system date."
			::= { dateTime 80 }
		
		
		-- 1.3.6.1.4.1.994.3.4.7.27.81
		dateTimeTime OBJECT-TYPE
			SYNTAX DescriptionString
			MAX-ACCESS read-write
			STATUS current
			DESCRIPTION
				"This is the system time."
			::= { dateTime 81 }
		
		
		-- 1.3.6.1.4.1.994.3.4.7.27.88
		dateTimeNegOffset OBJECT-TYPE
			SYNTAX Boolean
			MAX-ACCESS read-write
			STATUS current
			DESCRIPTION
				"True if a negative offset from UTC is desired"
			::= { dateTime 88 }
		
		
		-- 1.3.6.1.4.1.994.3.4.7.27.89
		dateTimeUTCOffset OBJECT-TYPE
			SYNTAX DescriptionString
			MAX-ACCESS read-write
			STATUS current
			DESCRIPTION
				"Time offset of local time compared to UTC"
			::= { dateTime 89 }


-- DCMProtocol table
		
		-- 1.3.6.1.4.1.994.3.4.7.28
		pDCMProtocolTable OBJECT-TYPE
			SYNTAX SEQUENCE OF PDCMProtocolEntry
			MAX-ACCESS not-accessible
			STATUS current
			DESCRIPTION
				"Table for configuration of DCMProtocol"
			::= { configuration 28 }
		
		
		-- 1.3.6.1.4.1.994.3.4.7.28.1
		pDCMProtocolEntry OBJECT-TYPE
			SYNTAX PDCMProtocolEntry
			MAX-ACCESS not-accessible
			STATUS current
			DESCRIPTION
				"Entry for configuration table of DCMProtocol"
				INDEX { pDCMProtocolIndex }
			::= { pDCMProtocolTable 1 }
		
		
		PDCMProtocolEntry ::= 
			SEQUENCE {
				pDCMProtocolDescription
					DescriptionString,
				pDCMProtocolConfigured
					Configured,
				pDCMProtocolBaseDCMAddress
					Integer32,
				pDCMProtocolIndex
					Integer32 (1..27)
			}
		
		-- 1.3.6.1.4.1.994.3.4.7.28.1.3
		pDCMProtocolDescription OBJECT-TYPE
			SYNTAX DescriptionString
			MAX-ACCESS read-only
			STATUS current
			DESCRIPTION
				"Description of the input device that DCM will poll."
			::= { pDCMProtocolEntry 3 }
		
		
		-- 1.3.6.1.4.1.994.3.4.7.28.1.10
		pDCMProtocolConfigured OBJECT-TYPE
			SYNTAX Configured
			MAX-ACCESS read-write
			STATUS current
			DESCRIPTION
				"If set to true, this input will be polled in DCM.  If set to false, it will not be polled."
			::= { pDCMProtocolEntry 10 }
		
		
		-- 1.3.6.1.4.1.994.3.4.7.28.1.83
		pDCMProtocolBaseDCMAddress OBJECT-TYPE
			SYNTAX Integer32
			MAX-ACCESS read-write
			STATUS current
			DESCRIPTION
				"Base DCM address for this input device."
			::= { pDCMProtocolEntry 83 }
		
		
		-- 1.3.6.1.4.1.994.3.4.7.28.1.999
		pDCMProtocolIndex OBJECT-TYPE
			SYNTAX Integer32 (1..27)
			MAX-ACCESS read-only
			STATUS current
			DESCRIPTION
				"Index."
			::= { pDCMProtocolEntry 999 }


-- dialOut table
		
		-- 1.3.6.1.4.1.994.3.4.7.29
		pdialOutTable OBJECT-TYPE
			SYNTAX SEQUENCE OF PdialOutEntry
			MAX-ACCESS not-accessible
			STATUS current
			DESCRIPTION
				"Table for configuration of dialOut"
			::= { configuration 29 }
		
		
		-- 1.3.6.1.4.1.994.3.4.7.29.1
		pdialOutEntry OBJECT-TYPE
			SYNTAX PdialOutEntry
			MAX-ACCESS not-accessible
			STATUS current
			DESCRIPTION
				"Entry for configuration table of dialOut"
				INDEX { pdialOutIndex }
			::= { pdialOutTable 1 }
		
		
		PdialOutEntry ::= 
			SEQUENCE {
				pdialOutConfigured
					Configured,
				pdialOutName
					DescriptionString,
				pdialOutPassword
					DescriptionString,
				pdialOutDialOutNumber
					DescriptionString,
				pdialOutIndex
					Integer32 (1..4)
			}
		
		-- 1.3.6.1.4.1.994.3.4.7.29.1.10
		pdialOutConfigured OBJECT-TYPE
			SYNTAX Configured
			MAX-ACCESS read-write
			STATUS current
			DESCRIPTION
				"Determines whether or not dial ou will be used to send SNMP traps."
			::= { pdialOutEntry 10 }
		
		
		-- 1.3.6.1.4.1.994.3.4.7.29.1.25
		pdialOutName OBJECT-TYPE
			SYNTAX DescriptionString
			MAX-ACCESS read-write
			STATUS current
			DESCRIPTION
				"Dial out Username"
			::= { pdialOutEntry 25 }
		
		
		-- 1.3.6.1.4.1.994.3.4.7.29.1.26
		pdialOutPassword OBJECT-TYPE
			SYNTAX DescriptionString
			MAX-ACCESS read-write
			STATUS current
			DESCRIPTION
				"Password to use when dialing out"
			::= { pdialOutEntry 26 }
		
		
		-- 1.3.6.1.4.1.994.3.4.7.29.1.79
		pdialOutDialOutNumber OBJECT-TYPE
			SYNTAX DescriptionString
			MAX-ACCESS read-write
			STATUS current
			DESCRIPTION
				"Number to dial for dial out"
			::= { pdialOutEntry 79 }
		
		
		-- 1.3.6.1.4.1.994.3.4.7.29.1.999
		pdialOutIndex OBJECT-TYPE
			SYNTAX Integer32 (1..4)
			MAX-ACCESS read-only
			STATUS current
			DESCRIPTION
				"Index."
			::= { pdialOutEntry 999 }


-- derivedDiscrete table
		
		-- 1.3.6.1.4.1.994.3.4.7.30
		pderivedDiscreteTable OBJECT-TYPE
			SYNTAX SEQUENCE OF PderivedDiscreteEntry
			MAX-ACCESS not-accessible
			STATUS current
			DESCRIPTION
				"Table for configuration of derivedDiscrete"
			::= { configuration 30 }
		
		
		-- 1.3.6.1.4.1.994.3.4.7.30.1
		pderivedDiscreteEntry OBJECT-TYPE
			SYNTAX PderivedDiscreteEntry
			MAX-ACCESS not-accessible
			STATUS current
			DESCRIPTION
				"Entry for configuration table of derivedDiscrete"
				INDEX { pderivedDiscreteIndex }
			::= { pderivedDiscreteTable 1 }
		
		
		PderivedDiscreteEntry ::= 
			SEQUENCE {
				pderivedDiscreteDescription
					DescriptionString,
				pderivedDiscreteDesc0
					DescriptionString,
				pderivedDiscreteDesc1
					DescriptionString,
				pderivedDiscreteConfigured
					Configured,
				pderivedDiscreteSendEmail
					Boolean,
				pderivedDiscreteSendSNMPTrap
					Boolean,
				pderivedDiscreteLevel0
					Level,
				pderivedDiscreteLevel1
					Level,
				pderivedDiscreteLiveDescription
					DescriptionString,
				pderivedDiscreteLiveLevel
					DescriptionString,
				pderivedDiscreteLiveTime
					DescriptionString,
				pderivedDiscreteElementAPkg
					Integer32,
				pderivedDiscreteElementAPoint
					Integer32,
				pderivedDiscreteElementBPkg
					Integer32,
				pderivedDiscreteElementBPoint
					Integer32,
				pderivedDiscreteDiscreteFormula
					DiscreteFormula,
				pderivedDiscreteTL1SID
					DescriptionString,
				pderivedDiscreteTL1COND
					DescriptionString,
				pderivedDiscreteTL1Eqpt
					DescriptionString,
				pderivedDiscreteTL1Env
					Boolean,
				pderivedDiscreteTL1Srveff
					TL1Srveff,
				pderivedDiscreteTL1Locn
					TL1Locn,
				pderivedDiscreteTL1Dirn
					TL1Dirn,
				pderivedDiscreteIndex
					Integer32 (1..16)
			}
		
		-- 1.3.6.1.4.1.994.3.4.7.30.1.3
		pderivedDiscreteDescription OBJECT-TYPE
			SYNTAX DescriptionString
			MAX-ACCESS read-write
			STATUS current
			DESCRIPTION
				"Description of the derived alarm point."
			::= { pderivedDiscreteEntry 3 }
		
		
		-- 1.3.6.1.4.1.994.3.4.7.30.1.4
		pderivedDiscreteDesc0 OBJECT-TYPE
			SYNTAX DescriptionString
			MAX-ACCESS read-write
			STATUS current
			DESCRIPTION
				"Description of the off state."
			::= { pderivedDiscreteEntry 4 }
		
		
		-- 1.3.6.1.4.1.994.3.4.7.30.1.5
		pderivedDiscreteDesc1 OBJECT-TYPE
			SYNTAX DescriptionString
			MAX-ACCESS read-write
			STATUS current
			DESCRIPTION
				"Description of the on state."
			::= { pderivedDiscreteEntry 5 }
		
		
		-- 1.3.6.1.4.1.994.3.4.7.30.1.10
		pderivedDiscreteConfigured OBJECT-TYPE
			SYNTAX Configured
			MAX-ACCESS read-write
			STATUS current
			DESCRIPTION
				"If set to true, changes of state will be reported.
				If set to false, not change of states will be reported."
			::= { pderivedDiscreteEntry 10 }
		
		
		-- 1.3.6.1.4.1.994.3.4.7.30.1.11
		pderivedDiscreteSendEmail OBJECT-TYPE
			SYNTAX Boolean
			MAX-ACCESS read-write
			STATUS current
			DESCRIPTION
				"If set to true, an email will be sent on a change of state.
				If false, no email will be sent."
			::= { pderivedDiscreteEntry 11 }
		
		
		-- 1.3.6.1.4.1.994.3.4.7.30.1.12
		pderivedDiscreteSendSNMPTrap OBJECT-TYPE
			SYNTAX Boolean
			MAX-ACCESS read-write
			STATUS current
			DESCRIPTION
				"If set to true, an SNMP trap will be sent on a change of state.
				If false, no SNMP trap will be sent."
			::= { pderivedDiscreteEntry 12 }
		
		
		-- 1.3.6.1.4.1.994.3.4.7.30.1.17
		pderivedDiscreteLevel0 OBJECT-TYPE
			SYNTAX Level
			MAX-ACCESS read-write
			STATUS current
			DESCRIPTION
				"Level of the off state."
			::= { pderivedDiscreteEntry 17 }
		
		
		-- 1.3.6.1.4.1.994.3.4.7.30.1.18
		pderivedDiscreteLevel1 OBJECT-TYPE
			SYNTAX Level
			MAX-ACCESS read-write
			STATUS current
			DESCRIPTION
				"Level of the on state."
			::= { pderivedDiscreteEntry 18 }
		
		
		-- 1.3.6.1.4.1.994.3.4.7.30.1.64
		pderivedDiscreteLiveDescription OBJECT-TYPE
			SYNTAX DescriptionString
			MAX-ACCESS read-only
			STATUS current
			DESCRIPTION
				"The current description of the alarm state."
			::= { pderivedDiscreteEntry 64 }
		
		
		-- 1.3.6.1.4.1.994.3.4.7.30.1.65
		pderivedDiscreteLiveLevel OBJECT-TYPE
			SYNTAX DescriptionString
			MAX-ACCESS read-only
			STATUS current
			DESCRIPTION
				"The current level of the alarm."
			::= { pderivedDiscreteEntry 65 }
		
		
		-- 1.3.6.1.4.1.994.3.4.7.30.1.67
		pderivedDiscreteLiveTime OBJECT-TYPE
			SYNTAX DescriptionString
			MAX-ACCESS read-only
			STATUS current
			DESCRIPTION
				"The time of the last change of state."
			::= { pderivedDiscreteEntry 67 }
		
		
		-- 1.3.6.1.4.1.994.3.4.7.30.1.90
		pderivedDiscreteElementAPkg OBJECT-TYPE
			SYNTAX Integer32
			MAX-ACCESS read-write
			STATUS current
			DESCRIPTION
				"Package where the alarm point is located for element A."
			::= { pderivedDiscreteEntry 90 }
		
		
		-- 1.3.6.1.4.1.994.3.4.7.30.1.91
		pderivedDiscreteElementAPoint OBJECT-TYPE
			SYNTAX Integer32
			MAX-ACCESS read-write
			STATUS current
			DESCRIPTION
				"Alarm point for element A."
			::= { pderivedDiscreteEntry 91 }
		
		
		-- 1.3.6.1.4.1.994.3.4.7.30.1.92
		pderivedDiscreteElementBPkg OBJECT-TYPE
			SYNTAX Integer32
			MAX-ACCESS read-write
			STATUS current
			DESCRIPTION
				"Package where the alarm point is located for element B."
			::= { pderivedDiscreteEntry 92 }
		
		
		-- 1.3.6.1.4.1.994.3.4.7.30.1.93
		pderivedDiscreteElementBPoint OBJECT-TYPE
			SYNTAX Integer32
			MAX-ACCESS read-write
			STATUS current
			DESCRIPTION
				"Alarm point for element B."
			::= { pderivedDiscreteEntry 93 }
		
		
		-- 1.3.6.1.4.1.994.3.4.7.30.1.94
		pderivedDiscreteDiscreteFormula OBJECT-TYPE
			SYNTAX DiscreteFormula
			MAX-ACCESS read-write
			STATUS current
			DESCRIPTION
				"The formula that will be used to compute the derived alarm."
			::= { pderivedDiscreteEntry 94 }
		
		
		-- 1.3.6.1.4.1.994.3.4.7.30.1.116
		pderivedDiscreteTL1SID OBJECT-TYPE
			SYNTAX DescriptionString
			MAX-ACCESS read-write
			STATUS current
			DESCRIPTION
				"(TL1) System ID associated with this item."
			::= { pderivedDiscreteEntry 116 }
		
		
		-- 1.3.6.1.4.1.994.3.4.7.30.1.117
		pderivedDiscreteTL1COND OBJECT-TYPE
			SYNTAX DescriptionString
			MAX-ACCESS read-write
			STATUS current
			DESCRIPTION
				"(TL1) Condition text associated with this item."
			::= { pderivedDiscreteEntry 117 }
		
		
		-- 1.3.6.1.4.1.994.3.4.7.30.1.118
		pderivedDiscreteTL1Eqpt OBJECT-TYPE
			SYNTAX DescriptionString
			MAX-ACCESS read-write
			STATUS current
			DESCRIPTION
				"(TL1) EQPT field associated with this item."
			::= { pderivedDiscreteEntry 118 }
		
		
		-- 1.3.6.1.4.1.994.3.4.7.30.1.119
		pderivedDiscreteTL1Env OBJECT-TYPE
			SYNTAX Boolean
			MAX-ACCESS read-write
			STATUS current
			DESCRIPTION
				"(TL1) Environmental field associated with this item."
			::= { pderivedDiscreteEntry 119 }
		
		
		-- 1.3.6.1.4.1.994.3.4.7.30.1.120
		pderivedDiscreteTL1Srveff OBJECT-TYPE
			SYNTAX TL1Srveff
			MAX-ACCESS read-write
			STATUS current
			DESCRIPTION
				"(TL1) Service Effecting field associated with this item."
			::= { pderivedDiscreteEntry 120 }
		
		
		-- 1.3.6.1.4.1.994.3.4.7.30.1.121
		pderivedDiscreteTL1Locn OBJECT-TYPE
			SYNTAX TL1Locn
			MAX-ACCESS read-write
			STATUS current
			DESCRIPTION
				"(TL1) Location field associated with this item."
			::= { pderivedDiscreteEntry 121 }
		
		
		-- 1.3.6.1.4.1.994.3.4.7.30.1.122
		pderivedDiscreteTL1Dirn OBJECT-TYPE
			SYNTAX TL1Dirn
			MAX-ACCESS read-write
			STATUS current
			DESCRIPTION
				"(TL1) Direction field associated with this item."
			::= { pderivedDiscreteEntry 122 }
		
		
		-- 1.3.6.1.4.1.994.3.4.7.30.1.999
		pderivedDiscreteIndex OBJECT-TYPE
			SYNTAX Integer32 (1..16)
			MAX-ACCESS read-only
			STATUS current
			DESCRIPTION
				"Index."
			::= { pderivedDiscreteEntry 999 }


-- license folder
		
		-- 1.3.6.1.4.1.994.3.4.7.31
		license OBJECT IDENTIFIER ::= {configuration 31 }
		
		-- 1.3.6.1.4.1.994.3.4.7.31.3
		licenseDescription OBJECT-TYPE
			SYNTAX DescriptionString
			MAX-ACCESS read-only
			STATUS current
			DESCRIPTION
				"This describes the status of the license"
			::= { license 3 }
		
		
		-- 1.3.6.1.4.1.994.3.4.7.31.84
		licenseLicenseKey OBJECT-TYPE
			SYNTAX DescriptionString
			MAX-ACCESS read-write
			STATUS current
			DESCRIPTION
				"This is the License Key."
			::= { license 84 }
		
		
		-- 1.3.6.1.4.1.994.3.4.7.31.85
		licenseExpires OBJECT-TYPE
			SYNTAX DescriptionString
			MAX-ACCESS read-only
			STATUS current
			DESCRIPTION
				"This is the date the current License will expire."
			::= { license 85 }
		
		
		-- 1.3.6.1.4.1.994.3.4.7.31.124
		licenseAllowTL1 OBJECT-TYPE
			SYNTAX Boolean
			MAX-ACCESS read-only
			STATUS current
			DESCRIPTION
				"This describes the status of TL1 support in the license"
			::= { license 124 }


-- e2aHost table
		
		-- 1.3.6.1.4.1.994.3.4.7.32
		pe2aHostTable OBJECT-TYPE
			SYNTAX SEQUENCE OF Pe2aHostEntry
			MAX-ACCESS not-accessible
			STATUS current
			DESCRIPTION
				"Table for configuration of e2aHost"
			::= { configuration 32 }
		
		
		-- 1.3.6.1.4.1.994.3.4.7.32.1
		pe2aHostEntry OBJECT-TYPE
			SYNTAX Pe2aHostEntry
			MAX-ACCESS not-accessible
			STATUS current
			DESCRIPTION
				"Entry for configuration table of e2aHost"
				INDEX { pe2aHostIndex }
			::= { pe2aHostTable 1 }
		
		
		Pe2aHostEntry ::= 
			SEQUENCE {
				pe2aHostDescription
					DescriptionString,
				pe2aHostConfigured
					Configured,
				pe2aHostIpAddress
					IpAddress,
				pe2aHostLevel0
					Level,
				pe2aHostLevel1
					Level,
				pe2aHostLevel2
					Level,
				pe2aHostRosterID
					Integer32,
				pe2aHostPollAddress
					Integer32,
				pe2aHostIPPortNum
					Integer32,
				pe2aHostTL1SID
					DescriptionString,
				pe2aHostTL1COND
					DescriptionString,
				pe2aHostTL1Eqpt
					DescriptionString,
				pe2aHostTL1Env
					Boolean,
				pe2aHostTL1Srveff
					TL1Srveff,
				pe2aHostTL1Locn
					TL1Locn,
				pe2aHostTL1Dirn
					TL1Dirn,
				pe2aHostIndex
					Integer32 (1..256)
			}
		
		-- 1.3.6.1.4.1.994.3.4.7.32.1.3
		pe2aHostDescription OBJECT-TYPE
			SYNTAX DescriptionString
			MAX-ACCESS read-write
			STATUS current
			DESCRIPTION
				"Description of the connection."
			::= { pe2aHostEntry 3 }
		
		
		-- 1.3.6.1.4.1.994.3.4.7.32.1.10
		pe2aHostConfigured OBJECT-TYPE
			SYNTAX Configured
			MAX-ACCESS read-write
			STATUS current
			DESCRIPTION
				"If set to true, this route will be used by E2A."
			::= { pe2aHostEntry 10 }
		
		
		-- 1.3.6.1.4.1.994.3.4.7.32.1.14
		pe2aHostIpAddress OBJECT-TYPE
			SYNTAX IpAddress
			MAX-ACCESS read-write
			STATUS current
			DESCRIPTION
				"The IP address of the remote device."
			::= { pe2aHostEntry 14 }
		
		
		-- 1.3.6.1.4.1.994.3.4.7.32.1.17
		pe2aHostLevel0 OBJECT-TYPE
			SYNTAX Level
			MAX-ACCESS read-write
			STATUS current
			DESCRIPTION
				"Alarm level associated with the online state."
			::= { pe2aHostEntry 17 }
		
		
		-- 1.3.6.1.4.1.994.3.4.7.32.1.18
		pe2aHostLevel1 OBJECT-TYPE
			SYNTAX Level
			MAX-ACCESS read-write
			STATUS current
			DESCRIPTION
				"Alarm level associated with the offline state."
			::= { pe2aHostEntry 18 }
		
		
		-- 1.3.6.1.4.1.994.3.4.7.32.1.19
		pe2aHostLevel2 OBJECT-TYPE
			SYNTAX Level
			MAX-ACCESS read-write
			STATUS current
			DESCRIPTION
				"Alarm level associated with the connecting state."
			::= { pe2aHostEntry 19 }
		
		
		-- 1.3.6.1.4.1.994.3.4.7.32.1.37
		pe2aHostRosterID OBJECT-TYPE
			SYNTAX Integer32
			MAX-ACCESS read-write
			STATUS current
			DESCRIPTION
				"Serial port number to use when connecting to WebMon."
			::= { pe2aHostEntry 37 }
		
		
		-- 1.3.6.1.4.1.994.3.4.7.32.1.56
		pe2aHostPollAddress OBJECT-TYPE
			SYNTAX Integer32
			MAX-ACCESS read-write
			STATUS current
			DESCRIPTION
				"The E2A address of the remote device."
			::= { pe2aHostEntry 56 }
		
		
		-- 1.3.6.1.4.1.994.3.4.7.32.1.73
		pe2aHostIPPortNum OBJECT-TYPE
			SYNTAX Integer32
			MAX-ACCESS read-write
			STATUS current
			DESCRIPTION
				"IP port number to use when connecting to the remote device."
			::= { pe2aHostEntry 73 }
		
		
		-- 1.3.6.1.4.1.994.3.4.7.32.1.116
		pe2aHostTL1SID OBJECT-TYPE
			SYNTAX DescriptionString
			MAX-ACCESS read-write
			STATUS current
			DESCRIPTION
				"(TL1) System ID associated with this item."
			::= { pe2aHostEntry 116 }
		
		
		-- 1.3.6.1.4.1.994.3.4.7.32.1.117
		pe2aHostTL1COND OBJECT-TYPE
			SYNTAX DescriptionString
			MAX-ACCESS read-write
			STATUS current
			DESCRIPTION
				"(TL1) Condition text associated with this item."
			::= { pe2aHostEntry 117 }
		
		
		-- 1.3.6.1.4.1.994.3.4.7.32.1.118
		pe2aHostTL1Eqpt OBJECT-TYPE
			SYNTAX DescriptionString
			MAX-ACCESS read-write
			STATUS current
			DESCRIPTION
				"(TL1) EQPT field associated with this item."
			::= { pe2aHostEntry 118 }
		
		
		-- 1.3.6.1.4.1.994.3.4.7.32.1.119
		pe2aHostTL1Env OBJECT-TYPE
			SYNTAX Boolean
			MAX-ACCESS read-write
			STATUS current
			DESCRIPTION
				"(TL1) Environmental field associated with this item."
			::= { pe2aHostEntry 119 }
		
		
		-- 1.3.6.1.4.1.994.3.4.7.32.1.120
		pe2aHostTL1Srveff OBJECT-TYPE
			SYNTAX TL1Srveff
			MAX-ACCESS read-write
			STATUS current
			DESCRIPTION
				"(TL1) Service Effecting field associated with this item."
			::= { pe2aHostEntry 120 }
		
		
		-- 1.3.6.1.4.1.994.3.4.7.32.1.121
		pe2aHostTL1Locn OBJECT-TYPE
			SYNTAX TL1Locn
			MAX-ACCESS read-write
			STATUS current
			DESCRIPTION
				"(TL1) Location field associated with this item."
			::= { pe2aHostEntry 121 }
		
		
		-- 1.3.6.1.4.1.994.3.4.7.32.1.122
		pe2aHostTL1Dirn OBJECT-TYPE
			SYNTAX TL1Dirn
			MAX-ACCESS read-write
			STATUS current
			DESCRIPTION
				"(TL1) Direction field associated with this item."
			::= { pe2aHostEntry 122 }
		
		
		-- 1.3.6.1.4.1.994.3.4.7.32.1.999
		pe2aHostIndex OBJECT-TYPE
			SYNTAX Integer32 (1..256)
			MAX-ACCESS read-only
			STATUS current
			DESCRIPTION
				"Index."
			::= { pe2aHostEntry 999 }


-- derivedAnalog table
		
		-- 1.3.6.1.4.1.994.3.4.7.33
		pderivedAnalogTable OBJECT-TYPE
			SYNTAX SEQUENCE OF PderivedAnalogEntry
			MAX-ACCESS not-accessible
			STATUS current
			DESCRIPTION
				"Table for configuration of derivedAnalog"
			::= { configuration 33 }
		
		
		-- 1.3.6.1.4.1.994.3.4.7.33.1
		pderivedAnalogEntry OBJECT-TYPE
			SYNTAX PderivedAnalogEntry
			MAX-ACCESS not-accessible
			STATUS current
			DESCRIPTION
				"Entry for configuration table of derivedAnalog"
				INDEX { pderivedAnalogIndex }
			::= { pderivedAnalogTable 1 }
		
		
		PderivedAnalogEntry ::= 
			SEQUENCE {
				pderivedAnalogDescription
					DescriptionString,
				pderivedAnalogDesc0
					DescriptionString,
				pderivedAnalogDesc1
					DescriptionString,
				pderivedAnalogDesc2
					DescriptionString,
				pderivedAnalogDesc3
					DescriptionString,
				pderivedAnalogDesc4
					DescriptionString,
				pderivedAnalogConfigured
					Configured,
				pderivedAnalogSendEmail
					Boolean,
				pderivedAnalogSendSNMPTrap
					Boolean,
				pderivedAnalogLevel0
					Level,
				pderivedAnalogLevel1
					Level,
				pderivedAnalogLevel2
					Level,
				pderivedAnalogLevel3
					Level,
				pderivedAnalogLevel4
					Level,
				pderivedAnalogThresh0
					DescriptionString,
				pderivedAnalogThresh1
					DescriptionString,
				pderivedAnalogThresh2
					DescriptionString,
				pderivedAnalogThresh3
					DescriptionString,
				pderivedAnalogThresh4
					DescriptionString,
				pderivedAnalogThresh5
					DescriptionString,
				pderivedAnalogUnits
					DescriptionString,
				pderivedAnalogLiveDescription
					DescriptionString,
				pderivedAnalogLiveLevel
					DescriptionString,
				pderivedAnalogLiveRaw
					DescriptionString,
				pderivedAnalogLiveTime
					DescriptionString,
				pderivedAnalogElementAPkg
					Integer32,
				pderivedAnalogElementAPoint
					Integer32,
				pderivedAnalogElementBPkg
					Integer32,
				pderivedAnalogElementBPoint
					Integer32,
				pderivedAnalogFormula
					DescriptionString,
				pderivedAnalogTL1SID
					DescriptionString,
				pderivedAnalogTL1COND
					DescriptionString,
				pderivedAnalogTL1Eqpt
					DescriptionString,
				pderivedAnalogTL1Env
					Boolean,
				pderivedAnalogTL1Srveff
					TL1Srveff,
				pderivedAnalogTL1Locn
					TL1Locn,
				pderivedAnalogTL1Dirn
					TL1Dirn,
				pderivedAnalogIndex
					Integer32 (1..16)
			}
		
		-- 1.3.6.1.4.1.994.3.4.7.33.1.3
		pderivedAnalogDescription OBJECT-TYPE
			SYNTAX DescriptionString
			MAX-ACCESS read-write
			STATUS current
			DESCRIPTION
				"Description of the derived alarm point."
			::= { pderivedAnalogEntry 3 }
		
		
		-- 1.3.6.1.4.1.994.3.4.7.33.1.4
		pderivedAnalogDesc0 OBJECT-TYPE
			SYNTAX DescriptionString
			MAX-ACCESS read-write
			STATUS current
			DESCRIPTION
				"The description for derived values between threshold 0 and threshold 1."
			::= { pderivedAnalogEntry 4 }
		
		
		-- 1.3.6.1.4.1.994.3.4.7.33.1.5
		pderivedAnalogDesc1 OBJECT-TYPE
			SYNTAX DescriptionString
			MAX-ACCESS read-write
			STATUS current
			DESCRIPTION
				"The description for derived values between threshold 1 and threshold 2."
			::= { pderivedAnalogEntry 5 }
		
		
		-- 1.3.6.1.4.1.994.3.4.7.33.1.6
		pderivedAnalogDesc2 OBJECT-TYPE
			SYNTAX DescriptionString
			MAX-ACCESS read-write
			STATUS current
			DESCRIPTION
				"The description for derived values between threshold 2 and threshold 3."
			::= { pderivedAnalogEntry 6 }
		
		
		-- 1.3.6.1.4.1.994.3.4.7.33.1.7
		pderivedAnalogDesc3 OBJECT-TYPE
			SYNTAX DescriptionString
			MAX-ACCESS read-write
			STATUS current
			DESCRIPTION
				"The description for derived values between threshold 3 and threshold 4."
			::= { pderivedAnalogEntry 7 }
		
		
		-- 1.3.6.1.4.1.994.3.4.7.33.1.8
		pderivedAnalogDesc4 OBJECT-TYPE
			SYNTAX DescriptionString
			MAX-ACCESS read-write
			STATUS current
			DESCRIPTION
				"The description for derived values between threshold 4 and threshold 5."
			::= { pderivedAnalogEntry 8 }
		
		
		-- 1.3.6.1.4.1.994.3.4.7.33.1.10
		pderivedAnalogConfigured OBJECT-TYPE
			SYNTAX Configured
			MAX-ACCESS read-write
			STATUS current
			DESCRIPTION
				"If set to true, changes of state will be reported.
				If set to false, not change of states will be reported."
			::= { pderivedAnalogEntry 10 }
		
		
		-- 1.3.6.1.4.1.994.3.4.7.33.1.11
		pderivedAnalogSendEmail OBJECT-TYPE
			SYNTAX Boolean
			MAX-ACCESS read-write
			STATUS current
			DESCRIPTION
				"If set to true, an email will be sent on a change of state.
				If false, no email will be sent."
			::= { pderivedAnalogEntry 11 }
		
		
		-- 1.3.6.1.4.1.994.3.4.7.33.1.12
		pderivedAnalogSendSNMPTrap OBJECT-TYPE
			SYNTAX Boolean
			MAX-ACCESS read-write
			STATUS current
			DESCRIPTION
				"If set to true, an SNMP trap will be sent on a change of state.
				If false, no SNMP trap will be sent."
			::= { pderivedAnalogEntry 12 }
		
		
		-- 1.3.6.1.4.1.994.3.4.7.33.1.17
		pderivedAnalogLevel0 OBJECT-TYPE
			SYNTAX Level
			MAX-ACCESS read-write
			STATUS current
			DESCRIPTION
				"The level for derived values between threshold 0 and threshold 1."
			::= { pderivedAnalogEntry 17 }
		
		
		-- 1.3.6.1.4.1.994.3.4.7.33.1.18
		pderivedAnalogLevel1 OBJECT-TYPE
			SYNTAX Level
			MAX-ACCESS read-write
			STATUS current
			DESCRIPTION
				"The level for derived values between threshold 1 and threshold 2."
			::= { pderivedAnalogEntry 18 }
		
		
		-- 1.3.6.1.4.1.994.3.4.7.33.1.19
		pderivedAnalogLevel2 OBJECT-TYPE
			SYNTAX Level
			MAX-ACCESS read-write
			STATUS current
			DESCRIPTION
				"The level for derived values between threshold 2 and threshold 3."
			::= { pderivedAnalogEntry 19 }
		
		
		-- 1.3.6.1.4.1.994.3.4.7.33.1.20
		pderivedAnalogLevel3 OBJECT-TYPE
			SYNTAX Level
			MAX-ACCESS read-write
			STATUS current
			DESCRIPTION
				"The level for derived values between threshold 3 and threshold 4."
			::= { pderivedAnalogEntry 20 }
		
		
		-- 1.3.6.1.4.1.994.3.4.7.33.1.21
		pderivedAnalogLevel4 OBJECT-TYPE
			SYNTAX Level
			MAX-ACCESS read-write
			STATUS current
			DESCRIPTION
				"The level for derived values between threshold 4 and threshold 5."
			::= { pderivedAnalogEntry 21 }
		
		
		-- 1.3.6.1.4.1.994.3.4.7.33.1.28
		pderivedAnalogThresh0 OBJECT-TYPE
			SYNTAX DescriptionString
			MAX-ACCESS read-write
			STATUS current
			DESCRIPTION
				"This is the maximum analog derived value."
			::= { pderivedAnalogEntry 28 }
		
		
		-- 1.3.6.1.4.1.994.3.4.7.33.1.29
		pderivedAnalogThresh1 OBJECT-TYPE
			SYNTAX DescriptionString
			MAX-ACCESS read-write
			STATUS current
			DESCRIPTION
				"This is the first threshold derived value."
			::= { pderivedAnalogEntry 29 }
		
		
		-- 1.3.6.1.4.1.994.3.4.7.33.1.30
		pderivedAnalogThresh2 OBJECT-TYPE
			SYNTAX DescriptionString
			MAX-ACCESS read-write
			STATUS current
			DESCRIPTION
				"This is the second threshold derived value."
			::= { pderivedAnalogEntry 30 }
		
		
		-- 1.3.6.1.4.1.994.3.4.7.33.1.31
		pderivedAnalogThresh3 OBJECT-TYPE
			SYNTAX DescriptionString
			MAX-ACCESS read-write
			STATUS current
			DESCRIPTION
				"This is the third threshold derived value."
			::= { pderivedAnalogEntry 31 }
		
		
		-- 1.3.6.1.4.1.994.3.4.7.33.1.32
		pderivedAnalogThresh4 OBJECT-TYPE
			SYNTAX DescriptionString
			MAX-ACCESS read-write
			STATUS current
			DESCRIPTION
				"This is the fourth threshold derived value."
			::= { pderivedAnalogEntry 32 }
		
		
		-- 1.3.6.1.4.1.994.3.4.7.33.1.33
		pderivedAnalogThresh5 OBJECT-TYPE
			SYNTAX DescriptionString
			MAX-ACCESS read-write
			STATUS current
			DESCRIPTION
				"This is the minimum threshold derived value."
			::= { pderivedAnalogEntry 33 }
		
		
		-- 1.3.6.1.4.1.994.3.4.7.33.1.46
		pderivedAnalogUnits OBJECT-TYPE
			SYNTAX DescriptionString
			MAX-ACCESS read-write
			STATUS current
			DESCRIPTION
				"Description of the units of measurement."
			::= { pderivedAnalogEntry 46 }
		
		
		-- 1.3.6.1.4.1.994.3.4.7.33.1.64
		pderivedAnalogLiveDescription OBJECT-TYPE
			SYNTAX DescriptionString
			MAX-ACCESS read-only
			STATUS current
			DESCRIPTION
				"The current description of the alarm state."
			::= { pderivedAnalogEntry 64 }
		
		
		-- 1.3.6.1.4.1.994.3.4.7.33.1.65
		pderivedAnalogLiveLevel OBJECT-TYPE
			SYNTAX DescriptionString
			MAX-ACCESS read-only
			STATUS current
			DESCRIPTION
				"The current level of the alarm."
			::= { pderivedAnalogEntry 65 }
		
		
		-- 1.3.6.1.4.1.994.3.4.7.33.1.66
		pderivedAnalogLiveRaw OBJECT-TYPE
			SYNTAX DescriptionString
			MAX-ACCESS read-only
			STATUS current
			DESCRIPTION
				"The current derived reading from the analog devices.  This value 
				will alwaysbe between the threshold 0 and threshold 5 values."
			::= { pderivedAnalogEntry 66 }
		
		
		-- 1.3.6.1.4.1.994.3.4.7.33.1.67
		pderivedAnalogLiveTime OBJECT-TYPE
			SYNTAX DescriptionString
			MAX-ACCESS read-only
			STATUS current
			DESCRIPTION
				"The time of the last change of state."
			::= { pderivedAnalogEntry 67 }
		
		
		-- 1.3.6.1.4.1.994.3.4.7.33.1.90
		pderivedAnalogElementAPkg OBJECT-TYPE
			SYNTAX Integer32
			MAX-ACCESS read-write
			STATUS current
			DESCRIPTION
				"Package where the alarm point is located for element A."
			::= { pderivedAnalogEntry 90 }
		
		
		-- 1.3.6.1.4.1.994.3.4.7.33.1.91
		pderivedAnalogElementAPoint OBJECT-TYPE
			SYNTAX Integer32
			MAX-ACCESS read-write
			STATUS current
			DESCRIPTION
				"Alarm point for element A."
			::= { pderivedAnalogEntry 91 }
		
		
		-- 1.3.6.1.4.1.994.3.4.7.33.1.92
		pderivedAnalogElementBPkg OBJECT-TYPE
			SYNTAX Integer32
			MAX-ACCESS read-write
			STATUS current
			DESCRIPTION
				"Package where the alarm point is located for element B."
			::= { pderivedAnalogEntry 92 }
		
		
		-- 1.3.6.1.4.1.994.3.4.7.33.1.93
		pderivedAnalogElementBPoint OBJECT-TYPE
			SYNTAX Integer32
			MAX-ACCESS read-write
			STATUS current
			DESCRIPTION
				"Alarm point for element B."
			::= { pderivedAnalogEntry 93 }
		
		
		-- 1.3.6.1.4.1.994.3.4.7.33.1.95
		pderivedAnalogFormula OBJECT-TYPE
			SYNTAX DescriptionString
			MAX-ACCESS read-write
			STATUS current
			DESCRIPTION
				"The formula that will be used to compute the derived alarm."
			::= { pderivedAnalogEntry 95 }
		
		
		-- 1.3.6.1.4.1.994.3.4.7.33.1.116
		pderivedAnalogTL1SID OBJECT-TYPE
			SYNTAX DescriptionString
			MAX-ACCESS read-write
			STATUS current
			DESCRIPTION
				"(TL1) System ID associated with this item."
			::= { pderivedAnalogEntry 116 }
		
		
		-- 1.3.6.1.4.1.994.3.4.7.33.1.117
		pderivedAnalogTL1COND OBJECT-TYPE
			SYNTAX DescriptionString
			MAX-ACCESS read-write
			STATUS current
			DESCRIPTION
				"(TL1) Condition text associated with this item."
			::= { pderivedAnalogEntry 117 }
		
		
		-- 1.3.6.1.4.1.994.3.4.7.33.1.118
		pderivedAnalogTL1Eqpt OBJECT-TYPE
			SYNTAX DescriptionString
			MAX-ACCESS read-write
			STATUS current
			DESCRIPTION
				"(TL1) EQPT field associated with this item."
			::= { pderivedAnalogEntry 118 }
		
		
		-- 1.3.6.1.4.1.994.3.4.7.33.1.119
		pderivedAnalogTL1Env OBJECT-TYPE
			SYNTAX Boolean
			MAX-ACCESS read-write
			STATUS current
			DESCRIPTION
				"(TL1) Environmental field associated with this item."
			::= { pderivedAnalogEntry 119 }
		
		
		-- 1.3.6.1.4.1.994.3.4.7.33.1.120
		pderivedAnalogTL1Srveff OBJECT-TYPE
			SYNTAX TL1Srveff
			MAX-ACCESS read-write
			STATUS current
			DESCRIPTION
				"(TL1) Service Effecting field associated with this item."
			::= { pderivedAnalogEntry 120 }
		
		
		-- 1.3.6.1.4.1.994.3.4.7.33.1.121
		pderivedAnalogTL1Locn OBJECT-TYPE
			SYNTAX TL1Locn
			MAX-ACCESS read-write
			STATUS current
			DESCRIPTION
				"(TL1) Location field associated with this item."
			::= { pderivedAnalogEntry 121 }
		
		
		-- 1.3.6.1.4.1.994.3.4.7.33.1.122
		pderivedAnalogTL1Dirn OBJECT-TYPE
			SYNTAX TL1Dirn
			MAX-ACCESS read-write
			STATUS current
			DESCRIPTION
				"(TL1) Direction field associated with this item."
			::= { pderivedAnalogEntry 122 }
		
		
		-- 1.3.6.1.4.1.994.3.4.7.33.1.999
		pderivedAnalogIndex OBJECT-TYPE
			SYNTAX Integer32 (1..16)
			MAX-ACCESS read-only
			STATUS current
			DESCRIPTION
				"Index."
			::= { pderivedAnalogEntry 999 }


-- gps table
		
		-- 1.3.6.1.4.1.994.3.4.7.34
		pgpsTable OBJECT-TYPE
			SYNTAX SEQUENCE OF PgpsEntry
			MAX-ACCESS not-accessible
			STATUS current
			DESCRIPTION
				"Table for configuration of gps"
			::= { configuration 34 }
		
		
		-- 1.3.6.1.4.1.994.3.4.7.34.1
		pgpsEntry OBJECT-TYPE
			SYNTAX PgpsEntry
			MAX-ACCESS not-accessible
			STATUS current
			DESCRIPTION
				"Entry for configuration table of gps"
				INDEX { pgpsIndex }
			::= { pgpsTable 1 }
		
		
		PgpsEntry ::= 
			SEQUENCE {
				pgpsDescription
					DescriptionString,
				pgpsDesc0
					DescriptionString,
				pgpsDesc1
					DescriptionString,
				pgpsDesc2
					DescriptionString,
				pgpsDesc3
					DescriptionString,
				pgpsDesc4
					DescriptionString,
				pgpsConfigured
					Configured,
				pgpsSendEmail
					Boolean,
				pgpsSendSNMPTrap
					Boolean,
				pgpsLevel0
					Level,
				pgpsLevel1
					Level,
				pgpsLevel2
					Level,
				pgpsLevel3
					Level,
				pgpsLevel4
					Level,
				pgpsThresh0
					DescriptionString,
				pgpsThresh1
					DescriptionString,
				pgpsThresh2
					DescriptionString,
				pgpsThresh3
					DescriptionString,
				pgpsThresh4
					DescriptionString,
				pgpsThresh5
					DescriptionString,
				pgpsUnits
					DescriptionString,
				pgpsLiveDescription
					DescriptionString,
				pgpsLiveLevel
					DescriptionString,
				pgpsLiveRaw
					DescriptionString,
				pgpsLiveTime
					DescriptionString,
				pgpsTL1SID
					DescriptionString,
				pgpsTL1COND
					DescriptionString,
				pgpsTL1Eqpt
					DescriptionString,
				pgpsTL1Env
					Boolean,
				pgpsTL1Srveff
					TL1Srveff,
				pgpsTL1Locn
					TL1Locn,
				pgpsTL1Dirn
					TL1Dirn,
				pgpsIndex
					Integer32 (1..3)
			}
		
		-- 1.3.6.1.4.1.994.3.4.7.34.1.3
		pgpsDescription OBJECT-TYPE
			SYNTAX DescriptionString
			MAX-ACCESS read-only
			STATUS current
			DESCRIPTION
				"Description of the onboard device."
			::= { pgpsEntry 3 }
		
		
		-- 1.3.6.1.4.1.994.3.4.7.34.1.4
		pgpsDesc0 OBJECT-TYPE
			SYNTAX DescriptionString
			MAX-ACCESS read-write
			STATUS current
			DESCRIPTION
				"The description for values between threshold 0 and threshold 1."
			::= { pgpsEntry 4 }
		
		
		-- 1.3.6.1.4.1.994.3.4.7.34.1.5
		pgpsDesc1 OBJECT-TYPE
			SYNTAX DescriptionString
			MAX-ACCESS read-write
			STATUS current
			DESCRIPTION
				"The description for values between threshold 1 and threshold 2."
			::= { pgpsEntry 5 }
		
		
		-- 1.3.6.1.4.1.994.3.4.7.34.1.6
		pgpsDesc2 OBJECT-TYPE
			SYNTAX DescriptionString
			MAX-ACCESS read-write
			STATUS current
			DESCRIPTION
				"The description for values between threshold 2 and threshold 3."
			::= { pgpsEntry 6 }
		
		
		-- 1.3.6.1.4.1.994.3.4.7.34.1.7
		pgpsDesc3 OBJECT-TYPE
			SYNTAX DescriptionString
			MAX-ACCESS read-write
			STATUS current
			DESCRIPTION
				"The description for values between threshold 3 and threshold 4."
			::= { pgpsEntry 7 }
		
		
		-- 1.3.6.1.4.1.994.3.4.7.34.1.8
		pgpsDesc4 OBJECT-TYPE
			SYNTAX DescriptionString
			MAX-ACCESS read-write
			STATUS current
			DESCRIPTION
				"The description for values between threshold 4 and threshold 5."
			::= { pgpsEntry 8 }
		
		
		-- 1.3.6.1.4.1.994.3.4.7.34.1.10
		pgpsConfigured OBJECT-TYPE
			SYNTAX Configured
			MAX-ACCESS read-write
			STATUS current
			DESCRIPTION
				"If set to true, the onboard sensors will be used.
				If set to false the will be ignored."
			::= { pgpsEntry 10 }
		
		
		-- 1.3.6.1.4.1.994.3.4.7.34.1.11
		pgpsSendEmail OBJECT-TYPE
			SYNTAX Boolean
			MAX-ACCESS read-write
			STATUS current
			DESCRIPTION
				"If set to true an email event will be set when a threshold is crossed.
				If set to false no email event will be sent."
			::= { pgpsEntry 11 }
		
		
		-- 1.3.6.1.4.1.994.3.4.7.34.1.12
		pgpsSendSNMPTrap OBJECT-TYPE
			SYNTAX Boolean
			MAX-ACCESS read-write
			STATUS current
			DESCRIPTION
				"If set to true an SNMP trap will be set when a threshold is crossed.
				If set to false no SNMP trap will be sent."
			::= { pgpsEntry 12 }
		
		
		-- 1.3.6.1.4.1.994.3.4.7.34.1.17
		pgpsLevel0 OBJECT-TYPE
			SYNTAX Level
			MAX-ACCESS read-write
			STATUS current
			DESCRIPTION
				"The level for values between threshold 0 and threshold 1."
			::= { pgpsEntry 17 }
		
		
		-- 1.3.6.1.4.1.994.3.4.7.34.1.18
		pgpsLevel1 OBJECT-TYPE
			SYNTAX Level
			MAX-ACCESS read-write
			STATUS current
			DESCRIPTION
				"The level for values between threshold 1 and threshold 2."
			::= { pgpsEntry 18 }
		
		
		-- 1.3.6.1.4.1.994.3.4.7.34.1.19
		pgpsLevel2 OBJECT-TYPE
			SYNTAX Level
			MAX-ACCESS read-write
			STATUS current
			DESCRIPTION
				"The level for values between threshold 2 and threshold 3."
			::= { pgpsEntry 19 }
		
		
		-- 1.3.6.1.4.1.994.3.4.7.34.1.20
		pgpsLevel3 OBJECT-TYPE
			SYNTAX Level
			MAX-ACCESS read-write
			STATUS current
			DESCRIPTION
				"The level for values between threshold 3 and threshold 4."
			::= { pgpsEntry 20 }
		
		
		-- 1.3.6.1.4.1.994.3.4.7.34.1.21
		pgpsLevel4 OBJECT-TYPE
			SYNTAX Level
			MAX-ACCESS read-write
			STATUS current
			DESCRIPTION
				"The level for values between threshold 4 and threshold 5."
			::= { pgpsEntry 21 }
		
		
		-- 1.3.6.1.4.1.994.3.4.7.34.1.28
		pgpsThresh0 OBJECT-TYPE
			SYNTAX DescriptionString
			MAX-ACCESS read-only
			STATUS current
			DESCRIPTION
				"This is the minimun analog value."
			::= { pgpsEntry 28 }
		
		
		-- 1.3.6.1.4.1.994.3.4.7.34.1.29
		pgpsThresh1 OBJECT-TYPE
			SYNTAX DescriptionString
			MAX-ACCESS read-write
			STATUS current
			DESCRIPTION
				"This is the first threshold value."
			::= { pgpsEntry 29 }
		
		
		-- 1.3.6.1.4.1.994.3.4.7.34.1.30
		pgpsThresh2 OBJECT-TYPE
			SYNTAX DescriptionString
			MAX-ACCESS read-write
			STATUS current
			DESCRIPTION
				"This is the second threshold value."
			::= { pgpsEntry 30 }
		
		
		-- 1.3.6.1.4.1.994.3.4.7.34.1.31
		pgpsThresh3 OBJECT-TYPE
			SYNTAX DescriptionString
			MAX-ACCESS read-write
			STATUS current
			DESCRIPTION
				"This is the third threshold value."
			::= { pgpsEntry 31 }
		
		
		-- 1.3.6.1.4.1.994.3.4.7.34.1.32
		pgpsThresh4 OBJECT-TYPE
			SYNTAX DescriptionString
			MAX-ACCESS read-write
			STATUS current
			DESCRIPTION
				"This is the fourth threshold value."
			::= { pgpsEntry 32 }
		
		
		-- 1.3.6.1.4.1.994.3.4.7.34.1.33
		pgpsThresh5 OBJECT-TYPE
			SYNTAX DescriptionString
			MAX-ACCESS read-only
			STATUS current
			DESCRIPTION
				"This is the maximum threshold value."
			::= { pgpsEntry 33 }
		
		
		-- 1.3.6.1.4.1.994.3.4.7.34.1.46
		pgpsUnits OBJECT-TYPE
			SYNTAX DescriptionString
			MAX-ACCESS read-only
			STATUS current
			DESCRIPTION
				"Description of the units of measurement."
			::= { pgpsEntry 46 }
		
		
		-- 1.3.6.1.4.1.994.3.4.7.34.1.64
		pgpsLiveDescription OBJECT-TYPE
			SYNTAX DescriptionString
			MAX-ACCESS read-only
			STATUS current
			DESCRIPTION
				"The description of  the current state of the onboard sensor"
			::= { pgpsEntry 64 }
		
		
		-- 1.3.6.1.4.1.994.3.4.7.34.1.65
		pgpsLiveLevel OBJECT-TYPE
			SYNTAX DescriptionString
			MAX-ACCESS read-only
			STATUS current
			DESCRIPTION
				"The level of the current state of the onboard sensor."
			::= { pgpsEntry 65 }
		
		
		-- 1.3.6.1.4.1.994.3.4.7.34.1.66
		pgpsLiveRaw OBJECT-TYPE
			SYNTAX DescriptionString
			MAX-ACCESS read-only
			STATUS current
			DESCRIPTION
				"The current reading from the onboard sensor.  This value 
				will always be between the threshold 0 and threshold 5 values."
			::= { pgpsEntry 66 }
		
		
		-- 1.3.6.1.4.1.994.3.4.7.34.1.67
		pgpsLiveTime OBJECT-TYPE
			SYNTAX DescriptionString
			MAX-ACCESS read-only
			STATUS current
			DESCRIPTION
				"The time of the last event."
			::= { pgpsEntry 67 }
		
		
		-- 1.3.6.1.4.1.994.3.4.7.34.1.116
		pgpsTL1SID OBJECT-TYPE
			SYNTAX DescriptionString
			MAX-ACCESS read-write
			STATUS current
			DESCRIPTION
				"(TL1) System ID associated with this item."
			::= { pgpsEntry 116 }
		
		
		-- 1.3.6.1.4.1.994.3.4.7.34.1.117
		pgpsTL1COND OBJECT-TYPE
			SYNTAX DescriptionString
			MAX-ACCESS read-write
			STATUS current
			DESCRIPTION
				"(TL1) Condition text associated with this item."
			::= { pgpsEntry 117 }
		
		
		-- 1.3.6.1.4.1.994.3.4.7.34.1.118
		pgpsTL1Eqpt OBJECT-TYPE
			SYNTAX DescriptionString
			MAX-ACCESS read-write
			STATUS current
			DESCRIPTION
				"(TL1) EQPT field associated with this item."
			::= { pgpsEntry 118 }
		
		
		-- 1.3.6.1.4.1.994.3.4.7.34.1.119
		pgpsTL1Env OBJECT-TYPE
			SYNTAX Boolean
			MAX-ACCESS read-write
			STATUS current
			DESCRIPTION
				"(TL1) Environmental field associated with this item."
			::= { pgpsEntry 119 }
		
		
		-- 1.3.6.1.4.1.994.3.4.7.34.1.120
		pgpsTL1Srveff OBJECT-TYPE
			SYNTAX TL1Srveff
			MAX-ACCESS read-write
			STATUS current
			DESCRIPTION
				"(TL1) Service Effecting field associated with this item."
			::= { pgpsEntry 120 }
		
		
		-- 1.3.6.1.4.1.994.3.4.7.34.1.121
		pgpsTL1Locn OBJECT-TYPE
			SYNTAX TL1Locn
			MAX-ACCESS read-write
			STATUS current
			DESCRIPTION
				"(TL1) Location field associated with this item."
			::= { pgpsEntry 121 }
		
		
		-- 1.3.6.1.4.1.994.3.4.7.34.1.122
		pgpsTL1Dirn OBJECT-TYPE
			SYNTAX TL1Dirn
			MAX-ACCESS read-write
			STATUS current
			DESCRIPTION
				"(TL1) Direction field associated with this item."
			::= { pgpsEntry 122 }
		
		
		-- 1.3.6.1.4.1.994.3.4.7.34.1.999
		pgpsIndex OBJECT-TYPE
			SYNTAX Integer32 (1..3)
			MAX-ACCESS read-only
			STATUS current
			DESCRIPTION
				"Index."
			::= { pgpsEntry 999 }


-- portRedirect table
		
		-- 1.3.6.1.4.1.994.3.4.7.35
		pportRedirectTable OBJECT-TYPE
			SYNTAX SEQUENCE OF PportRedirectEntry
			MAX-ACCESS not-accessible
			STATUS current
			DESCRIPTION
				"Table for configuration of portRedirect"
			::= { configuration 35 }
		
		
		-- 1.3.6.1.4.1.994.3.4.7.35.1
		pportRedirectEntry OBJECT-TYPE
			SYNTAX PportRedirectEntry
			MAX-ACCESS not-accessible
			STATUS current
			DESCRIPTION
				"Entry for configuration table of portRedirect"
				INDEX { pportRedirectIndex }
			::= { pportRedirectTable 1 }
		
		
		PportRedirectEntry ::= 
			SEQUENCE {
				pportRedirectDescription
					DescriptionString,
				pportRedirectConfigured
					Configured,
				pportRedirectIpAddress
					IpAddress,
				pportRedirectReadPeriod
					Integer32,
				pportRedirectRosterID
					Integer32,
				pportRedirectIPPortNum
					Integer32,
				pportRedirectIndex
					Integer32 (1..16)
			}
		
		-- 1.3.6.1.4.1.994.3.4.7.35.1.3
		pportRedirectDescription OBJECT-TYPE
			SYNTAX DescriptionString
			MAX-ACCESS read-write
			STATUS current
			DESCRIPTION
				"Description of the connection."
			::= { pportRedirectEntry 3 }
		
		
		-- 1.3.6.1.4.1.994.3.4.7.35.1.10
		pportRedirectConfigured OBJECT-TYPE
			SYNTAX Configured
			MAX-ACCESS read-write
			STATUS current
			DESCRIPTION
				"If set to true, this route will be allowed."
			::= { pportRedirectEntry 10 }
		
		
		-- 1.3.6.1.4.1.994.3.4.7.35.1.14
		pportRedirectIpAddress OBJECT-TYPE
			SYNTAX IpAddress
			MAX-ACCESS read-write
			STATUS current
			DESCRIPTION
				"The IP address of the remote device."
			::= { pportRedirectEntry 14 }
		
		
		-- 1.3.6.1.4.1.994.3.4.7.35.1.23
		pportRedirectReadPeriod OBJECT-TYPE
			SYNTAX Integer32
			MAX-ACCESS read-write
			STATUS current
			DESCRIPTION
				"Inactivity timeout (in minutes)."
			::= { pportRedirectEntry 23 }
		
		
		-- 1.3.6.1.4.1.994.3.4.7.35.1.37
		pportRedirectRosterID OBJECT-TYPE
			SYNTAX Integer32
			MAX-ACCESS read-write
			STATUS current
			DESCRIPTION
				"IP port number to use when connecting to the remote device."
			::= { pportRedirectEntry 37 }
		
		
		-- 1.3.6.1.4.1.994.3.4.7.35.1.73
		pportRedirectIPPortNum OBJECT-TYPE
			SYNTAX Integer32
			MAX-ACCESS read-write
			STATUS current
			DESCRIPTION
				"IP port number to use when connecting to WebMon."
			::= { pportRedirectEntry 73 }
		
		
		-- 1.3.6.1.4.1.994.3.4.7.35.1.999
		pportRedirectIndex OBJECT-TYPE
			SYNTAX Integer32 (1..16)
			MAX-ACCESS read-only
			STATUS current
			DESCRIPTION
				"Index."
			::= { pportRedirectEntry 999 }


-- scheduleA table
		
		-- 1.3.6.1.4.1.994.3.4.7.36
		pscheduleATable OBJECT-TYPE
			SYNTAX SEQUENCE OF PscheduleAEntry
			MAX-ACCESS not-accessible
			STATUS current
			DESCRIPTION
				"Table for configuration of scheduleA"
			::= { configuration 36 }
		
		
		-- 1.3.6.1.4.1.994.3.4.7.36.1
		pscheduleAEntry OBJECT-TYPE
			SYNTAX PscheduleAEntry
			MAX-ACCESS not-accessible
			STATUS current
			DESCRIPTION
				"Entry for configuration table of scheduleA"
				INDEX { pscheduleAIndex }
			::= { pscheduleATable 1 }
		
		
		PscheduleAEntry ::= 
			SEQUENCE {
				pscheduleADayOfWeek
					DayOfWeek,
				pscheduleAConfiguredState
					ConfiguredState,
				pscheduleAConfigured1
					ConfiguredState,
				pscheduleAConfigured2
					ConfiguredState,
				pscheduleAConfigured3
					ConfiguredState,
				pscheduleAConfigured4
					ConfiguredState,
				pscheduleATime0
					DescriptionString,
				pscheduleATime1
					DescriptionString,
				pscheduleATime2
					DescriptionString,
				pscheduleATime3
					DescriptionString,
				pscheduleATime4
					DescriptionString,
				pscheduleATime5
					DescriptionString,
				pscheduleAIndex
					Integer32 (1..7)
			}
		
		-- 1.3.6.1.4.1.994.3.4.7.36.1.102
		pscheduleADayOfWeek OBJECT-TYPE
			SYNTAX DayOfWeek
			MAX-ACCESS read-only
			STATUS current
			DESCRIPTION
				"The day of the week"
			::= { pscheduleAEntry 102 }
		
		
		-- 1.3.6.1.4.1.994.3.4.7.36.1.103
		pscheduleAConfiguredState OBJECT-TYPE
			SYNTAX ConfiguredState
			MAX-ACCESS read-write
			STATUS current
			DESCRIPTION
				"The state of the schedule at the beginning of the day."
			::= { pscheduleAEntry 103 }
		
		
		-- 1.3.6.1.4.1.994.3.4.7.36.1.104
		pscheduleAConfigured1 OBJECT-TYPE
			SYNTAX ConfiguredState
			MAX-ACCESS read-write
			STATUS current
			DESCRIPTION
				"The state of the schedule between time markers 1 and 2."
			::= { pscheduleAEntry 104 }
		
		
		-- 1.3.6.1.4.1.994.3.4.7.36.1.105
		pscheduleAConfigured2 OBJECT-TYPE
			SYNTAX ConfiguredState
			MAX-ACCESS read-write
			STATUS current
			DESCRIPTION
				"The state of the schedule between time markers 2 and 3."
			::= { pscheduleAEntry 105 }
		
		
		-- 1.3.6.1.4.1.994.3.4.7.36.1.106
		pscheduleAConfigured3 OBJECT-TYPE
			SYNTAX ConfiguredState
			MAX-ACCESS read-write
			STATUS current
			DESCRIPTION
				"The state of the schedule between time markers 3 and 4."
			::= { pscheduleAEntry 106 }
		
		
		-- 1.3.6.1.4.1.994.3.4.7.36.1.107
		pscheduleAConfigured4 OBJECT-TYPE
			SYNTAX ConfiguredState
			MAX-ACCESS read-write
			STATUS current
			DESCRIPTION
				"The state of the schedule at the end of the day."
			::= { pscheduleAEntry 107 }
		
		
		-- 1.3.6.1.4.1.994.3.4.7.36.1.108
		pscheduleATime0 OBJECT-TYPE
			SYNTAX DescriptionString
			MAX-ACCESS read-only
			STATUS current
			DESCRIPTION
				"Time marker 0, the beginning of the day."
			::= { pscheduleAEntry 108 }
		
		
		-- 1.3.6.1.4.1.994.3.4.7.36.1.109
		pscheduleATime1 OBJECT-TYPE
			SYNTAX DescriptionString
			MAX-ACCESS read-write
			STATUS current
			DESCRIPTION
				"Time marker 1."
			::= { pscheduleAEntry 109 }
		
		
		-- 1.3.6.1.4.1.994.3.4.7.36.1.110
		pscheduleATime2 OBJECT-TYPE
			SYNTAX DescriptionString
			MAX-ACCESS read-write
			STATUS current
			DESCRIPTION
				"Time marker 2."
			::= { pscheduleAEntry 110 }
		
		
		-- 1.3.6.1.4.1.994.3.4.7.36.1.111
		pscheduleATime3 OBJECT-TYPE
			SYNTAX DescriptionString
			MAX-ACCESS read-write
			STATUS current
			DESCRIPTION
				"Time marker 3."
			::= { pscheduleAEntry 111 }
		
		
		-- 1.3.6.1.4.1.994.3.4.7.36.1.112
		pscheduleATime4 OBJECT-TYPE
			SYNTAX DescriptionString
			MAX-ACCESS read-write
			STATUS current
			DESCRIPTION
				"Time marker 4."
			::= { pscheduleAEntry 112 }
		
		
		-- 1.3.6.1.4.1.994.3.4.7.36.1.113
		pscheduleATime5 OBJECT-TYPE
			SYNTAX DescriptionString
			MAX-ACCESS read-only
			STATUS current
			DESCRIPTION
				"Time marker 5, the end of the day."
			::= { pscheduleAEntry 113 }
		
		
		-- 1.3.6.1.4.1.994.3.4.7.36.1.999
		pscheduleAIndex OBJECT-TYPE
			SYNTAX Integer32 (1..7)
			MAX-ACCESS read-only
			STATUS current
			DESCRIPTION
				"Index."
			::= { pscheduleAEntry 999 }


-- scheduleB table
		
		-- 1.3.6.1.4.1.994.3.4.7.37
		pscheduleBTable OBJECT-TYPE
			SYNTAX SEQUENCE OF PscheduleBEntry
			MAX-ACCESS not-accessible
			STATUS current
			DESCRIPTION
				"Table for configuration of scheduleB"
			::= { configuration 37 }
		
		
		-- 1.3.6.1.4.1.994.3.4.7.37.1
		pscheduleBEntry OBJECT-TYPE
			SYNTAX PscheduleBEntry
			MAX-ACCESS not-accessible
			STATUS current
			DESCRIPTION
				"Entry for configuration table of scheduleB"
				INDEX { pscheduleBIndex }
			::= { pscheduleBTable 1 }
		
		
		PscheduleBEntry ::= 
			SEQUENCE {
				pscheduleBDayOfWeek
					DayOfWeek,
				pscheduleBConfiguredState
					ConfiguredState,
				pscheduleBConfigured1
					ConfiguredState,
				pscheduleBConfigured2
					ConfiguredState,
				pscheduleBConfigured3
					ConfiguredState,
				pscheduleBConfigured4
					ConfiguredState,
				pscheduleBTime0
					DescriptionString,
				pscheduleBTime1
					DescriptionString,
				pscheduleBTime2
					DescriptionString,
				pscheduleBTime3
					DescriptionString,
				pscheduleBTime4
					DescriptionString,
				pscheduleBTime5
					DescriptionString,
				pscheduleBIndex
					Integer32 (1..7)
			}
		
		-- 1.3.6.1.4.1.994.3.4.7.37.1.102
		pscheduleBDayOfWeek OBJECT-TYPE
			SYNTAX DayOfWeek
			MAX-ACCESS read-only
			STATUS current
			DESCRIPTION
				"The day of the week"
			::= { pscheduleBEntry 102 }
		
		
		-- 1.3.6.1.4.1.994.3.4.7.37.1.103
		pscheduleBConfiguredState OBJECT-TYPE
			SYNTAX ConfiguredState
			MAX-ACCESS read-write
			STATUS current
			DESCRIPTION
				"The state of the schedule at the beginning of the day."
			::= { pscheduleBEntry 103 }
		
		
		-- 1.3.6.1.4.1.994.3.4.7.37.1.104
		pscheduleBConfigured1 OBJECT-TYPE
			SYNTAX ConfiguredState
			MAX-ACCESS read-write
			STATUS current
			DESCRIPTION
				"The state of the schedule between time markers 1 and 2."
			::= { pscheduleBEntry 104 }
		
		
		-- 1.3.6.1.4.1.994.3.4.7.37.1.105
		pscheduleBConfigured2 OBJECT-TYPE
			SYNTAX ConfiguredState
			MAX-ACCESS read-write
			STATUS current
			DESCRIPTION
				"The state of the schedule between time markers 2 and 3."
			::= { pscheduleBEntry 105 }
		
		
		-- 1.3.6.1.4.1.994.3.4.7.37.1.106
		pscheduleBConfigured3 OBJECT-TYPE
			SYNTAX ConfiguredState
			MAX-ACCESS read-write
			STATUS current
			DESCRIPTION
				"The state of the schedule between time markers 3 and 4."
			::= { pscheduleBEntry 106 }
		
		
		-- 1.3.6.1.4.1.994.3.4.7.37.1.107
		pscheduleBConfigured4 OBJECT-TYPE
			SYNTAX ConfiguredState
			MAX-ACCESS read-write
			STATUS current
			DESCRIPTION
				"The state of the schedule at the end of the day."
			::= { pscheduleBEntry 107 }
		
		
		-- 1.3.6.1.4.1.994.3.4.7.37.1.108
		pscheduleBTime0 OBJECT-TYPE
			SYNTAX DescriptionString
			MAX-ACCESS read-only
			STATUS current
			DESCRIPTION
				"Time marker 0, the beginning of the day."
			::= { pscheduleBEntry 108 }
		
		
		-- 1.3.6.1.4.1.994.3.4.7.37.1.109
		pscheduleBTime1 OBJECT-TYPE
			SYNTAX DescriptionString
			MAX-ACCESS read-write
			STATUS current
			DESCRIPTION
				"Time marker 1."
			::= { pscheduleBEntry 109 }
		
		
		-- 1.3.6.1.4.1.994.3.4.7.37.1.110
		pscheduleBTime2 OBJECT-TYPE
			SYNTAX DescriptionString
			MAX-ACCESS read-write
			STATUS current
			DESCRIPTION
				"Time marker 2."
			::= { pscheduleBEntry 110 }
		
		
		-- 1.3.6.1.4.1.994.3.4.7.37.1.111
		pscheduleBTime3 OBJECT-TYPE
			SYNTAX DescriptionString
			MAX-ACCESS read-write
			STATUS current
			DESCRIPTION
				"Time marker 3."
			::= { pscheduleBEntry 111 }
		
		
		-- 1.3.6.1.4.1.994.3.4.7.37.1.112
		pscheduleBTime4 OBJECT-TYPE
			SYNTAX DescriptionString
			MAX-ACCESS read-write
			STATUS current
			DESCRIPTION
				"Time marker 4."
			::= { pscheduleBEntry 112 }
		
		
		-- 1.3.6.1.4.1.994.3.4.7.37.1.113
		pscheduleBTime5 OBJECT-TYPE
			SYNTAX DescriptionString
			MAX-ACCESS read-only
			STATUS current
			DESCRIPTION
				"Time marker 5, the end of the day."
			::= { pscheduleBEntry 113 }
		
		
		-- 1.3.6.1.4.1.994.3.4.7.37.1.999
		pscheduleBIndex OBJECT-TYPE
			SYNTAX Integer32 (1..7)
			MAX-ACCESS read-only
			STATUS current
			DESCRIPTION
				"Index."
			::= { pscheduleBEntry 999 }


-- scheduleC table
		
		-- 1.3.6.1.4.1.994.3.4.7.38
		pscheduleCTable OBJECT-TYPE
			SYNTAX SEQUENCE OF PscheduleCEntry
			MAX-ACCESS not-accessible
			STATUS current
			DESCRIPTION
				"Table for configuration of scheduleC"
			::= { configuration 38 }
		
		
		-- 1.3.6.1.4.1.994.3.4.7.38.1
		pscheduleCEntry OBJECT-TYPE
			SYNTAX PscheduleCEntry
			MAX-ACCESS not-accessible
			STATUS current
			DESCRIPTION
				"Entry for configuration table of scheduleC"
				INDEX { pscheduleCIndex }
			::= { pscheduleCTable 1 }
		
		
		PscheduleCEntry ::= 
			SEQUENCE {
				pscheduleCDayOfWeek
					DayOfWeek,
				pscheduleCConfiguredState
					ConfiguredState,
				pscheduleCConfigured1
					ConfiguredState,
				pscheduleCConfigured2
					ConfiguredState,
				pscheduleCConfigured3
					ConfiguredState,
				pscheduleCConfigured4
					ConfiguredState,
				pscheduleCTime0
					DescriptionString,
				pscheduleCTime1
					DescriptionString,
				pscheduleCTime2
					DescriptionString,
				pscheduleCTime3
					DescriptionString,
				pscheduleCTime4
					DescriptionString,
				pscheduleCTime5
					DescriptionString,
				pscheduleCIndex
					Integer32 (1..7)
			}
		
		-- 1.3.6.1.4.1.994.3.4.7.38.1.102
		pscheduleCDayOfWeek OBJECT-TYPE
			SYNTAX DayOfWeek
			MAX-ACCESS read-only
			STATUS current
			DESCRIPTION
				"The day of the week"
			::= { pscheduleCEntry 102 }
		
		
		-- 1.3.6.1.4.1.994.3.4.7.38.1.103
		pscheduleCConfiguredState OBJECT-TYPE
			SYNTAX ConfiguredState
			MAX-ACCESS read-write
			STATUS current
			DESCRIPTION
				"The state of the schedule at the beginning of the day."
			::= { pscheduleCEntry 103 }
		
		
		-- 1.3.6.1.4.1.994.3.4.7.38.1.104
		pscheduleCConfigured1 OBJECT-TYPE
			SYNTAX ConfiguredState
			MAX-ACCESS read-write
			STATUS current
			DESCRIPTION
				"The state of the schedule between time markers 1 and 2."
			::= { pscheduleCEntry 104 }
		
		
		-- 1.3.6.1.4.1.994.3.4.7.38.1.105
		pscheduleCConfigured2 OBJECT-TYPE
			SYNTAX ConfiguredState
			MAX-ACCESS read-write
			STATUS current
			DESCRIPTION
				"The state of the schedule between time markers 2 and 3."
			::= { pscheduleCEntry 105 }
		
		
		-- 1.3.6.1.4.1.994.3.4.7.38.1.106
		pscheduleCConfigured3 OBJECT-TYPE
			SYNTAX ConfiguredState
			MAX-ACCESS read-write
			STATUS current
			DESCRIPTION
				"The state of the schedule between time markers 3 and 4."
			::= { pscheduleCEntry 106 }
		
		
		-- 1.3.6.1.4.1.994.3.4.7.38.1.107
		pscheduleCConfigured4 OBJECT-TYPE
			SYNTAX ConfiguredState
			MAX-ACCESS read-write
			STATUS current
			DESCRIPTION
				"The state of the schedule at the end of the day."
			::= { pscheduleCEntry 107 }
		
		
		-- 1.3.6.1.4.1.994.3.4.7.38.1.108
		pscheduleCTime0 OBJECT-TYPE
			SYNTAX DescriptionString
			MAX-ACCESS read-only
			STATUS current
			DESCRIPTION
				"Time marker 0, the beginning of the day."
			::= { pscheduleCEntry 108 }
		
		
		-- 1.3.6.1.4.1.994.3.4.7.38.1.109
		pscheduleCTime1 OBJECT-TYPE
			SYNTAX DescriptionString
			MAX-ACCESS read-write
			STATUS current
			DESCRIPTION
				"Time marker 1."
			::= { pscheduleCEntry 109 }
		
		
		-- 1.3.6.1.4.1.994.3.4.7.38.1.110
		pscheduleCTime2 OBJECT-TYPE
			SYNTAX DescriptionString
			MAX-ACCESS read-write
			STATUS current
			DESCRIPTION
				"Time marker 2."
			::= { pscheduleCEntry 110 }
		
		
		-- 1.3.6.1.4.1.994.3.4.7.38.1.111
		pscheduleCTime3 OBJECT-TYPE
			SYNTAX DescriptionString
			MAX-ACCESS read-write
			STATUS current
			DESCRIPTION
				"Time marker 3."
			::= { pscheduleCEntry 111 }
		
		
		-- 1.3.6.1.4.1.994.3.4.7.38.1.112
		pscheduleCTime4 OBJECT-TYPE
			SYNTAX DescriptionString
			MAX-ACCESS read-write
			STATUS current
			DESCRIPTION
				"Time marker 4."
			::= { pscheduleCEntry 112 }
		
		
		-- 1.3.6.1.4.1.994.3.4.7.38.1.113
		pscheduleCTime5 OBJECT-TYPE
			SYNTAX DescriptionString
			MAX-ACCESS read-only
			STATUS current
			DESCRIPTION
				"Time marker 5, the end of the day."
			::= { pscheduleCEntry 113 }
		
		
		-- 1.3.6.1.4.1.994.3.4.7.38.1.999
		pscheduleCIndex OBJECT-TYPE
			SYNTAX Integer32 (1..7)
			MAX-ACCESS read-only
			STATUS current
			DESCRIPTION
				"Index."
			::= { pscheduleCEntry 999 }


-- scheduleD table
		
		-- 1.3.6.1.4.1.994.3.4.7.39
		pscheduleDTable OBJECT-TYPE
			SYNTAX SEQUENCE OF PscheduleDEntry
			MAX-ACCESS not-accessible
			STATUS current
			DESCRIPTION
				"Table for configuration of scheduleD"
			::= { configuration 39 }
		
		
		-- 1.3.6.1.4.1.994.3.4.7.39.1
		pscheduleDEntry OBJECT-TYPE
			SYNTAX PscheduleDEntry
			MAX-ACCESS not-accessible
			STATUS current
			DESCRIPTION
				"Entry for configuration table of scheduleD"
				INDEX { pscheduleDIndex }
			::= { pscheduleDTable 1 }
		
		
		PscheduleDEntry ::= 
			SEQUENCE {
				pscheduleDDayOfWeek
					DayOfWeek,
				pscheduleDConfiguredState
					ConfiguredState,
				pscheduleDConfigured1
					ConfiguredState,
				pscheduleDConfigured2
					ConfiguredState,
				pscheduleDConfigured3
					ConfiguredState,
				pscheduleDConfigured4
					ConfiguredState,
				pscheduleDTime0
					DescriptionString,
				pscheduleDTime1
					DescriptionString,
				pscheduleDTime2
					DescriptionString,
				pscheduleDTime3
					DescriptionString,
				pscheduleDTime4
					DescriptionString,
				pscheduleDTime5
					DescriptionString,
				pscheduleDIndex
					Integer32 (1..7)
			}
		
		-- 1.3.6.1.4.1.994.3.4.7.39.1.102
		pscheduleDDayOfWeek OBJECT-TYPE
			SYNTAX DayOfWeek
			MAX-ACCESS read-only
			STATUS current
			DESCRIPTION
				"The day of the week"
			::= { pscheduleDEntry 102 }
		
		
		-- 1.3.6.1.4.1.994.3.4.7.39.1.103
		pscheduleDConfiguredState OBJECT-TYPE
			SYNTAX ConfiguredState
			MAX-ACCESS read-write
			STATUS current
			DESCRIPTION
				"The state of the schedule at the beginning of the day."
			::= { pscheduleDEntry 103 }
		
		
		-- 1.3.6.1.4.1.994.3.4.7.39.1.104
		pscheduleDConfigured1 OBJECT-TYPE
			SYNTAX ConfiguredState
			MAX-ACCESS read-write
			STATUS current
			DESCRIPTION
				"The state of the schedule between time markers 1 and 2."
			::= { pscheduleDEntry 104 }
		
		
		-- 1.3.6.1.4.1.994.3.4.7.39.1.105
		pscheduleDConfigured2 OBJECT-TYPE
			SYNTAX ConfiguredState
			MAX-ACCESS read-write
			STATUS current
			DESCRIPTION
				"The state of the schedule between time markers 2 and 3."
			::= { pscheduleDEntry 105 }
		
		
		-- 1.3.6.1.4.1.994.3.4.7.39.1.106
		pscheduleDConfigured3 OBJECT-TYPE
			SYNTAX ConfiguredState
			MAX-ACCESS read-write
			STATUS current
			DESCRIPTION
				"The state of the schedule between time markers 3 and 4."
			::= { pscheduleDEntry 106 }
		
		
		-- 1.3.6.1.4.1.994.3.4.7.39.1.107
		pscheduleDConfigured4 OBJECT-TYPE
			SYNTAX ConfiguredState
			MAX-ACCESS read-write
			STATUS current
			DESCRIPTION
				"The state of the schedule at the end of the day."
			::= { pscheduleDEntry 107 }
		
		
		-- 1.3.6.1.4.1.994.3.4.7.39.1.108
		pscheduleDTime0 OBJECT-TYPE
			SYNTAX DescriptionString
			MAX-ACCESS read-only
			STATUS current
			DESCRIPTION
				"Time marker 0, the beginning of the day."
			::= { pscheduleDEntry 108 }
		
		
		-- 1.3.6.1.4.1.994.3.4.7.39.1.109
		pscheduleDTime1 OBJECT-TYPE
			SYNTAX DescriptionString
			MAX-ACCESS read-write
			STATUS current
			DESCRIPTION
				"Time marker 1."
			::= { pscheduleDEntry 109 }
		
		
		-- 1.3.6.1.4.1.994.3.4.7.39.1.110
		pscheduleDTime2 OBJECT-TYPE
			SYNTAX DescriptionString
			MAX-ACCESS read-write
			STATUS current
			DESCRIPTION
				"Time marker 2."
			::= { pscheduleDEntry 110 }
		
		
		-- 1.3.6.1.4.1.994.3.4.7.39.1.111
		pscheduleDTime3 OBJECT-TYPE
			SYNTAX DescriptionString
			MAX-ACCESS read-write
			STATUS current
			DESCRIPTION
				"Time marker 3."
			::= { pscheduleDEntry 111 }
		
		
		-- 1.3.6.1.4.1.994.3.4.7.39.1.112
		pscheduleDTime4 OBJECT-TYPE
			SYNTAX DescriptionString
			MAX-ACCESS read-write
			STATUS current
			DESCRIPTION
				"Time marker 4."
			::= { pscheduleDEntry 112 }
		
		
		-- 1.3.6.1.4.1.994.3.4.7.39.1.113
		pscheduleDTime5 OBJECT-TYPE
			SYNTAX DescriptionString
			MAX-ACCESS read-only
			STATUS current
			DESCRIPTION
				"Time marker 5, the end of the day."
			::= { pscheduleDEntry 113 }
		
		
		-- 1.3.6.1.4.1.994.3.4.7.39.1.999
		pscheduleDIndex OBJECT-TYPE
			SYNTAX Integer32 (1..7)
			MAX-ACCESS read-only
			STATUS current
			DESCRIPTION
				"Index."
			::= { pscheduleDEntry 999 }


-- tl1Settings folder
		
		-- 1.3.6.1.4.1.994.3.4.7.40
		tl1Settings OBJECT IDENTIFIER ::= {configuration 40 }
		
		-- 1.3.6.1.4.1.994.3.4.7.40.123
		tl1SettingsTL1Issue OBJECT-TYPE
			SYNTAX TL1Issue
			MAX-ACCESS read-write
			STATUS current
			DESCRIPTION
				"(TL1) TL1 issue associated with this device."
			::= { tl1Settings 123 }


-- DCPFProtocol table
		
		-- 1.3.6.1.4.1.994.3.4.7.41
		pDCPFProtocolTable OBJECT-TYPE
			SYNTAX SEQUENCE OF PDCPFProtocolEntry
			MAX-ACCESS not-accessible
			STATUS current
			DESCRIPTION
				"Table for configuration of DCPFProtocol"
			::= { configuration 41 }
		
		
		-- 1.3.6.1.4.1.994.3.4.7.41.1
		pDCPFProtocolEntry OBJECT-TYPE
			SYNTAX PDCPFProtocolEntry
			MAX-ACCESS not-accessible
			STATUS current
			DESCRIPTION
				"Entry for configuration table of DCPFProtocol"
				INDEX { pDCPFProtocolIndex }
			::= { pDCPFProtocolTable 1 }
		
		
		PDCPFProtocolEntry ::= 
			SEQUENCE {
				pDCPFProtocolDescription
					DescriptionString,
				pDCPFProtocolConfigured
					Configured,
				pDCPFProtocolBaseDCPFDisplay
					Integer32,
				pDCPFProtocolIndex
					Integer32 (1..27)
			}
		
		-- 1.3.6.1.4.1.994.3.4.7.41.1.3
		pDCPFProtocolDescription OBJECT-TYPE
			SYNTAX DescriptionString
			MAX-ACCESS read-only
			STATUS current
			DESCRIPTION
				"Description of the input device that DCPF will poll."
			::= { pDCPFProtocolEntry 3 }
		
		
		-- 1.3.6.1.4.1.994.3.4.7.41.1.10
		pDCPFProtocolConfigured OBJECT-TYPE
			SYNTAX Configured
			MAX-ACCESS read-write
			STATUS current
			DESCRIPTION
				"If set to true, this input will be polled in DCPF.  If set to false, it will not be polled."
			::= { pDCPFProtocolEntry 10 }
		
		
		-- 1.3.6.1.4.1.994.3.4.7.41.1.127
		pDCPFProtocolBaseDCPFDisplay OBJECT-TYPE
			SYNTAX Integer32
			MAX-ACCESS read-write
			STATUS current
			DESCRIPTION
				"Base DCPF display for this input device."
			::= { pDCPFProtocolEntry 127 }
		
		
		-- 1.3.6.1.4.1.994.3.4.7.41.1.999
		pDCPFProtocolIndex OBJECT-TYPE
			SYNTAX Integer32 (1..27)
			MAX-ACCESS read-only
			STATUS current
			DESCRIPTION
				"Index."
			::= { pDCPFProtocolEntry 999 }


-- dcpfSettings folder
		
		-- 1.3.6.1.4.1.994.3.4.7.42
		dcpfSettings OBJECT IDENTIFIER ::= {configuration 42 }
		
		-- 1.3.6.1.4.1.994.3.4.7.42.128
		dcpfSettingsDCPFAddress OBJECT-TYPE
			SYNTAX Integer32
			MAX-ACCESS read-write
			STATUS current
			DESCRIPTION
				"Base DCPF Address."
			::= { dcpfSettings 128 }


-- TABSProtocol table
		
		-- 1.3.6.1.4.1.994.3.4.7.43
		pTABSProtocolTable OBJECT-TYPE
			SYNTAX SEQUENCE OF PTABSProtocolEntry
			MAX-ACCESS not-accessible
			STATUS current
			DESCRIPTION
				"Table for configuration of TABSProtocol"
			::= { configuration 43 }
		
		
		-- 1.3.6.1.4.1.994.3.4.7.43.1
		pTABSProtocolEntry OBJECT-TYPE
			SYNTAX PTABSProtocolEntry
			MAX-ACCESS not-accessible
			STATUS current
			DESCRIPTION
				"Entry for configuration table of TABSProtocol"
				INDEX { pTABSProtocolIndex }
			::= { pTABSProtocolTable 1 }
		
		
		PTABSProtocolEntry ::= 
			SEQUENCE {
				pTABSProtocolDescription
					DescriptionString,
				pTABSProtocolConfigured
					Configured,
				pTABSProtocolBaseTABSDisplay
					Integer32,
				pTABSProtocolIndex
					Integer32 (1..27)
			}
		
		-- 1.3.6.1.4.1.994.3.4.7.43.1.3
		pTABSProtocolDescription OBJECT-TYPE
			SYNTAX DescriptionString
			MAX-ACCESS read-only
			STATUS current
			DESCRIPTION
				"Description of the input device that TABS will poll."
			::= { pTABSProtocolEntry 3 }
		
		
		-- 1.3.6.1.4.1.994.3.4.7.43.1.10
		pTABSProtocolConfigured OBJECT-TYPE
			SYNTAX Configured
			MAX-ACCESS read-write
			STATUS current
			DESCRIPTION
				"If set to true, this input will be polled in TABS.  If set to false, it will not be polled."
			::= { pTABSProtocolEntry 10 }
		
		
		-- 1.3.6.1.4.1.994.3.4.7.43.1.129
		pTABSProtocolBaseTABSDisplay OBJECT-TYPE
			SYNTAX Integer32
			MAX-ACCESS read-write
			STATUS current
			DESCRIPTION
				"Base TABS display for this input device."
			::= { pTABSProtocolEntry 129 }
		
		
		-- 1.3.6.1.4.1.994.3.4.7.43.1.999
		pTABSProtocolIndex OBJECT-TYPE
			SYNTAX Integer32 (1..27)
			MAX-ACCESS read-only
			STATUS current
			DESCRIPTION
				"Index."
			::= { pTABSProtocolEntry 999 }


-- tabsSettings folder
		
		-- 1.3.6.1.4.1.994.3.4.7.44
		tabsSettings OBJECT IDENTIFIER ::= {configuration 44 }
		
		-- 1.3.6.1.4.1.994.3.4.7.44.130
		tabsSettingsTABSAddress OBJECT-TYPE
			SYNTAX Integer32
			MAX-ACCESS read-write
			STATUS current
			DESCRIPTION
				"Base TABS Address."
			::= { tabsSettings 130 }


-- snmpCommands table
		
		-- 1.3.6.1.4.1.994.3.4.7.45
		psnmpCommandsTable OBJECT-TYPE
			SYNTAX SEQUENCE OF PsnmpCommandsEntry
			MAX-ACCESS not-accessible
			STATUS current
			DESCRIPTION
				"Table for configuration of snmpCommands"
			::= { configuration 45 }
		
		
		-- 1.3.6.1.4.1.994.3.4.7.45.1
		psnmpCommandsEntry OBJECT-TYPE
			SYNTAX PsnmpCommandsEntry
			MAX-ACCESS not-accessible
			STATUS current
			DESCRIPTION
				"Entry for configuration table of snmpCommands"
				INDEX { psnmpCommandsIndex }
			::= { psnmpCommandsTable 1 }
		
		
		PsnmpCommandsEntry ::= 
			SEQUENCE {
				psnmpCommandsDescription
					DescriptionString,
				psnmpCommandsConfigured
					Configured,
				psnmpCommandsIpAddress
					IpAddress,
				psnmpCommandsGet
					DescriptionString,
				psnmpCommandsSnmpVersion
					SnmpVersion,
				psnmpCommandsOutputAuto
					Integer32,
				psnmpCommandsOutputAutoPkg
					Integer32,
				psnmpCommandsIPPortNum
					Integer32,
				psnmpCommandsOID
					DescriptionString,
				psnmpCommandsSNMPVarbindType
					SNMPVarbindType,
				psnmpCommandsTextNormal
					DescriptionString,
				psnmpCommandsTextCritical
					DescriptionString,
				psnmpCommandsTextMajor
					DescriptionString,
				psnmpCommandsTextMinor
					DescriptionString,
				psnmpCommandsTextStatus
					DescriptionString,
				psnmpCommandsIndex
					Integer32 (1..16)
			}
		
		-- 1.3.6.1.4.1.994.3.4.7.45.1.3
		psnmpCommandsDescription OBJECT-TYPE
			SYNTAX DescriptionString
			MAX-ACCESS read-write
			STATUS current
			DESCRIPTION
				"Name for this SNMP command."
			::= { psnmpCommandsEntry 3 }
		
		
		-- 1.3.6.1.4.1.994.3.4.7.45.1.10
		psnmpCommandsConfigured OBJECT-TYPE
			SYNTAX Configured
			MAX-ACCESS read-write
			STATUS current
			DESCRIPTION
				"If set to true, this command will be sent for matching events.  If set to false, it will not be sent."
			::= { psnmpCommandsEntry 10 }
		
		
		-- 1.3.6.1.4.1.994.3.4.7.45.1.14
		psnmpCommandsIpAddress OBJECT-TYPE
			SYNTAX IpAddress
			MAX-ACCESS read-write
			STATUS current
			DESCRIPTION
				"Target (receiver) IP address of this SNMP command."
			::= { psnmpCommandsEntry 14 }
		
		
		-- 1.3.6.1.4.1.994.3.4.7.45.1.39
		psnmpCommandsGet OBJECT-TYPE
			SYNTAX DescriptionString
			MAX-ACCESS read-write
			STATUS current
			DESCRIPTION
				"SNMP community used with this command."
			::= { psnmpCommandsEntry 39 }
		
		
		-- 1.3.6.1.4.1.994.3.4.7.45.1.42
		psnmpCommandsSnmpVersion OBJECT-TYPE
			SYNTAX SnmpVersion
			MAX-ACCESS read-write
			STATUS current
			DESCRIPTION
				"SNMP version to be used with this command."
			::= { psnmpCommandsEntry 42 }
		
		
		-- 1.3.6.1.4.1.994.3.4.7.45.1.49
		psnmpCommandsOutputAuto OBJECT-TYPE
			SYNTAX Integer32
			MAX-ACCESS read-write
			STATUS current
			DESCRIPTION
				"Source alarm point for this SNMP command."
			::= { psnmpCommandsEntry 49 }
		
		
		-- 1.3.6.1.4.1.994.3.4.7.45.1.71
		psnmpCommandsOutputAutoPkg OBJECT-TYPE
			SYNTAX Integer32
			MAX-ACCESS read-write
			STATUS current
			DESCRIPTION
				"Package where the source alarm point is located."
			::= { psnmpCommandsEntry 71 }
		
		
		-- 1.3.6.1.4.1.994.3.4.7.45.1.73
		psnmpCommandsIPPortNum OBJECT-TYPE
			SYNTAX Integer32
			MAX-ACCESS read-write
			STATUS current
			DESCRIPTION
				"Target (receiver) IP port of this SNMP command."
			::= { psnmpCommandsEntry 73 }
		
		
		-- 1.3.6.1.4.1.994.3.4.7.45.1.132
		psnmpCommandsOID OBJECT-TYPE
			SYNTAX DescriptionString
			MAX-ACCESS read-write
			STATUS current
			DESCRIPTION
				"Target OID used with this command"
			::= { psnmpCommandsEntry 132 }
		
		
		-- 1.3.6.1.4.1.994.3.4.7.45.1.134
		psnmpCommandsSNMPVarbindType OBJECT-TYPE
			SYNTAX SNMPVarbindType
			MAX-ACCESS read-write
			STATUS current
			DESCRIPTION
				"Type of value sent to target, if this is a set command."
			::= { psnmpCommandsEntry 134 }
		
		
		-- 1.3.6.1.4.1.994.3.4.7.45.1.135
		psnmpCommandsTextNormal OBJECT-TYPE
			SYNTAX DescriptionString
			MAX-ACCESS read-write
			STATUS current
			DESCRIPTION
				"Value sent to target for normal condition for a set command."
			::= { psnmpCommandsEntry 135 }
		
		
		-- 1.3.6.1.4.1.994.3.4.7.45.1.136
		psnmpCommandsTextCritical OBJECT-TYPE
			SYNTAX DescriptionString
			MAX-ACCESS read-write
			STATUS current
			DESCRIPTION
				"Value sent to target for critical condition for a set command."
			::= { psnmpCommandsEntry 136 }
		
		
		-- 1.3.6.1.4.1.994.3.4.7.45.1.137
		psnmpCommandsTextMajor OBJECT-TYPE
			SYNTAX DescriptionString
			MAX-ACCESS read-write
			STATUS current
			DESCRIPTION
				"Value sent to target for major condition for a set command."
			::= { psnmpCommandsEntry 137 }
		
		
		-- 1.3.6.1.4.1.994.3.4.7.45.1.138
		psnmpCommandsTextMinor OBJECT-TYPE
			SYNTAX DescriptionString
			MAX-ACCESS read-write
			STATUS current
			DESCRIPTION
				"Value sent to target for minor condition for a set command."
			::= { psnmpCommandsEntry 138 }
		
		
		-- 1.3.6.1.4.1.994.3.4.7.45.1.139
		psnmpCommandsTextStatus OBJECT-TYPE
			SYNTAX DescriptionString
			MAX-ACCESS read-write
			STATUS current
			DESCRIPTION
				"Value sent to target for status condition for a set command."
			::= { psnmpCommandsEntry 139 }
		
		
		-- 1.3.6.1.4.1.994.3.4.7.45.1.999
		psnmpCommandsIndex OBJECT-TYPE
			SYNTAX Integer32 (1..16)
			MAX-ACCESS read-only
			STATUS current
			DESCRIPTION
				"Index."
			::= { psnmpCommandsEntry 999 }


-- battMon folder
		
		-- 1.3.6.1.4.1.994.3.4.7.46
		battMon OBJECT IDENTIFIER ::= {configuration 46 }
		
		-- 1.3.6.1.4.1.994.3.4.7.46.10
		battMonConfigured OBJECT-TYPE
			SYNTAX Configured
			MAX-ACCESS read-write
			STATUS current
			DESCRIPTION
				"If set to true, this command will be sent for matching events.  If set to false, it will not be sent."
			::= { battMon 10 }
		
		
		-- 1.3.6.1.4.1.994.3.4.7.46.49
		battMonOutputAuto OBJECT-TYPE
			SYNTAX Integer32
			MAX-ACCESS read-write
			STATUS current
			DESCRIPTION
				"Source alarm point for this SNMP command."
			::= { battMon 49 }
		
		
		-- 1.3.6.1.4.1.994.3.4.7.46.71
		battMonOutputAutoPkg OBJECT-TYPE
			SYNTAX Integer32
			MAX-ACCESS read-write
			STATUS current
			DESCRIPTION
				"Package where the source alarm point is located."
			::= { battMon 71 }


-- BankInfo table
		
		-- 1.3.6.1.4.1.994.3.4.7.47
		pBankInfoTable OBJECT-TYPE
			SYNTAX SEQUENCE OF PBankInfoEntry
			MAX-ACCESS not-accessible
			STATUS current
			DESCRIPTION
				"Table for configuration of BankInfo"
			::= { configuration 47 }
		
		
		-- 1.3.6.1.4.1.994.3.4.7.47.1
		pBankInfoEntry OBJECT-TYPE
			SYNTAX PBankInfoEntry
			MAX-ACCESS not-accessible
			STATUS current
			DESCRIPTION
				"Entry for configuration table of BankInfo"
				INDEX { pBankInfoIndex }
			::= { pBankInfoTable 1 }
		
		
		PBankInfoEntry ::= 
			SEQUENCE {
				pBankInfoDescription
					DescriptionString,
				pBankInfoConfigured
					Configured,
				pBankInfoPresent
					Boolean,
				pBankInfoSlotId
					SlotId,
				pBankInfoIOFormat
					IOFormat,
				pBankInfoIndex
					Integer32 (1..16)
			}
		
		-- 1.3.6.1.4.1.994.3.4.7.47.1.3
		pBankInfoDescription OBJECT-TYPE
			SYNTAX DescriptionString
			MAX-ACCESS read-only
			STATUS current
			DESCRIPTION
				"Description of the slot contents."
			::= { pBankInfoEntry 3 }
		
		
		-- 1.3.6.1.4.1.994.3.4.7.47.1.10
		pBankInfoConfigured OBJECT-TYPE
			SYNTAX Configured
			MAX-ACCESS read-write
			STATUS current
			DESCRIPTION
				"Schedule of when this bank is in use."
			::= { pBankInfoEntry 10 }
		
		
		-- 1.3.6.1.4.1.994.3.4.7.47.1.68
		pBankInfoPresent OBJECT-TYPE
			SYNTAX Boolean
			MAX-ACCESS read-only
			STATUS current
			DESCRIPTION
				"If true indicates the bank is connected to the WebMon.
				If false indicates that the bank is not connected."
			::= { pBankInfoEntry 68 }
		
		
		-- 1.3.6.1.4.1.994.3.4.7.47.1.69
		pBankInfoSlotId OBJECT-TYPE
			SYNTAX SlotId
			MAX-ACCESS read-write
			STATUS current
			DESCRIPTION
				"Identifies the type of card in slot."
			::= { pBankInfoEntry 69 }
		
		
		-- 1.3.6.1.4.1.994.3.4.7.47.1.75
		pBankInfoIOFormat OBJECT-TYPE
			SYNTAX IOFormat
			MAX-ACCESS read-write
			STATUS current
			DESCRIPTION
				""
			::= { pBankInfoEntry 75 }
		
		
		-- 1.3.6.1.4.1.994.3.4.7.47.1.999
		pBankInfoIndex OBJECT-TYPE
			SYNTAX Integer32 (1..16)
			MAX-ACCESS read-only
			STATUS current
			DESCRIPTION
				"Index."
			::= { pBankInfoEntry 999 }


-- Slot1 table
		
		-- 1.3.6.1.4.1.994.3.4.7.18
		pSlot1Table OBJECT-TYPE
			SYNTAX SEQUENCE OF PSlot1Entry
			MAX-ACCESS not-accessible
			STATUS current
			DESCRIPTION
				"Table for configuration of Slot1"
			::= { configuration 18 }
		
		
		-- 1.3.6.1.4.1.994.3.4.7.18.1
		pSlot1Entry OBJECT-TYPE
			SYNTAX PSlot1Entry
			MAX-ACCESS not-accessible
			STATUS current
			DESCRIPTION
				"Entry for configuration table of Slot1"
				INDEX { pSlot1Index }
			::= { pSlot1Table 1 }
		
		
		PSlot1Entry ::= 
			SEQUENCE {
				pSlot1Description
					DescriptionString,
				pSlot1Desc0
					DescriptionString,
				pSlot1Desc1
					DescriptionString,
				pSlot1Desc2
					DescriptionString,
				pSlot1Desc3
					DescriptionString,
				pSlot1Desc4
					DescriptionString,
				pSlot1Desc5
					DescriptionString,
				pSlot1Configured
					Configured,
				pSlot1SendEmail
					Boolean,
				pSlot1SendSNMPTrap
					Boolean,
				pSlot1IpAddress
					IpAddress,
				pSlot1Level0
					Level,
				pSlot1Level1
					Level,
				pSlot1Level2
					Level,
				pSlot1Level3
					Level,
				pSlot1Level4
					Level,
				pSlot1Level5
					Level,
				pSlot1ReadPeriod
					Integer32,
				pSlot1Thresh0
					DescriptionString,
				pSlot1Thresh1
					DescriptionString,
				pSlot1Thresh2
					DescriptionString,
				pSlot1Thresh3
					DescriptionString,
				pSlot1Thresh4
					DescriptionString,
				pSlot1Thresh5
					DescriptionString,
				pSlot1ContactStyle
					ContactStyle,
				pSlot1Units
					DescriptionString,
				pSlot1OutputMode
					OutputMode,
				pSlot1OutputState
					OutputState,
				pSlot1OutputAuto
					Integer32,
				pSlot1BaudRate
					BaudRate,
				pSlot1DataBits
					DataBits,
				pSlot1Parity
					Parity,
				pSlot1StopBits
					StopBits,
				pSlot1Protocol
					Protocol,
				pSlot1SerialRTS
					SerialRTS,
				pSlot1SerialCTS
					SerialCTS,
				pSlot1LiveDescription
					DescriptionString,
				pSlot1LiveLevel
					DescriptionString,
				pSlot1LiveRaw
					DescriptionString,
				pSlot1LiveTime
					DescriptionString,
				pSlot1Present
					Boolean,
				pSlot1OutputAutoPkg
					Integer32,
				pSlot1VoltageRange
					VoltageRange,
				pSlot1IPPortNum
					Integer32,
				pSlot1IOFormat
					IOFormat,
				pSlot1PortType
					PortType,
				pSlot1TL1SID
					DescriptionString,
				pSlot1TL1COND
					DescriptionString,
				pSlot1TL1Eqpt
					DescriptionString,
				pSlot1TL1Env
					Boolean,
				pSlot1TL1Srveff
					TL1Srveff,
				pSlot1TL1Locn
					TL1Locn,
				pSlot1TL1Dirn
					TL1Dirn,
				pSlot1SensorType
					SensorType,
				pSlot1Index
					Integer32 (1..32)
			}
		
		-- 1.3.6.1.4.1.994.3.4.7.18.1.3
		pSlot1Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot1Entry 3 }
		
		
		-- 1.3.6.1.4.1.994.3.4.7.18.1.4
		pSlot1Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot1Entry 4 }
		
		
		-- 1.3.6.1.4.1.994.3.4.7.18.1.5
		pSlot1Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot1Entry 5 }
		
		
		-- 1.3.6.1.4.1.994.3.4.7.18.1.6
		pSlot1Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot1Entry 6 }
		
		
		-- 1.3.6.1.4.1.994.3.4.7.18.1.7
		pSlot1Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot1Entry 7 }
		
		
		-- 1.3.6.1.4.1.994.3.4.7.18.1.8
		pSlot1Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot1Entry 8 }
		
		
		-- 1.3.6.1.4.1.994.3.4.7.18.1.9
		pSlot1Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot1Entry 9 }
		
		
		-- 1.3.6.1.4.1.994.3.4.7.18.1.10
		pSlot1Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot1Entry 10 }
		
		
		-- 1.3.6.1.4.1.994.3.4.7.18.1.11
		pSlot1SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot1Entry 11 }
		
		
		-- 1.3.6.1.4.1.994.3.4.7.18.1.12
		pSlot1SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot1Entry 12 }
		
		
		-- 1.3.6.1.4.1.994.3.4.7.18.1.14
		pSlot1IpAddress OBJECT-TYPE
			SYNTAX IpAddress
			MAX-ACCESS read-write
			STATUS current
			DESCRIPTION
				"This field is used in the following card types:
				serial-ports - IP Address of the target device."
			::= { pSlot1Entry 14 }
		
		
		-- 1.3.6.1.4.1.994.3.4.7.18.1.17
		pSlot1Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot1Entry 17 }
		
		
		-- 1.3.6.1.4.1.994.3.4.7.18.1.18
		pSlot1Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot1Entry 18 }
		
		
		-- 1.3.6.1.4.1.994.3.4.7.18.1.19
		pSlot1Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot1Entry 19 }
		
		
		-- 1.3.6.1.4.1.994.3.4.7.18.1.20
		pSlot1Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot1Entry 20 }
		
		
		-- 1.3.6.1.4.1.994.3.4.7.18.1.21
		pSlot1Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot1Entry 21 }
		
		
		-- 1.3.6.1.4.1.994.3.4.7.18.1.22
		pSlot1Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot1Entry 22 }
		
		
		-- 1.3.6.1.4.1.994.3.4.7.18.1.23
		pSlot1ReadPeriod OBJECT-TYPE
			SYNTAX Integer32
			MAX-ACCESS read-write
			STATUS current
			DESCRIPTION
				"This field is used in the following card types:
				serial-ports - Inactivity timeout (in minutes)."
			::= { pSlot1Entry 23 }
		
		
		-- 1.3.6.1.4.1.994.3.4.7.18.1.28
		pSlot1Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot1Entry 28 }
		
		
		-- 1.3.6.1.4.1.994.3.4.7.18.1.29
		pSlot1Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot1Entry 29 }
		
		
		-- 1.3.6.1.4.1.994.3.4.7.18.1.30
		pSlot1Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot1Entry 30 }
		
		
		-- 1.3.6.1.4.1.994.3.4.7.18.1.31
		pSlot1Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot1Entry 31 }
		
		
		-- 1.3.6.1.4.1.994.3.4.7.18.1.32
		pSlot1Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot1Entry 32 }
		
		
		-- 1.3.6.1.4.1.994.3.4.7.18.1.33
		pSlot1Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot1Entry 33 }
		
		
		-- 1.3.6.1.4.1.994.3.4.7.18.1.44
		pSlot1ContactStyle OBJECT-TYPE
			SYNTAX ContactStyle
			MAX-ACCESS read-write
			STATUS current
			DESCRIPTION
				"This field is used in the following card types:
				discrete-inputs - Determines the type of contact."
			::= { pSlot1Entry 44 }
		
		
		-- 1.3.6.1.4.1.994.3.4.7.18.1.46
		pSlot1Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot1Entry 46 }
		
		
		-- 1.3.6.1.4.1.994.3.4.7.18.1.47
		pSlot1OutputMode OBJECT-TYPE
			SYNTAX OutputMode
			MAX-ACCESS read-write
			STATUS current
			DESCRIPTION
				"This field is used in the following card types:
				discrete-outputs - Defines the different ways a control point can be activated."
			::= { pSlot1Entry 47 }
		
		
		-- 1.3.6.1.4.1.994.3.4.7.18.1.48
		pSlot1OutputState OBJECT-TYPE
			SYNTAX OutputState
			MAX-ACCESS read-write
			STATUS current
			DESCRIPTION
				"This field is used in the following card types:
				discrete-outputs - A value of 0 will open the control point.
				A value of 1 will close the control point."
			::= { pSlot1Entry 48 }
		
		
		-- 1.3.6.1.4.1.994.3.4.7.18.1.49
		pSlot1OutputAuto OBJECT-TYPE
			SYNTAX Integer32
			MAX-ACCESS read-write
			STATUS current
			DESCRIPTION
				"This field is used in the following card types:
				discrete-outputs - When this control point is opened, this alarm point will change state 
				to the on state."
			::= { pSlot1Entry 49 }
		
		
		-- 1.3.6.1.4.1.994.3.4.7.18.1.57
		pSlot1BaudRate OBJECT-TYPE
			SYNTAX BaudRate
			MAX-ACCESS read-write
			STATUS current
			DESCRIPTION
				"This field is used in the following card types:
				serial-ports - Baud rate of the serial port."
			::= { pSlot1Entry 57 }
		
		
		-- 1.3.6.1.4.1.994.3.4.7.18.1.58
		pSlot1DataBits OBJECT-TYPE
			SYNTAX DataBits
			MAX-ACCESS read-write
			STATUS current
			DESCRIPTION
				"This field is used in the following card types:
				serial-ports - Number of data bit for the serial port."
			::= { pSlot1Entry 58 }
		
		
		-- 1.3.6.1.4.1.994.3.4.7.18.1.59
		pSlot1Parity OBJECT-TYPE
			SYNTAX Parity
			MAX-ACCESS read-write
			STATUS current
			DESCRIPTION
				"This field is used in the following card types:
				serial-ports - Parity of the serial port."
			::= { pSlot1Entry 59 }
		
		
		-- 1.3.6.1.4.1.994.3.4.7.18.1.60
		pSlot1StopBits OBJECT-TYPE
			SYNTAX StopBits
			MAX-ACCESS read-write
			STATUS current
			DESCRIPTION
				"This field is used in the following card types:
				serial-ports - Number of stop bits for the serial port."
			::= { pSlot1Entry 60 }
		
		
		-- 1.3.6.1.4.1.994.3.4.7.18.1.61
		pSlot1Protocol OBJECT-TYPE
			SYNTAX Protocol
			MAX-ACCESS read-write
			STATUS current
			DESCRIPTION
				"This field is used in the following card types:
				serial-ports - Protocol the serial port is speaking."
			::= { pSlot1Entry 61 }
		
		
		-- 1.3.6.1.4.1.994.3.4.7.18.1.62
		pSlot1SerialRTS OBJECT-TYPE
			SYNTAX SerialRTS
			MAX-ACCESS read-write
			STATUS current
			DESCRIPTION
				"This field is used in the following card types:
				serial-ports - Request To Send (RTS) setting for the serial port."
			::= { pSlot1Entry 62 }
		
		
		-- 1.3.6.1.4.1.994.3.4.7.18.1.63
		pSlot1SerialCTS OBJECT-TYPE
			SYNTAX SerialCTS
			MAX-ACCESS read-write
			STATUS current
			DESCRIPTION
				"This field is used in the following card types:
				serial-ports - Clear To Send (CTS) setting for the serial port."
			::= { pSlot1Entry 63 }
		
		
		-- 1.3.6.1.4.1.994.3.4.7.18.1.64
		pSlot1LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot1Entry 64 }
		
		
		-- 1.3.6.1.4.1.994.3.4.7.18.1.65
		pSlot1LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot1Entry 65 }
		
		
		-- 1.3.6.1.4.1.994.3.4.7.18.1.66
		pSlot1LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot1Entry 66 }
		
		
		-- 1.3.6.1.4.1.994.3.4.7.18.1.67
		pSlot1LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot1Entry 67 }
		
		
		-- 1.3.6.1.4.1.994.3.4.7.18.1.68
		pSlot1Present OBJECT-TYPE
			SYNTAX Boolean
			MAX-ACCESS read-only
			STATUS current
			DESCRIPTION
				"This field is used in the following card types:
				serial-ports - If set to true, the serial port exists.
				If set to false the serial port does not exist."
			::= { pSlot1Entry 68 }
		
		
		-- 1.3.6.1.4.1.994.3.4.7.18.1.71
		pSlot1OutputAutoPkg OBJECT-TYPE
			SYNTAX Integer32
			MAX-ACCESS read-write
			STATUS current
			DESCRIPTION
				"This field is used in the following card types:
				discrete-outputs - When this control point is opened, this is the package that the alarm
				point is located."
			::= { pSlot1Entry 71 }
		
		
		-- 1.3.6.1.4.1.994.3.4.7.18.1.72
		pSlot1VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot1Entry 72 }
		
		
		-- 1.3.6.1.4.1.994.3.4.7.18.1.73
		pSlot1IPPortNum OBJECT-TYPE
			SYNTAX Integer32
			MAX-ACCESS read-write
			STATUS current
			DESCRIPTION
				"This field is used in the following card types:
				serial-ports - IP port number of the target device."
			::= { pSlot1Entry 73 }
		
		
		-- 1.3.6.1.4.1.994.3.4.7.18.1.75
		pSlot1IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot1Entry 75 }
		
		
		-- 1.3.6.1.4.1.994.3.4.7.18.1.76
		pSlot1PortType OBJECT-TYPE
			SYNTAX PortType
			MAX-ACCESS read-only
			STATUS current
			DESCRIPTION
				"This field is used in the following card types:
				serial-ports - The type of serial port."
			::= { pSlot1Entry 76 }
		
		
		-- 1.3.6.1.4.1.994.3.4.7.18.1.116
		pSlot1TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot1Entry 116 }
		
		
		-- 1.3.6.1.4.1.994.3.4.7.18.1.117
		pSlot1TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot1Entry 117 }
		
		
		-- 1.3.6.1.4.1.994.3.4.7.18.1.118
		pSlot1TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot1Entry 118 }
		
		
		-- 1.3.6.1.4.1.994.3.4.7.18.1.119
		pSlot1TL1Env OBJECT-TYPE
			SYNTAX Boolean
			MAX-ACCESS read-write
			STATUS current
			DESCRIPTION
				"This field is used in the following card types:
				discrete-inputs - 
				onboard-sensors - 
				analog-Inputs - 
				analog-Sensors - "
			::= { pSlot1Entry 119 }
		
		
		-- 1.3.6.1.4.1.994.3.4.7.18.1.120
		pSlot1TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot1Entry 120 }
		
		
		-- 1.3.6.1.4.1.994.3.4.7.18.1.121
		pSlot1TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot1Entry 121 }
		
		
		-- 1.3.6.1.4.1.994.3.4.7.18.1.122
		pSlot1TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot1Entry 122 }
		
		
		-- 1.3.6.1.4.1.994.3.4.7.18.1.131
		pSlot1SensorType OBJECT-TYPE
			SYNTAX SensorType
			MAX-ACCESS read-write
			STATUS current
			DESCRIPTION
				"This field is used in the following card types:
				analog-Inputs - The type of sensor.
				analog-Sensors - The type of sensor."
			::= { pSlot1Entry 131 }
		
		
		-- 1.3.6.1.4.1.994.3.4.7.18.1.999
		pSlot1Index OBJECT-TYPE
			SYNTAX Integer32 (1..32)
			MAX-ACCESS read-only
			STATUS current
			DESCRIPTION
				"Index."
			::= { pSlot1Entry 999 }


-- Slot2 table
		
		-- 1.3.6.1.4.1.994.3.4.7.19
		pSlot2Table OBJECT-TYPE
			SYNTAX SEQUENCE OF PSlot2Entry
			MAX-ACCESS not-accessible
			STATUS current
			DESCRIPTION
				"Table for configuration of Slot2"
			::= { configuration 19 }
		
		
		-- 1.3.6.1.4.1.994.3.4.7.19.1
		pSlot2Entry OBJECT-TYPE
			SYNTAX PSlot2Entry
			MAX-ACCESS not-accessible
			STATUS current
			DESCRIPTION
				"Entry for configuration table of Slot2"
				INDEX { pSlot2Index }
			::= { pSlot2Table 1 }
		
		
		PSlot2Entry ::= 
			SEQUENCE {
				pSlot2Description
					DescriptionString,
				pSlot2Desc0
					DescriptionString,
				pSlot2Desc1
					DescriptionString,
				pSlot2Desc2
					DescriptionString,
				pSlot2Desc3
					DescriptionString,
				pSlot2Desc4
					DescriptionString,
				pSlot2Desc5
					DescriptionString,
				pSlot2Configured
					Configured,
				pSlot2SendEmail
					Boolean,
				pSlot2SendSNMPTrap
					Boolean,
				pSlot2IpAddress
					IpAddress,
				pSlot2Level0
					Level,
				pSlot2Level1
					Level,
				pSlot2Level2
					Level,
				pSlot2Level3
					Level,
				pSlot2Level4
					Level,
				pSlot2Level5
					Level,
				pSlot2ReadPeriod
					Integer32,
				pSlot2Thresh0
					DescriptionString,
				pSlot2Thresh1
					DescriptionString,
				pSlot2Thresh2
					DescriptionString,
				pSlot2Thresh3
					DescriptionString,
				pSlot2Thresh4
					DescriptionString,
				pSlot2Thresh5
					DescriptionString,
				pSlot2ContactStyle
					ContactStyle,
				pSlot2Units
					DescriptionString,
				pSlot2OutputMode
					OutputMode,
				pSlot2OutputState
					OutputState,
				pSlot2OutputAuto
					Integer32,
				pSlot2BaudRate
					BaudRate,
				pSlot2DataBits
					DataBits,
				pSlot2Parity
					Parity,
				pSlot2StopBits
					StopBits,
				pSlot2Protocol
					Protocol,
				pSlot2SerialRTS
					SerialRTS,
				pSlot2SerialCTS
					SerialCTS,
				pSlot2LiveDescription
					DescriptionString,
				pSlot2LiveLevel
					DescriptionString,
				pSlot2LiveRaw
					DescriptionString,
				pSlot2LiveTime
					DescriptionString,
				pSlot2Present
					Boolean,
				pSlot2OutputAutoPkg
					Integer32,
				pSlot2VoltageRange
					VoltageRange,
				pSlot2IPPortNum
					Integer32,
				pSlot2IOFormat
					IOFormat,
				pSlot2PortType
					PortType,
				pSlot2TL1SID
					DescriptionString,
				pSlot2TL1COND
					DescriptionString,
				pSlot2TL1Eqpt
					DescriptionString,
				pSlot2TL1Env
					Boolean,
				pSlot2TL1Srveff
					TL1Srveff,
				pSlot2TL1Locn
					TL1Locn,
				pSlot2TL1Dirn
					TL1Dirn,
				pSlot2SensorType
					SensorType,
				pSlot2Index
					Integer32 (1..32)
			}
		
		-- 1.3.6.1.4.1.994.3.4.7.19.1.3
		pSlot2Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot2Entry 3 }
		
		
		-- 1.3.6.1.4.1.994.3.4.7.19.1.4
		pSlot2Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot2Entry 4 }
		
		
		-- 1.3.6.1.4.1.994.3.4.7.19.1.5
		pSlot2Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot2Entry 5 }
		
		
		-- 1.3.6.1.4.1.994.3.4.7.19.1.6
		pSlot2Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot2Entry 6 }
		
		
		-- 1.3.6.1.4.1.994.3.4.7.19.1.7
		pSlot2Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot2Entry 7 }
		
		
		-- 1.3.6.1.4.1.994.3.4.7.19.1.8
		pSlot2Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot2Entry 8 }
		
		
		-- 1.3.6.1.4.1.994.3.4.7.19.1.9
		pSlot2Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot2Entry 9 }
		
		
		-- 1.3.6.1.4.1.994.3.4.7.19.1.10
		pSlot2Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot2Entry 10 }
		
		
		-- 1.3.6.1.4.1.994.3.4.7.19.1.11
		pSlot2SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot2Entry 11 }
		
		
		-- 1.3.6.1.4.1.994.3.4.7.19.1.12
		pSlot2SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot2Entry 12 }
		
		
		-- 1.3.6.1.4.1.994.3.4.7.19.1.14
		pSlot2IpAddress OBJECT-TYPE
			SYNTAX IpAddress
			MAX-ACCESS read-write
			STATUS current
			DESCRIPTION
				"This field is used in the following card types:
				serial-ports - IP Address of the target device."
			::= { pSlot2Entry 14 }
		
		
		-- 1.3.6.1.4.1.994.3.4.7.19.1.17
		pSlot2Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot2Entry 17 }
		
		
		-- 1.3.6.1.4.1.994.3.4.7.19.1.18
		pSlot2Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot2Entry 18 }
		
		
		-- 1.3.6.1.4.1.994.3.4.7.19.1.19
		pSlot2Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot2Entry 19 }
		
		
		-- 1.3.6.1.4.1.994.3.4.7.19.1.20
		pSlot2Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot2Entry 20 }
		
		
		-- 1.3.6.1.4.1.994.3.4.7.19.1.21
		pSlot2Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot2Entry 21 }
		
		
		-- 1.3.6.1.4.1.994.3.4.7.19.1.22
		pSlot2Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot2Entry 22 }
		
		
		-- 1.3.6.1.4.1.994.3.4.7.19.1.23
		pSlot2ReadPeriod OBJECT-TYPE
			SYNTAX Integer32
			MAX-ACCESS read-write
			STATUS current
			DESCRIPTION
				"This field is used in the following card types:
				serial-ports - Inactivity timeout (in minutes)."
			::= { pSlot2Entry 23 }
		
		
		-- 1.3.6.1.4.1.994.3.4.7.19.1.28
		pSlot2Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot2Entry 28 }
		
		
		-- 1.3.6.1.4.1.994.3.4.7.19.1.29
		pSlot2Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot2Entry 29 }
		
		
		-- 1.3.6.1.4.1.994.3.4.7.19.1.30
		pSlot2Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot2Entry 30 }
		
		
		-- 1.3.6.1.4.1.994.3.4.7.19.1.31
		pSlot2Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot2Entry 31 }
		
		
		-- 1.3.6.1.4.1.994.3.4.7.19.1.32
		pSlot2Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot2Entry 32 }
		
		
		-- 1.3.6.1.4.1.994.3.4.7.19.1.33
		pSlot2Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot2Entry 33 }
		
		
		-- 1.3.6.1.4.1.994.3.4.7.19.1.44
		pSlot2ContactStyle OBJECT-TYPE
			SYNTAX ContactStyle
			MAX-ACCESS read-write
			STATUS current
			DESCRIPTION
				"This field is used in the following card types:
				discrete-inputs - Determines the type of contact."
			::= { pSlot2Entry 44 }
		
		
		-- 1.3.6.1.4.1.994.3.4.7.19.1.46
		pSlot2Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot2Entry 46 }
		
		
		-- 1.3.6.1.4.1.994.3.4.7.19.1.47
		pSlot2OutputMode OBJECT-TYPE
			SYNTAX OutputMode
			MAX-ACCESS read-write
			STATUS current
			DESCRIPTION
				"This field is used in the following card types:
				discrete-outputs - Defines the different ways a control point can be activated."
			::= { pSlot2Entry 47 }
		
		
		-- 1.3.6.1.4.1.994.3.4.7.19.1.48
		pSlot2OutputState OBJECT-TYPE
			SYNTAX OutputState
			MAX-ACCESS read-write
			STATUS current
			DESCRIPTION
				"This field is used in the following card types:
				discrete-outputs - A value of 0 will open the control point.
				A value of 1 will close the control point."
			::= { pSlot2Entry 48 }
		
		
		-- 1.3.6.1.4.1.994.3.4.7.19.1.49
		pSlot2OutputAuto OBJECT-TYPE
			SYNTAX Integer32
			MAX-ACCESS read-write
			STATUS current
			DESCRIPTION
				"This field is used in the following card types:
				discrete-outputs - When this control point is opened, this alarm point will change state 
				to the on state."
			::= { pSlot2Entry 49 }
		
		
		-- 1.3.6.1.4.1.994.3.4.7.19.1.57
		pSlot2BaudRate OBJECT-TYPE
			SYNTAX BaudRate
			MAX-ACCESS read-write
			STATUS current
			DESCRIPTION
				"This field is used in the following card types:
				serial-ports - Baud rate of the serial port."
			::= { pSlot2Entry 57 }
		
		
		-- 1.3.6.1.4.1.994.3.4.7.19.1.58
		pSlot2DataBits OBJECT-TYPE
			SYNTAX DataBits
			MAX-ACCESS read-write
			STATUS current
			DESCRIPTION
				"This field is used in the following card types:
				serial-ports - Number of data bit for the serial port."
			::= { pSlot2Entry 58 }
		
		
		-- 1.3.6.1.4.1.994.3.4.7.19.1.59
		pSlot2Parity OBJECT-TYPE
			SYNTAX Parity
			MAX-ACCESS read-write
			STATUS current
			DESCRIPTION
				"This field is used in the following card types:
				serial-ports - Parity of the serial port."
			::= { pSlot2Entry 59 }
		
		
		-- 1.3.6.1.4.1.994.3.4.7.19.1.60
		pSlot2StopBits OBJECT-TYPE
			SYNTAX StopBits
			MAX-ACCESS read-write
			STATUS current
			DESCRIPTION
				"This field is used in the following card types:
				serial-ports - Number of stop bits for the serial port."
			::= { pSlot2Entry 60 }
		
		
		-- 1.3.6.1.4.1.994.3.4.7.19.1.61
		pSlot2Protocol OBJECT-TYPE
			SYNTAX Protocol
			MAX-ACCESS read-write
			STATUS current
			DESCRIPTION
				"This field is used in the following card types:
				serial-ports - Protocol the serial port is speaking."
			::= { pSlot2Entry 61 }
		
		
		-- 1.3.6.1.4.1.994.3.4.7.19.1.62
		pSlot2SerialRTS OBJECT-TYPE
			SYNTAX SerialRTS
			MAX-ACCESS read-write
			STATUS current
			DESCRIPTION
				"This field is used in the following card types:
				serial-ports - Request To Send (RTS) setting for the serial port."
			::= { pSlot2Entry 62 }
		
		
		-- 1.3.6.1.4.1.994.3.4.7.19.1.63
		pSlot2SerialCTS OBJECT-TYPE
			SYNTAX SerialCTS
			MAX-ACCESS read-write
			STATUS current
			DESCRIPTION
				"This field is used in the following card types:
				serial-ports - Clear To Send (CTS) setting for the serial port."
			::= { pSlot2Entry 63 }
		
		
		-- 1.3.6.1.4.1.994.3.4.7.19.1.64
		pSlot2LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot2Entry 64 }
		
		
		-- 1.3.6.1.4.1.994.3.4.7.19.1.65
		pSlot2LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot2Entry 65 }
		
		
		-- 1.3.6.1.4.1.994.3.4.7.19.1.66
		pSlot2LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot2Entry 66 }
		
		
		-- 1.3.6.1.4.1.994.3.4.7.19.1.67
		pSlot2LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot2Entry 67 }
		
		
		-- 1.3.6.1.4.1.994.3.4.7.19.1.68
		pSlot2Present OBJECT-TYPE
			SYNTAX Boolean
			MAX-ACCESS read-only
			STATUS current
			DESCRIPTION
				"This field is used in the following card types:
				serial-ports - If set to true, the serial port exists.
				If set to false the serial port does not exist."
			::= { pSlot2Entry 68 }
		
		
		-- 1.3.6.1.4.1.994.3.4.7.19.1.71
		pSlot2OutputAutoPkg OBJECT-TYPE
			SYNTAX Integer32
			MAX-ACCESS read-write
			STATUS current
			DESCRIPTION
				"This field is used in the following card types:
				discrete-outputs - When this control point is opened, this is the package that the alarm
				point is located."
			::= { pSlot2Entry 71 }
		
		
		-- 1.3.6.1.4.1.994.3.4.7.19.1.72
		pSlot2VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot2Entry 72 }
		
		
		-- 1.3.6.1.4.1.994.3.4.7.19.1.73
		pSlot2IPPortNum OBJECT-TYPE
			SYNTAX Integer32
			MAX-ACCESS read-write
			STATUS current
			DESCRIPTION
				"This field is used in the following card types:
				serial-ports - IP port number of the target device."
			::= { pSlot2Entry 73 }
		
		
		-- 1.3.6.1.4.1.994.3.4.7.19.1.75
		pSlot2IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot2Entry 75 }
		
		
		-- 1.3.6.1.4.1.994.3.4.7.19.1.76
		pSlot2PortType OBJECT-TYPE
			SYNTAX PortType
			MAX-ACCESS read-only
			STATUS current
			DESCRIPTION
				"This field is used in the following card types:
				serial-ports - The type of serial port."
			::= { pSlot2Entry 76 }
		
		
		-- 1.3.6.1.4.1.994.3.4.7.19.1.116
		pSlot2TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot2Entry 116 }
		
		
		-- 1.3.6.1.4.1.994.3.4.7.19.1.117
		pSlot2TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot2Entry 117 }
		
		
		-- 1.3.6.1.4.1.994.3.4.7.19.1.118
		pSlot2TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot2Entry 118 }
		
		
		-- 1.3.6.1.4.1.994.3.4.7.19.1.119
		pSlot2TL1Env OBJECT-TYPE
			SYNTAX Boolean
			MAX-ACCESS read-write
			STATUS current
			DESCRIPTION
				"This field is used in the following card types:
				discrete-inputs - 
				onboard-sensors - 
				analog-Inputs - 
				analog-Sensors - "
			::= { pSlot2Entry 119 }
		
		
		-- 1.3.6.1.4.1.994.3.4.7.19.1.120
		pSlot2TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot2Entry 120 }
		
		
		-- 1.3.6.1.4.1.994.3.4.7.19.1.121
		pSlot2TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot2Entry 121 }
		
		
		-- 1.3.6.1.4.1.994.3.4.7.19.1.122
		pSlot2TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot2Entry 122 }
		
		
		-- 1.3.6.1.4.1.994.3.4.7.19.1.131
		pSlot2SensorType OBJECT-TYPE
			SYNTAX SensorType
			MAX-ACCESS read-write
			STATUS current
			DESCRIPTION
				"This field is used in the following card types:
				analog-Inputs - The type of sensor.
				analog-Sensors - The type of sensor."
			::= { pSlot2Entry 131 }
		
		
		-- 1.3.6.1.4.1.994.3.4.7.19.1.999
		pSlot2Index OBJECT-TYPE
			SYNTAX Integer32 (1..32)
			MAX-ACCESS read-only
			STATUS current
			DESCRIPTION
				"Index."
			::= { pSlot2Entry 999 }


-- Slot3 table
		
		-- 1.3.6.1.4.1.994.3.4.7.20
		pSlot3Table OBJECT-TYPE
			SYNTAX SEQUENCE OF PSlot3Entry
			MAX-ACCESS not-accessible
			STATUS current
			DESCRIPTION
				"Table for configuration of Slot3"
			::= { configuration 20 }
		
		
		-- 1.3.6.1.4.1.994.3.4.7.20.1
		pSlot3Entry OBJECT-TYPE
			SYNTAX PSlot3Entry
			MAX-ACCESS not-accessible
			STATUS current
			DESCRIPTION
				"Entry for configuration table of Slot3"
				INDEX { pSlot3Index }
			::= { pSlot3Table 1 }
		
		
		PSlot3Entry ::= 
			SEQUENCE {
				pSlot3Description
					DescriptionString,
				pSlot3Desc0
					DescriptionString,
				pSlot3Desc1
					DescriptionString,
				pSlot3Desc2
					DescriptionString,
				pSlot3Desc3
					DescriptionString,
				pSlot3Desc4
					DescriptionString,
				pSlot3Desc5
					DescriptionString,
				pSlot3Configured
					Configured,
				pSlot3SendEmail
					Boolean,
				pSlot3SendSNMPTrap
					Boolean,
				pSlot3IpAddress
					IpAddress,
				pSlot3Level0
					Level,
				pSlot3Level1
					Level,
				pSlot3Level2
					Level,
				pSlot3Level3
					Level,
				pSlot3Level4
					Level,
				pSlot3Level5
					Level,
				pSlot3ReadPeriod
					Integer32,
				pSlot3Thresh0
					DescriptionString,
				pSlot3Thresh1
					DescriptionString,
				pSlot3Thresh2
					DescriptionString,
				pSlot3Thresh3
					DescriptionString,
				pSlot3Thresh4
					DescriptionString,
				pSlot3Thresh5
					DescriptionString,
				pSlot3ContactStyle
					ContactStyle,
				pSlot3Units
					DescriptionString,
				pSlot3OutputMode
					OutputMode,
				pSlot3OutputState
					OutputState,
				pSlot3OutputAuto
					Integer32,
				pSlot3BaudRate
					BaudRate,
				pSlot3DataBits
					DataBits,
				pSlot3Parity
					Parity,
				pSlot3StopBits
					StopBits,
				pSlot3Protocol
					Protocol,
				pSlot3SerialRTS
					SerialRTS,
				pSlot3SerialCTS
					SerialCTS,
				pSlot3LiveDescription
					DescriptionString,
				pSlot3LiveLevel
					DescriptionString,
				pSlot3LiveRaw
					DescriptionString,
				pSlot3LiveTime
					DescriptionString,
				pSlot3Present
					Boolean,
				pSlot3OutputAutoPkg
					Integer32,
				pSlot3VoltageRange
					VoltageRange,
				pSlot3IPPortNum
					Integer32,
				pSlot3IOFormat
					IOFormat,
				pSlot3PortType
					PortType,
				pSlot3TL1SID
					DescriptionString,
				pSlot3TL1COND
					DescriptionString,
				pSlot3TL1Eqpt
					DescriptionString,
				pSlot3TL1Env
					Boolean,
				pSlot3TL1Srveff
					TL1Srveff,
				pSlot3TL1Locn
					TL1Locn,
				pSlot3TL1Dirn
					TL1Dirn,
				pSlot3SensorType
					SensorType,
				pSlot3Index
					Integer32 (1..32)
			}
		
		-- 1.3.6.1.4.1.994.3.4.7.20.1.3
		pSlot3Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot3Entry 3 }
		
		
		-- 1.3.6.1.4.1.994.3.4.7.20.1.4
		pSlot3Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot3Entry 4 }
		
		
		-- 1.3.6.1.4.1.994.3.4.7.20.1.5
		pSlot3Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot3Entry 5 }
		
		
		-- 1.3.6.1.4.1.994.3.4.7.20.1.6
		pSlot3Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot3Entry 6 }
		
		
		-- 1.3.6.1.4.1.994.3.4.7.20.1.7
		pSlot3Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot3Entry 7 }
		
		
		-- 1.3.6.1.4.1.994.3.4.7.20.1.8
		pSlot3Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot3Entry 8 }
		
		
		-- 1.3.6.1.4.1.994.3.4.7.20.1.9
		pSlot3Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot3Entry 9 }
		
		
		-- 1.3.6.1.4.1.994.3.4.7.20.1.10
		pSlot3Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot3Entry 10 }
		
		
		-- 1.3.6.1.4.1.994.3.4.7.20.1.11
		pSlot3SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot3Entry 11 }
		
		
		-- 1.3.6.1.4.1.994.3.4.7.20.1.12
		pSlot3SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot3Entry 12 }
		
		
		-- 1.3.6.1.4.1.994.3.4.7.20.1.14
		pSlot3IpAddress OBJECT-TYPE
			SYNTAX IpAddress
			MAX-ACCESS read-write
			STATUS current
			DESCRIPTION
				"This field is used in the following card types:
				serial-ports - IP Address of the target device."
			::= { pSlot3Entry 14 }
		
		
		-- 1.3.6.1.4.1.994.3.4.7.20.1.17
		pSlot3Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot3Entry 17 }
		
		
		-- 1.3.6.1.4.1.994.3.4.7.20.1.18
		pSlot3Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot3Entry 18 }
		
		
		-- 1.3.6.1.4.1.994.3.4.7.20.1.19
		pSlot3Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot3Entry 19 }
		
		
		-- 1.3.6.1.4.1.994.3.4.7.20.1.20
		pSlot3Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot3Entry 20 }
		
		
		-- 1.3.6.1.4.1.994.3.4.7.20.1.21
		pSlot3Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot3Entry 21 }
		
		
		-- 1.3.6.1.4.1.994.3.4.7.20.1.22
		pSlot3Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot3Entry 22 }
		
		
		-- 1.3.6.1.4.1.994.3.4.7.20.1.23
		pSlot3ReadPeriod OBJECT-TYPE
			SYNTAX Integer32
			MAX-ACCESS read-write
			STATUS current
			DESCRIPTION
				"This field is used in the following card types:
				serial-ports - Inactivity timeout (in minutes)."
			::= { pSlot3Entry 23 }
		
		
		-- 1.3.6.1.4.1.994.3.4.7.20.1.28
		pSlot3Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot3Entry 28 }
		
		
		-- 1.3.6.1.4.1.994.3.4.7.20.1.29
		pSlot3Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot3Entry 29 }
		
		
		-- 1.3.6.1.4.1.994.3.4.7.20.1.30
		pSlot3Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot3Entry 30 }
		
		
		-- 1.3.6.1.4.1.994.3.4.7.20.1.31
		pSlot3Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot3Entry 31 }
		
		
		-- 1.3.6.1.4.1.994.3.4.7.20.1.32
		pSlot3Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot3Entry 32 }
		
		
		-- 1.3.6.1.4.1.994.3.4.7.20.1.33
		pSlot3Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot3Entry 33 }
		
		
		-- 1.3.6.1.4.1.994.3.4.7.20.1.44
		pSlot3ContactStyle OBJECT-TYPE
			SYNTAX ContactStyle
			MAX-ACCESS read-write
			STATUS current
			DESCRIPTION
				"This field is used in the following card types:
				discrete-inputs - Determines the type of contact."
			::= { pSlot3Entry 44 }
		
		
		-- 1.3.6.1.4.1.994.3.4.7.20.1.46
		pSlot3Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot3Entry 46 }
		
		
		-- 1.3.6.1.4.1.994.3.4.7.20.1.47
		pSlot3OutputMode OBJECT-TYPE
			SYNTAX OutputMode
			MAX-ACCESS read-write
			STATUS current
			DESCRIPTION
				"This field is used in the following card types:
				discrete-outputs - Defines the different ways a control point can be activated."
			::= { pSlot3Entry 47 }
		
		
		-- 1.3.6.1.4.1.994.3.4.7.20.1.48
		pSlot3OutputState OBJECT-TYPE
			SYNTAX OutputState
			MAX-ACCESS read-write
			STATUS current
			DESCRIPTION
				"This field is used in the following card types:
				discrete-outputs - A value of 0 will open the control point.
				A value of 1 will close the control point."
			::= { pSlot3Entry 48 }
		
		
		-- 1.3.6.1.4.1.994.3.4.7.20.1.49
		pSlot3OutputAuto OBJECT-TYPE
			SYNTAX Integer32
			MAX-ACCESS read-write
			STATUS current
			DESCRIPTION
				"This field is used in the following card types:
				discrete-outputs - When this control point is opened, this alarm point will change state 
				to the on state."
			::= { pSlot3Entry 49 }
		
		
		-- 1.3.6.1.4.1.994.3.4.7.20.1.57
		pSlot3BaudRate OBJECT-TYPE
			SYNTAX BaudRate
			MAX-ACCESS read-write
			STATUS current
			DESCRIPTION
				"This field is used in the following card types:
				serial-ports - Baud rate of the serial port."
			::= { pSlot3Entry 57 }
		
		
		-- 1.3.6.1.4.1.994.3.4.7.20.1.58
		pSlot3DataBits OBJECT-TYPE
			SYNTAX DataBits
			MAX-ACCESS read-write
			STATUS current
			DESCRIPTION
				"This field is used in the following card types:
				serial-ports - Number of data bit for the serial port."
			::= { pSlot3Entry 58 }
		
		
		-- 1.3.6.1.4.1.994.3.4.7.20.1.59
		pSlot3Parity OBJECT-TYPE
			SYNTAX Parity
			MAX-ACCESS read-write
			STATUS current
			DESCRIPTION
				"This field is used in the following card types:
				serial-ports - Parity of the serial port."
			::= { pSlot3Entry 59 }
		
		
		-- 1.3.6.1.4.1.994.3.4.7.20.1.60
		pSlot3StopBits OBJECT-TYPE
			SYNTAX StopBits
			MAX-ACCESS read-write
			STATUS current
			DESCRIPTION
				"This field is used in the following card types:
				serial-ports - Number of stop bits for the serial port."
			::= { pSlot3Entry 60 }
		
		
		-- 1.3.6.1.4.1.994.3.4.7.20.1.61
		pSlot3Protocol OBJECT-TYPE
			SYNTAX Protocol
			MAX-ACCESS read-write
			STATUS current
			DESCRIPTION
				"This field is used in the following card types:
				serial-ports - Protocol the serial port is speaking."
			::= { pSlot3Entry 61 }
		
		
		-- 1.3.6.1.4.1.994.3.4.7.20.1.62
		pSlot3SerialRTS OBJECT-TYPE
			SYNTAX SerialRTS
			MAX-ACCESS read-write
			STATUS current
			DESCRIPTION
				"This field is used in the following card types:
				serial-ports - Request To Send (RTS) setting for the serial port."
			::= { pSlot3Entry 62 }
		
		
		-- 1.3.6.1.4.1.994.3.4.7.20.1.63
		pSlot3SerialCTS OBJECT-TYPE
			SYNTAX SerialCTS
			MAX-ACCESS read-write
			STATUS current
			DESCRIPTION
				"This field is used in the following card types:
				serial-ports - Clear To Send (CTS) setting for the serial port."
			::= { pSlot3Entry 63 }
		
		
		-- 1.3.6.1.4.1.994.3.4.7.20.1.64
		pSlot3LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot3Entry 64 }
		
		
		-- 1.3.6.1.4.1.994.3.4.7.20.1.65
		pSlot3LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot3Entry 65 }
		
		
		-- 1.3.6.1.4.1.994.3.4.7.20.1.66
		pSlot3LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot3Entry 66 }
		
		
		-- 1.3.6.1.4.1.994.3.4.7.20.1.67
		pSlot3LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot3Entry 67 }
		
		
		-- 1.3.6.1.4.1.994.3.4.7.20.1.68
		pSlot3Present OBJECT-TYPE
			SYNTAX Boolean
			MAX-ACCESS read-only
			STATUS current
			DESCRIPTION
				"This field is used in the following card types:
				serial-ports - If set to true, the serial port exists.
				If set to false the serial port does not exist."
			::= { pSlot3Entry 68 }
		
		
		-- 1.3.6.1.4.1.994.3.4.7.20.1.71
		pSlot3OutputAutoPkg OBJECT-TYPE
			SYNTAX Integer32
			MAX-ACCESS read-write
			STATUS current
			DESCRIPTION
				"This field is used in the following card types:
				discrete-outputs - When this control point is opened, this is the package that the alarm
				point is located."
			::= { pSlot3Entry 71 }
		
		
		-- 1.3.6.1.4.1.994.3.4.7.20.1.72
		pSlot3VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot3Entry 72 }
		
		
		-- 1.3.6.1.4.1.994.3.4.7.20.1.73
		pSlot3IPPortNum OBJECT-TYPE
			SYNTAX Integer32
			MAX-ACCESS read-write
			STATUS current
			DESCRIPTION
				"This field is used in the following card types:
				serial-ports - IP port number of the target device."
			::= { pSlot3Entry 73 }
		
		
		-- 1.3.6.1.4.1.994.3.4.7.20.1.75
		pSlot3IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot3Entry 75 }
		
		
		-- 1.3.6.1.4.1.994.3.4.7.20.1.76
		pSlot3PortType OBJECT-TYPE
			SYNTAX PortType
			MAX-ACCESS read-only
			STATUS current
			DESCRIPTION
				"This field is used in the following card types:
				serial-ports - The type of serial port."
			::= { pSlot3Entry 76 }
		
		
		-- 1.3.6.1.4.1.994.3.4.7.20.1.116
		pSlot3TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot3Entry 116 }
		
		
		-- 1.3.6.1.4.1.994.3.4.7.20.1.117
		pSlot3TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot3Entry 117 }
		
		
		-- 1.3.6.1.4.1.994.3.4.7.20.1.118
		pSlot3TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot3Entry 118 }
		
		
		-- 1.3.6.1.4.1.994.3.4.7.20.1.119
		pSlot3TL1Env OBJECT-TYPE
			SYNTAX Boolean
			MAX-ACCESS read-write
			STATUS current
			DESCRIPTION
				"This field is used in the following card types:
				discrete-inputs - 
				onboard-sensors - 
				analog-Inputs - 
				analog-Sensors - "
			::= { pSlot3Entry 119 }
		
		
		-- 1.3.6.1.4.1.994.3.4.7.20.1.120
		pSlot3TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot3Entry 120 }
		
		
		-- 1.3.6.1.4.1.994.3.4.7.20.1.121
		pSlot3TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot3Entry 121 }
		
		
		-- 1.3.6.1.4.1.994.3.4.7.20.1.122
		pSlot3TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot3Entry 122 }
		
		
		-- 1.3.6.1.4.1.994.3.4.7.20.1.131
		pSlot3SensorType OBJECT-TYPE
			SYNTAX SensorType
			MAX-ACCESS read-write
			STATUS current
			DESCRIPTION
				"This field is used in the following card types:
				analog-Inputs - The type of sensor.
				analog-Sensors - The type of sensor."
			::= { pSlot3Entry 131 }
		
		
		-- 1.3.6.1.4.1.994.3.4.7.20.1.999
		pSlot3Index OBJECT-TYPE
			SYNTAX Integer32 (1..32)
			MAX-ACCESS read-only
			STATUS current
			DESCRIPTION
				"Index."
			::= { pSlot3Entry 999 }


-- Slot4 table
		
		-- 1.3.6.1.4.1.994.3.4.7.21
		pSlot4Table OBJECT-TYPE
			SYNTAX SEQUENCE OF PSlot4Entry
			MAX-ACCESS not-accessible
			STATUS current
			DESCRIPTION
				"Table for configuration of Slot4"
			::= { configuration 21 }
		
		
		-- 1.3.6.1.4.1.994.3.4.7.21.1
		pSlot4Entry OBJECT-TYPE
			SYNTAX PSlot4Entry
			MAX-ACCESS not-accessible
			STATUS current
			DESCRIPTION
				"Entry for configuration table of Slot4"
				INDEX { pSlot4Index }
			::= { pSlot4Table 1 }
		
		
		PSlot4Entry ::= 
			SEQUENCE {
				pSlot4Description
					DescriptionString,
				pSlot4Desc0
					DescriptionString,
				pSlot4Desc1
					DescriptionString,
				pSlot4Desc2
					DescriptionString,
				pSlot4Desc3
					DescriptionString,
				pSlot4Desc4
					DescriptionString,
				pSlot4Desc5
					DescriptionString,
				pSlot4Configured
					Configured,
				pSlot4SendEmail
					Boolean,
				pSlot4SendSNMPTrap
					Boolean,
				pSlot4IpAddress
					IpAddress,
				pSlot4Level0
					Level,
				pSlot4Level1
					Level,
				pSlot4Level2
					Level,
				pSlot4Level3
					Level,
				pSlot4Level4
					Level,
				pSlot4Level5
					Level,
				pSlot4ReadPeriod
					Integer32,
				pSlot4Thresh0
					DescriptionString,
				pSlot4Thresh1
					DescriptionString,
				pSlot4Thresh2
					DescriptionString,
				pSlot4Thresh3
					DescriptionString,
				pSlot4Thresh4
					DescriptionString,
				pSlot4Thresh5
					DescriptionString,
				pSlot4ContactStyle
					ContactStyle,
				pSlot4Units
					DescriptionString,
				pSlot4OutputMode
					OutputMode,
				pSlot4OutputState
					OutputState,
				pSlot4OutputAuto
					Integer32,
				pSlot4BaudRate
					BaudRate,
				pSlot4DataBits
					DataBits,
				pSlot4Parity
					Parity,
				pSlot4StopBits
					StopBits,
				pSlot4Protocol
					Protocol,
				pSlot4SerialRTS
					SerialRTS,
				pSlot4SerialCTS
					SerialCTS,
				pSlot4LiveDescription
					DescriptionString,
				pSlot4LiveLevel
					DescriptionString,
				pSlot4LiveRaw
					DescriptionString,
				pSlot4LiveTime
					DescriptionString,
				pSlot4Present
					Boolean,
				pSlot4OutputAutoPkg
					Integer32,
				pSlot4VoltageRange
					VoltageRange,
				pSlot4IPPortNum
					Integer32,
				pSlot4IOFormat
					IOFormat,
				pSlot4PortType
					PortType,
				pSlot4TL1SID
					DescriptionString,
				pSlot4TL1COND
					DescriptionString,
				pSlot4TL1Eqpt
					DescriptionString,
				pSlot4TL1Env
					Boolean,
				pSlot4TL1Srveff
					TL1Srveff,
				pSlot4TL1Locn
					TL1Locn,
				pSlot4TL1Dirn
					TL1Dirn,
				pSlot4SensorType
					SensorType,
				pSlot4Index
					Integer32 (1..32)
			}
		
		-- 1.3.6.1.4.1.994.3.4.7.21.1.3
		pSlot4Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot4Entry 3 }
		
		
		-- 1.3.6.1.4.1.994.3.4.7.21.1.4
		pSlot4Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot4Entry 4 }
		
		
		-- 1.3.6.1.4.1.994.3.4.7.21.1.5
		pSlot4Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot4Entry 5 }
		
		
		-- 1.3.6.1.4.1.994.3.4.7.21.1.6
		pSlot4Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot4Entry 6 }
		
		
		-- 1.3.6.1.4.1.994.3.4.7.21.1.7
		pSlot4Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot4Entry 7 }
		
		
		-- 1.3.6.1.4.1.994.3.4.7.21.1.8
		pSlot4Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot4Entry 8 }
		
		
		-- 1.3.6.1.4.1.994.3.4.7.21.1.9
		pSlot4Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot4Entry 9 }
		
		
		-- 1.3.6.1.4.1.994.3.4.7.21.1.10
		pSlot4Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot4Entry 10 }
		
		
		-- 1.3.6.1.4.1.994.3.4.7.21.1.11
		pSlot4SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot4Entry 11 }
		
		
		-- 1.3.6.1.4.1.994.3.4.7.21.1.12
		pSlot4SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot4Entry 12 }
		
		
		-- 1.3.6.1.4.1.994.3.4.7.21.1.14
		pSlot4IpAddress OBJECT-TYPE
			SYNTAX IpAddress
			MAX-ACCESS read-write
			STATUS current
			DESCRIPTION
				"This field is used in the following card types:
				serial-ports - IP Address of the target device."
			::= { pSlot4Entry 14 }
		
		
		-- 1.3.6.1.4.1.994.3.4.7.21.1.17
		pSlot4Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot4Entry 17 }
		
		
		-- 1.3.6.1.4.1.994.3.4.7.21.1.18
		pSlot4Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot4Entry 18 }
		
		
		-- 1.3.6.1.4.1.994.3.4.7.21.1.19
		pSlot4Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot4Entry 19 }
		
		
		-- 1.3.6.1.4.1.994.3.4.7.21.1.20
		pSlot4Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot4Entry 20 }
		
		
		-- 1.3.6.1.4.1.994.3.4.7.21.1.21
		pSlot4Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot4Entry 21 }
		
		
		-- 1.3.6.1.4.1.994.3.4.7.21.1.22
		pSlot4Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot4Entry 22 }
		
		
		-- 1.3.6.1.4.1.994.3.4.7.21.1.23
		pSlot4ReadPeriod OBJECT-TYPE
			SYNTAX Integer32
			MAX-ACCESS read-write
			STATUS current
			DESCRIPTION
				"This field is used in the following card types:
				serial-ports - Inactivity timeout (in minutes)."
			::= { pSlot4Entry 23 }
		
		
		-- 1.3.6.1.4.1.994.3.4.7.21.1.28
		pSlot4Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot4Entry 28 }
		
		
		-- 1.3.6.1.4.1.994.3.4.7.21.1.29
		pSlot4Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot4Entry 29 }
		
		
		-- 1.3.6.1.4.1.994.3.4.7.21.1.30
		pSlot4Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot4Entry 30 }
		
		
		-- 1.3.6.1.4.1.994.3.4.7.21.1.31
		pSlot4Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot4Entry 31 }
		
		
		-- 1.3.6.1.4.1.994.3.4.7.21.1.32
		pSlot4Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot4Entry 32 }
		
		
		-- 1.3.6.1.4.1.994.3.4.7.21.1.33
		pSlot4Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot4Entry 33 }
		
		
		-- 1.3.6.1.4.1.994.3.4.7.21.1.44
		pSlot4ContactStyle OBJECT-TYPE
			SYNTAX ContactStyle
			MAX-ACCESS read-write
			STATUS current
			DESCRIPTION
				"This field is used in the following card types:
				discrete-inputs - Determines the type of contact."
			::= { pSlot4Entry 44 }
		
		
		-- 1.3.6.1.4.1.994.3.4.7.21.1.46
		pSlot4Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot4Entry 46 }
		
		
		-- 1.3.6.1.4.1.994.3.4.7.21.1.47
		pSlot4OutputMode OBJECT-TYPE
			SYNTAX OutputMode
			MAX-ACCESS read-write
			STATUS current
			DESCRIPTION
				"This field is used in the following card types:
				discrete-outputs - Defines the different ways a control point can be activated."
			::= { pSlot4Entry 47 }
		
		
		-- 1.3.6.1.4.1.994.3.4.7.21.1.48
		pSlot4OutputState OBJECT-TYPE
			SYNTAX OutputState
			MAX-ACCESS read-write
			STATUS current
			DESCRIPTION
				"This field is used in the following card types:
				discrete-outputs - A value of 0 will open the control point.
				A value of 1 will close the control point."
			::= { pSlot4Entry 48 }
		
		
		-- 1.3.6.1.4.1.994.3.4.7.21.1.49
		pSlot4OutputAuto OBJECT-TYPE
			SYNTAX Integer32
			MAX-ACCESS read-write
			STATUS current
			DESCRIPTION
				"This field is used in the following card types:
				discrete-outputs - When this control point is opened, this alarm point will change state 
				to the on state."
			::= { pSlot4Entry 49 }
		
		
		-- 1.3.6.1.4.1.994.3.4.7.21.1.57
		pSlot4BaudRate OBJECT-TYPE
			SYNTAX BaudRate
			MAX-ACCESS read-write
			STATUS current
			DESCRIPTION
				"This field is used in the following card types:
				serial-ports - Baud rate of the serial port."
			::= { pSlot4Entry 57 }
		
		
		-- 1.3.6.1.4.1.994.3.4.7.21.1.58
		pSlot4DataBits OBJECT-TYPE
			SYNTAX DataBits
			MAX-ACCESS read-write
			STATUS current
			DESCRIPTION
				"This field is used in the following card types:
				serial-ports - Number of data bit for the serial port."
			::= { pSlot4Entry 58 }
		
		
		-- 1.3.6.1.4.1.994.3.4.7.21.1.59
		pSlot4Parity OBJECT-TYPE
			SYNTAX Parity
			MAX-ACCESS read-write
			STATUS current
			DESCRIPTION
				"This field is used in the following card types:
				serial-ports - Parity of the serial port."
			::= { pSlot4Entry 59 }
		
		
		-- 1.3.6.1.4.1.994.3.4.7.21.1.60
		pSlot4StopBits OBJECT-TYPE
			SYNTAX StopBits
			MAX-ACCESS read-write
			STATUS current
			DESCRIPTION
				"This field is used in the following card types:
				serial-ports - Number of stop bits for the serial port."
			::= { pSlot4Entry 60 }
		
		
		-- 1.3.6.1.4.1.994.3.4.7.21.1.61
		pSlot4Protocol OBJECT-TYPE
			SYNTAX Protocol
			MAX-ACCESS read-write
			STATUS current
			DESCRIPTION
				"This field is used in the following card types:
				serial-ports - Protocol the serial port is speaking."
			::= { pSlot4Entry 61 }
		
		
		-- 1.3.6.1.4.1.994.3.4.7.21.1.62
		pSlot4SerialRTS OBJECT-TYPE
			SYNTAX SerialRTS
			MAX-ACCESS read-write
			STATUS current
			DESCRIPTION
				"This field is used in the following card types:
				serial-ports - Request To Send (RTS) setting for the serial port."
			::= { pSlot4Entry 62 }
		
		
		-- 1.3.6.1.4.1.994.3.4.7.21.1.63
		pSlot4SerialCTS OBJECT-TYPE
			SYNTAX SerialCTS
			MAX-ACCESS read-write
			STATUS current
			DESCRIPTION
				"This field is used in the following card types:
				serial-ports - Clear To Send (CTS) setting for the serial port."
			::= { pSlot4Entry 63 }
		
		
		-- 1.3.6.1.4.1.994.3.4.7.21.1.64
		pSlot4LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot4Entry 64 }
		
		
		-- 1.3.6.1.4.1.994.3.4.7.21.1.65
		pSlot4LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot4Entry 65 }
		
		
		-- 1.3.6.1.4.1.994.3.4.7.21.1.66
		pSlot4LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot4Entry 66 }
		
		
		-- 1.3.6.1.4.1.994.3.4.7.21.1.67
		pSlot4LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot4Entry 67 }
		
		
		-- 1.3.6.1.4.1.994.3.4.7.21.1.68
		pSlot4Present OBJECT-TYPE
			SYNTAX Boolean
			MAX-ACCESS read-only
			STATUS current
			DESCRIPTION
				"This field is used in the following card types:
				serial-ports - If set to true, the serial port exists.
				If set to false the serial port does not exist."
			::= { pSlot4Entry 68 }
		
		
		-- 1.3.6.1.4.1.994.3.4.7.21.1.71
		pSlot4OutputAutoPkg OBJECT-TYPE
			SYNTAX Integer32
			MAX-ACCESS read-write
			STATUS current
			DESCRIPTION
				"This field is used in the following card types:
				discrete-outputs - When this control point is opened, this is the package that the alarm
				point is located."
			::= { pSlot4Entry 71 }
		
		
		-- 1.3.6.1.4.1.994.3.4.7.21.1.72
		pSlot4VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot4Entry 72 }
		
		
		-- 1.3.6.1.4.1.994.3.4.7.21.1.73
		pSlot4IPPortNum OBJECT-TYPE
			SYNTAX Integer32
			MAX-ACCESS read-write
			STATUS current
			DESCRIPTION
				"This field is used in the following card types:
				serial-ports - IP port number of the target device."
			::= { pSlot4Entry 73 }
		
		
		-- 1.3.6.1.4.1.994.3.4.7.21.1.75
		pSlot4IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot4Entry 75 }
		
		
		-- 1.3.6.1.4.1.994.3.4.7.21.1.76
		pSlot4PortType OBJECT-TYPE
			SYNTAX PortType
			MAX-ACCESS read-only
			STATUS current
			DESCRIPTION
				"This field is used in the following card types:
				serial-ports - The type of serial port."
			::= { pSlot4Entry 76 }
		
		
		-- 1.3.6.1.4.1.994.3.4.7.21.1.116
		pSlot4TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot4Entry 116 }
		
		
		-- 1.3.6.1.4.1.994.3.4.7.21.1.117
		pSlot4TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot4Entry 117 }
		
		
		-- 1.3.6.1.4.1.994.3.4.7.21.1.118
		pSlot4TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot4Entry 118 }
		
		
		-- 1.3.6.1.4.1.994.3.4.7.21.1.119
		pSlot4TL1Env OBJECT-TYPE
			SYNTAX Boolean
			MAX-ACCESS read-write
			STATUS current
			DESCRIPTION
				"This field is used in the following card types:
				discrete-inputs - 
				onboard-sensors - 
				analog-Inputs - 
				analog-Sensors - "
			::= { pSlot4Entry 119 }
		
		
		-- 1.3.6.1.4.1.994.3.4.7.21.1.120
		pSlot4TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot4Entry 120 }
		
		
		-- 1.3.6.1.4.1.994.3.4.7.21.1.121
		pSlot4TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot4Entry 121 }
		
		
		-- 1.3.6.1.4.1.994.3.4.7.21.1.122
		pSlot4TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot4Entry 122 }
		
		
		-- 1.3.6.1.4.1.994.3.4.7.21.1.131
		pSlot4SensorType OBJECT-TYPE
			SYNTAX SensorType
			MAX-ACCESS read-write
			STATUS current
			DESCRIPTION
				"This field is used in the following card types:
				analog-Inputs - The type of sensor.
				analog-Sensors - The type of sensor."
			::= { pSlot4Entry 131 }
		
		
		-- 1.3.6.1.4.1.994.3.4.7.21.1.999
		pSlot4Index OBJECT-TYPE
			SYNTAX Integer32 (1..32)
			MAX-ACCESS read-only
			STATUS current
			DESCRIPTION
				"Index."
			::= { pSlot4Entry 999 }


-- Slot5 table
		
		-- 1.3.6.1.4.1.994.3.4.7.22
		pSlot5Table OBJECT-TYPE
			SYNTAX SEQUENCE OF PSlot5Entry
			MAX-ACCESS not-accessible
			STATUS current
			DESCRIPTION
				"Table for configuration of Slot5"
			::= { configuration 22 }
		
		
		-- 1.3.6.1.4.1.994.3.4.7.22.1
		pSlot5Entry OBJECT-TYPE
			SYNTAX PSlot5Entry
			MAX-ACCESS not-accessible
			STATUS current
			DESCRIPTION
				"Entry for configuration table of Slot5"
				INDEX { pSlot5Index }
			::= { pSlot5Table 1 }
		
		
		PSlot5Entry ::= 
			SEQUENCE {
				pSlot5Description
					DescriptionString,
				pSlot5Desc0
					DescriptionString,
				pSlot5Desc1
					DescriptionString,
				pSlot5Desc2
					DescriptionString,
				pSlot5Desc3
					DescriptionString,
				pSlot5Desc4
					DescriptionString,
				pSlot5Desc5
					DescriptionString,
				pSlot5Configured
					Configured,
				pSlot5SendEmail
					Boolean,
				pSlot5SendSNMPTrap
					Boolean,
				pSlot5IpAddress
					IpAddress,
				pSlot5Level0
					Level,
				pSlot5Level1
					Level,
				pSlot5Level2
					Level,
				pSlot5Level3
					Level,
				pSlot5Level4
					Level,
				pSlot5Level5
					Level,
				pSlot5ReadPeriod
					Integer32,
				pSlot5Thresh0
					DescriptionString,
				pSlot5Thresh1
					DescriptionString,
				pSlot5Thresh2
					DescriptionString,
				pSlot5Thresh3
					DescriptionString,
				pSlot5Thresh4
					DescriptionString,
				pSlot5Thresh5
					DescriptionString,
				pSlot5ContactStyle
					ContactStyle,
				pSlot5Units
					DescriptionString,
				pSlot5OutputMode
					OutputMode,
				pSlot5OutputState
					OutputState,
				pSlot5OutputAuto
					Integer32,
				pSlot5BaudRate
					BaudRate,
				pSlot5DataBits
					DataBits,
				pSlot5Parity
					Parity,
				pSlot5StopBits
					StopBits,
				pSlot5Protocol
					Protocol,
				pSlot5SerialRTS
					SerialRTS,
				pSlot5SerialCTS
					SerialCTS,
				pSlot5LiveDescription
					DescriptionString,
				pSlot5LiveLevel
					DescriptionString,
				pSlot5LiveRaw
					DescriptionString,
				pSlot5LiveTime
					DescriptionString,
				pSlot5Present
					Boolean,
				pSlot5OutputAutoPkg
					Integer32,
				pSlot5VoltageRange
					VoltageRange,
				pSlot5IPPortNum
					Integer32,
				pSlot5IOFormat
					IOFormat,
				pSlot5PortType
					PortType,
				pSlot5TL1SID
					DescriptionString,
				pSlot5TL1COND
					DescriptionString,
				pSlot5TL1Eqpt
					DescriptionString,
				pSlot5TL1Env
					Boolean,
				pSlot5TL1Srveff
					TL1Srveff,
				pSlot5TL1Locn
					TL1Locn,
				pSlot5TL1Dirn
					TL1Dirn,
				pSlot5SensorType
					SensorType,
				pSlot5Index
					Integer32 (1..32)
			}
		
		-- 1.3.6.1.4.1.994.3.4.7.22.1.3
		pSlot5Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot5Entry 3 }
		
		
		-- 1.3.6.1.4.1.994.3.4.7.22.1.4
		pSlot5Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot5Entry 4 }
		
		
		-- 1.3.6.1.4.1.994.3.4.7.22.1.5
		pSlot5Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot5Entry 5 }
		
		
		-- 1.3.6.1.4.1.994.3.4.7.22.1.6
		pSlot5Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot5Entry 6 }
		
		
		-- 1.3.6.1.4.1.994.3.4.7.22.1.7
		pSlot5Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot5Entry 7 }
		
		
		-- 1.3.6.1.4.1.994.3.4.7.22.1.8
		pSlot5Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot5Entry 8 }
		
		
		-- 1.3.6.1.4.1.994.3.4.7.22.1.9
		pSlot5Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot5Entry 9 }
		
		
		-- 1.3.6.1.4.1.994.3.4.7.22.1.10
		pSlot5Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot5Entry 10 }
		
		
		-- 1.3.6.1.4.1.994.3.4.7.22.1.11
		pSlot5SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot5Entry 11 }
		
		
		-- 1.3.6.1.4.1.994.3.4.7.22.1.12
		pSlot5SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot5Entry 12 }
		
		
		-- 1.3.6.1.4.1.994.3.4.7.22.1.14
		pSlot5IpAddress OBJECT-TYPE
			SYNTAX IpAddress
			MAX-ACCESS read-write
			STATUS current
			DESCRIPTION
				"This field is used in the following card types:
				serial-ports - IP Address of the target device."
			::= { pSlot5Entry 14 }
		
		
		-- 1.3.6.1.4.1.994.3.4.7.22.1.17
		pSlot5Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot5Entry 17 }
		
		
		-- 1.3.6.1.4.1.994.3.4.7.22.1.18
		pSlot5Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot5Entry 18 }
		
		
		-- 1.3.6.1.4.1.994.3.4.7.22.1.19
		pSlot5Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot5Entry 19 }
		
		
		-- 1.3.6.1.4.1.994.3.4.7.22.1.20
		pSlot5Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot5Entry 20 }
		
		
		-- 1.3.6.1.4.1.994.3.4.7.22.1.21
		pSlot5Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot5Entry 21 }
		
		
		-- 1.3.6.1.4.1.994.3.4.7.22.1.22
		pSlot5Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot5Entry 22 }
		
		
		-- 1.3.6.1.4.1.994.3.4.7.22.1.23
		pSlot5ReadPeriod OBJECT-TYPE
			SYNTAX Integer32
			MAX-ACCESS read-write
			STATUS current
			DESCRIPTION
				"This field is used in the following card types:
				serial-ports - Inactivity timeout (in minutes)."
			::= { pSlot5Entry 23 }
		
		
		-- 1.3.6.1.4.1.994.3.4.7.22.1.28
		pSlot5Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot5Entry 28 }
		
		
		-- 1.3.6.1.4.1.994.3.4.7.22.1.29
		pSlot5Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot5Entry 29 }
		
		
		-- 1.3.6.1.4.1.994.3.4.7.22.1.30
		pSlot5Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot5Entry 30 }
		
		
		-- 1.3.6.1.4.1.994.3.4.7.22.1.31
		pSlot5Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot5Entry 31 }
		
		
		-- 1.3.6.1.4.1.994.3.4.7.22.1.32
		pSlot5Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot5Entry 32 }
		
		
		-- 1.3.6.1.4.1.994.3.4.7.22.1.33
		pSlot5Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot5Entry 33 }
		
		
		-- 1.3.6.1.4.1.994.3.4.7.22.1.44
		pSlot5ContactStyle OBJECT-TYPE
			SYNTAX ContactStyle
			MAX-ACCESS read-write
			STATUS current
			DESCRIPTION
				"This field is used in the following card types:
				discrete-inputs - Determines the type of contact."
			::= { pSlot5Entry 44 }
		
		
		-- 1.3.6.1.4.1.994.3.4.7.22.1.46
		pSlot5Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot5Entry 46 }
		
		
		-- 1.3.6.1.4.1.994.3.4.7.22.1.47
		pSlot5OutputMode OBJECT-TYPE
			SYNTAX OutputMode
			MAX-ACCESS read-write
			STATUS current
			DESCRIPTION
				"This field is used in the following card types:
				discrete-outputs - Defines the different ways a control point can be activated."
			::= { pSlot5Entry 47 }
		
		
		-- 1.3.6.1.4.1.994.3.4.7.22.1.48
		pSlot5OutputState OBJECT-TYPE
			SYNTAX OutputState
			MAX-ACCESS read-write
			STATUS current
			DESCRIPTION
				"This field is used in the following card types:
				discrete-outputs - A value of 0 will open the control point.
				A value of 1 will close the control point."
			::= { pSlot5Entry 48 }
		
		
		-- 1.3.6.1.4.1.994.3.4.7.22.1.49
		pSlot5OutputAuto OBJECT-TYPE
			SYNTAX Integer32
			MAX-ACCESS read-write
			STATUS current
			DESCRIPTION
				"This field is used in the following card types:
				discrete-outputs - When this control point is opened, this alarm point will change state 
				to the on state."
			::= { pSlot5Entry 49 }
		
		
		-- 1.3.6.1.4.1.994.3.4.7.22.1.57
		pSlot5BaudRate OBJECT-TYPE
			SYNTAX BaudRate
			MAX-ACCESS read-write
			STATUS current
			DESCRIPTION
				"This field is used in the following card types:
				serial-ports - Baud rate of the serial port."
			::= { pSlot5Entry 57 }
		
		
		-- 1.3.6.1.4.1.994.3.4.7.22.1.58
		pSlot5DataBits OBJECT-TYPE
			SYNTAX DataBits
			MAX-ACCESS read-write
			STATUS current
			DESCRIPTION
				"This field is used in the following card types:
				serial-ports - Number of data bit for the serial port."
			::= { pSlot5Entry 58 }
		
		
		-- 1.3.6.1.4.1.994.3.4.7.22.1.59
		pSlot5Parity OBJECT-TYPE
			SYNTAX Parity
			MAX-ACCESS read-write
			STATUS current
			DESCRIPTION
				"This field is used in the following card types:
				serial-ports - Parity of the serial port."
			::= { pSlot5Entry 59 }
		
		
		-- 1.3.6.1.4.1.994.3.4.7.22.1.60
		pSlot5StopBits OBJECT-TYPE
			SYNTAX StopBits
			MAX-ACCESS read-write
			STATUS current
			DESCRIPTION
				"This field is used in the following card types:
				serial-ports - Number of stop bits for the serial port."
			::= { pSlot5Entry 60 }
		
		
		-- 1.3.6.1.4.1.994.3.4.7.22.1.61
		pSlot5Protocol OBJECT-TYPE
			SYNTAX Protocol
			MAX-ACCESS read-write
			STATUS current
			DESCRIPTION
				"This field is used in the following card types:
				serial-ports - Protocol the serial port is speaking."
			::= { pSlot5Entry 61 }
		
		
		-- 1.3.6.1.4.1.994.3.4.7.22.1.62
		pSlot5SerialRTS OBJECT-TYPE
			SYNTAX SerialRTS
			MAX-ACCESS read-write
			STATUS current
			DESCRIPTION
				"This field is used in the following card types:
				serial-ports - Request To Send (RTS) setting for the serial port."
			::= { pSlot5Entry 62 }
		
		
		-- 1.3.6.1.4.1.994.3.4.7.22.1.63
		pSlot5SerialCTS OBJECT-TYPE
			SYNTAX SerialCTS
			MAX-ACCESS read-write
			STATUS current
			DESCRIPTION
				"This field is used in the following card types:
				serial-ports - Clear To Send (CTS) setting for the serial port."
			::= { pSlot5Entry 63 }
		
		
		-- 1.3.6.1.4.1.994.3.4.7.22.1.64
		pSlot5LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot5Entry 64 }
		
		
		-- 1.3.6.1.4.1.994.3.4.7.22.1.65
		pSlot5LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot5Entry 65 }
		
		
		-- 1.3.6.1.4.1.994.3.4.7.22.1.66
		pSlot5LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot5Entry 66 }
		
		
		-- 1.3.6.1.4.1.994.3.4.7.22.1.67
		pSlot5LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot5Entry 67 }
		
		
		-- 1.3.6.1.4.1.994.3.4.7.22.1.68
		pSlot5Present OBJECT-TYPE
			SYNTAX Boolean
			MAX-ACCESS read-only
			STATUS current
			DESCRIPTION
				"This field is used in the following card types:
				serial-ports - If set to true, the serial port exists.
				If set to false the serial port does not exist."
			::= { pSlot5Entry 68 }
		
		
		-- 1.3.6.1.4.1.994.3.4.7.22.1.71
		pSlot5OutputAutoPkg OBJECT-TYPE
			SYNTAX Integer32
			MAX-ACCESS read-write
			STATUS current
			DESCRIPTION
				"This field is used in the following card types:
				discrete-outputs - When this control point is opened, this is the package that the alarm
				point is located."
			::= { pSlot5Entry 71 }
		
		
		-- 1.3.6.1.4.1.994.3.4.7.22.1.72
		pSlot5VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot5Entry 72 }
		
		
		-- 1.3.6.1.4.1.994.3.4.7.22.1.73
		pSlot5IPPortNum OBJECT-TYPE
			SYNTAX Integer32
			MAX-ACCESS read-write
			STATUS current
			DESCRIPTION
				"This field is used in the following card types:
				serial-ports - IP port number of the target device."
			::= { pSlot5Entry 73 }
		
		
		-- 1.3.6.1.4.1.994.3.4.7.22.1.75
		pSlot5IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot5Entry 75 }
		
		
		-- 1.3.6.1.4.1.994.3.4.7.22.1.76
		pSlot5PortType OBJECT-TYPE
			SYNTAX PortType
			MAX-ACCESS read-only
			STATUS current
			DESCRIPTION
				"This field is used in the following card types:
				serial-ports - The type of serial port."
			::= { pSlot5Entry 76 }
		
		
		-- 1.3.6.1.4.1.994.3.4.7.22.1.116
		pSlot5TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot5Entry 116 }
		
		
		-- 1.3.6.1.4.1.994.3.4.7.22.1.117
		pSlot5TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot5Entry 117 }
		
		
		-- 1.3.6.1.4.1.994.3.4.7.22.1.118
		pSlot5TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot5Entry 118 }
		
		
		-- 1.3.6.1.4.1.994.3.4.7.22.1.119
		pSlot5TL1Env OBJECT-TYPE
			SYNTAX Boolean
			MAX-ACCESS read-write
			STATUS current
			DESCRIPTION
				"This field is used in the following card types:
				discrete-inputs - 
				onboard-sensors - 
				analog-Inputs - 
				analog-Sensors - "
			::= { pSlot5Entry 119 }
		
		
		-- 1.3.6.1.4.1.994.3.4.7.22.1.120
		pSlot5TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot5Entry 120 }
		
		
		-- 1.3.6.1.4.1.994.3.4.7.22.1.121
		pSlot5TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot5Entry 121 }
		
		
		-- 1.3.6.1.4.1.994.3.4.7.22.1.122
		pSlot5TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot5Entry 122 }
		
		
		-- 1.3.6.1.4.1.994.3.4.7.22.1.131
		pSlot5SensorType OBJECT-TYPE
			SYNTAX SensorType
			MAX-ACCESS read-write
			STATUS current
			DESCRIPTION
				"This field is used in the following card types:
				analog-Inputs - The type of sensor.
				analog-Sensors - The type of sensor."
			::= { pSlot5Entry 131 }
		
		
		-- 1.3.6.1.4.1.994.3.4.7.22.1.999
		pSlot5Index OBJECT-TYPE
			SYNTAX Integer32 (1..32)
			MAX-ACCESS read-only
			STATUS current
			DESCRIPTION
				"Index."
			::= { pSlot5Entry 999 }


-- Slot6 table
		
		-- 1.3.6.1.4.1.994.3.4.7.23
		pSlot6Table OBJECT-TYPE
			SYNTAX SEQUENCE OF PSlot6Entry
			MAX-ACCESS not-accessible
			STATUS current
			DESCRIPTION
				"Table for configuration of Slot6"
			::= { configuration 23 }
		
		
		-- 1.3.6.1.4.1.994.3.4.7.23.1
		pSlot6Entry OBJECT-TYPE
			SYNTAX PSlot6Entry
			MAX-ACCESS not-accessible
			STATUS current
			DESCRIPTION
				"Entry for configuration table of Slot6"
				INDEX { pSlot6Index }
			::= { pSlot6Table 1 }
		
		
		PSlot6Entry ::= 
			SEQUENCE {
				pSlot6Description
					DescriptionString,
				pSlot6Desc0
					DescriptionString,
				pSlot6Desc1
					DescriptionString,
				pSlot6Desc2
					DescriptionString,
				pSlot6Desc3
					DescriptionString,
				pSlot6Desc4
					DescriptionString,
				pSlot6Desc5
					DescriptionString,
				pSlot6Configured
					Configured,
				pSlot6SendEmail
					Boolean,
				pSlot6SendSNMPTrap
					Boolean,
				pSlot6IpAddress
					IpAddress,
				pSlot6Level0
					Level,
				pSlot6Level1
					Level,
				pSlot6Level2
					Level,
				pSlot6Level3
					Level,
				pSlot6Level4
					Level,
				pSlot6Level5
					Level,
				pSlot6ReadPeriod
					Integer32,
				pSlot6Thresh0
					DescriptionString,
				pSlot6Thresh1
					DescriptionString,
				pSlot6Thresh2
					DescriptionString,
				pSlot6Thresh3
					DescriptionString,
				pSlot6Thresh4
					DescriptionString,
				pSlot6Thresh5
					DescriptionString,
				pSlot6ContactStyle
					ContactStyle,
				pSlot6Units
					DescriptionString,
				pSlot6OutputMode
					OutputMode,
				pSlot6OutputState
					OutputState,
				pSlot6OutputAuto
					Integer32,
				pSlot6BaudRate
					BaudRate,
				pSlot6DataBits
					DataBits,
				pSlot6Parity
					Parity,
				pSlot6StopBits
					StopBits,
				pSlot6Protocol
					Protocol,
				pSlot6SerialRTS
					SerialRTS,
				pSlot6SerialCTS
					SerialCTS,
				pSlot6LiveDescription
					DescriptionString,
				pSlot6LiveLevel
					DescriptionString,
				pSlot6LiveRaw
					DescriptionString,
				pSlot6LiveTime
					DescriptionString,
				pSlot6Present
					Boolean,
				pSlot6OutputAutoPkg
					Integer32,
				pSlot6VoltageRange
					VoltageRange,
				pSlot6IPPortNum
					Integer32,
				pSlot6IOFormat
					IOFormat,
				pSlot6PortType
					PortType,
				pSlot6TL1SID
					DescriptionString,
				pSlot6TL1COND
					DescriptionString,
				pSlot6TL1Eqpt
					DescriptionString,
				pSlot6TL1Env
					Boolean,
				pSlot6TL1Srveff
					TL1Srveff,
				pSlot6TL1Locn
					TL1Locn,
				pSlot6TL1Dirn
					TL1Dirn,
				pSlot6SensorType
					SensorType,
				pSlot6Index
					Integer32 (1..32)
			}
		
		-- 1.3.6.1.4.1.994.3.4.7.23.1.3
		pSlot6Description OBJECT-TYPE
			SYNTAX DescriptionString
			MAX-ACCESS read-write
			STATUS current
			DESCRIPTION
				"This field is used in the following card types:
				discrete-inputs - Description of the alarm point.
				discrete-outputs - Description of the control point.
				serial-ports - Description of the serial port.
				onboard-sensors - Description of the onboard device.
				analog-Inputs - Description of the analog input device.
				analog-Sensors - Description of the sensor input device."
			::= { pSlot6Entry 3 }
		
		
		-- 1.3.6.1.4.1.994.3.4.7.23.1.4
		pSlot6Desc0 OBJECT-TYPE
			SYNTAX DescriptionString
			MAX-ACCESS read-write
			STATUS current
			DESCRIPTION
				"This field is used in the following card types:
				discrete-inputs - Description of the off state.
				discrete-outputs - Description when the control point is open.
				onboard-sensors - The description for values between threshold 0 and threshold 1.
				analog-Inputs - The description for values between threshold 0 and threshold 1.
				analog-Sensors - The description for values between threshold 0 and threshold 1."
			::= { pSlot6Entry 4 }
		
		
		-- 1.3.6.1.4.1.994.3.4.7.23.1.5
		pSlot6Desc1 OBJECT-TYPE
			SYNTAX DescriptionString
			MAX-ACCESS read-write
			STATUS current
			DESCRIPTION
				"This field is used in the following card types:
				discrete-inputs - Description of the on state.
				discrete-outputs - Description when the control point is closed.
				onboard-sensors - The description for values between threshold 1 and threshold 2.
				analog-Inputs - The description for values between threshold 1 and threshold 2.
				analog-Sensors - The description for values between threshold 1 and threshold 2."
			::= { pSlot6Entry 5 }
		
		
		-- 1.3.6.1.4.1.994.3.4.7.23.1.6
		pSlot6Desc2 OBJECT-TYPE
			SYNTAX DescriptionString
			MAX-ACCESS read-write
			STATUS current
			DESCRIPTION
				"This field is used in the following card types:
				onboard-sensors - The description for values between threshold 2 and threshold 3.
				analog-Inputs - The description for values between threshold 2 and threshold 3.
				analog-Sensors - The description for values between threshold 2 and threshold 3."
			::= { pSlot6Entry 6 }
		
		
		-- 1.3.6.1.4.1.994.3.4.7.23.1.7
		pSlot6Desc3 OBJECT-TYPE
			SYNTAX DescriptionString
			MAX-ACCESS read-write
			STATUS current
			DESCRIPTION
				"This field is used in the following card types:
				onboard-sensors - The description for values between threshold 3 and threshold 4.
				analog-Inputs - The description for values between threshold 3 and threshold 4.
				analog-Sensors - The description for values between threshold 3 and threshold 4."
			::= { pSlot6Entry 7 }
		
		
		-- 1.3.6.1.4.1.994.3.4.7.23.1.8
		pSlot6Desc4 OBJECT-TYPE
			SYNTAX DescriptionString
			MAX-ACCESS read-write
			STATUS current
			DESCRIPTION
				"This field is used in the following card types:
				onboard-sensors - The description for values between threshold 4 and threshold 5.
				analog-Inputs - The description for values between threshold 4 and threshold 5.
				analog-Sensors - The description for values between threshold 4 and threshold 5."
			::= { pSlot6Entry 8 }
		
		
		-- 1.3.6.1.4.1.994.3.4.7.23.1.9
		pSlot6Desc5 OBJECT-TYPE
			SYNTAX DescriptionString
			MAX-ACCESS read-write
			STATUS current
			DESCRIPTION
				"This field is used in the following card types:
				analog-Inputs - Description for a communications failure to the sensor.
				analog-Sensors - Description for a communications failure to the sensor."
			::= { pSlot6Entry 9 }
		
		
		-- 1.3.6.1.4.1.994.3.4.7.23.1.10
		pSlot6Configured OBJECT-TYPE
			SYNTAX Configured
			MAX-ACCESS read-write
			STATUS current
			DESCRIPTION
				"This field is used in the following card types:
				discrete-inputs - If set to true, changes of state will be reported.
				If set to false, not change of states will be reported.
				discrete-outputs - If set to true, the control point will operate.
				If false, it will not operate.
				serial-ports - If set to true, this serial port will be usable.
				If set to false the port will not be usable.
				onboard-sensors - If set to true, the onboard sensors will be used.
				If set to false the will be ignored.
				analog-Inputs - If set to true, the analog inputs will be usable.
				If set to false the analog inputs will be ignored.
				analog-Sensors - If set to true, the sensor inputs will be usable.
				If set to false the sensor inputs will be ignored."
			::= { pSlot6Entry 10 }
		
		
		-- 1.3.6.1.4.1.994.3.4.7.23.1.11
		pSlot6SendEmail OBJECT-TYPE
			SYNTAX Boolean
			MAX-ACCESS read-write
			STATUS current
			DESCRIPTION
				"This field is used in the following card types:
				discrete-inputs - If set to true, an email will be sent on a change of state.
				If false, no email will be sent.
				onboard-sensors - If set to true an email event will be set when a threshold is crossed.
				If set to false no email event will be sent.
				analog-Inputs - If set to true an email event will be set when a threshold is crossed.
				If set to false no email event will be sent.
				analog-Sensors - If set to true an email event will be set when a threshold is crossed.
				If set to false no email event will be sent."
			::= { pSlot6Entry 11 }
		
		
		-- 1.3.6.1.4.1.994.3.4.7.23.1.12
		pSlot6SendSNMPTrap OBJECT-TYPE
			SYNTAX Boolean
			MAX-ACCESS read-write
			STATUS current
			DESCRIPTION
				"This field is used in the following card types:
				discrete-inputs - If set to true, an SNMP trap will be sent on a change of state.
				If false, no SNMP trap will be sent.
				onboard-sensors - If set to true an SNMP trap will be set when a threshold is crossed.
				If set to false no SNMP trap will be sent.
				analog-Inputs - If set to true an SNMP trap will be set when a threshold is crossed.
				If set to false no SNMP trap will be sent.
				analog-Sensors - If set to true an SNMP trap will be set when a threshold is crossed.
				If set to false no SNMP trap will be sent."
			::= { pSlot6Entry 12 }
		
		
		-- 1.3.6.1.4.1.994.3.4.7.23.1.14
		pSlot6IpAddress OBJECT-TYPE
			SYNTAX IpAddress
			MAX-ACCESS read-write
			STATUS current
			DESCRIPTION
				"This field is used in the following card types:
				serial-ports - IP Address of the target device."
			::= { pSlot6Entry 14 }
		
		
		-- 1.3.6.1.4.1.994.3.4.7.23.1.17
		pSlot6Level0 OBJECT-TYPE
			SYNTAX Level
			MAX-ACCESS read-write
			STATUS current
			DESCRIPTION
				"This field is used in the following card types:
				discrete-inputs - Level of the off state.
				discrete-outputs - Level of the control point when open.
				onboard-sensors - The level for values between threshold 0 and threshold 1.
				analog-Inputs - The level for values between threshold 0 and threshold 1.
				analog-Sensors - The level for values between threshold 0 and threshold 1."
			::= { pSlot6Entry 17 }
		
		
		-- 1.3.6.1.4.1.994.3.4.7.23.1.18
		pSlot6Level1 OBJECT-TYPE
			SYNTAX Level
			MAX-ACCESS read-write
			STATUS current
			DESCRIPTION
				"This field is used in the following card types:
				discrete-inputs - Level of the on state.
				discrete-outputs - Level of the control point when closed.
				onboard-sensors - The level for values between threshold 1 and threshold 2.
				analog-Inputs - The level for values between threshold 1 and threshold 2.
				analog-Sensors - The level for values between threshold 1 and threshold 2."
			::= { pSlot6Entry 18 }
		
		
		-- 1.3.6.1.4.1.994.3.4.7.23.1.19
		pSlot6Level2 OBJECT-TYPE
			SYNTAX Level
			MAX-ACCESS read-write
			STATUS current
			DESCRIPTION
				"This field is used in the following card types:
				onboard-sensors - The level for values between threshold 2 and threshold 3.
				analog-Inputs - The level for values between threshold 2 and threshold 3.
				analog-Sensors - The level for values between threshold 2 and threshold 3."
			::= { pSlot6Entry 19 }
		
		
		-- 1.3.6.1.4.1.994.3.4.7.23.1.20
		pSlot6Level3 OBJECT-TYPE
			SYNTAX Level
			MAX-ACCESS read-write
			STATUS current
			DESCRIPTION
				"This field is used in the following card types:
				onboard-sensors - The level for values between threshold 3 and threshold 4.
				analog-Inputs - The level for values between threshold 3 and threshold 4.
				analog-Sensors - The level for values between threshold 3 and threshold 4."
			::= { pSlot6Entry 20 }
		
		
		-- 1.3.6.1.4.1.994.3.4.7.23.1.21
		pSlot6Level4 OBJECT-TYPE
			SYNTAX Level
			MAX-ACCESS read-write
			STATUS current
			DESCRIPTION
				"This field is used in the following card types:
				onboard-sensors - The level for values between threshold 4 and threshold 5.
				analog-Inputs - The level for values between threshold 4 and threshold 5.
				analog-Sensors - The level for values between threshold 4 and threshold 5."
			::= { pSlot6Entry 21 }
		
		
		-- 1.3.6.1.4.1.994.3.4.7.23.1.22
		pSlot6Level5 OBJECT-TYPE
			SYNTAX Level
			MAX-ACCESS read-write
			STATUS current
			DESCRIPTION
				"This field is used in the following card types:
				analog-Inputs - Level of a communications failure to the sensor.
				analog-Sensors - Level of a communications failure to the sensor."
			::= { pSlot6Entry 22 }
		
		
		-- 1.3.6.1.4.1.994.3.4.7.23.1.23
		pSlot6ReadPeriod OBJECT-TYPE
			SYNTAX Integer32
			MAX-ACCESS read-write
			STATUS current
			DESCRIPTION
				"This field is used in the following card types:
				serial-ports - Inactivity timeout (in minutes)."
			::= { pSlot6Entry 23 }
		
		
		-- 1.3.6.1.4.1.994.3.4.7.23.1.28
		pSlot6Thresh0 OBJECT-TYPE
			SYNTAX DescriptionString
			MAX-ACCESS read-only
			STATUS current
			DESCRIPTION
				"This field is used in the following card types:
				onboard-sensors - This is the minimun analog value.
				analog-Inputs - This is the maximum analog value.
				analog-Sensors - This is the maximum analog value."
			::= { pSlot6Entry 28 }
		
		
		-- 1.3.6.1.4.1.994.3.4.7.23.1.29
		pSlot6Thresh1 OBJECT-TYPE
			SYNTAX DescriptionString
			MAX-ACCESS read-write
			STATUS current
			DESCRIPTION
				"This field is used in the following card types:
				onboard-sensors - This is the first threshold value.
				analog-Inputs - This is the first threshold value.
				analog-Sensors - This is the first threshold value."
			::= { pSlot6Entry 29 }
		
		
		-- 1.3.6.1.4.1.994.3.4.7.23.1.30
		pSlot6Thresh2 OBJECT-TYPE
			SYNTAX DescriptionString
			MAX-ACCESS read-write
			STATUS current
			DESCRIPTION
				"This field is used in the following card types:
				onboard-sensors - This is the second threshold value.
				analog-Inputs - This is the second threshold value.
				analog-Sensors - This is the second threshold value."
			::= { pSlot6Entry 30 }
		
		
		-- 1.3.6.1.4.1.994.3.4.7.23.1.31
		pSlot6Thresh3 OBJECT-TYPE
			SYNTAX DescriptionString
			MAX-ACCESS read-write
			STATUS current
			DESCRIPTION
				"This field is used in the following card types:
				onboard-sensors - This is the third threshold value.
				analog-Inputs - This is the third threshold value.
				analog-Sensors - This is the third threshold value."
			::= { pSlot6Entry 31 }
		
		
		-- 1.3.6.1.4.1.994.3.4.7.23.1.32
		pSlot6Thresh4 OBJECT-TYPE
			SYNTAX DescriptionString
			MAX-ACCESS read-write
			STATUS current
			DESCRIPTION
				"This field is used in the following card types:
				onboard-sensors - This is the fourth threshold value.
				analog-Inputs - This is the fourth threshold value.
				analog-Sensors - This is the fourth threshold value."
			::= { pSlot6Entry 32 }
		
		
		-- 1.3.6.1.4.1.994.3.4.7.23.1.33
		pSlot6Thresh5 OBJECT-TYPE
			SYNTAX DescriptionString
			MAX-ACCESS read-only
			STATUS current
			DESCRIPTION
				"This field is used in the following card types:
				onboard-sensors - This is the maximum threshold value.
				analog-Inputs - This is the minimum threshold value.
				analog-Sensors - This is the minimum threshold value."
			::= { pSlot6Entry 33 }
		
		
		-- 1.3.6.1.4.1.994.3.4.7.23.1.44
		pSlot6ContactStyle OBJECT-TYPE
			SYNTAX ContactStyle
			MAX-ACCESS read-write
			STATUS current
			DESCRIPTION
				"This field is used in the following card types:
				discrete-inputs - Determines the type of contact."
			::= { pSlot6Entry 44 }
		
		
		-- 1.3.6.1.4.1.994.3.4.7.23.1.46
		pSlot6Units OBJECT-TYPE
			SYNTAX DescriptionString
			MAX-ACCESS read-only
			STATUS current
			DESCRIPTION
				"This field is used in the following card types:
				onboard-sensors - Description of the units of measurement.
				analog-Inputs - Description of the units of measurement.
				analog-Sensors - Description of the units of measurement."
			::= { pSlot6Entry 46 }
		
		
		-- 1.3.6.1.4.1.994.3.4.7.23.1.47
		pSlot6OutputMode OBJECT-TYPE
			SYNTAX OutputMode
			MAX-ACCESS read-write
			STATUS current
			DESCRIPTION
				"This field is used in the following card types:
				discrete-outputs - Defines the different ways a control point can be activated."
			::= { pSlot6Entry 47 }
		
		
		-- 1.3.6.1.4.1.994.3.4.7.23.1.48
		pSlot6OutputState OBJECT-TYPE
			SYNTAX OutputState
			MAX-ACCESS read-write
			STATUS current
			DESCRIPTION
				"This field is used in the following card types:
				discrete-outputs - A value of 0 will open the control point.
				A value of 1 will close the control point."
			::= { pSlot6Entry 48 }
		
		
		-- 1.3.6.1.4.1.994.3.4.7.23.1.49
		pSlot6OutputAuto OBJECT-TYPE
			SYNTAX Integer32
			MAX-ACCESS read-write
			STATUS current
			DESCRIPTION
				"This field is used in the following card types:
				discrete-outputs - When this control point is opened, this alarm point will change state 
				to the on state."
			::= { pSlot6Entry 49 }
		
		
		-- 1.3.6.1.4.1.994.3.4.7.23.1.57
		pSlot6BaudRate OBJECT-TYPE
			SYNTAX BaudRate
			MAX-ACCESS read-write
			STATUS current
			DESCRIPTION
				"This field is used in the following card types:
				serial-ports - Baud rate of the serial port."
			::= { pSlot6Entry 57 }
		
		
		-- 1.3.6.1.4.1.994.3.4.7.23.1.58
		pSlot6DataBits OBJECT-TYPE
			SYNTAX DataBits
			MAX-ACCESS read-write
			STATUS current
			DESCRIPTION
				"This field is used in the following card types:
				serial-ports - Number of data bit for the serial port."
			::= { pSlot6Entry 58 }
		
		
		-- 1.3.6.1.4.1.994.3.4.7.23.1.59
		pSlot6Parity OBJECT-TYPE
			SYNTAX Parity
			MAX-ACCESS read-write
			STATUS current
			DESCRIPTION
				"This field is used in the following card types:
				serial-ports - Parity of the serial port."
			::= { pSlot6Entry 59 }
		
		
		-- 1.3.6.1.4.1.994.3.4.7.23.1.60
		pSlot6StopBits OBJECT-TYPE
			SYNTAX StopBits
			MAX-ACCESS read-write
			STATUS current
			DESCRIPTION
				"This field is used in the following card types:
				serial-ports - Number of stop bits for the serial port."
			::= { pSlot6Entry 60 }
		
		
		-- 1.3.6.1.4.1.994.3.4.7.23.1.61
		pSlot6Protocol OBJECT-TYPE
			SYNTAX Protocol
			MAX-ACCESS read-write
			STATUS current
			DESCRIPTION
				"This field is used in the following card types:
				serial-ports - Protocol the serial port is speaking."
			::= { pSlot6Entry 61 }
		
		
		-- 1.3.6.1.4.1.994.3.4.7.23.1.62
		pSlot6SerialRTS OBJECT-TYPE
			SYNTAX SerialRTS
			MAX-ACCESS read-write
			STATUS current
			DESCRIPTION
				"This field is used in the following card types:
				serial-ports - Request To Send (RTS) setting for the serial port."
			::= { pSlot6Entry 62 }
		
		
		-- 1.3.6.1.4.1.994.3.4.7.23.1.63
		pSlot6SerialCTS OBJECT-TYPE
			SYNTAX SerialCTS
			MAX-ACCESS read-write
			STATUS current
			DESCRIPTION
				"This field is used in the following card types:
				serial-ports - Clear To Send (CTS) setting for the serial port."
			::= { pSlot6Entry 63 }
		
		
		-- 1.3.6.1.4.1.994.3.4.7.23.1.64
		pSlot6LiveDescription OBJECT-TYPE
			SYNTAX DescriptionString
			MAX-ACCESS read-only
			STATUS current
			DESCRIPTION
				"This field is used in the following card types:
				discrete-inputs - The current description of the alarm state.
				onboard-sensors - The description of  the current state of the onboard sensor
				analog-Inputs - The description of  the current state of the analog input.
				analog-Sensors - The description of  the current state of the sensor input."
			::= { pSlot6Entry 64 }
		
		
		-- 1.3.6.1.4.1.994.3.4.7.23.1.65
		pSlot6LiveLevel OBJECT-TYPE
			SYNTAX DescriptionString
			MAX-ACCESS read-only
			STATUS current
			DESCRIPTION
				"This field is used in the following card types:
				discrete-inputs - The current level of the alarm.
				onboard-sensors - The level of the current state of the onboard sensor.
				analog-Inputs - The level of the current state of the analog input.
				analog-Sensors - The level of the current state of the sensor input."
			::= { pSlot6Entry 65 }
		
		
		-- 1.3.6.1.4.1.994.3.4.7.23.1.66
		pSlot6LiveRaw OBJECT-TYPE
			SYNTAX DescriptionString
			MAX-ACCESS read-only
			STATUS current
			DESCRIPTION
				"This field is used in the following card types:
				onboard-sensors - The current reading from the onboard sensor.  This value 
				will always be between the threshold 0 and threshold 5 values.
				analog-Inputs - The current reading from the analog input.  This value 
				will always be between the threshold 0 and threshold 5 values.
				analog-Sensors - The current reading from the sensor input.  This value 
				will always be between the threshold 0 and threshold 5 values."
			::= { pSlot6Entry 66 }
		
		
		-- 1.3.6.1.4.1.994.3.4.7.23.1.67
		pSlot6LiveTime OBJECT-TYPE
			SYNTAX DescriptionString
			MAX-ACCESS read-only
			STATUS current
			DESCRIPTION
				"This field is used in the following card types:
				discrete-inputs - The time of the last change of state.
				onboard-sensors - The time of the last event.
				analog-Inputs - The time of the last event.
				analog-Sensors - The time of the last event."
			::= { pSlot6Entry 67 }
		
		
		-- 1.3.6.1.4.1.994.3.4.7.23.1.68
		pSlot6Present OBJECT-TYPE
			SYNTAX Boolean
			MAX-ACCESS read-only
			STATUS current
			DESCRIPTION
				"This field is used in the following card types:
				serial-ports - If set to true, the serial port exists.
				If set to false the serial port does not exist."
			::= { pSlot6Entry 68 }
		
		
		-- 1.3.6.1.4.1.994.3.4.7.23.1.71
		pSlot6OutputAutoPkg OBJECT-TYPE
			SYNTAX Integer32
			MAX-ACCESS read-write
			STATUS current
			DESCRIPTION
				"This field is used in the following card types:
				discrete-outputs - When this control point is opened, this is the package that the alarm
				point is located."
			::= { pSlot6Entry 71 }
		
		
		-- 1.3.6.1.4.1.994.3.4.7.23.1.72
		pSlot6VoltageRange OBJECT-TYPE
			SYNTAX VoltageRange
			MAX-ACCESS read-only
			STATUS current
			DESCRIPTION
				"This field is used in the following card types:
				onboard-sensors - The voltage range.
				analog-Inputs - The voltage range.
				analog-Sensors - The voltage range."
			::= { pSlot6Entry 72 }
		
		
		-- 1.3.6.1.4.1.994.3.4.7.23.1.73
		pSlot6IPPortNum OBJECT-TYPE
			SYNTAX Integer32
			MAX-ACCESS read-write
			STATUS current
			DESCRIPTION
				"This field is used in the following card types:
				serial-ports - IP port number of the target device."
			::= { pSlot6Entry 73 }
		
		
		-- 1.3.6.1.4.1.994.3.4.7.23.1.75
		pSlot6IOFormat OBJECT-TYPE
			SYNTAX IOFormat
			MAX-ACCESS read-only
			STATUS current
			DESCRIPTION
				"This field is used in the following card types:
				discrete-inputs - The io format of discrete inputs.
				discrete-outputs - The io format of discrete outputs.
				serial-ports - The io format of serial ports.
				onboard-sensors - The io format of onboard sensors.
				analog-Inputs - The io format of analog inputs.
				analog-Sensors - The io format of analog sensors."
			::= { pSlot6Entry 75 }
		
		
		-- 1.3.6.1.4.1.994.3.4.7.23.1.76
		pSlot6PortType OBJECT-TYPE
			SYNTAX PortType
			MAX-ACCESS read-only
			STATUS current
			DESCRIPTION
				"This field is used in the following card types:
				serial-ports - The type of serial port."
			::= { pSlot6Entry 76 }
		
		
		-- 1.3.6.1.4.1.994.3.4.7.23.1.116
		pSlot6TL1SID OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot6Entry 116 }
		
		
		-- 1.3.6.1.4.1.994.3.4.7.23.1.117
		pSlot6TL1COND OBJECT-TYPE
			SYNTAX DescriptionString
			MAX-ACCESS read-write
			STATUS current
			DESCRIPTION
				"This field is used in the following card types:
				discrete-inputs - 
				discrete-outputs - 
				onboard-sensors - 
				analog-Inputs - 
				analog-Sensors - "
			::= { pSlot6Entry 117 }
		
		
		-- 1.3.6.1.4.1.994.3.4.7.23.1.118
		pSlot6TL1Eqpt OBJECT-TYPE
			SYNTAX DescriptionString
			MAX-ACCESS read-write
			STATUS current
			DESCRIPTION
				"This field is used in the following card types:
				discrete-inputs - 
				onboard-sensors - 
				analog-Inputs - 
				analog-Sensors - "
			::= { pSlot6Entry 118 }
		
		
		-- 1.3.6.1.4.1.994.3.4.7.23.1.119
		pSlot6TL1Env OBJECT-TYPE
			SYNTAX Boolean
			MAX-ACCESS read-write
			STATUS current
			DESCRIPTION
				"This field is used in the following card types:
				discrete-inputs - 
				onboard-sensors - 
				analog-Inputs - 
				analog-Sensors - "
			::= { pSlot6Entry 119 }
		
		
		-- 1.3.6.1.4.1.994.3.4.7.23.1.120
		pSlot6TL1Srveff OBJECT-TYPE
			SYNTAX TL1Srveff
			MAX-ACCESS read-write
			STATUS current
			DESCRIPTION
				"This field is used in the following card types:
				discrete-inputs - 
				onboard-sensors - 
				analog-Inputs - 
				analog-Sensors - "
			::= { pSlot6Entry 120 }
		
		
		-- 1.3.6.1.4.1.994.3.4.7.23.1.121
		pSlot6TL1Locn OBJECT-TYPE
			SYNTAX TL1Locn
			MAX-ACCESS read-write
			STATUS current
			DESCRIPTION
				"This field is used in the following card types:
				discrete-inputs - 
				onboard-sensors - 
				analog-Inputs - 
				analog-Sensors - "
			::= { pSlot6Entry 121 }
		
		
		-- 1.3.6.1.4.1.994.3.4.7.23.1.122
		pSlot6TL1Dirn OBJECT-TYPE
			SYNTAX TL1Dirn
			MAX-ACCESS read-write
			STATUS current
			DESCRIPTION
				"This field is used in the following card types:
				discrete-inputs - 
				onboard-sensors - 
				analog-Inputs - 
				analog-Sensors - "
			::= { pSlot6Entry 122 }
		
		
		-- 1.3.6.1.4.1.994.3.4.7.23.1.131
		pSlot6SensorType OBJECT-TYPE
			SYNTAX SensorType
			MAX-ACCESS read-write
			STATUS current
			DESCRIPTION
				"This field is used in the following card types:
				analog-Inputs - The type of sensor.
				analog-Sensors - The type of sensor."
			::= { pSlot6Entry 131 }
		
		
		-- 1.3.6.1.4.1.994.3.4.7.23.1.999
		pSlot6Index OBJECT-TYPE
			SYNTAX Integer32 (1..32)
			MAX-ACCESS read-only
			STATUS current
			DESCRIPTION
				"Index."
			::= { pSlot6Entry 999 }



		-- 1.3.6.1.4.1.994.3.4.7.999
		configObjectGroup OBJECT-GROUP
			OBJECTS { 
				systemGeneralLocation,
				systemGeneralDescription,
				systemGeneralIpAddress,
				systemGeneralSubnetMask,
				systemGeneralGatewayAddress,
				systemGeneralMeasureStyle,
				systemGeneralMacAddress,
				systemGeneralProductType,
				systemGeneralIPPortNum,
				systemGeneralVersion,
				pTrapTargetDescription,
				pTrapTargetConfigured,
				pTrapTargetIpAddress,
				pTrapTargetSnmpVersion,
				pTrapTargetIPPortNum,
				pTrapTargetBackupIPAddress,
				pTrapTargetUseDialout,
				pTrapTargetDialoutTarget,
				pTrapTargetAuthKey,
				pTrapTargetPrivKey,
				pTrapTargetSNMPAccess,
				pTrapTargetEngineID,
				pTrapTargetIndex,
				pEmailAddress,
				pEmailDescription,
				pEmailConfigured,
				pEmailIndex,
				pRemoteSensorDescription,
				pRemoteSensorDesc0,
				pRemoteSensorDesc1,
				pRemoteSensorDesc2,
				pRemoteSensorDesc3,
				pRemoteSensorDesc4,
				pRemoteSensorDesc5,
				pRemoteSensorConfigured,
				pRemoteSensorSendEmail,
				pRemoteSensorSendSNMPTrap,
				pRemoteSensorLevel0,
				pRemoteSensorLevel1,
				pRemoteSensorLevel2,
				pRemoteSensorLevel3,
				pRemoteSensorLevel4,
				pRemoteSensorLevel5,
				pRemoteSensorThresh0,
				pRemoteSensorThresh1,
				pRemoteSensorThresh2,
				pRemoteSensorThresh3,
				pRemoteSensorThresh4,
				pRemoteSensorThresh5,
				pRemoteSensorUnits,
				pRemoteSensorPollAddress,
				pRemoteSensorLiveDescription,
				pRemoteSensorLiveLevel,
				pRemoteSensorLiveRaw,
				pRemoteSensorLiveTime,
				pRemoteSensorTL1SID,
				pRemoteSensorTL1COND,
				pRemoteSensorTL1Eqpt,
				pRemoteSensorTL1Env,
				pRemoteSensorTL1Srveff,
				pRemoteSensorTL1Locn,
				pRemoteSensorTL1Dirn,
				pRemoteSensorMODBUSCommand,
				pRemoteSensorStartRegister,
				pRemoteSensorIndex,
				pOnboardSensorDescription,
				pOnboardSensorDesc0,
				pOnboardSensorDesc1,
				pOnboardSensorDesc2,
				pOnboardSensorDesc3,
				pOnboardSensorDesc4,
				pOnboardSensorDesc5,
				pOnboardSensorConfigured,
				pOnboardSensorSendEmail,
				pOnboardSensorSendSNMPTrap,
				pOnboardSensorLevel0,
				pOnboardSensorLevel1,
				pOnboardSensorLevel2,
				pOnboardSensorLevel3,
				pOnboardSensorLevel4,
				pOnboardSensorLevel5,
				pOnboardSensorThresh0,
				pOnboardSensorThresh1,
				pOnboardSensorThresh2,
				pOnboardSensorThresh3,
				pOnboardSensorThresh4,
				pOnboardSensorThresh5,
				pOnboardSensorUnits,
				pOnboardSensorLiveDescription,
				pOnboardSensorLiveLevel,
				pOnboardSensorLiveRaw,
				pOnboardSensorLiveTime,
				pOnboardSensorTL1SID,
				pOnboardSensorTL1COND,
				pOnboardSensorTL1Eqpt,
				pOnboardSensorTL1Env,
				pOnboardSensorTL1Srveff,
				pOnboardSensorTL1Locn,
				pOnboardSensorTL1Dirn,
				pOnboardSensorIndex,
				pNetDevicesDescription,
				pNetDevicesDesc0,
				pNetDevicesDesc1,
				pNetDevicesConfigured,
				pNetDevicesSendEmail,
				pNetDevicesSendSNMPTrap,
				pNetDevicesIpAddress,
				pNetDevicesLevel0,
				pNetDevicesLevel1,
				pNetDevicesLiveDescription,
				pNetDevicesLiveLevel,
				pNetDevicesLiveRaw,
				pNetDevicesLiveTime,
				pNetDevicesTL1SID,
				pNetDevicesTL1COND,
				pNetDevicesTL1Eqpt,
				pNetDevicesTL1Env,
				pNetDevicesTL1Srveff,
				pNetDevicesTL1Locn,
				pNetDevicesTL1Dirn,
				pNetDevicesIndex,
				pAccountsConfigured,
				pAccountsName,
				pAccountsEncPassword,
				pAccountsUserLevel,
				pAccountsUnsecured,
				pAccountsAuthKey,
				pAccountsPrivKey,
				pAccountsSNMPAccess,
				pAccountsIndex,
				cameraConfigured,
				cameraIpAddress,
				cameraCameraStyle,
				snmpGeneralConfigured,
				snmpGeneralReadPeriod,
				snmpGeneralGet,
				snmpGeneralSet,
				snmpGeneralTrap,
				snmpGeneralIPPortNum,
				snmpGeneralEngineID,
				emailGeneralAddress,
				emailGeneralConfigured,
				emailGeneralIpAddress,
				emailGeneralPassword,
				emailGeneralIPPortNum,
				pSerialDescription,
				pSerialConfigured,
				pSerialIpAddress,
				pSerialReadPeriod,
				pSerialBaudRate,
				pSerialDataBits,
				pSerialParity,
				pSerialStopBits,
				pSerialProtocol,
				pSerialSerialRTS,
				pSerialSerialCTS,
				pSerialPresent,
				pSerialIPPortNum,
				pSerialPortType,
				pSerialIndex,
				pSelfTestDescription,
				pSelfTestConfigured,
				pSelfTestIndex,
				pInternalFaultsDescription,
				pInternalFaultsDesc0,
				pInternalFaultsDesc1,
				pInternalFaultsDesc2,
				pInternalFaultsDesc3,
				pInternalFaultsSendEmail,
				pInternalFaultsSendSNMPTrap,
				pInternalFaultsLevel0,
				pInternalFaultsLevel1,
				pInternalFaultsLevel2,
				pInternalFaultsLevel3,
				pInternalFaultsIgnoreOff,
				pInternalFaultsLiveDescription,
				pInternalFaultsLiveLevel,
				pInternalFaultsLiveTime,
				pInternalFaultsIndex,
				pSlotInfoDescription,
				pSlotInfoRecord,
				pSlotInfoPresent,
				pSlotInfoSlotId,
				pSlotInfoIndex,
				pNetPortsDescription,
				pNetPortsIPPortNum,
				pNetPortsIndex,
				wirelessModemBackupIPAddress,
				wirelessModemTime,
				wirelessModemTransmit,
				wirelessModemUseWirelessNetwork,
				wirelessModemUseResetTime,
				wirelessModemResponseWaitTime,
				wirelessModemSecondary,
				webmonSecurityUserLevel,
				webmonSecurityUnsecured,
				dateTimeConfigured,
				dateTimeIpAddress,
				dateTimeDaylightSaving,
				dateTimeDate,
				dateTimeTime,
				dateTimeNegOffset,
				dateTimeUTCOffset,
				pDCMProtocolDescription,
				pDCMProtocolConfigured,
				pDCMProtocolBaseDCMAddress,
				pDCMProtocolIndex,
				pdialOutConfigured,
				pdialOutName,
				pdialOutPassword,
				pdialOutDialOutNumber,
				pdialOutIndex,
				pderivedDiscreteDescription,
				pderivedDiscreteDesc0,
				pderivedDiscreteDesc1,
				pderivedDiscreteConfigured,
				pderivedDiscreteSendEmail,
				pderivedDiscreteSendSNMPTrap,
				pderivedDiscreteLevel0,
				pderivedDiscreteLevel1,
				pderivedDiscreteLiveDescription,
				pderivedDiscreteLiveLevel,
				pderivedDiscreteLiveTime,
				pderivedDiscreteElementAPkg,
				pderivedDiscreteElementAPoint,
				pderivedDiscreteElementBPkg,
				pderivedDiscreteElementBPoint,
				pderivedDiscreteDiscreteFormula,
				pderivedDiscreteTL1SID,
				pderivedDiscreteTL1COND,
				pderivedDiscreteTL1Eqpt,
				pderivedDiscreteTL1Env,
				pderivedDiscreteTL1Srveff,
				pderivedDiscreteTL1Locn,
				pderivedDiscreteTL1Dirn,
				pderivedDiscreteIndex,
				licenseDescription,
				licenseLicenseKey,
				licenseExpires,
				licenseAllowTL1,
				pe2aHostDescription,
				pe2aHostConfigured,
				pe2aHostIpAddress,
				pe2aHostLevel0,
				pe2aHostLevel1,
				pe2aHostLevel2,
				pe2aHostRosterID,
				pe2aHostPollAddress,
				pe2aHostIPPortNum,
				pe2aHostTL1SID,
				pe2aHostTL1COND,
				pe2aHostTL1Eqpt,
				pe2aHostTL1Env,
				pe2aHostTL1Srveff,
				pe2aHostTL1Locn,
				pe2aHostTL1Dirn,
				pe2aHostIndex,
				pderivedAnalogDescription,
				pderivedAnalogDesc0,
				pderivedAnalogDesc1,
				pderivedAnalogDesc2,
				pderivedAnalogDesc3,
				pderivedAnalogDesc4,
				pderivedAnalogConfigured,
				pderivedAnalogSendEmail,
				pderivedAnalogSendSNMPTrap,
				pderivedAnalogLevel0,
				pderivedAnalogLevel1,
				pderivedAnalogLevel2,
				pderivedAnalogLevel3,
				pderivedAnalogLevel4,
				pderivedAnalogThresh0,
				pderivedAnalogThresh1,
				pderivedAnalogThresh2,
				pderivedAnalogThresh3,
				pderivedAnalogThresh4,
				pderivedAnalogThresh5,
				pderivedAnalogUnits,
				pderivedAnalogLiveDescription,
				pderivedAnalogLiveLevel,
				pderivedAnalogLiveRaw,
				pderivedAnalogLiveTime,
				pderivedAnalogElementAPkg,
				pderivedAnalogElementAPoint,
				pderivedAnalogElementBPkg,
				pderivedAnalogElementBPoint,
				pderivedAnalogFormula,
				pderivedAnalogTL1SID,
				pderivedAnalogTL1COND,
				pderivedAnalogTL1Eqpt,
				pderivedAnalogTL1Env,
				pderivedAnalogTL1Srveff,
				pderivedAnalogTL1Locn,
				pderivedAnalogTL1Dirn,
				pderivedAnalogIndex,
				pgpsDescription,
				pgpsDesc0,
				pgpsDesc1,
				pgpsDesc2,
				pgpsDesc3,
				pgpsDesc4,
				pgpsConfigured,
				pgpsSendEmail,
				pgpsSendSNMPTrap,
				pgpsLevel0,
				pgpsLevel1,
				pgpsLevel2,
				pgpsLevel3,
				pgpsLevel4,
				pgpsThresh0,
				pgpsThresh1,
				pgpsThresh2,
				pgpsThresh3,
				pgpsThresh4,
				pgpsThresh5,
				pgpsUnits,
				pgpsLiveDescription,
				pgpsLiveLevel,
				pgpsLiveRaw,
				pgpsLiveTime,
				pgpsTL1SID,
				pgpsTL1COND,
				pgpsTL1Eqpt,
				pgpsTL1Env,
				pgpsTL1Srveff,
				pgpsTL1Locn,
				pgpsTL1Dirn,
				pgpsIndex,
				pportRedirectDescription,
				pportRedirectConfigured,
				pportRedirectIpAddress,
				pportRedirectReadPeriod,
				pportRedirectRosterID,
				pportRedirectIPPortNum,
				pportRedirectIndex,
				pscheduleADayOfWeek,
				pscheduleAConfiguredState,
				pscheduleAConfigured1,
				pscheduleAConfigured2,
				pscheduleAConfigured3,
				pscheduleAConfigured4,
				pscheduleATime0,
				pscheduleATime1,
				pscheduleATime2,
				pscheduleATime3,
				pscheduleATime4,
				pscheduleATime5,
				pscheduleAIndex,
				pscheduleBDayOfWeek,
				pscheduleBConfiguredState,
				pscheduleBConfigured1,
				pscheduleBConfigured2,
				pscheduleBConfigured3,
				pscheduleBConfigured4,
				pscheduleBTime0,
				pscheduleBTime1,
				pscheduleBTime2,
				pscheduleBTime3,
				pscheduleBTime4,
				pscheduleBTime5,
				pscheduleBIndex,
				pscheduleCDayOfWeek,
				pscheduleCConfiguredState,
				pscheduleCConfigured1,
				pscheduleCConfigured2,
				pscheduleCConfigured3,
				pscheduleCConfigured4,
				pscheduleCTime0,
				pscheduleCTime1,
				pscheduleCTime2,
				pscheduleCTime3,
				pscheduleCTime4,
				pscheduleCTime5,
				pscheduleCIndex,
				pscheduleDDayOfWeek,
				pscheduleDConfiguredState,
				pscheduleDConfigured1,
				pscheduleDConfigured2,
				pscheduleDConfigured3,
				pscheduleDConfigured4,
				pscheduleDTime0,
				pscheduleDTime1,
				pscheduleDTime2,
				pscheduleDTime3,
				pscheduleDTime4,
				pscheduleDTime5,
				pscheduleDIndex,
				tl1SettingsTL1Issue,
				pDCPFProtocolDescription,
				pDCPFProtocolConfigured,
				pDCPFProtocolBaseDCPFDisplay,
				pDCPFProtocolIndex,
				dcpfSettingsDCPFAddress,
				pTABSProtocolDescription,
				pTABSProtocolConfigured,
				pTABSProtocolBaseTABSDisplay,
				pTABSProtocolIndex,
				tabsSettingsTABSAddress,
				psnmpCommandsDescription,
				psnmpCommandsConfigured,
				psnmpCommandsIpAddress,
				psnmpCommandsGet,
				psnmpCommandsSnmpVersion,
				psnmpCommandsOutputAuto,
				psnmpCommandsOutputAutoPkg,
				psnmpCommandsIPPortNum,
				psnmpCommandsOID,
				psnmpCommandsSNMPVarbindType,
				psnmpCommandsTextNormal,
				psnmpCommandsTextCritical,
				psnmpCommandsTextMajor,
				psnmpCommandsTextMinor,
				psnmpCommandsTextStatus,
				psnmpCommandsIndex,
				battMonConfigured,
				battMonOutputAuto,
				battMonOutputAutoPkg,
				pBankInfoDescription,
				pBankInfoConfigured,
				pBankInfoPresent,
				pBankInfoSlotId,
				pBankInfoIOFormat,
				pBankInfoIndex,
				pSlot1Description,
				pSlot1Desc0,
				pSlot1Desc1,
				pSlot1Desc2,
				pSlot1Desc3,
				pSlot1Desc4,
				pSlot1Desc5,
				pSlot1Configured,
				pSlot1SendEmail,
				pSlot1SendSNMPTrap,
				pSlot1IpAddress,
				pSlot1Level0,
				pSlot1Level1,
				pSlot1Level2,
				pSlot1Level3,
				pSlot1Level4,
				pSlot1Level5,
				pSlot1ReadPeriod,
				pSlot1Thresh0,
				pSlot1Thresh1,
				pSlot1Thresh2,
				pSlot1Thresh3,
				pSlot1Thresh4,
				pSlot1Thresh5,
				pSlot1ContactStyle,
				pSlot1Units,
				pSlot1OutputMode,
				pSlot1OutputState,
				pSlot1OutputAuto,
				pSlot1BaudRate,
				pSlot1DataBits,
				pSlot1Parity,
				pSlot1StopBits,
				pSlot1Protocol,
				pSlot1SerialRTS,
				pSlot1SerialCTS,
				pSlot1LiveDescription,
				pSlot1LiveLevel,
				pSlot1LiveRaw,
				pSlot1LiveTime,
				pSlot1Present,
				pSlot1OutputAutoPkg,
				pSlot1VoltageRange,
				pSlot1IPPortNum,
				pSlot1IOFormat,
				pSlot1PortType,
				pSlot1TL1SID,
				pSlot1TL1COND,
				pSlot1TL1Eqpt,
				pSlot1TL1Env,
				pSlot1TL1Srveff,
				pSlot1TL1Locn,
				pSlot1TL1Dirn,
				pSlot1SensorType,
				pSlot1Index,
				pSlot2Description,
				pSlot2Desc0,
				pSlot2Desc1,
				pSlot2Desc2,
				pSlot2Desc3,
				pSlot2Desc4,
				pSlot2Desc5,
				pSlot2Configured,
				pSlot2SendEmail,
				pSlot2SendSNMPTrap,
				pSlot2IpAddress,
				pSlot2Level0,
				pSlot2Level1,
				pSlot2Level2,
				pSlot2Level3,
				pSlot2Level4,
				pSlot2Level5,
				pSlot2ReadPeriod,
				pSlot2Thresh0,
				pSlot2Thresh1,
				pSlot2Thresh2,
				pSlot2Thresh3,
				pSlot2Thresh4,
				pSlot2Thresh5,
				pSlot2ContactStyle,
				pSlot2Units,
				pSlot2OutputMode,
				pSlot2OutputState,
				pSlot2OutputAuto,
				pSlot2BaudRate,
				pSlot2DataBits,
				pSlot2Parity,
				pSlot2StopBits,
				pSlot2Protocol,
				pSlot2SerialRTS,
				pSlot2SerialCTS,
				pSlot2LiveDescription,
				pSlot2LiveLevel,
				pSlot2LiveRaw,
				pSlot2LiveTime,
				pSlot2Present,
				pSlot2OutputAutoPkg,
				pSlot2VoltageRange,
				pSlot2IPPortNum,
				pSlot2IOFormat,
				pSlot2PortType,
				pSlot2TL1SID,
				pSlot2TL1COND,
				pSlot2TL1Eqpt,
				pSlot2TL1Env,
				pSlot2TL1Srveff,
				pSlot2TL1Locn,
				pSlot2TL1Dirn,
				pSlot2SensorType,
				pSlot2Index,
				pSlot3Description,
				pSlot3Desc0,
				pSlot3Desc1,
				pSlot3Desc2,
				pSlot3Desc3,
				pSlot3Desc4,
				pSlot3Desc5,
				pSlot3Configured,
				pSlot3SendEmail,
				pSlot3SendSNMPTrap,
				pSlot3IpAddress,
				pSlot3Level0,
				pSlot3Level1,
				pSlot3Level2,
				pSlot3Level3,
				pSlot3Level4,
				pSlot3Level5,
				pSlot3ReadPeriod,
				pSlot3Thresh0,
				pSlot3Thresh1,
				pSlot3Thresh2,
				pSlot3Thresh3,
				pSlot3Thresh4,
				pSlot3Thresh5,
				pSlot3ContactStyle,
				pSlot3Units,
				pSlot3OutputMode,
				pSlot3OutputState,
				pSlot3OutputAuto,
				pSlot3BaudRate,
				pSlot3DataBits,
				pSlot3Parity,
				pSlot3StopBits,
				pSlot3Protocol,
				pSlot3SerialRTS,
				pSlot3SerialCTS,
				pSlot3LiveDescription,
				pSlot3LiveLevel,
				pSlot3LiveRaw,
				pSlot3LiveTime,
				pSlot3Present,
				pSlot3OutputAutoPkg,
				pSlot3VoltageRange,
				pSlot3IPPortNum,
				pSlot3IOFormat,
				pSlot3PortType,
				pSlot3TL1SID,
				pSlot3TL1COND,
				pSlot3TL1Eqpt,
				pSlot3TL1Env,
				pSlot3TL1Srveff,
				pSlot3TL1Locn,
				pSlot3TL1Dirn,
				pSlot3SensorType,
				pSlot3Index,
				pSlot4Description,
				pSlot4Desc0,
				pSlot4Desc1,
				pSlot4Desc2,
				pSlot4Desc3,
				pSlot4Desc4,
				pSlot4Desc5,
				pSlot4Configured,
				pSlot4SendEmail,
				pSlot4SendSNMPTrap,
				pSlot4IpAddress,
				pSlot4Level0,
				pSlot4Level1,
				pSlot4Level2,
				pSlot4Level3,
				pSlot4Level4,
				pSlot4Level5,
				pSlot4ReadPeriod,
				pSlot4Thresh0,
				pSlot4Thresh1,
				pSlot4Thresh2,
				pSlot4Thresh3,
				pSlot4Thresh4,
				pSlot4Thresh5,
				pSlot4ContactStyle,
				pSlot4Units,
				pSlot4OutputMode,
				pSlot4OutputState,
				pSlot4OutputAuto,
				pSlot4BaudRate,
				pSlot4DataBits,
				pSlot4Parity,
				pSlot4StopBits,
				pSlot4Protocol,
				pSlot4SerialRTS,
				pSlot4SerialCTS,
				pSlot4LiveDescription,
				pSlot4LiveLevel,
				pSlot4LiveRaw,
				pSlot4LiveTime,
				pSlot4Present,
				pSlot4OutputAutoPkg,
				pSlot4VoltageRange,
				pSlot4IPPortNum,
				pSlot4IOFormat,
				pSlot4PortType,
				pSlot4TL1SID,
				pSlot4TL1COND,
				pSlot4TL1Eqpt,
				pSlot4TL1Env,
				pSlot4TL1Srveff,
				pSlot4TL1Locn,
				pSlot4TL1Dirn,
				pSlot4SensorType,
				pSlot4Index,
				pSlot5Description,
				pSlot5Desc0,
				pSlot5Desc1,
				pSlot5Desc2,
				pSlot5Desc3,
				pSlot5Desc4,
				pSlot5Desc5,
				pSlot5Configured,
				pSlot5SendEmail,
				pSlot5SendSNMPTrap,
				pSlot5IpAddress,
				pSlot5Level0,
				pSlot5Level1,
				pSlot5Level2,
				pSlot5Level3,
				pSlot5Level4,
				pSlot5Level5,
				pSlot5ReadPeriod,
				pSlot5Thresh0,
				pSlot5Thresh1,
				pSlot5Thresh2,
				pSlot5Thresh3,
				pSlot5Thresh4,
				pSlot5Thresh5,
				pSlot5ContactStyle,
				pSlot5Units,
				pSlot5OutputMode,
				pSlot5OutputState,
				pSlot5OutputAuto,
				pSlot5BaudRate,
				pSlot5DataBits,
				pSlot5Parity,
				pSlot5StopBits,
				pSlot5Protocol,
				pSlot5SerialRTS,
				pSlot5SerialCTS,
				pSlot5LiveDescription,
				pSlot5LiveLevel,
				pSlot5LiveRaw,
				pSlot5LiveTime,
				pSlot5Present,
				pSlot5OutputAutoPkg,
				pSlot5VoltageRange,
				pSlot5IPPortNum,
				pSlot5IOFormat,
				pSlot5PortType,
				pSlot5TL1SID,
				pSlot5TL1COND,
				pSlot5TL1Eqpt,
				pSlot5TL1Env,
				pSlot5TL1Srveff,
				pSlot5TL1Locn,
				pSlot5TL1Dirn,
				pSlot5SensorType,
				pSlot5Index,
				pSlot6Description,
				pSlot6Desc0,
				pSlot6Desc1,
				pSlot6Desc2,
				pSlot6Desc3,
				pSlot6Desc4,
				pSlot6Desc5,
				pSlot6Configured,
				pSlot6SendEmail,
				pSlot6SendSNMPTrap,
				pSlot6IpAddress,
				pSlot6Level0,
				pSlot6Level1,
				pSlot6Level2,
				pSlot6Level3,
				pSlot6Level4,
				pSlot6Level5,
				pSlot6ReadPeriod,
				pSlot6Thresh0,
				pSlot6Thresh1,
				pSlot6Thresh2,
				pSlot6Thresh3,
				pSlot6Thresh4,
				pSlot6Thresh5,
				pSlot6ContactStyle,
				pSlot6Units,
				pSlot6OutputMode,
				pSlot6OutputState,
				pSlot6OutputAuto,
				pSlot6BaudRate,
				pSlot6DataBits,
				pSlot6Parity,
				pSlot6StopBits,
				pSlot6Protocol,
				pSlot6SerialRTS,
				pSlot6SerialCTS,
				pSlot6LiveDescription,
				pSlot6LiveLevel,
				pSlot6LiveRaw,
				pSlot6LiveTime,
				pSlot6Present,
				pSlot6OutputAutoPkg,
				pSlot6VoltageRange,
				pSlot6IPPortNum,
				pSlot6IOFormat,
				pSlot6PortType,
				pSlot6TL1SID,
				pSlot6TL1COND,
				pSlot6TL1Eqpt,
				pSlot6TL1Env,
				pSlot6TL1Srveff,
				pSlot6TL1Locn,
				pSlot6TL1Dirn,
				pSlot6SensorType,
				pSlot6Index
			}
			STATUS current
			DESCRIPTION 
				"Description."
			::= { configuration 999 }



--
-- Trap definitions
--
 
		notificationGroup NOTIFICATION-GROUP
			NOTIFICATIONS { analogEventTrap, remoteDeviceEventTrap, faultTrap, digitalEventTrap }
			STATUS current
			DESCRIPTION
				"Group containing all the notification types."
			::= { webMon 4 }
		
		objectGroup OBJECT-GROUP
			OBJECTS { systemGeneralDescription, 
                   systemGeneralLocation, 
                   analogInputDescription, 
                   analogLiveLevel, 
                   analogLiveReading, 
                   analogUnitsOfMeasurement, 
                   analogLiveState, 
                   analogLiveStateDescription,
                   analogAlarmState,
                   analogSourceDescription,
                   analogSourceIndex, 
                   digitalInputDescription,
                   digitalAlarmState, 
                   digitalLiveLevel, 
                   digitalLiveState, 
                   digitalLiveStateDescription,
                   digitalSourceDescription,
                   digitalSourceIndex, 
                   remoteDeviceDescription, 
                   remoteDeviceLiveLevel, 
                   remoteDeviceLiveState,
                   remoteDeviceAlarmState,
                   remoteDeviceSourceDescription,
                   remoteDeviceSourceIndex,
                   faultDescription, 
                   faultLiveLevel, 
                   faultStateDescription,
                   faultAlarmState,
                   faultSourceDescription,
                   faultSourceIndex  }
			STATUS current
			DESCRIPTION
				"Group containing all the objects."
			::= { webMon 5 }
		
		traps OBJECT-IDENTITY
			STATUS current
			DESCRIPTION
				"Category containing all the traps.  Each trap has sibling data nodes 
				that contain the data associated with the most recently sent trap
				of that particular type.  A GET-REQUEST sent to the WebMon for those
				data nodes will allow you to verify the data received in a recent
				trap."
			::= { webMon 6 }
		
		analogInputs OBJECT-IDENTITY
			STATUS current
			DESCRIPTION
				"Subtree containing trap and associated data for analog inputs.
				
				Analog inputs measure a value.  The input always has a live 
				reading, but traps are only sent on events, which are defined as 
				the live reading crossing (or passing) one of the user-defined 
				thresholds.  
				"
			::= { traps 1 }
		
		analogEventTrap NOTIFICATION-TYPE
			OBJECTS { systemGeneralDescription, 
                   systemGeneralLocation, 
                   analogInputDescription, 
                   analogLiveLevel, 
                   analogLiveReading, 
                   analogLiveState, 
                   analogLiveStateDescription, 
                   analogUnitsOfMeasurement,
                   analogAlarmState,
                   analogSourceDescription,
                   analogSourceIndex}
			STATUS current
			DESCRIPTION
				"Notification sent upon an analog input reading crossing a 
				threshold."
			::= { analogInputs 1 }
		
		analogInputDescription OBJECT-TYPE
			SYNTAX DescriptionString
			MAX-ACCESS read-only
			STATUS current
			DESCRIPTION
				"Description of the analog input."
			::= { analogInputs 2 }
		
		analogLiveLevel OBJECT-TYPE
			SYNTAX Level
			MAX-ACCESS read-only
			STATUS current
			DESCRIPTION
				"The level associated with the analogLiveReading for this input."
			::= { analogInputs 3 }
		
		analogLiveReading OBJECT-TYPE
			SYNTAX DescriptionString
			MAX-ACCESS read-only
			STATUS current
			DESCRIPTION
				"The reading from the analog input described by 
				analogInputDescription at the time the trap was sent.  It is in the 
				units described in analogUnitsOfMeasurement."
			::= { analogInputs 5 }
		
		analogUnitsOfMeasurement OBJECT-TYPE
			SYNTAX DescriptionString
			MAX-ACCESS read-only
			STATUS current
			DESCRIPTION
				"The units of measurement associated with the analogLiveReading."
			::= { analogInputs 6 }
		
		analogLiveState OBJECT-TYPE
			SYNTAX AnalogState
			MAX-ACCESS read-only
			STATUS current
			DESCRIPTION
				"The state associated with analogLiveReading."
			::= { analogInputs 7 }
		
		analogLiveStateDescription OBJECT-TYPE
			SYNTAX DescriptionString
			MAX-ACCESS read-only
			STATUS current
			DESCRIPTION
				"The description of the range in which the analogLiveReading is."
			::= { analogInputs 8 }

      analogAlarmState OBJECT-TYPE
         SYNTAX Boolean
         MAX-ACCESS read-only
         STATUS current
         DESCRIPTION
            "If true this field indicates the alarmed state.  
             If false this field indicates the not alarmed state."
         ::= { analogInputs 9}
         
		analogSourceDescription OBJECT-TYPE
			SYNTAX DescriptionString
			MAX-ACCESS not-accessible
			STATUS current
			DESCRIPTION
				"Description of the event source."
			::= { analogInputs 101 }
		
		analogSourceIndex OBJECT-TYPE
			SYNTAX Integer32
			MAX-ACCESS not-accessible
			STATUS current
			DESCRIPTION
				"Index of the event source."
			::= { analogInputs 102 }
		
		digitalInputs OBJECT-IDENTITY
			STATUS current
			DESCRIPTION
				"Subtree containing trap and associated data for digital inputs.
				
				Digital inputs monitor a binary state.  The input is always in one 
				of two states.  Traps are sent on events, which are defined as a
				change in the live state."
			::= { traps 2 }
		
		digitalEventTrap NOTIFICATION-TYPE
			OBJECTS { systemGeneralDescription, 
                   systemGeneralLocation, 
                   digitalInputDescription, 
			          digitalLiveLevel, 
			          digitalLiveState, 
			          digitalLiveStateDescription,
			          digitalAlarmState,
			          digitalSourceDescription,
			          digitalSourceIndex}
			STATUS current
			DESCRIPTION
				"Notification sent upon change of state on a digital input."
			::= { digitalInputs 1 }
		
		digitalInputDescription OBJECT-TYPE
			SYNTAX DescriptionString
			MAX-ACCESS read-only
			STATUS current
			DESCRIPTION
				"Description of the digital input."
			::= { digitalInputs 2 }
		
		digitalLiveLevel OBJECT-TYPE
			SYNTAX Level
			MAX-ACCESS read-only
			STATUS current
			DESCRIPTION
				"The level associated with digitalLiveState for this input."
			::= { digitalInputs 3 }
		
		digitalLiveState OBJECT-TYPE
			SYNTAX DigitalState
			MAX-ACCESS read-only
			STATUS current
			DESCRIPTION
				"The state of the digital input described by digitalInputDescription 
				at the time the trap was sent."
			::= { digitalInputs 4 }
		
		digitalLiveStateDescription OBJECT-TYPE
			SYNTAX DescriptionString
			MAX-ACCESS read-only
			STATUS current
			DESCRIPTION
				"The description of the digitalLiveState."
			::= { digitalInputs 5 }
		
      digitalAlarmState OBJECT-TYPE
         SYNTAX Boolean
         MAX-ACCESS read-only
         STATUS current
         DESCRIPTION
            "If true this field indicates the alarmed state.  
             If false this field indicates the not alarmed state."
         ::= {digitalInputs 6}
         
		digitalSourceDescription OBJECT-TYPE
			SYNTAX DescriptionString
			MAX-ACCESS not-accessible
			STATUS current
			DESCRIPTION
				"Description of the event source."
			::= { digitalInputs 101 }
		
		digitalSourceIndex OBJECT-TYPE
			SYNTAX Integer32
			MAX-ACCESS not-accessible
			STATUS current
			DESCRIPTION
				"Index of the event source."
			::= { digitalInputs 102 }
		
         
		remoteDevices OBJECT-IDENTITY
			STATUS current
			DESCRIPTION
				"Subtree containing trap and associated data for monitored remote 
				devices.
				
				Remote devices are monitored for network connectivity.  The device's
				live state is always either online or offline.  Traps are sent on 
				events, which are defined as a change in the live state."
			::= { traps 3 }
		
		remoteDeviceEventTrap NOTIFICATION-TYPE
			OBJECTS { systemGeneralDescription, 
                   systemGeneralLocation, 
                   remoteDeviceDescription, 
                   remoteDeviceLiveState, 
                   remoteDeviceLiveLevel,
                   remoteDeviceAlarmState,
                   remoteDeviceSourceDescription,
                   remoteDeviceSourceIndex }
			STATUS current
			DESCRIPTION
				"Notification sent upon change of state of a remote device."
			::= { remoteDevices 1 }
		
		remoteDeviceDescription OBJECT-TYPE
			SYNTAX DescriptionString
			MAX-ACCESS read-only
			STATUS current
			DESCRIPTION
				"Description of the remote device."
			::= { remoteDevices 2 }
		
		remoteDeviceLiveLevel OBJECT-TYPE
			SYNTAX Level
			MAX-ACCESS read-only
			STATUS current
			DESCRIPTION
				"The level associated with remoteDeviceLiveState."
			::= { remoteDevices 3 }
		
		remoteDeviceLiveState OBJECT-TYPE
			SYNTAX ConnectivityState
			MAX-ACCESS read-only
			STATUS current
			DESCRIPTION
				"The state of the remote device described by remoteDeviceDescription 
				at the time the trap was sent.  Online indicates connected, offline
				indicates not connected."
			::= { remoteDevices 4 }
   
      remoteDeviceAlarmState OBJECT-TYPE
         SYNTAX Boolean
         MAX-ACCESS read-only
         STATUS current
         DESCRIPTION
            "If true this field indicates the alarmed state.  
             If false this field indicates the not alarmed state."
         ::= { remoteDevices 5}
		
		remoteDeviceSourceDescription OBJECT-TYPE
			SYNTAX DescriptionString
			MAX-ACCESS not-accessible
			STATUS current
			DESCRIPTION
				"Description of the event source."
			::= { remoteDevices 101 }
		
		remoteDeviceSourceIndex OBJECT-TYPE
			SYNTAX Integer32
			MAX-ACCESS not-accessible
			STATUS current
			DESCRIPTION
				"Index of the event source."
			::= { remoteDevices 102 }
		
		faults OBJECT-IDENTITY
			STATUS current
			DESCRIPTION
				"Subtree containing trap and associated data for faults.
				
				Faults are conditions internal to the WebMon.  The only data 
				associated with this trap is a string that describes the condition."
			::= { traps 4 }
		
		faultTrap NOTIFICATION-TYPE
			OBJECTS { systemGeneralDescription, 
                   systemGeneralLocation, 
                   faultDescription, 
                   faultLiveLevel, 
                   faultStateDescription,
                   faultAlarmState,
                   faultSourceDescription,
                   faultSourceIndex}
			STATUS current
			DESCRIPTION
				"Notification sent when a fault is encountered."
			::= { faults 1 }
		
		faultDescription OBJECT-TYPE
			SYNTAX DescriptionString
			MAX-ACCESS read-only
			STATUS current
			DESCRIPTION
				"Description of the condition at the WebMon."
			::= { faults 2 }
		
		faultLiveLevel OBJECT-TYPE
			SYNTAX Level
			MAX-ACCESS read-only
			STATUS current
			DESCRIPTION
				"The level associated with faultStateDescription."
			::= { faults 3 }
		
		faultStateDescription  OBJECT-TYPE
			SYNTAX DescriptionString
			MAX-ACCESS read-only
			STATUS current
			DESCRIPTION
				"The description of the state of this fault."
			::= { faults 4 }
		
		faultAlarmState  OBJECT-TYPE
			SYNTAX Boolean
			MAX-ACCESS read-only
			STATUS current
			DESCRIPTION
            "If true this field indicates the alarmed state.  
             If false this field indicates the not alarmed state."
			::= { faults 5 }

		faultSourceDescription OBJECT-TYPE
			SYNTAX DescriptionString
			MAX-ACCESS not-accessible
			STATUS current
			DESCRIPTION
				"Description of the event source."
			::= { faults 101 }
		
		faultSourceIndex OBJECT-TYPE
			SYNTAX Integer32
			MAX-ACCESS not-accessible
			STATUS current
			DESCRIPTION
				"Index of the event source."
			::= { faults 102 }
		
	
	END

--
-- WEBMON-EDGE-MATRIX-MIB.my
--
