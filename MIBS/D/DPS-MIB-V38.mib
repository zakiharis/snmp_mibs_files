--  Title:    DPS_V41.MIB

--  Version:  v4.1

--

--  Copyright @ 1997-2004 DPS Inc. All Rights Reserved

--

--  This MIB defines objects for the DPS products.

--

--



DPS-MIB-V38 DEFINITIONS ::= BEGIN



IMPORTS

	DisplayString

		FROM RFC1213-MIB

	OBJECT-TYPE

		FROM RFC-1212

	enterprises

		FROM RFC1155-SMI;



dpsInc OBJECT IDENTIFIER ::= {enterprises  2682}



dpsAlarmControl OBJECT IDENTIFIER ::= {dpsInc 1}



tmonXM OBJECT IDENTIFIER ::= {dpsAlarmControl 1}



tmonIdent OBJECT IDENTIFIER ::= {tmonXM 1}



tmonIdentManufacturer OBJECT-TYPE

	SYNTAX  DisplayString

	ACCESS  read-only

	STATUS  mandatory

	DESCRIPTION "The TMON/XM Unit manufacturer."

	::= {tmonIdent  1}



tmonIdentModel OBJECT-TYPE

	SYNTAX  DisplayString

	ACCESS  read-only

	STATUS  mandatory

	DESCRIPTION "The TMON/XM model designation."

	::= {tmonIdent  2}



tmonIdentSoftwareVersion OBJECT-TYPE

	SYNTAX  DisplayString

	ACCESS  read-only

	STATUS  mandatory

	DESCRIPTION "The TMON/XM SNMP Agent software version."

	::= {tmonIdent  3}



tmonAlarmTable OBJECT-TYPE

	SYNTAX  SEQUENCE OF TMonAlarmEntry

	ACCESS  not-accessible

	STATUS  mandatory

	DESCRIPTION "A table of TMon Alarm-specific information."

	::= {tmonXM 2}



tmonAlarmEntry OBJECT-TYPE

	SYNTAX  TMonAlarmEntry

	ACCESS  not-accessible

	STATUS  mandatory

	DESCRIPTION "Information about a particular TMon alarm."

	INDEX   {tmonAIndex}

	::= {tmonAlarmTable 1}



TMonAlarmEntry ::= SEQUENCE  {tmonAIndex		INTEGER,

										tmonASite		DisplayString,

										tmonADesc		DisplayString,

										tmonAState		DisplayString,

										tmonASeverity	DisplayString,

										tmonAChgDate	DisplayString,

										tmonAChgTime	DisplayString,

										tmonAAuxDesc   DisplayString,

										tmonADispDesc  DisplayString,

										tmonAPntType	INTEGER,

										tmonAPort		INTEGER,

										tmonAAddress	INTEGER,

										tmonADisplay	INTEGER,

										tmonAPoint		INTEGER}



tmonAIndex OBJECT-TYPE

	SYNTAX  INTEGER

	ACCESS  read-only

	STATUS  mandatory

	DESCRIPTION "Tmon alarm table index (1..NumberOfAlarms)."

	::={tmonAlarmEntry 1}



tmonASite OBJECT-TYPE

	SYNTAX  DisplayString (SIZE (30))

	ACCESS  read-only

	STATUS  mandatory

	DESCRIPTION "The site of the alarm (i.e. Atlanta Hub, Sub-Station H32)."

	::= {tmonAlarmEntry 2}



tmonADesc OBJECT-TYPE

	SYNTAX  DisplayString (SIZE (40))

	ACCESS  read-only

	STATUS  mandatory

	DESCRIPTION "A user-defined text string associated with the alarm 

					 (i.e. South Door, Generator, Power Grid 1)."

	::= {tmonAlarmEntry 3}



tmonAState OBJECT-TYPE

	SYNTAX  DisplayString (SIZE (8))

	ACCESS  read-only

	STATUS  mandatory

	DESCRIPTION "The current alarm state."

	::= {tmonAlarmEntry 4}



tmonASeverity OBJECT-TYPE

	SYNTAX  DisplayString (SIZE (8))

	ACCESS  read-only

	STATUS  mandatory

	DESCRIPTION "The severity of the last alarm event."

	::= {tmonAlarmEntry 5}



tmonAChgDate OBJECT-TYPE

	SYNTAX  DisplayString (SIZE (8))

	ACCESS  read-only

	STATUS  mandatory

	DESCRIPTION "The date (mm/dd/yy) of the last alarm event."

	::= {tmonAlarmEntry 6}



tmonAChgTime OBJECT-TYPE

	SYNTAX  DisplayString (SIZE (8))

	ACCESS  read-only

	STATUS  mandatory

	DESCRIPTION "The time (hh:mm:ss) of the last alarm event."

	::= {tmonAlarmEntry 7}



tmonAAuxDesc OBJECT-TYPE

	SYNTAX  DisplayString (SIZE (30))

	ACCESS  read-only

	STATUS  mandatory

	DESCRIPTION "An auxiliary user-defined text string associated with the

					 alarm (i.e. This remote needs servicing)."

	::= {tmonAlarmEntry 8}



tmonADispDesc OBJECT-TYPE

	SYNTAX  DisplayString (SIZE (14))

	ACCESS  read-only

	STATUS  mandatory

	DESCRIPTION "A description of the display on which this point appears."

	::= {tmonAlarmEntry 9}



tmonAPntType OBJECT-TYPE

	SYNTAX  INTEGER

	ACCESS  read-only

	STATUS  mandatory

	DESCRIPTION "Type of this point."

	::={tmonAlarmEntry 10}



tmonAPort OBJECT-TYPE

	SYNTAX  INTEGER

	ACCESS  read-only

	STATUS  mandatory

	DESCRIPTION "Port on which this point is reported."

	::={tmonAlarmEntry 11}



tmonAAddress OBJECT-TYPE

	SYNTAX  INTEGER

	ACCESS  read-only

	STATUS  mandatory

	DESCRIPTION "Address of unit reporting this point."

	::={tmonAlarmEntry 12}



tmonADisplay OBJECT-TYPE

	SYNTAX  INTEGER

	ACCESS  read-only

	STATUS  mandatory

	DESCRIPTION "Display on which this point appears."

	::={tmonAlarmEntry 13}



tmonAPoint OBJECT-TYPE

	SYNTAX  INTEGER

	ACCESS  read-only

	STATUS  mandatory

	DESCRIPTION "Index into display of this point."

	::={tmonAlarmEntry 14}





-- structure used to issue a command to tmonXM element



tmonCommandGrid OBJECT IDENTIFIER ::= {tmonXM 3}



tmonCPType OBJECT-TYPE

	SYNTAX  INTEGER

	ACCESS  read-write

	STATUS  mandatory

	DESCRIPTION "Tmon point type."

	::= {tmonCommandGrid 1}



tmonCPort OBJECT-TYPE

	SYNTAX  INTEGER

	ACCESS  read-write

	STATUS  mandatory

	DESCRIPTION "Tmon port number."

	::= {tmonCommandGrid 2}



tmonCAddress OBJECT-TYPE

	SYNTAX  INTEGER

	ACCESS  read-write

	STATUS  mandatory

	DESCRIPTION "Tmon_port address number."

	::= {tmonCommandGrid 3}



tmonCDisplay OBJECT-TYPE

	SYNTAX  INTEGER

	ACCESS  read-write

	STATUS  mandatory

	DESCRIPTION "Tmon_port_address display number."

	::= {tmonCommandGrid 4}



tmonCPoint OBJECT-TYPE

	SYNTAX  INTEGER (1..64)

	ACCESS  read-write

	STATUS  mandatory

	DESCRIPTION "Tmon_port_display point number (1-64)."

	::= {tmonCommandGrid 5}



tmonCEvent OBJECT-TYPE

	SYNTAX  INTEGER

	ACCESS  read-write

	STATUS  mandatory

	DESCRIPTION "Tmon event ID."

	::= {tmonCommandGrid 6}



tmonCAction OBJECT-TYPE

	SYNTAX  INTEGER {	latch(1),

							release(2),

							momentary(3),

							ack(17),

							tag(18),

							untag(19)

						 }

	ACCESS  read-write

	STATUS  mandatory

	DESCRIPTION "Requested command action (tmonXM will ignore if invalid)."

	::= {tmonCommandGrid 7}



tmonCAuxText OBJECT-TYPE

	SYNTAX  DisplayString (SIZE (30))

	ACCESS  read-write

	STATUS  mandatory

	DESCRIPTION "An auxiliary user-defined text string associated with the

					 command (i.e. User_initials)."

	::= {tmonCommandGrid 8}



tmonCResult OBJECT-TYPE

	SYNTAX  INTEGER { success(1),

							failure(2),

							pending(3)

						 }

	ACCESS  read-only

	STATUS  mandatory

	DESCRIPTION "Command result."

	::= {tmonCommandGrid 9}







dpsRTU OBJECT IDENTIFIER ::= {dpsAlarmControl 2}



dpsRTUIdent OBJECT IDENTIFIER ::= {dpsRTU 1}



dpsRTUManufacturer OBJECT-TYPE

	SYNTAX  DisplayString (SIZE (30))

	ACCESS  read-only

	STATUS  mandatory

	DESCRIPTION "The Remote Telemetry Unit manufacturer."

	::= {dpsRTUIdent  1}



dpsRTUModel OBJECT-TYPE

	SYNTAX  DisplayString (SIZE (30))

	ACCESS  read-only

	STATUS  mandatory

	DESCRIPTION "The RTU model designation."

	::= {dpsRTUIdent  2}



dpsRTUFirmwareVersion OBJECT-TYPE

	SYNTAX  DisplayString (SIZE (20))

	ACCESS  read-only

	STATUS  mandatory

	DESCRIPTION "The RTU firmware version."

	::= {dpsRTUIdent  3}



dpsRTUDateTime OBJECT-TYPE

	SYNTAX  DisplayString (SIZE (23))

	ACCESS  read-write

	STATUS  mandatory

	DESCRIPTION "The RTU system date and time."

	::= {dpsRTUIdent  4}



dpsRTUSyncReq OBJECT-TYPE

	SYNTAX  INTEGER {	sync(1) }

	ACCESS  read-write

	STATUS  mandatory

	DESCRIPTION "Caution: SETting this object initiates traps for all

					 standing alarms."

	::= {dpsRTUIdent  5}





-- structure used to access displays managed by this RTU



dpsRTUDisplayGrid OBJECT-TYPE

	SYNTAX  SEQUENCE OF DPSrtuDispEntry

	ACCESS  not-accessible

	STATUS  mandatory

	DESCRIPTION "Holds information on displays managed by the RTU."

	::= {dpsRTU 2}



dpsRTUDisplayEntry OBJECT-TYPE

	SYNTAX  DPSrtuDispEntry

	ACCESS  not-accessible

	STATUS  mandatory

	DESCRIPTION "Information about a particular RTU display."

	INDEX   {dpsRTUPort, dpsRTUAddress, dpsRTUDisplay}

	::= {dpsRTUDisplayGrid 1}



DPSrtuDispEntry ::= SEQUENCE 	{	dpsRTUPort			INTEGER,

											dpsRTUAddress		INTEGER,

											dpsRTUDisplay		INTEGER,

											dpsRTUDispDesc		DisplayString,

											dpsRTUPntMap		DisplayString}



dpsRTUPort OBJECT-TYPE

	SYNTAX  INTEGER

	ACCESS  read-only

	STATUS  mandatory

	DESCRIPTION "RTU port number."

	::= {dpsRTUDisplayEntry 1}



dpsRTUAddress OBJECT-TYPE

	SYNTAX  INTEGER

	ACCESS  read-only

	STATUS  mandatory

	DESCRIPTION "RTU_port address number."

	::= {dpsRTUDisplayEntry 2}



dpsRTUDisplay OBJECT-TYPE

	SYNTAX  INTEGER

	ACCESS  read-only

	STATUS  mandatory

	DESCRIPTION "RTU_port_address display number."

	::= {dpsRTUDisplayEntry 3}



dpsRTUDispDesc OBJECT-TYPE

	SYNTAX  DisplayString (SIZE (20))

	ACCESS  read-only

	STATUS  mandatory

	DESCRIPTION "A description of the associated display."

	::= {dpsRTUDisplayEntry 4}



dpsRTUPntMap OBJECT-TYPE

	SYNTAX  DisplayString (SIZE (71))

	ACCESS  read-only

	STATUS  mandatory

	DESCRIPTION "A map of the points appearing in this display."

	::= {dpsRTUDisplayEntry 5}





-- structure used to issue a control to a managed point



dpsRTUControlGrid OBJECT IDENTIFIER ::= {dpsRTU 3}



dpsRTUCPort OBJECT-TYPE

	SYNTAX  INTEGER

	ACCESS  read-write

	STATUS  mandatory

	DESCRIPTION "RTU port number."

	::= {dpsRTUControlGrid 1}



dpsRTUCAddress OBJECT-TYPE

	SYNTAX  INTEGER

	ACCESS  read-write

	STATUS  mandatory

	DESCRIPTION "RTU_port address number."

	::= {dpsRTUControlGrid 2}



dpsRTUCDisplay OBJECT-TYPE

	SYNTAX  INTEGER

	ACCESS  read-write

	STATUS  mandatory

	DESCRIPTION "RTU_port_address display number."

	::= {dpsRTUControlGrid 3}



dpsRTUCPoint OBJECT-TYPE

	SYNTAX  INTEGER (1..64)

	ACCESS  read-write

	STATUS  mandatory

	DESCRIPTION "RTU_port_display point number (1-64)."

	::= {dpsRTUControlGrid 4}



dpsRTUCAction OBJECT-TYPE

	SYNTAX  INTEGER {	latch(1),

							release(2),

							momentary(3)

						 }

	ACCESS  read-write

	STATUS  mandatory

	DESCRIPTION "Requested action on point (RTU will ignore if invalid)."

	::= {dpsRTUControlGrid 5}







dpsRTUAlarmGrid OBJECT-TYPE

	SYNTAX  SEQUENCE OF DPSrtuAlarmEntry

	ACCESS  not-accessible

	STATUS  mandatory

	DESCRIPTION "Holds individual alarm point information."

	::= {dpsRTU 5}



dpsRTUAlarmEntry OBJECT-TYPE

	SYNTAX  DPSrtuAlarmEntry

	ACCESS  not-accessible

	STATUS  mandatory

	DESCRIPTION "Detailed information about a particular RTU display."

	INDEX   {dpsRTUAPort, dpsRTUAAddress, dpsRTUADisplay, dpsRTUAPoint}

	::= {dpsRTUAlarmGrid 1}



DPSrtuAlarmEntry ::= SEQUENCE	 {	dpsRTUAPort			INTEGER,

											dpsRTUAAddress		INTEGER,

											dpsRTUADisplay		INTEGER,

											dpsRTUAPoint		INTEGER,

											dpsRTUAPntDesc		DisplayString,

											dpsRTUAState		DisplayString}



dpsRTUAPort OBJECT-TYPE

	SYNTAX  INTEGER

	ACCESS  read-only

	STATUS  mandatory

	DESCRIPTION "RTU port number."

	::= {dpsRTUAlarmEntry 1}



dpsRTUAAddress OBJECT-TYPE

	SYNTAX  INTEGER

	ACCESS  read-only

	STATUS  mandatory

	DESCRIPTION "RTU_port address number."

	::= {dpsRTUAlarmEntry 2}



dpsRTUADisplay OBJECT-TYPE

	SYNTAX  INTEGER

	ACCESS  read-only

	STATUS  mandatory

	DESCRIPTION "RTU_port_address display number."

	::= {dpsRTUAlarmEntry 3}



dpsRTUAPoint OBJECT-TYPE

	SYNTAX  INTEGER

	ACCESS  read-only

	STATUS  mandatory

	DESCRIPTION "RTU_port_address_display point number."

	::= {dpsRTUAlarmEntry 4}



dpsRTUAPntDesc OBJECT-TYPE

	SYNTAX  DisplayString (SIZE (21))

	ACCESS  read-only

	STATUS  mandatory

	DESCRIPTION "A description of this point."

	::= {dpsRTUAlarmEntry 5}



dpsRTUAState OBJECT-TYPE

	SYNTAX  DisplayString (SIZE (8))

	ACCESS  read-only

	STATUS  mandatory

	DESCRIPTION "The current state of this point."

	::= {dpsRTUAlarmEntry 6}





-- TRAP definitions



tmonCRalarmSet TRAP-TYPE

	ENTERPRISE	tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a critical alarm is set."

	::= 10



tmonCRalarmClr TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a critical alarm clears."

	::= 11



tmonMJalarmSet TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a major alarm is set."

	::= 12



tmonMJalarmClr TRAP-TYPE

	ENTERPRISE	tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a major alarm clears."

	::= 13



tmonMNalarmSet TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a minor alarm is set."

	::= 14



tmonMNalarmClr TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a minor alarm clears."

	::= 15



tmonSTalarmSet TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a status alarm is set."

	::= 16



tmonSTalarmClr TRAP-TYPE

	ENTERPRISE  tmonXM

	VARIABLES {	tmonASite, tmonADesc, tmonAState, tmonASeverity, tmonAChgDate,

					tmonAChgTime, tmonAAuxDesc, tmonADispDesc, tmonAPntType,

					tmonAPort, tmonAAddress, tmonADisplay, tmonAPoint, tmonCEvent }

	DESCRIPTION "Generated when a status alarm clears."

	::= 17



dpsRTUPointSet TRAP-TYPE

	ENTERPRISE  dpsRTU

	VARIABLES {	sysDescr, sysLocation, dpsRTUDateTime,

					dpsRTUAPort, dpsRTUAAddress, dpsRTUADisplay, dpsRTUAPoint,

					dpsRTUAPntDesc, dpsRTUAState }

	DESCRIPTION "Generated when a point is set."

	::= 20



dpsRTUPointClr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when a point clears."

	::= 21



dpsRTUsumPSet TRAP-TYPE

	ENTERPRISE  dpsRTU

	VARIABLES {	sysDescr, sysLocation, dpsRTUDateTime }

	DESCRIPTION "Generated when any point is set."

	::= 101



dpsRTUsumPClr TRAP-TYPE

	ENTERPRISE  dpsRTU

	VARIABLES {	sysDescr, sysLocation, dpsRTUDateTime }

	DESCRIPTION "Generated when all points clear."

	::= 102



dpsRTUcomFailed TRAP-TYPE

	ENTERPRISE  dpsRTU

	VARIABLES {	sysDescr, sysLocation, dpsRTUDateTime }

	DESCRIPTION "Generated when polled unit fails to respond."

	::= 103



dpsRTUcomRestored TRAP-TYPE

	ENTERPRISE  dpsRTU

	VARIABLES {	sysDescr, sysLocation, dpsRTUDateTime }

	DESCRIPTION "Generated when failed unit resumes responding."

	::= 104



END
