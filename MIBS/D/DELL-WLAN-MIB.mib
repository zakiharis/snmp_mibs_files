-- ArubaOS 6.4.3.7_53990
DELL-WLAN-MIB DEFINITIONS ::= BEGIN

   IMPORTS
       MODULE-IDENTITY, OBJECT-TYPE,
       OBJECT-IDENTITY,
	   enterprises,
       snmpModules                           FROM SNMPv2-SMI
       TEXTUAL-CONVENTION                    FROM SNMPv2-TC
       MODULE-COMPLIANCE, OBJECT-GROUP       FROM SNMPv2-CONF;


-- The top node

dell OBJECT IDENTIFIER ::= { enterprises 674 }
powerConnect OBJECT IDENTIFIER ::= { dell 10895 }

-- Dell W-650 product, this object is the SYSOID
w-650 OBJECT IDENTIFIER ::= { powerConnect 5001 }
-- Dell W-651 product, this object is the SYSOID
w-651 OBJECT IDENTIFIER ::= { powerConnect 5002 }
-- Dell W-3200 product, this object is the SYSOID
w-3200 OBJECT IDENTIFIER ::= { powerConnect 5003 }
-- Dell W-3400 product, this object is the SYSOID
w-3400 OBJECT IDENTIFIER ::= { powerConnect 5004 }
-- Dell W-3600 product, this object is the SYSOID
w-3600 OBJECT IDENTIFIER ::= { powerConnect 5005 }
-- Dell W-AP92 product, this object is the SYSOID
w-AP92 OBJECT IDENTIFIER ::= { powerConnect 5006 }
-- Dell W-AP93 product, this object is the SYSOID
w-AP93 OBJECT IDENTIFIER ::= { powerConnect 5007 }
-- Dell W-AP105 product, this object is the SYSOID
w-AP105 OBJECT IDENTIFIER ::= { powerConnect 5008 }
-- Dell W-AP124 product, this object is the SYSOID
w-AP124 OBJECT IDENTIFIER ::= { powerConnect 5009 }
-- Dell W-AP125 product, this object is the SYSOID
w-AP125 OBJECT IDENTIFIER ::= { powerConnect 5010 }
-- Dell W-RAP5 product, this object is the SYSOID
w-RAP5 OBJECT IDENTIFIER ::= { powerConnect 5011 }
-- Dell W-RAP5WN product, this object is the SYSOID
w-RAP5WN OBJECT IDENTIFIER ::= { powerConnect 5012 }
-- Dell W-RAP2 product, this object is the SYSOID
w-RAP2 OBJECT IDENTIFIER ::= { powerConnect 5013 }
-- Dell W-620 product, this object is the SYSOID
w-620 OBJECT IDENTIFIER ::= { powerConnect 5014 }

-- Dell W-6000M3 product, this object is the SYSOID
w-6000M3 OBJECT IDENTIFIER ::= { powerConnect 5015 }

-- Dell W-7210 product, this object is the SYSOID
w-7210 OBJECT IDENTIFIER ::= { powerConnect 5027 }
-- Dell W-7220 product, this object is the SYSOID
w-7220 OBJECT IDENTIFIER ::= { powerConnect 5028 }
-- Dell W-7240 product, this object is the SYSOID
w-7240 OBJECT IDENTIFIER ::= { powerConnect 5029 }

-- Dell W-7005 product, this object is the SYSOID
w-7005 OBJECT IDENTIFIER ::= { powerConnect 5043 }
-- Dell W-7010 product, this object is the SYSOID
w-7010 OBJECT IDENTIFIER ::= { powerConnect 5044 }
-- Dell W-7030 product, this object is the SYSOID
w-7030 OBJECT IDENTIFIER ::= { powerConnect 5049 }

-- Dell W-7205 product, this object is the SYSOID
w-7205 OBJECT IDENTIFIER ::= { powerConnect 5050 }
-- Dell W-7024 product, this object is the SYSOID
w-7024 OBJECT IDENTIFIER ::= { powerConnect 5051 }

-- Dell W-AP68 product, this object is the SYSOID
w-AP68 OBJECT IDENTIFIER ::= { powerConnect 5016 }
-- Dell W-AP68P product, this object is the SYSOID
w-AP68P OBJECT IDENTIFIER ::= { powerConnect 5017 }

-- Dell W-AP175P product, this object is the SYSOID
w-AP175P OBJECT IDENTIFIER ::= { powerConnect 5018 }
-- Dell W-AP175AC product, this object is the SYSOID
w-AP175AC OBJECT IDENTIFIER ::= { powerConnect 5019 }
-- Dell W-AP175DC product, this object is the SYSOID
w-AP175DC OBJECT IDENTIFIER ::= { powerConnect 5020 }

-- Dell W-AP134 product, this object is the SYSOID
w-AP134 OBJECT IDENTIFIER ::= { powerConnect 5021 }
-- Dell W-AP135 product, this object is the SYSOID
w-AP135 OBJECT IDENTIFIER ::= { powerConnect 5022 }

-- Dell W-AP93H product, this object is the SYSOID
w-AP93H OBJECT IDENTIFIER ::= { powerConnect 5023 }
-- Dell W-AP104 product, this object is the SYSOID
w-AP104 OBJECT IDENTIFIER ::= { powerConnect 5024 }

-- Dell W-RAP3WN product, this object is the SYSOID
w-IAP3WN OBJECT IDENTIFIER ::= { powerConnect 5025 }
-- Dell W-RAP3WNP product, this object is the SYSOID
w-IAP3WNP OBJECT IDENTIFIER ::= { powerConnect 5026 }

-- Dell W-IAP108 product, this object is the SYSOID
w-IAP108 OBJECT IDENTIFIER ::= { powerConnect 5031 }
-- Dell W-IAP109 product, this object is the SYSOID
w-IAP109 OBJECT IDENTIFIER ::= { powerConnect 5032 }


-- Dell W-AP224 product, this object is the SYSOID
w-AP224 OBJECT IDENTIFIER ::= { powerConnect 5033 }
-- Dell W-AP225 product, this object is the SYSOID
w-AP225 OBJECT IDENTIFIER ::= { powerConnect 5034 }


-- Dell W-IAP155 product, this object is the SYSOID
w-IAP155 OBJECT IDENTIFIER ::= { powerConnect 5035 }
-- Dell W-IAP155P product, this object is the SYSOID
w-IAP155P OBJECT IDENTIFIER ::= { powerConnect 5036 }
-- Dell W-AP114 product, this object is the SYSOID
w-AP114 OBJECT IDENTIFIER ::= { powerConnect 5037 }
-- Dell W-AP115 product, this object is the SYSOID
w-AP115 OBJECT IDENTIFIER ::= { powerConnect 5038 }

-- Dell W-AP274 product, this object is the SYSOID
w-AP274 OBJECT IDENTIFIER ::= { powerConnect 5039 }
-- Dell W-AP275 product, this object is the SYSOID
w-AP275 OBJECT IDENTIFIER ::= { powerConnect 5040 }
-- Dell W-AP277 product, this object is the SYSOID
w-AP277 OBJECT IDENTIFIER ::= { powerConnect 5052 }
-- Dell W-AP228 product, this object is the SYSOID
w-AP228 OBJECT IDENTIFIER ::= { powerConnect 5054 }

-- Dell W-AP103 product, this object is the SYSOID
w-AP103 OBJECT IDENTIFIER ::= { powerConnect 5045 }
-- Dell W-AP103H product, this object is the SYSOID
w-AP103H OBJECT IDENTIFIER ::= { powerConnect 5046 }

-- Dell W-AP204 product, this object is the SYSOID
w-AP204 OBJECT IDENTIFIER ::= { powerConnect 5047 }
-- Dell W-AP205 product, this object is the SYSOID
w-AP205 OBJECT IDENTIFIER ::= { powerConnect 5048 }
-- Dell W-AP205H product, this object is the SYSOID
w-AP205H OBJECT IDENTIFIER ::= { powerConnect 5055 }

-- Dell W-AP214 product, this object is the SYSOID
w-AP214 OBJECT IDENTIFIER ::= { powerConnect 5041 }
-- Dell W-AP215 product, this object is the SYSOID
w-AP215 OBJECT IDENTIFIER ::= { powerConnect 5042 }

END
