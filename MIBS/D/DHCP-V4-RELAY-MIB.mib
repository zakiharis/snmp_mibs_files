-- extracted from draft-senthil-dhc-v4relay-mib-00.txt
-- at Thu Feb 12 06:16:55 2004

        DHCP-V4-RELAY-MIB DEFINITIONS ::= BEGIN 
         
        IMPORTS 
           Counter64, Counter32, Gauge32, Unsigned32, MODULE-IDENTITY, 
           OBJECT-TYPE, OBJECT-IDENTITY, NOTIFICATION-TYPE, mib-2 
              FROM SNMPv2-SMI 
            
           TEXTUAL-CONVENTION, RowStatus, DateAndTime FROM SNMPv2-TC 
            
           SnmpAdminString FROM SNMP-FRAMEWORK-MIB 
           
           InetAddressIPv4 FROM INET-ADDRESS-MIB 
            
           MODULE-COMPLIANCE, OBJECT-GROUP, NOTIFICATION-GROUP 
           FROM SNMPv2-CONF
			  dhcp FROM DHCP-MIB; 
         
         
        dhcpv4Relay  MODULE-IDENTITY 
           LAST-UPDATED   "200402091510Z" 
           ORGANIZATION 
              "IETF DHC Working Group 
              General Discussion: dhcwg@ietf.org 
              Subscribe: http://www1.ietf.org/mailman/listinfo/dhcwg 
              Archive: http://www1.ietf.org/mailman/listinfo/dhcwg 
              Chair: Ralph Droms, rdroms@cisco.com" 
           CONTACT-INFO 
              "        Senthil Kumar Balasubramanian
                       Hewlett Packard Company,
              Postal:  29 Cunnigham Road, 
                       Bangalore, India 560 052 
                 Tel:  +91-(80)-205-3103 
                 Fax:  +91-(80)-235-2364 
              E-mail:  ksenthil@india.hp.com 
               
                       Vijayabhaskar Annamalai Kalusivalingam,
              Postal:  Hewlett Packard Company, 
                       29 Cunnigham Road, 
                       Bangalore, India 560 052 
                 Tel:  +91-(80)-205-3085
                 Fax:  +91-(80)-235-2364
              E-mail:  vijayak@india.hp.com" 
           DESCRIPTION 
              "The MIB module for entities implementing the Relay Agent part  
              of the Bootstrap Protocol (BOOTP) and the Dynamic Host 
              Configuration protocol (DHCP) for Internet Protocol version 
              4(IPv4).
               
              Copyright (C) The Internet Society (2004).  This version of 
              this MIB module is part of RFC xxxx;  see the RFC itself for 
              full legal notices." 
              -- RFC Editor assigns xxxx and removes this comment 
               
           REVISION "200402091510Z" -- 09 February 2004
           DESCRIPTION "Initial Version, published as RFC xxxx." 
              -- RFC Editor assigns xxxx and removes this comment 
           ::= { dhcp 3 } -- Work in Progress
         
        -- declare top-level MIB objects 
               
        dhcpv4RelayObjects  OBJECT-IDENTITY 
           STATUS      current 
           DESCRIPTION 
              "DHCP Relay MIB identification objects are all defined 
              in this branch." 
        ::= { dhcpv4Relay 1 } 
         
        dhcpv4RelaySystem  OBJECT-IDENTITY 
           STATUS      current 
           DESCRIPTION 
              "Group of objects that are related to the overall system." 
        ::= { dhcpv4RelayObjects 1 } 
         
        relayCounters  OBJECT-IDENTITY 
           STATUS      current 
           DESCRIPTION 
              "Group of objects that count various BOOTP Relay events." 
        ::= { dhcpv4RelayObjects 2 } 
         
        dhcpv4RAIFObjects  OBJECT-IDENTITY 
           STATUS      current 
           DESCRIPTION 
              "Objects that are associated with Relay Agent Information 
              Option"
           REFERENCE 
              "RFC-3046 and its descendents." 
        ::= { dhcpv4RelayObjects 3 } --RFC 3046 and its decesndents.
        -- dhcpv4RelaySystem Group 
         
        dhcpv4RelaySystemDescr  OBJECT-TYPE 
           SYNTAX      SnmpAdminString (SIZE(0..255)) 
           MAX-ACCESS  read-only 
           STATUS      current 
           DESCRIPTION 
              "A textual description of the relay.  This value should 
              have the FQDN name." 
           ::= { dhcpv4RelaySystem 1 } 
         
        dhcpv4RelaySystemObjectID  OBJECT-TYPE 
           SYNTAX      OBJECT IDENTIFIER 
           MAX-ACCESS  read-only 
           STATUS      current 
           DESCRIPTION 
              "The vendor's authoritative identification of the network 
              management subsystem contained in this entity.  This value is 
              allocated within the SMI enterprise subtree (1.3.6.1.4.1) and 
              provides an easy and unambiguous means for determining what 
              kind of relay is being managed.  For example, if vendor Ohso 
              Soft, Inc. is assigned the subtree 1.3.6.1.4.1.4242, it may 
              assign the identifier 1.3.6.1.4.1.4242.1.1 to its Ursa DHCP 
              Relay." 
           ::= { dhcpv4RelaySystem 2 } 

	maxHopCountAllowed	OBJECT-TYPE
           SYNTAX      INTEGER 
           MAX-ACCESS  read-write 
           STATUS      current 
           DESCRIPTION 
	      "The maximum hop count that a DHCP/BOOTP packet can have to 
 	      pass through the relay"

           ::= { dhcpv4RelaySystem 3 }          
         
        dhcpv4RelayandServer  OBJECT-TYPE 
           SYNTAX      INTEGER { 
	               relayOnly(1), 
	               relayandServer(2)
           } 
           MAX-ACCESS  read-write 
           STATUS      current 
           DESCRIPTION 
              "The type of the Relay. The types are:
              (1) Acts only as DHCP Relay.
              (2) Acts as both as DHCP Relay and Server for independent 
              networks" 
           ::= { dhcpv4RelaySystem 4 }          
           
	seconds OBJECT-TYPE
           SYNTAX      Unsigned32 
           MAX-ACCESS  read-write
           STATUS      current 
           DESCRIPTION 
              "The time interval for which the relay chooses a server. In the 
              subsequent 'seconds' interval the relay chooses the next server 
              in the list for relaying the packets from the clients."
           ::= { dhcpv4RelaySystem 5 } 
     
       relaySubnettoServerMapTable OBJECT-TYPE

           SYNTAX      SEQUENCE OF RelaySubnettoServerMapEntry 
           MAX-ACCESS  read-write
           STATUS      current 
           DESCRIPTION 
              "The list of subnets that the relay manages. This table maps the
              subnets with a list of servers serving them along with the maximum
              seconds value the BOOTP/DHCP packet can have to make the relay 
              to choose a server, beyond which the relay chooses the next server
              in the list. The server list will be an ordered list of preference."
           ::= { dhcpv4RelaySystem 6 } 

        relaySubnettoServerMapEntry  OBJECT-TYPE 
           SYNTAX      RelaySubnettoServerMapEntry 
           MAX-ACCESS  read-write
           STATUS      current 
           DESCRIPTION 
              "A logical row in the relaySubnettoServerMapEntry." 
           INDEX { 
              clientSubnetID
           } 
           ::= { relaySubnettoServerMapTable 1} 
         
        RelaySubnettoServerMapEntry ::= SEQUENCE { 
           clientSubnetID				InetAddressIPv4,
	   serverAddress				InetAddressIPv4,
           relayNetToSerMapStatus          		RowStatus
        }

        clientSubnetID			OBJECT-TYPE
           SYNTAX      InetAddressIPv4 
           MAX-ACCESS  read-write
           STATUS      current 
           DESCRIPTION 
              "The subnet address of the link on which the client resides" 
           ::= { relaySubnettoServerMapEntry 1 } 

        serverAddress			OBJECT-TYPE
           SYNTAX      InetAddressIPv4 
           MAX-ACCESS  read-write
           STATUS      current 
           DESCRIPTION 
              "The address of the DHCP/BOOTP server."
           ::= { relaySubnettoServerMapEntry 2 } 

	relayNetToSerMapStatus OBJECT-TYPE

           SYNTAX      RowStatus
           MAX-ACCESS  read-create
           STATUS      current
           DESCRIPTION
           "The status column used for creating, modifying, and deleting instances 
           of the columnar objects in the relaySubnettoServerMapEntry table."
    	   DEFVAL  { active }
           ::= { relaySubnettoServerMapEntry 3 } 
	
 

     -- dhcpv4RAIFObjects Group Starts.
     
     dhcpv4RAIFOption  OBJECT-TYPE 
           SYNTAX      INTEGER { 
	               enable(1), 
	               disable(2) 
           } 
           MAX-ACCESS  read-only 
           STATUS      current 
           DESCRIPTION 
              "Enables/Disables addition of RAIF Option by the Relay. The values are:
               (1) Enables addition of RAIF Option by the Relay.
               (2) Disables addition of RAIF Option by the Relay."
           REFERENCE 
              "RFC-3046." 
           ::= { dhcpv4RAIFObjects 1 }
     
     maxPktSizeWithRAIFOption OBJECT-TYPE
           SYNTAX      INTEGER 
           MAX-ACCESS  read-write 
           STATUS      current 
           DESCRIPTION 
              "Maximux size of a DHCP packet after including RAIF Option that
              is allowed to pass through the Relay"
           REFERENCE 
              "RFC-3046." 
      	   ::= { dhcpv4RAIFObjects 2 } 
     	   
     dhcpv4RAIFCounterObject OBJECT IDENTIFIER
     	   ::= { dhcpv4RAIFObjects 3 }
     	   
     sizeWithRAIFExceedLimitCount OBJECT-TYPE
           SYNTAX      Counter32
           MAX-ACCESS  read-only 
           STATUS      current 
           DESCRIPTION 
		"Number of DHCP packets exceeded the maximum size after including
		RAIF Option."
           REFERENCE 
              "RFC-2131." 
      	   ::= { dhcpv4RAIFCounterObject 1 }

     relayOptionAddedCount  OBJECT-TYPE
           SYNTAX      Counter32
           MAX-ACCESS  read-only 
           STATUS      current 
           DESCRIPTION 
              "Number of RAIF Option added by the relay while forwarding to 
              the servers"
           REFERENCE 
              "RFC-3046." 
      	   ::= { dhcpv4RAIFCounterObject 2 }

     relayOptionRemovedCount  OBJECT-TYPE
           SYNTAX      Counter32
           MAX-ACCESS  read-only 
           STATUS      current 
           DESCRIPTION 
              "Number of RAIF Option removed by the relay while forwarding to 
              the clients"
           REFERENCE 
              "RFC-3046." 
      	   ::= { dhcpv4RAIFCounterObject 3 }
      	   
     incorrectRAIFOptionCount  OBJECT-TYPE
           SYNTAX      Counter32
           MAX-ACCESS  read-only 
           STATUS      current 
           DESCRIPTION 
              "Number of incorrect RAIF Option in DHCP packet received by the
              relay"
           REFERENCE 
              "RFC-3046." 
      	   ::= { dhcpv4RAIFCounterObject 4 }

	docsisDCISubOptionAddedCount  OBJECT-TYPE
           SYNTAX      Counter32
           MAX-ACCESS  read-only 
           STATUS      current 
           DESCRIPTION 
              "Number of DOCSIS-DCI SubOption added by the relay while forwarding 
              to the servers"
           REFERENCE 
              "RFC-3256." 
      	   ::= { dhcpv4RAIFCounterObject 5 }

	docsisDCISubOptionRemoved OBJECT-TYPE
           SYNTAX      Counter32
           MAX-ACCESS  read-only 
           STATUS      current 
           DESCRIPTION 
              "Number of DOCSIS-DCI SubOption removed by the relay while forwarding 
              to the servers"
           REFERENCE 
              "RFC-3256." 
      	   ::= { dhcpv4RAIFCounterObject 6 }

	linkSelSubOptionAddedCount	 OBJECT-TYPE
           SYNTAX      Counter32
           MAX-ACCESS  read-only 
           STATUS      current 
           DESCRIPTION 
              "Number of Link Selection SubOption added by the relay while forwarding 
              to the servers"
           REFERENCE 
              "RFC-3527." 
      	   ::= { dhcpv4RAIFCounterObject 7 }

	linkSelSubOptionRemovedCount  OBJECT-TYPE
           SYNTAX      Counter32 
           MAX-ACCESS  read-only 
           STATUS      current 
           DESCRIPTION 
              "Number of Link Selection SubOption removed by the relay while forwarding 
              to the servers"
           REFERENCE 
              "RFC-3527." 
      	   ::= { dhcpv4RAIFCounterObject 8 }

     -- relayCounters Group 
         
        relayToServerCount  OBJECT-TYPE 
           SYNTAX      Counter32 
           MAX-ACCESS  read-only 
           STATUS      current 
           DESCRIPTION 
              "The number of BOOTREQUEST packets that are relayed to the servers."
           REFERENCE
              "RFC-2131." 
           ::= { relayCounters 1 } 
         
        relayToClientCount  OBJECT-TYPE 
           SYNTAX      Counter32 
           MAX-ACCESS  read-only 
           STATUS      current 
           DESCRIPTION 
              "The number of BOOTREPLY packets that are relayed back to the clients"
           REFERENCE 
              "RFC-2131." 
           ::= { relayCounters 2 } 

        relayCountInvalids  OBJECT-TYPE 
           SYNTAX      Counter32 
           MAX-ACCESS  read-only 
           STATUS      current 
           DESCRIPTION 
              "The number of BOOTP packets dropped by the relay without forwarding
              (e.g., hop count exceeded the limit)."
           ::= { relayCounters 3 } 
         
     	giaddrSpoofCount OBJECT-TYPE
           SYNTAX      Counter32
           MAX-ACCESS  read-only 
           STATUS      current 
           DESCRIPTION 
              "Number of DHCP packets arrived with giaddr spoofed the relay's 
              address"
       	   ::= { relayCounters 4 }

        END 

-- 
--         Copyright (C), 2004, The Internet Society.  All Rights Reserved. 
-- 
--         This document and translations of it may be copied and furnished to 
--         others, and derivative works that comment on or otherwise explain it 
--         or assist in its implementation may be prepared, copied, published 
--         and distributed, in whole or in part, without restriction of any 
--         kind, provided that the above copyright notice and this paragraph are 
--         included on all such copies and derivative works.  However, this 
--         document itself may not be modified in any way, such as by removing 
--         the copyright notice or references to the Internet Society or other 
--         Internet organizations, except as needed for the purpose of 
--         developing Internet standards in which case the procedures for 
--         copyrights defined in the Internet Standards process must be 
--         followed, or as required to translate it into languages other than 
--         English. 
-- 
--         The limited permissions granted above are perpetual and will not be 
--         revoked by the Internet Society or its successors or assigns. 
-- 
--         This document and the information contained herein is provided on an 
--         "AS IS" basis and THE INTERNET SOCIETY AND THE INTERNET ENGINEERING 
--         TASK FORCE DISCLAIMS ALL WARRANTIES, EXPRESS OR IMPLIED, INCLUDING 
--         BUT NOT LIMITED TO ANY WARRANTY THAT THE USE OF THE INFORMATION 
--         HEREIN WILL NOT INFRINGE ANY RIGHTS OR ANY IMPLIED WARRANTIES OF 
--         MERCHANTABILITY OR FITNESS FOR A PARTICULAR PURPOSE. 
--
