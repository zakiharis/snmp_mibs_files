DMTF-LAN-ADAPTER-MIB DEFINITIONS ::= BEGIN

IMPORTS
	OBJECT-TYPE, NOTIFICATION-TYPE,
	MODULE-IDENTITY, enterprises, Counter32, Counter64, Gauge32, Integer32
		FROM SNMPv2-SMI
	DmiString,
	dmiEventDateTime,dmiCompId,dmiEventSeverity,
	dmiEventStateKey,dmiEventAssociatedGroup,
	dmiEventSystem,dmiEventSubSystem
		FROM DMTF-DMI-MIB;

DmiCounter		::= Counter32
DmiCounter64		::= Counter64
DmiGauge		::= Gauge32
DmiInteger		::= Integer32
DmiOctetstring		::= OCTET STRING
DmiCompId		::= INTEGER
DmiGroupId		::= INTEGER

dmtf                	OBJECT IDENTIFIER ::= { enterprises 412 }
dmtfStdMifs         	OBJECT IDENTIFIER ::= { dmtf 2 }
dmtfDynOids         	OBJECT IDENTIFIER ::= { dmtf 3 }


dmtfLANAdapterMIF MODULE-IDENTITY
     LAST-UPDATED "9710221800Z"
     ORGANIZATION "Desktop Management Task Force"
     CONTACT-INFO
          "         DMTF Technical Advisory Committee

		    Mailstop JF2-53
                    2111 N.E. 25th Avenue
                    Hillsboro, OR 97124

		    Phone: +1 503 264-9300
                    Email: dmtf-info@dmtf.org
          "
     DESCRIPTION
          "This MIB is a translation of the DMTF LAN Adapter MIF,
          based on the translation rules defined by the
          DMTF DMI to SNMP Mapping Standard, Version 1.0.

	  DMI-based systems running a DMI-to-SNMP Mapping
          Agent provide the ability to access DMI component
          instrumentation via SNMP protocol operations.
          "
::= { dmtfStdMifs 2 }


Sdmtf802AlternateAddress ::= SEQUENCE {
	dmtf802AlternateAddressState INTEGER,
	alternateAddressIndex	DmiInteger,
	portIndex	DmiInteger,
	addressType	DmiInteger,
	alternateAddress	DmiString
}

dmtf802AlternateAddressTable OBJECT-TYPE
	SYNTAX		SEQUENCE OF Sdmtf802AlternateAddress
	MAX-ACCESS	not-accessible
	STATUS		current
	DESCRIPTION	"Contains objects related to alternate addresses for each
network adapter port."
	::= { dmtfLANAdapterMIF 2 }

dmtf802AlternateAddressEntry OBJECT-TYPE
	SYNTAX		Sdmtf802AlternateAddress
	MAX-ACCESS	not-accessible
	STATUS		current
	DESCRIPTION	"Contains objects related to alternate addresses for each
network adapter port."
	--INDEX		{ DmiCompId,DmiGroupId, alternateAddressIndex }
	::= { dmtf802AlternateAddressTable 1 }


dmtf802AlternateAddressState OBJECT-TYPE
	SYNTAX		INTEGER {
		active(1),
		notInService(2),
		notReady(3),
		createAndGo(4),
		createAndWait(5),
		destroy(6)
	}
	MAX-ACCESS	read-write
	STATUS		current
	DESCRIPTION ""
	REFERENCE "'DMTF|802 Alternate Address|001' 0"
	::= { dmtf802AlternateAddressEntry 0 }

alternateAddressIndex OBJECT-TYPE
	SYNTAX		DmiInteger
	MAX-ACCESS	read-only
	STATUS		current
	DESCRIPTION	"This is an arbitrary number assigned to each alternate address.
The Alternate Address Index usually starts with 1 and increments for each
additional alternate address."
	REFERENCE "'DMTF|802 Alternate Address|001' 1"
	::= { dmtf802AlternateAddressEntry 1 }

portIndex OBJECT-TYPE
	SYNTAX		DmiInteger
	MAX-ACCESS	read-only
	STATUS		current
	DESCRIPTION	"The value of the Port Index attribute for the network port
that uses this alternate address, i.e. the 'port number'."
	REFERENCE "'DMTF|802 Alternate Address|001' 2"
	::= { dmtf802AlternateAddressEntry 2 }

addressType OBJECT-TYPE
	SYNTAX		INTEGER {
		multicast(1),
		functional(2),
		group(3)
	}
	MAX-ACCESS	read-only
	STATUS		current
	DESCRIPTION	"This is the type of alternate address, e.g. multicast, functiona
, etc."
	REFERENCE "'DMTF|802 Alternate Address|001' 3"
	::= { dmtf802AlternateAddressEntry 3 }

alternateAddress OBJECT-TYPE
	SYNTAX		DmiString
	MAX-ACCESS	read-only
	STATUS		current
	DESCRIPTION	"This is the actual alternate address value."
	REFERENCE "'DMTF|802 Alternate Address|001' 4"
	::= { dmtf802AlternateAddressEntry 4 }

SdmtfBootROMCapabilities ::= SEQUENCE {
	dmtfBootROMCapabilitiesState INTEGER,
	capabilityIndex	DmiInteger,
	capabilityDescription	DmiString,
	capabilityStatus	DmiString
}

dmtfBootROMCapabilitiesTable OBJECT-TYPE
	SYNTAX		SEQUENCE OF SdmtfBootROMCapabilities
	MAX-ACCESS	not-accessible
	STATUS		current
	DESCRIPTION	"This group describes the capabilities or special features
supported by this ROM."
	::= { dmtfLANAdapterMIF 6 }

dmtfBootROMCapabilitiesEntry OBJECT-TYPE
	SYNTAX		SdmtfBootROMCapabilities
	MAX-ACCESS	not-accessible
	STATUS		current
	DESCRIPTION	"This group describes the capabilities or special features
supported by this ROM."
	--INDEX		{ DmiCompId,DmiGroupId, capabilityIndex }
	::= { dmtfBootROMCapabilitiesTable 1 }


dmtfBootROMCapabilitiesState OBJECT-TYPE
	SYNTAX		INTEGER {
		active(1),
		notInService(2),
		notReady(3),
		createAndGo(4),
		createAndWait(5),
		destroy(6)
	}
	MAX-ACCESS	read-write
	STATUS		current
	DESCRIPTION ""
	REFERENCE "'DMTF|Boot ROM Capabilities|001' 0"
	::= { dmtfBootROMCapabilitiesEntry 0 }

capabilityIndex OBJECT-TYPE
	SYNTAX		DmiInteger
	MAX-ACCESS	read-only
	STATUS		current
	DESCRIPTION	"This is an arbitrary number assigned to each capability.
The Capability Index usually starts with 1 and increments for each additional
capability."
	REFERENCE "'DMTF|Boot ROM Capabilities|001' 1"
	::= { dmtfBootROMCapabilitiesEntry 1 }

capabilityDescription OBJECT-TYPE
	SYNTAX		DmiString
	MAX-ACCESS	read-only
	STATUS		current
	DESCRIPTION	"This is a clear description of a property or special feature
of the ROM, e.g. 'virus protection'."
	REFERENCE "'DMTF|Boot ROM Capabilities|001' 2"
	::= { dmtfBootROMCapabilitiesEntry 2 }

capabilityStatus OBJECT-TYPE
	SYNTAX		DmiString
	MAX-ACCESS	read-only
	STATUS		current
	DESCRIPTION	"The current state or value associated with the capability
or special feature, e.g. 'enabled', 'active', etc."
	REFERENCE "'DMTF|Boot ROM Capabilities|001' 3"
	::= { dmtfBootROMCapabilitiesEntry 3 }

SdmtfBootROMConfiguration ::= SEQUENCE {
	bootROMDescription	DmiString,
	bootROMVersion	DmiString,
	remoteBootProtocolType	DmiInteger,
	remoteBootProtocolVersion	DmiString
}

dmtfBootROMConfigurationTable OBJECT-TYPE
	SYNTAX		SEQUENCE OF SdmtfBootROMConfiguration
	MAX-ACCESS	not-accessible
	STATUS		current
	DESCRIPTION	"This group describes the characteristics of the boot ROM."
	::= { dmtfLANAdapterMIF 5 }

dmtfBootROMConfigurationEntry OBJECT-TYPE
	SYNTAX		SdmtfBootROMConfiguration
	MAX-ACCESS	not-accessible
	STATUS		current
	DESCRIPTION	"This group describes the characteristics of the boot ROM."
	--INDEX		{ DmiCompId,DmiGroupId }
	::= { dmtfBootROMConfigurationTable 1 }


bootROMDescription OBJECT-TYPE
	SYNTAX		DmiString
	MAX-ACCESS	read-only
	STATUS		current
	DESCRIPTION	"This is the description of the software contained in the
boot ROM."
	REFERENCE "'DMTF|Boot ROM Configuration|001' 1"
	::= { dmtfBootROMConfigurationEntry 1 }

bootROMVersion OBJECT-TYPE
	SYNTAX		DmiString
	MAX-ACCESS	read-only
	STATUS		current
	DESCRIPTION	"This is the version number of the boot ROM software."
	REFERENCE "'DMTF|Boot ROM Configuration|001' 2"
	::= { dmtfBootROMConfigurationEntry 2 }

remoteBootProtocolType OBJECT-TYPE
	SYNTAX		INTEGER {
		other(1),
		none(2),
		rPL(3),
		bootP(4),
		dECMOP(5),
		nativeNetWare(6)
	}
	MAX-ACCESS	read-only
	STATUS		current
	DESCRIPTION	"This is the type of remote boot protocol supported by this
ROM."
	REFERENCE "'DMTF|Boot ROM Configuration|001' 3"
	::= { dmtfBootROMConfigurationEntry 3 }

remoteBootProtocolVersion OBJECT-TYPE
	SYNTAX		DmiString
	MAX-ACCESS	read-only
	STATUS		current
	DESCRIPTION	"The version of the remote boot protocol supported by this
ROM."
	REFERENCE "'DMTF|Boot ROM Configuration|001' 4"
	::= { dmtfBootROMConfigurationEntry 4 }

SdmtfNetworkAdapter802Port ::= SEQUENCE {
	dmtfNetworkAdapter802PortState INTEGER,
	portIndex	DmiInteger,
	permanentNetworkAddress	DmiString,
	currentNetworkAddress	DmiString,
	connectorType	DmiInteger,
	dataRate	DmiInteger,
	totalPacketsTransmitted	DmiCounter64,
	totalBytesTransmitted	DmiCounter64,
	totalPacketsReceived	DmiCounter64,
	totalBytesReceived	DmiCounter64,
	totalTransmitErrors	DmiCounter64,
	totalReceiveErrors	DmiCounter64,
	totalHostErrors	DmiCounter64,
	totalWireErrors	DmiCounter64
}

dmtfNetworkAdapter802PortTable OBJECT-TYPE
	SYNTAX		SEQUENCE OF SdmtfNetworkAdapter802Port
	MAX-ACCESS	not-accessible
	STATUS		current
	DESCRIPTION	"Contains objects related to each of the network ports on
the network adapter."
	::= { dmtfLANAdapterMIF 1 }

dmtfNetworkAdapter802PortEntry OBJECT-TYPE
	SYNTAX		SdmtfNetworkAdapter802Port
	MAX-ACCESS	not-accessible
	STATUS		current
	DESCRIPTION	"Contains objects related to each of the network ports on
the network adapter."
	--INDEX		{ DmiCompId,DmiGroupId, portIndex }
	::= { dmtfNetworkAdapter802PortTable 1 }


dmtfNetworkAdapter802PortState OBJECT-TYPE
	SYNTAX		INTEGER {
		active(1),
		notInService(2),
		notReady(3),
		createAndGo(4),
		createAndWait(5),
		destroy(6)
	}
	MAX-ACCESS	read-write
	STATUS		current
DESCRIPTION ""
	REFERENCE "'DMTF|Network Adapter 802 Port|001' 0"
	::= { dmtfNetworkAdapter802PortEntry 0 }

portIndex2 OBJECT-TYPE
	SYNTAX		DmiInteger
	MAX-ACCESS	read-only
	STATUS		current
	DESCRIPTION	"This attribute is the ordinal of the network port within
the network adapter, i.e. the 'port number'."
	REFERENCE "'DMTF|Network Adapter 802 Port|001' 1"
	::= { dmtfNetworkAdapter802PortEntry 1 }

permanentNetworkAddress OBJECT-TYPE
	SYNTAX		DmiString
	MAX-ACCESS	read-only
	STATUS		current
	DESCRIPTION	"This is the node address stored permanently in the adapter."
	REFERENCE "'DMTF|Network Adapter 802 Port|001' 2"
	::= { dmtfNetworkAdapter802PortEntry 2 }

currentNetworkAddress OBJECT-TYPE
	SYNTAX		DmiString
	MAX-ACCESS	read-only
	STATUS		current
	DESCRIPTION	"This is the node address that can be modified by software,
sometimes referred to as the Locally Administered Address (LAA)."
	REFERENCE "'DMTF|Network Adapter 802 Port|001' 3"
	::= { dmtfNetworkAdapter802PortEntry 3 }

connectorType OBJECT-TYPE
	SYNTAX		INTEGER {
		unknown(1),
		aUI(2),
		uTPCategory3(3),
		uTPCategory4(4),
		uTPCategory5(5),
		bNC(6),
		sTPRJ45(7),
		sTPDB9(8),
		fiberMIC(9),
		appleAUI(10)
	}
	MAX-ACCESS	read-only
	STATUS		current
	DESCRIPTION	"This is the type of connector currently being used to physically
attach this port to the LAN."
	REFERENCE "'DMTF|Network Adapter 802 Port|001' 4"
	::= { dmtfNetworkAdapter802PortEntry 4 }

dataRate OBJECT-TYPE
	SYNTAX		DmiInteger
	MAX-ACCESS	read-only
	STATUS		current
	DESCRIPTION	"This is the rate at which data is transferred over the LAN
in Mbps."
	REFERENCE "'DMTF|Network Adapter 802 Port|001' 5"
	::= { dmtfNetworkAdapter802PortEntry 5 }

totalPacketsTransmitted OBJECT-TYPE
	SYNTAX		DmiCounter64
	MAX-ACCESS	read-only
	STATUS		current
	DESCRIPTION	"This is the total number of packets transmitted."
	REFERENCE "'DMTF|Network Adapter 802 Port|001' 6"
	::= { dmtfNetworkAdapter802PortEntry 6 }

totalBytesTransmitted OBJECT-TYPE
	SYNTAX		DmiCounter64
	MAX-ACCESS	read-only
	STATUS		current
	DESCRIPTION	"This is the total number of bytes transmitted."
	REFERENCE "'DMTF|Network Adapter 802 Port|001' 7"
	::= { dmtfNetworkAdapter802PortEntry 7 }

totalPacketsReceived OBJECT-TYPE
	SYNTAX		DmiCounter64
	MAX-ACCESS	read-only
	STATUS		current
	DESCRIPTION	"This is the total number of packets received."
	REFERENCE "'DMTF|Network Adapter 802 Port|001' 8"
	::= { dmtfNetworkAdapter802PortEntry 8 }

totalBytesReceived OBJECT-TYPE
	SYNTAX		DmiCounter64
	MAX-ACCESS	read-only
	STATUS		current
	DESCRIPTION	"This is the total number of bytes received."
	REFERENCE "'DMTF|Network Adapter 802 Port|001' 9"
	::= { dmtfNetworkAdapter802PortEntry 9 }

totalTransmitErrors OBJECT-TYPE
	SYNTAX		DmiCounter64
	MAX-ACCESS	read-only
	STATUS		current
	DESCRIPTION	"This is the total number of transmit errors of any type."
	REFERENCE "'DMTF|Network Adapter 802 Port|001' 10"
	::= { dmtfNetworkAdapter802PortEntry 10 }

totalReceiveErrors OBJECT-TYPE
	SYNTAX		DmiCounter64
	MAX-ACCESS	read-only
	STATUS		current
	DESCRIPTION	"This is the total number of receive errors of any type."
	REFERENCE "'DMTF|Network Adapter 802 Port|001' 11"
	::= { dmtfNetworkAdapter802PortEntry 11 }

totalHostErrors OBJECT-TYPE
	SYNTAX		DmiCounter64
	MAX-ACCESS	read-only
	STATUS		current
	DESCRIPTION	"This is the total number of errors due to problems with the
network adapter host interface.(e.g. overrun / underrun errors)."
	REFERENCE "'DMTF|Network Adapter 802 Port|001' 12"
	::= { dmtfNetworkAdapter802PortEntry 12 }

totalWireErrors OBJECT-TYPE
	SYNTAX		DmiCounter64
	MAX-ACCESS	read-only
	STATUS		current
	DESCRIPTION	"This is the total number of errors due to problems with the
network (e.g. receive CRC Errors)."
	REFERENCE "'DMTF|Network Adapter 802 Port|001' 13"
	::= { dmtfNetworkAdapter802PortEntry 13 }

SdmtfNetworkAdapterDriver ::= SEQUENCE {
	dmtfNetworkAdapterDriverState INTEGER,
	driverIndex	DmiInteger,
	driverSoftwareName	DmiString,
	driverSoftwareVersion	DmiString,
	driverSoftwareDescription	DmiString,
	driverSize	DmiInteger,
	driverInterfaceType	DmiInteger,
	driverInterfaceVersion	DmiString,
	driverInterfaceDescription	DmiString
}

dmtfNetworkAdapterDriverTable OBJECT-TYPE
	SYNTAX		SEQUENCE OF SdmtfNetworkAdapterDriver
	MAX-ACCESS	not-accessible
	STATUS		current
	DESCRIPTION	""
	::= { dmtfLANAdapterMIF 3 }

dmtfNetworkAdapterDriverEntry OBJECT-TYPE
	SYNTAX		SdmtfNetworkAdapterDriver
	MAX-ACCESS	not-accessible
	STATUS		current
	DESCRIPTION	""
	--INDEX		{ DmiCompId,DmiGroupId, driverIndex }
	::= { dmtfNetworkAdapterDriverTable 1 }


dmtfNetworkAdapterDriverState OBJECT-TYPE
	SYNTAX		INTEGER {
		active(1),
		notInService(2),
		notReady(3),
		createAndGo(4),
		createAndWait(5),
		destroy(6)
	}
	MAX-ACCESS	read-write
	STATUS		current
	DESCRIPTION ""
	REFERENCE "'DMTF|Network Adapter Driver|001' 0"
	::= { dmtfNetworkAdapterDriverEntry 0 }

driverIndex OBJECT-TYPE
	SYNTAX		DmiInteger
	MAX-ACCESS	read-only
	STATUS		current
	DESCRIPTION	""
	REFERENCE "'DMTF|Network Adapter Driver|001' 1"
	::= { dmtfNetworkAdapterDriverEntry 1 }

driverSoftwareName OBJECT-TYPE
	SYNTAX		DmiString
	MAX-ACCESS	read-only
	STATUS		current
	DESCRIPTION	""
	REFERENCE "'DMTF|Network Adapter Driver|001' 2"
	::= { dmtfNetworkAdapterDriverEntry 2 }

driverSoftwareVersion OBJECT-TYPE
	SYNTAX		DmiString
	MAX-ACCESS	read-only
	STATUS		current
	DESCRIPTION	""
	REFERENCE "'DMTF|Network Adapter Driver|001' 3"
	::= { dmtfNetworkAdapterDriverEntry 3 }

driverSoftwareDescription OBJECT-TYPE
	SYNTAX		DmiString
	MAX-ACCESS	read-only
	STATUS		current
	DESCRIPTION	""
	REFERENCE "'DMTF|Network Adapter Driver|001' 4"
	::= { dmtfNetworkAdapterDriverEntry 4 }

driverSize OBJECT-TYPE
	SYNTAX		DmiInteger
	MAX-ACCESS	read-only
	STATUS		current
	DESCRIPTION	""
	REFERENCE "'DMTF|Network Adapter Driver|001' 5"
	::= { dmtfNetworkAdapterDriverEntry 5 }

driverInterfaceType OBJECT-TYPE
	SYNTAX		INTEGER {
		other(1),
		iPX(2),
		oDI(3),
		nDIS(4),
		packetDriver(5),
		lANtastic(6),
		uNIX(7),
		appletalk(8),
		iBMLanSupportProgram(9),
		lLC(10),
		netbios(11),
		pathworksDLL(12)
	}
	MAX-ACCESS	read-only
	STATUS		current
	DESCRIPTION	""
	REFERENCE "'DMTF|Network Adapter Driver|001' 6"
	::= { dmtfNetworkAdapterDriverEntry 6 }

driverInterfaceVersion OBJECT-TYPE
	SYNTAX		DmiString
	MAX-ACCESS	read-only
	STATUS		current
	DESCRIPTION	""
	REFERENCE "'DMTF|Network Adapter Driver|001' 7"
	::= { dmtfNetworkAdapterDriverEntry 7 }

driverInterfaceDescription OBJECT-TYPE
	SYNTAX		DmiString
	MAX-ACCESS	read-only
	STATUS		current
	DESCRIPTION	""
	REFERENCE "'DMTF|Network Adapter Driver|001' 8"
	::= { dmtfNetworkAdapterDriverEntry 8 }

SdmtfNetworkAdapterHardware ::= SEQUENCE {
	networkTopology	DmiInteger,
	transmissionCapability	DmiInteger,
	networkAdapterRAMSize	DmiInteger,
	busType	DmiInteger,
	busWidth	DmiInteger
}

dmtfNetworkAdapterHardwareTable OBJECT-TYPE
	SYNTAX		SEQUENCE OF SdmtfNetworkAdapterHardware
	MAX-ACCESS	not-accessible
	STATUS		current
	DESCRIPTION	"Contains objects related to the network adapter hardware."
	::= { dmtfLANAdapterMIF 4 }

dmtfNetworkAdapterHardwareEntry OBJECT-TYPE
	SYNTAX		SdmtfNetworkAdapterHardware
	MAX-ACCESS	not-accessible
	STATUS		current
	DESCRIPTION	"Contains objects related to the network adapter hardware."
	--INDEX		{ DmiCompId,DmiGroupId }
	::= { dmtfNetworkAdapterHardwareTable 1 }


networkTopology OBJECT-TYPE
	SYNTAX		INTEGER {
		other(1),
		x10MbpsEthernet(2),
		x100MbpsEthernet(3),
		x10010MbpsEthernet(4),
		x100MbpsVGAnyLAN(5),
		x4MbpsTokenRing(6),
		x16MbpsTokenRing(7),
		x164MbpsTokenRing(8),
		x2MbpsArcnet(9),
		x20MbpsArcnet(10),
		fDDI(11),
		aTM(12),
		appleTalk(13)
	}
	MAX-ACCESS	read-only
	STATUS		current
	DESCRIPTION	"This is the network media access method/topology supported
by this adapter."
	REFERENCE "'DMTF|Network Adapter Hardware|001' 1"
	::= { dmtfNetworkAdapterHardwareEntry 1 }

transmissionCapability OBJECT-TYPE
	SYNTAX		INTEGER {
		normal(1),
		fullDuplex(2)
	}
	MAX-ACCESS	read-only
	STATUS		current
	DESCRIPTION	"The transmission capabilities of the adapter."
	REFERENCE "'DMTF|Network Adapter Hardware|001' 2"
	::= { dmtfNetworkAdapterHardwareEntry 2 }

networkAdapterRAMSize OBJECT-TYPE
	SYNTAX		DmiInteger
	MAX-ACCESS	read-only
	STATUS		current
	DESCRIPTION	"This is the total size of adapter RAM in Kb."
	REFERENCE "'DMTF|Network Adapter Hardware|001' 3"
	::= { dmtfNetworkAdapterHardwareEntry 3 }

busType OBJECT-TYPE
	SYNTAX		INTEGER {
		other(1),
		iSA(2),
		eISA(3),
		mCA(4),
		pCI(5),
		vL(6),
		pCMCIA(7),
		parallel(8),
		nEC98(9),
		motherboard(256)
	}
	MAX-ACCESS	read-only
	STATUS		current
	DESCRIPTION	"This is the type of bus used to interface the adapter to
the host."
	REFERENCE "'DMTF|Network Adapter Hardware|001' 4"
	::= { dmtfNetworkAdapterHardwareEntry 4 }

busWidth OBJECT-TYPE
	SYNTAX		INTEGER {
		other(1),
		unknown(2),
		x8BitCard(3),
		x16BitCard(4),
		x32BitCard(5),
		x64BitCard(6),
		x128BitCard(7)
	}
	MAX-ACCESS	read-only
	STATUS		current
	DESCRIPTION	"This is the width (in bits) of the data path used to interface
the adapter with the host."
	REFERENCE "'DMTF|Network Adapter Hardware|001' 5"
	::= { dmtfNetworkAdapterHardwareEntry 5 }

END
