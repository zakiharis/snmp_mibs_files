-- extracted from draft-koehler-aaa-diameter-nasreq-mib-01.txt
-- at Fri May 14 06:20:55 2004

DIAMETER-NASREQ-APPLICATION-MIB DEFINITIONS ::= BEGIN

IMPORTS
       MODULE-IDENTITY, OBJECT-TYPE, OBJECT-IDENTITY,
       Counter32, Unsigned32,
       TimeTicks, mib-2                 FROM SNMPv2-SMI
       InetAddressType, InetAddress     FROM INET-ADDRESS-MIB
       SnmpAdminString                  FROM SNMP-FRAMEWORK-MIB
       MODULE-COMPLIANCE, OBJECT-GROUP  FROM SNMPv2-CONF;

diameterMIB MODULE-IDENTITY
       LAST-UPDATED "200202260000Z"
       ORGANIZATION "IETF AAA Working Group."
       CONTACT-INFO
          " Jay Koehler
            Cisco Systems, Inc.
            10850 Murdock Road
            Knoxville, TN 37932
            US
            Phone: +1 865 671 0429
            EMail: jkoehler@cisco.com
            Mark Eklund
            Cisco Systems, Inc.
            10850 Murdock Road
            Knoxville, TN 37932
            US
            Phone: +1 865 671 6255
            Email: meklund@cisco.com

            Hai Li
            Cisco Systems, Inc.
            10850 Murdock Road
            Knoxville, TN 37932
            US
            Phone: +1 865 671 0429
            EMail: haili@cisco.com"
       DESCRIPTION
           "The MIB module is based on the Diameter NASREQ Application,
            draft-ietf-aaa-diameternasreq-08.txt."
       ::= { mib-2 119 }

diameterNasreqAppMIB OBJECT IDENTIFIER ::= {diameterMIB 2}

diameterNasreqAppNotifs      OBJECT IDENTIFIER ::=
                                    { diameterNasreqAppMIB 0 }
diameterNasreqAppObjects     OBJECT IDENTIFIER ::=
                                    { diameterNasreqAppMIB 1 }
diameterNasreqAppConform     OBJECT IDENTIFIER ::=
                                    { diameterNasreqAppMIB 2 }

dnaHostCfgs         OBJECT IDENTIFIER ::= { diameterNasreqAppObjects 1 }
dnaHostStats        OBJECT IDENTIFIER ::= { diameterNasreqAppObjects 2 }
dnaHostSessionInfo  OBJECT IDENTIFIER ::= { diameterNasreqAppObjects 3 }
dnaPeerStats        OBJECT IDENTIFIER ::= { diameterNasreqAppObjects 4 }

dnaHostAddressType OBJECT-TYPE
       SYNTAX      InetAddressType
       MAX-ACCESS  read-only
       STATUS      current
       DESCRIPTION
             "The type of internet address stored
              in diameterHostAddress."
       ::= { dnaHostCfgs 1 }

dnaHostAddress OBJECT-TYPE
       SYNTAX      InetAddress
       MAX-ACCESS  read-only
       STATUS      current
       DESCRIPTION
             "The IP-Address that corresponds to the
              Origin-Host AVP."
       ::= { dnaHostCfgs 2 }

dnaRadiusGateway OBJECT-TYPE
       SYNTAX      INTEGER { no(1),
                             yes(2) }
       MAX-ACCESS  read-only
       STATUS      current
       DESCRIPTION
             "Tells if this server is acting as
              a RADIUS/Diameter gateway."
       ::= { dnaHostCfgs 3 }

dnaEapStatsTable OBJECT-TYPE
       SYNTAX      SEQUENCE OF DnaEapStatsEntry
       MAX-ACCESS  not-accessible
       STATUS      current
       DESCRIPTION
              "Table listing EAP counts."
       ::= { dnaHostStats 1 }

dnaEapStatsEntry OBJECT-TYPE
       SYNTAX     DnaPerPeerStatsEntry
       MAX-ACCESS not-accessible
       STATUS     current
       DESCRIPTION
             "A row entry representing an EAP method."
       INDEX     { dnaEapMethodIndex }
       ::= { dnaEapStatsTable 1 }

DnaPerPeerStatsEntry ::= SEQUENCE {
       dnaEapMethodIndex                          Unsigned32,
       dnaEapMethodCount                           Counter32 }

dnaEapMethodIndex  OBJECT-TYPE
       SYNTAX      Unsigned32 (1..4294967295)
       MAX-ACCESS  read-only
       STATUS      current
       DESCRIPTION
             "A number uniquely identifying the EAP
              method."
       ::= { dnaEapStatsEntry 1 }

dnaEapMethodCount  OBJECT-TYPE
       SYNTAX      Unsigned32 (1..4294967295)
       MAX-ACCESS  read-only
       STATUS      current
       DESCRIPTION
             "The number of EAP requests for each method."
       ::= { dnaEapStatsEntry 2 }

dnaPerPeerStatsTable OBJECT-TYPE
       SYNTAX     SEQUENCE OF DnaPerPeerStatsEntry
       MAX-ACCESS not-accessible
       STATUS     current
       DESCRIPTION
             "The table listing the Diameter
              Nasreq Peer Statistics."
       ::= { dnaPeerStats 1 }

dnaPerPeerStatsEntry OBJECT-TYPE
       SYNTAX     DnaPerPeerStatsEntry
       MAX-ACCESS not-accessible
       STATUS     current
       DESCRIPTION
             "A row entry representing a Diameter
              Peer."
       INDEX     { dnaPeerServerIndex }
       ::= { dnaPerPeerStatsTable 1 }

DnaPerPeerStatsEntry ::= SEQUENCE {
       dnaPeerServerIndex                        Unsigned32,
       dnaPerPeerStatsAARIn                       Counter32,
       dnaPerPeerStatsAAROut                      Counter32,
       dnaPerPeerStatsDERIn                       Counter32,
       dnaPerPeerStatsDEROut                      Counter32,
       dnaPerPeerStatsAARDropped                  Counter32,
       dnaPerPeerStatsDERDropped                  Counter32 }

dnaPeerServerIndex OBJECT-TYPE
       SYNTAX     Unsigned32 (1..4294967295)
       MAX-ACCESS not-accessible
       STATUS     current
       DESCRIPTION
             "A number uniquely identifying each Diameter Peer
              with which the host server communicates."
       ::= { dnaPerPeerStatsEntry  1 }

dnaPerPeerStatsAARIn OBJECT-TYPE
       SYNTAX      Counter32
       MAX-ACCESS  read-only
       STATUS      current
       DESCRIPTION
             "AA-Request in per peer."
       ::= { dnaPerPeerStatsEntry 2 }

dnaPerPeerStatsAAROut OBJECT-TYPE
       SYNTAX      Counter32
       MAX-ACCESS  read-only
       STATUS      current
       DESCRIPTION
             "AA-Request out per peer."
       ::= { dnaPerPeerStatsEntry 3 }

dnaPerPeerStatsDERIn OBJECT-TYPE
       SYNTAX      Counter32
       MAX-ACCESS  read-only
       STATUS      current
       DESCRIPTION
             "Diameter-EAP-Request in per peer."
       ::= { dnaPerPeerStatsEntry 4 }

dnaPerPeerStatsDEROut OBJECT-TYPE
       SYNTAX     Counter32
       MAX-ACCESS read-only
       STATUS     current
       DESCRIPTION
             "Diameter-EAP-Answer out per peer."
       ::= { dnaPerPeerStatsEntry 5 }

dnaPerPeerStatsAARDropped OBJECT-TYPE
       SYNTAX     Counter32
       MAX-ACCESS read-only
       STATUS     current
       DESCRIPTION
             "AA-Request dropped per peer."
       ::= { dnaPerPeerStatsEntry 6 }

dnaPerPeerStatsDERDropped OBJECT-TYPE
       SYNTAX     Counter32
       MAX-ACCESS read-only
       STATUS     current
       DESCRIPTION
             "AA-Request dropped per peer."
       ::= { dnaPerPeerStatsEntry 7 }

dnaHostTotalSessions OBJECT-TYPE
       SYNTAX     Counter32
       MAX-ACCESS read-only
       STATUS     current
       DESCRIPTION
             "The total number of sessions
              since uptime."
       ::= { dnaHostSessionInfo 1 }

dnaHostTotalActiveSessions OBJECT-TYPE
       SYNTAX     Counter32
       MAX-ACCESS read-only
       STATUS     current
       DESCRIPTION
             "The total number of active sessions."
       ::= { dnaHostSessionInfo 2 }

dnaPerPeerActiveSessionTable OBJECT-TYPE
       SYNTAX     SEQUENCE OF DnaPerPeerActiveSessionEntry
       MAX-ACCESS not-accessible
       STATUS     current
       DESCRIPTION
             "The (conceptual) table listing the Diameter
              Nasreq Active Session Information."
       ::= { dnaPeerStats 2 }

dnaPerPeerActiveSessionEntry OBJECT-TYPE
       SYNTAX     DnaPerPeerActiveSessionEntry
       MAX-ACCESS not-accessible
       STATUS     current
       DESCRIPTION
             "An entry (conceptual row) representing a
              Diameter peer."
       INDEX     { dnaPeerServerIndex,
                   dnaPerPeerSessionIndex }
       ::= { dnaPerPeerActiveSessionTable 1 }

DnaPerPeerActiveSessionEntry ::= SEQUENCE {
       dnaPerPeerSessionIndex                    Unsigned32,
       dnaPerPeerSessionId                  SnmpAdminString,
       dnaPerPeerSessionUptime                    TimeTicks,
       dnaPerPeerSessionAuthenStatus                INTEGER,
       dnaPerPeerSessionAuthorStatus                INTEGER,
       dnaPerPeerSessionReauthenCount             Counter32,
       dnaPerPeerSessionReauthorCount             Counter32,
       dnaPerPeerSessionAuthorLifetime            TimeTicks }

dnaPerPeerSessionIndex OBJECT-TYPE
       SYNTAX     Unsigned32 (1..4294967295)
       MAX-ACCESS read-only
       STATUS     current
       DESCRIPTION
             "A number identifying a peer session."
       ::= { dnaPerPeerActiveSessionEntry 1 }

dnaPerPeerSessionId OBJECT-TYPE
       SYNTAX     SnmpAdminString
       MAX-ACCESS read-only
       STATUS     current
       DESCRIPTION
             "A unique string used to identify a specific
              session."
       ::= { dnaPerPeerActiveSessionEntry 2 }

dnaPerPeerSessionUptime OBJECT-TYPE
       SYNTAX     TimeTicks
       MAX-ACCESS read-only
       STATUS     current
       DESCRIPTION
             "The total amount of time the session has
              been up."
       ::= { dnaPerPeerActiveSessionEntry 3 }

dnaPerPeerSessionAuthenStatus  OBJECT-TYPE
       SYNTAX     INTEGER { notauthen(1),
                            inprogess(2),
                            authenticated(3) }
       MAX-ACCESS read-only
       STATUS     current
       DESCRIPTION
             "The authentication status of a session."
       ::= { dnaPerPeerActiveSessionEntry 4 }

dnaPerPeerSessionAuthorStatus OBJECT-TYPE
       SYNTAX     INTEGER { notauthor(1),
                            inprogess(2),
                            authorized(3) }
       MAX-ACCESS read-only
       STATUS     current
       DESCRIPTION
             "The authorization status of a session."
       ::= { dnaPerPeerActiveSessionEntry 5 }

dnaPerPeerSessionReauthenCount OBJECT-TYPE
       SYNTAX     Counter32
       MAX-ACCESS read-only
       STATUS     current
       DESCRIPTION
             "The number of times this session has
              been re-authenticated."
       ::= { dnaPerPeerActiveSessionEntry 6 }

dnaPerPeerSessionReauthorCount OBJECT-TYPE
       SYNTAX     Counter32
       MAX-ACCESS read-only
       STATUS     current
       DESCRIPTION
             "The number of times this session has
              been re-authorized."
       ::= { dnaPerPeerActiveSessionEntry 7 }

dnaPerPeerSessionAuthorLifetime OBJECT-TYPE
       SYNTAX     TimeTicks
       MAX-ACCESS read-only
       STATUS     current
       DESCRIPTION
             "The maximum number of seconds of service
              to be provided to the user before the
              user is to be re-authenticated and/or
              re-authorized."
       ::= { dnaPerPeerActiveSessionEntry 8 }

dnaHistorySessionTable OBJECT-TYPE
       SYNTAX     SEQUENCE OF DnaHistorySessionEntry
       MAX-ACCESS not-accessible
       STATUS     current
       DESCRIPTION
             "The (conceptual) table listing session
              history information."
       ::= { dnaPeerStats 3 }

dnaHistorySessionEntry OBJECT-TYPE
       SYNTAX     DnaHistorySessionEntry
       MAX-ACCESS not-accessible
       STATUS     current
       DESCRIPTION
             "An entry (conceptual row) representing
              information for a session."
       INDEX     { dnaHistorySessionIndex }
       ::= { dnaHistorySessionTable 1 }

DnaHistorySessionEntry ::= SEQUENCE {
       dnaHistorySessionIndex                    Unsigned32,
       dnaHistorySessionId                  SnmpAdminString,
       dnaHistorySessionUptime                    TimeTicks,
       dnaHistorySessionAuthenStatus                INTEGER,
       dnaHistorySessionAuthorStatus                INTEGER,
       dnaHistorySessionReauthenCount             Counter32,
       dnaHistorySessionReauthorCount             Counter32,
       dnaHistorySessionAuthorLifetime            TimeTicks }

dnaHistorySessionIndex OBJECT-TYPE
       SYNTAX     Unsigned32 (1..4294967295)
       MAX-ACCESS not-accessible
       STATUS     current
       DESCRIPTION
             "The maximum number of session information
              to keep."
       ::= { dnaHistorySessionEntry 1 }

dnaHistorySessionId OBJECT-TYPE
       SYNTAX     SnmpAdminString
       MAX-ACCESS read-only
       STATUS     current
       DESCRIPTION
             "A unique string used to identify a specific
              session."
       ::= { dnaHistorySessionEntry 2 }

dnaHistorySessionUptime OBJECT-TYPE
       SYNTAX     TimeTicks
       MAX-ACCESS read-only
       STATUS     current
       DESCRIPTION
             "The total amount of time the session has
              been up."
       ::= { dnaHistorySessionEntry 3 }

dnaHistorySessionAuthenStatus  OBJECT-TYPE
       SYNTAX     INTEGER { notauthen(1),
                            inprogess(2),
                            authenticated(3) }
       MAX-ACCESS read-only
       STATUS     current
       DESCRIPTION
             "The authentication status of a session."
       ::= { dnaHistorySessionEntry 4 }

dnaHistorySessionAuthorStatus OBJECT-TYPE
       SYNTAX     INTEGER { notauthor(1),
                            inprogess(2),
                            authorized(3) }
       MAX-ACCESS read-only
       STATUS     current
       DESCRIPTION
             "The authorization status of a session."
       ::= { dnaHistorySessionEntry 5 }

dnaHistorySessionReauthenCount OBJECT-TYPE
       SYNTAX     Counter32
       MAX-ACCESS read-only
       STATUS     current
       DESCRIPTION
             "The number of times this session has
              been re-authenticated."
       ::= { dnaHistorySessionEntry 6 }

dnaHistorySessionReauthorCount OBJECT-TYPE
       SYNTAX     Counter32
       MAX-ACCESS read-only
       STATUS     current
       DESCRIPTION
             "The number of times this session has
              been re-authorized."
       ::= { dnaHistorySessionEntry 7 }

dnaHistorySessionAuthorLifetime OBJECT-TYPE
       SYNTAX     TimeTicks
       MAX-ACCESS read-only
       STATUS     current
       DESCRIPTION
             "The maximum number of seconds of service
              to be provided to the user before the
              user is to be re-authenticated and/or
              re-authorized."
       ::= { dnaHistorySessionEntry 8 }

-- Conformance
 dnaMIBCompliances
  OBJECT IDENTIFIER ::= { diameterNasreqAppConform 1 } 
  dnaMIBGroups
  OBJECT IDENTIFIER ::= { diameterNasreqAppConform 2 }

-- Compliance Statements 

dnaMIBCompliance MODULE-COMPLIANCE
       STATUS     current
       DESCRIPTION
            "The compliance statement for diameter base
             protocol entities."
       MODULE -- this module
            MANDATORY-GROUPS { dnaHostCfgGroup }
       ::= { dnaMIBCompliances 1 }

-- Units of Conformance 

dnaHostCfgGroup OBJECT-GROUP
      OBJECTS {
              dnaHostAddressType,
              dnaHostAddress,
              dnaRadiusGateway

      }
      STATUS  current
      DESCRIPTION
            "A collection of objects providing configuration common
             to the server."
      ::= { dnaMIBGroups 1 }

END

-- 
--    Copyright (C) The Internet Society (2001).  All Rights Reserved.
-- 
--    This document and translations of it may be copied and furnished to
--    others, and derivative works that comment on or otherwise explain it
--    or assist in its implmentation may be prepared, copied, published and
--    distributed, in whole or in part, without restriction of any kind,
--    provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
-- 
--    The limited permissions granted above are perpetual and will not be
--    revoked by the Internet Society or its successors or assigns.
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
