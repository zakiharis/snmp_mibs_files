DEMO-MIB DEFINITIONS ::= BEGIN

/*EXPORTS -- everything --;*/

IMPORTS
   OBJECT-TYPE, Counter64, Gauge32, Integer32
		FROM SNMPv2-SMI
	OBJECT-GROUP
		FROM SNMPv2-CONF
   ifIndex
		FROM RFC1213-MIB
	NsapAddress
		FROM Nortel-Magellan-Passport-StandardTextualConventionsMIB;


mtrDemo		OBJECT IDENTIFIER ::=
		    { iso-ccitt(3) mhs(6) group(6) mtr(200) 5 }


mtrDemoGroup OBJECT-GROUP
    OBJECTS { mtrBigNumber, mtrNsapAddress, mtrBitString, mtrColumn }
    STATUS     mandatory
    DESCRIPTION
	"The demo group."
    ::= { mtrDemo 1 }

mtrBigNumber OBJECT-TYPE
    SYNTAX     Counter64
    MAX-ACCESS read-write
    STATUS     mandatory
    DESCRIPTION
	"A big number.  On startup, the agent initializes this to the value

		18,023,456,790,123,456,789
	"
    ::= { mtrDemoGroup 1 }

mtrNsapAddress OBJECT-TYPE
    SYNTAX     NsapAddress
    MAX-ACCESS read-write
    STATUS     mandatory
    DESCRIPTION
	"An OSI Network Address.  On startup, the agent initializes this to
	 the value

		NS+47000580ffff000000012301230123456789ab01
	"
    ::= { mtrDemoGroup 2 }

mtrBitString OBJECT-TYPE
    SYNTAX     BIT STRING { 
                          rejectA-A(0),
                          rejectA-B(1),
                          rejectA-S(2),
                          rejectA-M(3),
                          rejectB-A(4),
                          rejectB-B(5),
                          rejectB-S(6),
                          rejectB-M(7),
                          rejectS-A(8),
                          rejectS-B(9),
                          rejectS-S(10),
                          rejectS-M(11),
                          rejectM-A(12),
                          rejectM-B(13),
                          rejectM-S(14),
                          rejectM-M(15)
		}
    MAX-ACCESS read-write
    STATUS     mandatory
    DESCRIPTION
	"A string of bits.  On startup, the agent initializes this to the value

		'0000000000000000'B
	"
    ::= { mtrDemoGroup 3 }

mtrTable OBJECT-TYPE
    SYNTAX     SEQUENCE OF MtrEntry
    MAX-ACCESS not-accessible
    STATUS     mandatory
    DESCRIPTION
	"A mtr table used for testing..."
    ::= { mtrDemoGroup 4 }

mtrEntry OBJECT-TYPE
    SYNTAX     MtrEntry
    MAX-ACCESS not-accessible
    STATUS     mandatory
    DESCRIPTION
	"An entry (conceptual row) in the mtrTable."
    INDEX   { mtrIndex }
    ::= { mtrTable 1 }

MtrEntry ::=
    SEQUENCE {
	mtrIndex INTEGER (0..50000),
	mtrColumn Integer32
    }

mtrIndex OBJECT-TYPE
    SYNTAX     INTEGER (0..50000)
    MAX-ACCESS not-accessible
    STATUS     mandatory
    DESCRIPTION
	"The auxilary variable used to identify (conceptual) rows in the 
	 mtrTable."
    ::= { mtrEntry 1 }

mtrColumn OBJECT-TYPE
    SYNTAX     Integer32
    MAX-ACCESS read-only
    STATUS     mandatory
    DESCRIPTION
	"The column."
    ::= { mtrEntry 2 }


END
