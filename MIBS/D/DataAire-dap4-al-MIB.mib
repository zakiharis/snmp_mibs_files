--
-- Data Aire-dap4_al.MIB
-- MIB generated by Data Aire
-- Tuesday, 12 July 2011
--

    DataAire-dap4-al-MIB DEFINITIONS ::= BEGIN
 
		IMPORTS
			OBJECT-GROUP
				FROM SNMPv2-CONF			
			sysContact, sysName, sysLocation			
				FROM SNMPv2-MIB
			enterprises, MODULE-IDENTITY, OBJECT-TYPE, Integer32			
				FROM SNMPv2-SMI;		
		
        dap4-alMIB MODULE-IDENTITY
      		LAST-UPDATED  "201107120850Z"		-- July 12, 2011 at 08:50 GMT
      		ORGANIZATION  "Data Aire"
      		CONTACT-INFO
                "
                        Data Aire
                        230 West Blueridge Ave
                        Orange, CA
                        Tel: 1-800-347-2473
                        E-mail: sales@dataaire.com
                "
      		DESCRIPTION
                "This is the MIB module for the dap4_al device."
			REVISION "201107120850Z"
			DESCRIPTION
                "version 1.0"
			::= { instruments 1 }
	
	
--
-- Node definitions
--
	
		-- 1.3.6.1.4.1.9839
		carel OBJECT IDENTIFIER ::= { enterprises 9839 }
		
		-- 1.3.6.1.4.1.9839.1
		systm OBJECT IDENTIFIER ::= { carel 1 }
		
		-- 1.3.6.1.4.1.9839.1.1
		agentRelease OBJECT-TYPE
			SYNTAX Integer32
			UNITS "N/A"
			MAX-ACCESS read-only
			STATUS current
			DESCRIPTION "Release of the Agent."
		::= { systm 1 }
		
		-- 1.3.6.1.4.1.9839.1.2
		agentCode OBJECT-TYPE
			SYNTAX Integer32
			UNITS "N/A"
			MAX-ACCESS read-only
			STATUS current
   			DESCRIPTION "Code of the Agent. 2=pCOWeb."
		::= { systm 2 }
		
		-- 1.3.6.1.4.1.9839.2
		instruments OBJECT IDENTIFIER ::= { carel 2 }
		
		-- 1.3.6.1.4.1.9839.2.0
 		pCOWebInfo OBJECT IDENTIFIER ::= { instruments 0 }
		

		-- 1.3.6.1.4.1.9839.2.0.10
		pCOStatusgroup OBJECT IDENTIFIER ::= { pCOWebInfo 10 }
		
		-- 1.3.6.1.4.1.9839.2.0.10.1
		pCOId1-Status OBJECT-TYPE
			SYNTAX Integer32
			UNITS "N/A"
			MAX-ACCESS read-only
			STATUS current
			DESCRIPTION "Status of pCOId1. 0=Offline, 1=Init, 2=Online"
			::= { pCOStatusgroup 1 }

		-- ... You will have how many pCOIdX-Status objects as the pCOs connected to pCOWeb.

		-- 1.3.6.1.4.1.9839.2.0.11
		pCOErrorsNumbergroup OBJECT IDENTIFIER ::= { pCOWebInfo 11 }
		
		-- 1.3.6.1.4.1.9839.2.0.11.1
		pCOId1-ErrorsNumber OBJECT-TYPE
			SYNTAX Integer32
			UNITS "N/A"
			MAX-ACCESS read-only
			STATUS current
			DESCRIPTION "Number of Communication Errors from pCOId1 to pCOWeb."
			::= { pCOErrorsNumbergroup 1 }

		-- ... You will have how many pCOIdX-ErrorsNumber objects as the pCOs connected to pCOWeb.

	-- 1.3.6.1.4.1.9839.2.1.1
	digitalObjects OBJECT IDENTIFIER ::= { dap4-alMIB 1 }

        -- 1.3.6.1.4.1.9839.2.1.1.1
        dehum-on OBJECT-TYPE
                    SYNTAX Integer32 (0..1)
                    UNITS "N/A"
                    MAX-ACCESS read-only
                    STATUS current
                    DESCRIPTION "Dehumidify mode is running"
                    DEFVAL { 0 }
                    ::= { digitalObjects 1 }

        -- 1.3.6.1.4.1.9839.2.1.1.2
        hum-on OBJECT-TYPE
                    SYNTAX Integer32 (0..1)
                    UNITS "N/A"
                    MAX-ACCESS read-only
                    STATUS current
                    DESCRIPTION "Humidifier is running"
                    DEFVAL { 0 }
                    ::= { digitalObjects 2 }

        -- 1.3.6.1.4.1.9839.2.1.1.3
        engy-on OBJECT-TYPE
                    SYNTAX Integer32 (0..1)
                    UNITS "N/A"
                    MAX-ACCESS read-only
                    STATUS current
                    DESCRIPTION "Energy saver is running"
                    DEFVAL { 0 }
                    ::= { digitalObjects 3 }

        -- 1.3.6.1.4.1.9839.2.1.1.4
        cool-inhibit OBJECT-TYPE
                    SYNTAX Integer32 (0..1)
                    UNITS "N/A"
                    MAX-ACCESS read-only
                    STATUS current
                    DESCRIPTION "Cooling inhibit from Zone Master"
                    DEFVAL { 0 }
                    ::= { digitalObjects 4 }

        -- 1.3.6.1.4.1.9839.2.1.1.5
        heat-held OBJECT-TYPE
                    SYNTAX Integer32 (0..1)
                    UNITS "N/A"
                    MAX-ACCESS read-only
                    STATUS current
                    DESCRIPTION "Heat inhibited due to alarm condition"
                    DEFVAL { 0 }
                    ::= { digitalObjects 5 }

        -- 1.3.6.1.4.1.9839.2.1.1.6
        humidifier-inhibit OBJECT-TYPE
                    SYNTAX Integer32 (0..1)
                    UNITS "N/A"
                    MAX-ACCESS read-only
                    STATUS current
                    DESCRIPTION "Humidifier stopped due to alarm"
                    DEFVAL { 0 }
                    ::= { digitalObjects 6 }

        -- 1.3.6.1.4.1.9839.2.1.1.7
        dehum-inhibit OBJECT-TYPE
                    SYNTAX Integer32 (0..1)
                    UNITS "N/A"
                    MAX-ACCESS read-only
                    STATUS current
                    DESCRIPTION "Dehum is inhibited"
                    DEFVAL { 0 }
                    ::= { digitalObjects 7 }

        -- 1.3.6.1.4.1.9839.2.1.1.8
        rht-during-dehum OBJECT-TYPE
                    SYNTAX Integer32 (0..1)
                    UNITS "N/A"
                    MAX-ACCESS read-only
                    STATUS current
                    DESCRIPTION "reheat during dehum"
                    DEFVAL { 0 }
                    ::= { digitalObjects 8 }

        -- 1.3.6.1.4.1.9839.2.1.1.9
        floor-wtr-alm OBJECT-TYPE
                    SYNTAX Integer32 (0..1)
                    UNITS "N/A"
                    MAX-ACCESS read-only
                    STATUS current
                    DESCRIPTION "Water under floor alarm"
                    DEFVAL { 0 }
                    ::= { digitalObjects 9 }

        -- 1.3.6.1.4.1.9839.2.1.1.10
        air-flow-alm OBJECT-TYPE
                    SYNTAX Integer32 (0..1)
                    UNITS "N/A"
                    MAX-ACCESS read-only
                    STATUS current
                    DESCRIPTION "No air flow alarm"
                    DEFVAL { 0 }
                    ::= { digitalObjects 10 }

        -- 1.3.6.1.4.1.9839.2.1.1.11
        filter-alm OBJECT-TYPE
                    SYNTAX Integer32 (0..1)
                    UNITS "N/A"
                    MAX-ACCESS read-only
                    STATUS current
                    DESCRIPTION "Dirty filter from digital input"
                    DEFVAL { 0 }
                    ::= { digitalObjects 11 }

        -- 1.3.6.1.4.1.9839.2.1.1.12
        humidifier-alm OBJECT-TYPE
                    SYNTAX Integer32 (0..1)
                    UNITS "N/A"
                    MAX-ACCESS read-only
                    STATUS current
                    DESCRIPTION "Alarm from humidifier digital input"
                    DEFVAL { 0 }
                    ::= { digitalObjects 12 }

        -- 1.3.6.1.4.1.9839.2.1.1.13
        firestat-alm OBJECT-TYPE
                    SYNTAX Integer32 (0..1)
                    UNITS "N/A"
                    MAX-ACCESS read-only
                    STATUS current
                    DESCRIPTION "Temperature of return air above firestat alarm set point"
                    DEFVAL { 0 }
                    ::= { digitalObjects 13 }

        -- 1.3.6.1.4.1.9839.2.1.1.14
        shortcycle-alm OBJECT-TYPE
                    SYNTAX Integer32 (0..1)
                    UNITS "N/A"
                    MAX-ACCESS read-only
                    STATUS current
                    DESCRIPTION "One or more comps has short cycled"
                    DEFVAL { 0 }
                    ::= { digitalObjects 14 }

        -- 1.3.6.1.4.1.9839.2.1.1.15
        humidity-fail OBJECT-TYPE
                    SYNTAX Integer32 (0..1)
                    UNITS "N/A"
                    MAX-ACCESS read-only
                    STATUS current
                    DESCRIPTION "Sensor is out of range"
                    DEFVAL { 0 }
                    ::= { digitalObjects 15 }

        -- 1.3.6.1.4.1.9839.2.1.1.16
        ret-air-fail OBJECT-TYPE
                    SYNTAX Integer32 (0..1)
                    UNITS "N/A"
                    MAX-ACCESS read-only
                    STATUS current
                    DESCRIPTION "Sensor is out of range"
                    DEFVAL { 0 }
                    ::= { digitalObjects 16 }

        -- 1.3.6.1.4.1.9839.2.1.1.17
        maint-alm OBJECT-TYPE
                    SYNTAX Integer32 (0..1)
                    UNITS "N/A"
                    MAX-ACCESS read-only
                    STATUS current
                    DESCRIPTION "Maintenance Schedule Due alarm"
                    DEFVAL { 0 }
                    ::= { digitalObjects 17 }

        -- 1.3.6.1.4.1.9839.2.1.1.18
        c1-hp-alm OBJECT-TYPE
                    SYNTAX Integer32 (0..1)
                    UNITS "N/A"
                    MAX-ACCESS read-only
                    STATUS current
                    DESCRIPTION "High pressure alarm"
                    DEFVAL { 0 }
                    ::= { digitalObjects 18 }

        -- 1.3.6.1.4.1.9839.2.1.1.19
        c1-lp-alm OBJECT-TYPE
                    SYNTAX Integer32 (0..1)
                    UNITS "N/A"
                    MAX-ACCESS read-only
                    STATUS current
                    DESCRIPTION "Low pressure alarm"
                    DEFVAL { 0 }
                    ::= { digitalObjects 19 }

        -- 1.3.6.1.4.1.9839.2.1.1.20
        c2-hp-alm OBJECT-TYPE
                    SYNTAX Integer32 (0..1)
                    UNITS "N/A"
                    MAX-ACCESS read-only
                    STATUS current
                    DESCRIPTION "High pressure alarm"
                    DEFVAL { 0 }
                    ::= { digitalObjects 20 }

        -- 1.3.6.1.4.1.9839.2.1.1.21
        c2-lp-alm OBJECT-TYPE
                    SYNTAX Integer32 (0..1)
                    UNITS "N/A"
                    MAX-ACCESS read-only
                    STATUS current
                    DESCRIPTION "Low pressure alarm"
                    DEFVAL { 0 }
                    ::= { digitalObjects 21 }

        -- 1.3.6.1.4.1.9839.2.1.1.22
        smoke-alm OBJECT-TYPE
                    SYNTAX Integer32 (0..1)
                    UNITS "N/A"
                    MAX-ACCESS read-only
                    STATUS current
                    DESCRIPTION "Smoke detected from digital input"
                    DEFVAL { 0 }
                    ::= { digitalObjects 22 }

        -- 1.3.6.1.4.1.9839.2.1.1.23
        wtr-flow-alm OBJECT-TYPE
                    SYNTAX Integer32 (0..1)
                    UNITS "N/A"
                    MAX-ACCESS read-only
                    STATUS current
                    DESCRIPTION "No water flow alarm"
                    DEFVAL { 0 }
                    ::= { digitalObjects 23 }

        -- 1.3.6.1.4.1.9839.2.1.1.24
        disch-air-fail OBJECT-TYPE
                    SYNTAX Integer32 (0..1)
                    UNITS "N/A"
                    MAX-ACCESS read-only
                    STATUS current
                    DESCRIPTION "Sensor is out of range"
                    DEFVAL { 0 }
                    ::= { digitalObjects 24 }

        -- 1.3.6.1.4.1.9839.2.1.1.25
        ra-tmp-hi-alm OBJECT-TYPE
                    SYNTAX Integer32 (0..1)
                    UNITS "N/A"
                    MAX-ACCESS read-only
                    STATUS current
                    DESCRIPTION "Temperature of return air above alarm set point"
                    DEFVAL { 0 }
                    ::= { digitalObjects 25 }

        -- 1.3.6.1.4.1.9839.2.1.1.26
        ra-tmp-lo-alm OBJECT-TYPE
                    SYNTAX Integer32 (0..1)
                    UNITS "N/A"
                    MAX-ACCESS read-only
                    STATUS current
                    DESCRIPTION "Temperature of return air below alarm set point"
                    DEFVAL { 0 }
                    ::= { digitalObjects 26 }

        -- 1.3.6.1.4.1.9839.2.1.1.27
        hum-hi-alm OBJECT-TYPE
                    SYNTAX Integer32 (0..1)
                    UNITS "N/A"
                    MAX-ACCESS read-only
                    STATUS current
                    DESCRIPTION "Humidity above alarm set point"
                    DEFVAL { 0 }
                    ::= { digitalObjects 27 }

        -- 1.3.6.1.4.1.9839.2.1.1.28
        hum-lo-alm OBJECT-TYPE
                    SYNTAX Integer32 (0..1)
                    UNITS "N/A"
                    MAX-ACCESS read-only
                    STATUS current
                    DESCRIPTION "Humidity below alarm set point"
                    DEFVAL { 0 }
                    ::= { digitalObjects 28 }

        -- 1.3.6.1.4.1.9839.2.1.1.29
        fan-overload OBJECT-TYPE
                    SYNTAX Integer32 (0..1)
                    UNITS "N/A"
                    MAX-ACCESS read-only
                    STATUS current
                    DESCRIPTION "Fan overload"
                    DEFVAL { 0 }
                    ::= { digitalObjects 29 }

        -- 1.3.6.1.4.1.9839.2.1.1.30
        stdby-pump-on OBJECT-TYPE
                    SYNTAX Integer32 (0..1)
                    UNITS "N/A"
                    MAX-ACCESS read-only
                    STATUS current
                    DESCRIPTION "Standby pump on: Check primary pump -Optional alarm. Pump failure input signal required"
                    DEFVAL { 0 }
                    ::= { digitalObjects 30 }

        -- 1.3.6.1.4.1.9839.2.1.1.31
        cust-msg-sw1 OBJECT-TYPE
                    SYNTAX Integer32 (0..1)
                    UNITS "N/A"
                    MAX-ACCESS read-only
                    STATUS current
                    DESCRIPTION "Custom alarm #1 -Optional alarm. External alarm input required. Factory programmed custom message required"
                    DEFVAL { 0 }
                    ::= { digitalObjects 31 }

        -- 1.3.6.1.4.1.9839.2.1.1.32
        cust-msg-sw2 OBJECT-TYPE
                    SYNTAX Integer32 (0..1)
                    UNITS "N/A"
                    MAX-ACCESS read-only
                    STATUS current
                    DESCRIPTION "Custom alarm #2 -Optional alarm. External alarm input required. Factory programmed custom message required"
                    DEFVAL { 0 }
                    ::= { digitalObjects 32 }

        -- 1.3.6.1.4.1.9839.2.1.1.33
        cust-msg-sw3 OBJECT-TYPE
                    SYNTAX Integer32 (0..1)
                    UNITS "N/A"
                    MAX-ACCESS read-only
                    STATUS current
                    DESCRIPTION "Custom alarm #3 -Optional alarm. External alarm input required. Factory programmed custom message required"
                    DEFVAL { 0 }
                    ::= { digitalObjects 33 }

        -- 1.3.6.1.4.1.9839.2.1.1.34
        cust-msg-sw4 OBJECT-TYPE
                    SYNTAX Integer32 (0..1)
                    UNITS "N/A"
                    MAX-ACCESS read-only
                    STATUS current
                    DESCRIPTION "Custom alarm #4 -Optional alarm. External alarm input required. Factory programmed custom message required"
                    DEFVAL { 0 }
                    ::= { digitalObjects 34 }

        -- 1.3.6.1.4.1.9839.2.1.1.35
        humsw-inhibit OBJECT-TYPE
                    SYNTAX Integer32 (0..1)
                    UNITS "N/A"
                    MAX-ACCESS read-only
                    STATUS current
                    DESCRIPTION "Humidifier stopped due to custom alarm switch"
                    DEFVAL { 0 }
                    ::= { digitalObjects 35 }

        -- 1.3.6.1.4.1.9839.2.1.1.36
        heat-inhibit OBJECT-TYPE
                    SYNTAX Integer32 (0..1)
                    UNITS "N/A"
                    MAX-ACCESS read-only
                    STATUS current
                    DESCRIPTION "Heat inhibited due to custom switch alarm condition"
                    DEFVAL { 0 }
                    ::= { digitalObjects 36 }

        -- 1.3.6.1.4.1.9839.2.1.1.37
        rht-hum-inhibit OBJECT-TYPE
                    SYNTAX Integer32 (0..1)
                    UNITS "N/A"
                    MAX-ACCESS read-only
                    STATUS current
                    DESCRIPTION "Reheat and humidification inhibited from operation"
                    DEFVAL { 0 }
                    ::= { digitalObjects 37 }

        -- 1.3.6.1.4.1.9839.2.1.1.38
        disch-tmp-lo-alm OBJECT-TYPE
                    SYNTAX Integer32 (0..1)
                    UNITS "N/A"
                    MAX-ACCESS read-only
                    STATUS current
                    DESCRIPTION "Temperature of discharge air below alarm set point"
                    DEFVAL { 0 }
                    ::= { digitalObjects 38 }

        -- 1.3.6.1.4.1.9839.2.1.1.39
        override-alm OBJECT-TYPE
                    SYNTAX Integer32 (0..1)
                    UNITS "N/A"
                    MAX-ACCESS read-only
                    STATUS current
                    DESCRIPTION "Manual override: Check bypass switches - Standard alarm. Manual override switch is on"
                    DEFVAL { 0 }
                    ::= { digitalObjects 39 }

        -- 1.3.6.1.4.1.9839.2.1.1.40
        condensation-alm OBJECT-TYPE
                    SYNTAX Integer32 (0..1)
                    UNITS "N/A"
                    MAX-ACCESS read-only
                    STATUS current
                    DESCRIPTION "High condensation from digital input"
                    DEFVAL { 0 }
                    ::= { digitalObjects 40 }

        -- 1.3.6.1.4.1.9839.2.1.1.41
        unit-in-standby OBJECT-TYPE
                    SYNTAX Integer32 (0..1)
                    UNITS "N/A"
                    MAX-ACCESS read-only
                    STATUS current
                    DESCRIPTION "Unit in standby, all functions held off - Optional alarm. Control input signal required Factory setting required "
                    DEFVAL { 0 }
                    ::= { digitalObjects 41 }

        -- 1.3.6.1.4.1.9839.2.1.1.42
        cw-sns-fail OBJECT-TYPE
                    SYNTAX Integer32 (0..1)
                    UNITS "N/A"
                    MAX-ACCESS read-only
                    STATUS current
                    DESCRIPTION "Sensor is out of range"
                    DEFVAL { 0 }
                    ::= { digitalObjects 42 }

        -- 1.3.6.1.4.1.9839.2.1.1.43
        humsw-chk-cyl OBJECT-TYPE
                    SYNTAX Integer32 (0..1)
                    UNITS "N/A"
                    MAX-ACCESS read-only
                    STATUS current
                    DESCRIPTION "Humidifier stopped due to custom alarm switch"
                    DEFVAL { 0 }
                    ::= { digitalObjects 43 }

        -- 1.3.6.1.4.1.9839.2.1.1.44
        bms-cooling-inhibit OBJECT-TYPE
                    SYNTAX Integer32 (0..1)
                    UNITS "N/A"
                    MAX-ACCESS read-write
                    STATUS current
                    DESCRIPTION "Cooling operation inhibited by BMS"
                    DEFVAL { 0 }
                    ::= { digitalObjects 44 }

        -- 1.3.6.1.4.1.9839.2.1.1.45
        bms-heat-inhibit OBJECT-TYPE
                    SYNTAX Integer32 (0..1)
                    UNITS "N/A"
                    MAX-ACCESS read-write
                    STATUS current
                    DESCRIPTION "Heat inhibited due to bms"
                    DEFVAL { 0 }
                    ::= { digitalObjects 45 }

        -- 1.3.6.1.4.1.9839.2.1.1.46
        bms-humidifier-inhibit OBJECT-TYPE
                    SYNTAX Integer32 (0..1)
                    UNITS "N/A"
                    MAX-ACCESS read-write
                    STATUS current
                    DESCRIPTION "Humidifier operation inhibited by BMS"
                    DEFVAL { 0 }
                    ::= { digitalObjects 46 }

        -- 1.3.6.1.4.1.9839.2.1.1.47
        bms-dehum-inhibit OBJECT-TYPE
                    SYNTAX Integer32 (0..1)
                    UNITS "N/A"
                    MAX-ACCESS read-write
                    STATUS current
                    DESCRIPTION "Dehumidify mode inhibited by bms"
                    DEFVAL { 0 }
                    ::= { digitalObjects 47 }

        -- 1.3.6.1.4.1.9839.2.1.1.48
        fan-inhibit-bms OBJECT-TYPE
                    SYNTAX Integer32 (0..1)
                    UNITS "N/A"
                    MAX-ACCESS read-write
                    STATUS current
                    DESCRIPTION "Inhibit fan by bms"
                    DEFVAL { 0 }
                    ::= { digitalObjects 48 }

        -- 1.3.6.1.4.1.9839.2.1.1.49
        hum-expect OBJECT-TYPE
                    SYNTAX Integer32 (0..1)
                    UNITS "N/A"
                    MAX-ACCESS read-only
                    STATUS current
                    DESCRIPTION "Reduces control humidity cycling"
                    DEFVAL { 0 }
                    ::= { digitalObjects 49 }

        -- 1.3.6.1.4.1.9839.2.1.1.50
        usashr-f-c OBJECT-TYPE
                    SYNTAX Integer32 (0..1)
                    UNITS "N/A"
                    MAX-ACCESS read-write
                    STATUS current
                    DESCRIPTION "Temperature Mode 0=_C 1=_F"
                    DEFVAL { 0 }
                    ::= { digitalObjects 50 }

        -- 1.3.6.1.4.1.9839.2.1.1.52
        lead-comp OBJECT-TYPE
                    SYNTAX Integer32 (0..1)
                    UNITS "N/A"
                    MAX-ACCESS read-only
                    STATUS current
                    DESCRIPTION "Lead compressor select 0= C1, 1= C2"
                    DEFVAL { 0 }
                    ::= { digitalObjects 52 }

        -- 1.3.6.1.4.1.9839.2.1.1.53
        wtrvlv-dir OBJECT-TYPE
                    SYNTAX Integer32 (0..1)
                    UNITS "N/A"
                    MAX-ACCESS read-only
                    STATUS current
                    DESCRIPTION "Water valve direct or reverse acting"
                    DEFVAL { 0 }
                    ::= { digitalObjects 53 }

        -- 1.3.6.1.4.1.9839.2.1.1.54
        ups-on-alm OBJECT-TYPE
                    SYNTAX Integer32 (0..1)
                    UNITS "N/A"
                    MAX-ACCESS read-only
                    STATUS current
                    DESCRIPTION "Alarm: UPS power on: Check main power  -Optional alarm. External alarm input required"
                    DEFVAL { 0 }
                    ::= { digitalObjects 54 }

        -- 1.3.6.1.4.1.9839.2.1.1.55
        pwrup-alm OBJECT-TYPE
                    SYNTAX Integer32 (0..1)
                    UNITS "N/A"
                    MAX-ACCESS read-only
                    STATUS current
                    DESCRIPTION "Loss of power requires manual reset of alarm"
                    DEFVAL { 0 }
                    ::= { digitalObjects 55 }

        -- 1.3.6.1.4.1.9839.2.1.1.56
        seetag-cust-alm1 OBJECT-TYPE
                    SYNTAX Integer32 (0..1)
                    UNITS "N/A"
                    MAX-ACCESS read-only
                    STATUS current
                    DESCRIPTION "Local alarm #1: See tag inside door =Optional alarm. External alarm input required"
                    DEFVAL { 0 }
                    ::= { digitalObjects 56 }

        -- 1.3.6.1.4.1.9839.2.1.1.57
        seetag-cust-alm2 OBJECT-TYPE
                    SYNTAX Integer32 (0..1)
                    UNITS "N/A"
                    MAX-ACCESS read-only
                    STATUS current
                    DESCRIPTION "Local alarm #2: See tag inside door =Optional alarm. External alarm input required"
                    DEFVAL { 0 }
                    ::= { digitalObjects 57 }

        -- 1.3.6.1.4.1.9839.2.1.1.58
        seetag-cust-alm3 OBJECT-TYPE
                    SYNTAX Integer32 (0..1)
                    UNITS "N/A"
                    MAX-ACCESS read-only
                    STATUS current
                    DESCRIPTION "Local alarm #3: See tag inside door =Optional alarm. External alarm input required"
                    DEFVAL { 0 }
                    ::= { digitalObjects 58 }

        -- 1.3.6.1.4.1.9839.2.1.1.59
        seetag-cust-alm4 OBJECT-TYPE
                    SYNTAX Integer32 (0..1)
                    UNITS "N/A"
                    MAX-ACCESS read-only
                    STATUS current
                    DESCRIPTION "Local alarm #4: See tag inside door =Optional alarm. External alarm input required"
                    DEFVAL { 0 }
                    ::= { digitalObjects 59 }

        -- 1.3.6.1.4.1.9839.2.1.1.60
        shortcycle-alm-en OBJECT-TYPE
                    SYNTAX Integer32 (0..1)
                    UNITS "N/A"
                    MAX-ACCESS read-only
                    STATUS current
                    DESCRIPTION "Enable short cycle alarm of the compressors"
                    DEFVAL { 0 }
                    ::= { digitalObjects 60 }

        -- 1.3.6.1.4.1.9839.2.1.1.61
        superv-off OBJECT-TYPE
                    SYNTAX Integer32 (0..1)
                    UNITS "N/A"
                    MAX-ACCESS read-only
                    STATUS current
                    DESCRIPTION "Supervisor (BMS) On-Off. Show the state OFFbyBMS in main mask (1: Off; 0: On"
                    DEFVAL { 0 }
                    ::= { digitalObjects 61 }

        -- 1.3.6.1.4.1.9839.2.1.1.62
        bms-heartbeat OBJECT-TYPE
                    SYNTAX Integer32 (0..1)
                    UNITS "N/A"
                    MAX-ACCESS read-only
                    STATUS current
                    DESCRIPTION "Bms heartbeat - pCO looks for update every 10 minutes"
                    DEFVAL { 0 }
                    ::= { digitalObjects 62 }


        -- 1.3.6.1.4.1.9839.2.1.2
        analogObjects OBJECT IDENTIFIER ::= { dap4-alMIB 2 }

        -- 1.3.6.1.4.1.9839.2.1.2.1
        ret-air-tmp OBJECT-TYPE
                    SYNTAX Integer32 (-32768..32767)
                    UNITS "N/A"
                    MAX-ACCESS read-only
                    STATUS current
                    DESCRIPTION "Temperature of return air"
                    DEFVAL { 0 }
                    ::= { analogObjects 1 }

 	-- 1.3.6.1.4.1.9839.2.1.2.2
        minmax-24hr-retair-maximum OBJECT-TYPE
                    SYNTAX Integer32 (-32768..32767)
                    UNITS "N/A"
                    MAX-ACCESS read-only
                    STATUS current
                    DESCRIPTION "Maximum Return air temp in last 24hrs"
                    DEFVAL { 0 }
                    ::= { analogObjects 2 }

        -- 1.3.6.1.4.1.9839.2.1.2.3
        minmax-24hr-retair-minumum OBJECT-TYPE
                    SYNTAX Integer32 (-32768..32767)
                    UNITS "N/A"
                    MAX-ACCESS read-only
                    STATUS current
                    DESCRIPTION "Minimum Return air temp in last 24hrs"
                    DEFVAL { 0 }
                    ::= { analogObjects 3 }

        -- 1.3.6.1.4.1.9839.2.1.2.4
        temp-setpoint OBJECT-TYPE
                    SYNTAX Integer32 (-9999..9999)
                    UNITS "N/A"
                    MAX-ACCESS read-write
                    STATUS current
                    DESCRIPTION "Temperature setpoint"
                    DEFVAL { 0 }
                    ::= { analogObjects 4 }

        -- 1.3.6.1.4.1.9839.2.1.2.5
        temp-deadband OBJECT-TYPE
                    SYNTAX Integer32 (0..99)
                    UNITS "N/A"
                    MAX-ACCESS read-write
                    STATUS current
                    DESCRIPTION "Amount from setpoint before a comp is staged on"
                    DEFVAL { 0 }
                    ::= { analogObjects 5 }

        -- 1.3.6.1.4.1.9839.2.1.2.6
        humidity-ain-offs OBJECT-TYPE
                    SYNTAX Integer32 (-32768..32767)
                    UNITS "N/A"
                    MAX-ACCESS read-only
                    STATUS current
                    DESCRIPTION "Humidity Sensor Calibration"
                    DEFVAL { 0 }
                    ::= { analogObjects 6 }

        -- 1.3.6.1.4.1.9839.2.1.2.7
        return-ain-offs OBJECT-TYPE
                    SYNTAX Integer32 (-32768..32767)
                    UNITS "N/A"
                    MAX-ACCESS read-only
                    STATUS current
                    DESCRIPTION "Return Temperature Sensor Calibration"
                    DEFVAL { 0 }
                    ::= { analogObjects 7 }

        -- 1.3.6.1.4.1.9839.2.1.2.8
        cw-tmp OBJECT-TYPE
                    SYNTAX Integer32 (-32768..32767)
                    UNITS "N/A"
                    MAX-ACCESS read-only
                    STATUS current
                    DESCRIPTION "Temperature of chilled water"
                    DEFVAL { 0 }
                    ::= { analogObjects 8 }

        -- 1.3.6.1.4.1.9839.2.1.2.9
        disch-air-tmp OBJECT-TYPE
                    SYNTAX Integer32 (-32768..32767)
                    UNITS "N/A"
                    MAX-ACCESS read-only
                    STATUS current
                    DESCRIPTION "Temperature of discharge air"
                    DEFVAL { 0 }
                    ::= { analogObjects 9 }

        -- 1.3.6.1.4.1.9839.2.1.2.10
        discharge-ain-offs OBJECT-TYPE
                    SYNTAX Integer32 (-32768..32767)
                    UNITS "N/A"
                    MAX-ACCESS read-only
                    STATUS current
                    DESCRIPTION "Discharge Temperature Sensor Calibration - Optional discharge air temperature sensor required (B9)"
                    DEFVAL { 0 }
                    ::= { analogObjects 10 }

        -- 1.3.6.1.4.1.9839.2.1.2.11
        cw-ain-offs OBJECT-TYPE
                    SYNTAX Integer32 (-32768..32767)
                    UNITS "N/A"
                    MAX-ACCESS read-only
                    STATUS current
                    DESCRIPTION "Chilled Water Temperature Sensor Calibration - Optional chilled water temperature sensor required (B10)"
                    DEFVAL { 0 }
                    ::= { analogObjects 11 }

        -- 1.3.6.1.4.1.9839.2.1.2.12
        engsaver-setpoint OBJECT-TYPE
                    SYNTAX Integer32 (-9999..9999)
                    UNITS "N/A"
                    MAX-ACCESS read-write
                    STATUS current
                    DESCRIPTION "Temperature setpoint where chilled water will is requested"
                    DEFVAL { 0 }
                    ::= { analogObjects 12 }

        -- 1.3.6.1.4.1.9839.2.1.2.13
        opt1-analog OBJECT-TYPE
                    SYNTAX Integer32 (-32768..32767)
                    UNITS "N/A"
                    MAX-ACCESS read-only
                    STATUS current
                    DESCRIPTION "Value of the analog input"
                    DEFVAL { 0 }
                    ::= { analogObjects 13 }

        -- 1.3.6.1.4.1.9839.2.1.2.14
        opt2-analog OBJECT-TYPE
                    SYNTAX Integer32 (-32768..32767)
                    UNITS "N/A"
                    MAX-ACCESS read-only
                    STATUS current
                    DESCRIPTION "Value of the analog input"
                    DEFVAL { 0 }
                    ::= { analogObjects 14 }

        -- 1.3.6.1.4.1.9839.2.1.2.15
        opt3-analog OBJECT-TYPE
                    SYNTAX Integer32 (-32768..32767)
                    UNITS "N/A"
                    MAX-ACCESS read-only
                    STATUS current
                    DESCRIPTION "Value of the analog input"
                    DEFVAL { 0 }
                    ::= { analogObjects 15 }

        -- 1.3.6.1.4.1.9839.2.1.2.16
        opt4-analog OBJECT-TYPE
                    SYNTAX Integer32 (-32768..32767)
                    UNITS "N/A"
                    MAX-ACCESS read-only
                    STATUS current
                    DESCRIPTION "Value of the analog input"
                    DEFVAL { 0 }
                    ::= { analogObjects 16 }

        -- 1.3.6.1.4.1.9839.2.1.2.17
        opt-sns-1-y1 OBJECT-TYPE
                    SYNTAX Integer32 (-32768..32767)
                    UNITS "N/A"
                    MAX-ACCESS read-only
                    STATUS current
                    DESCRIPTION "Analog Sensor 1 Minimum Value"
                    DEFVAL { 0 }
                    ::= { analogObjects 17 }

        -- 1.3.6.1.4.1.9839.2.1.2.18
        opt-sns-1-y2 OBJECT-TYPE
                    SYNTAX Integer32 (-32768..32767)
                    UNITS "N/A"
                    MAX-ACCESS read-only
                    STATUS current
                    DESCRIPTION "Analog Sensor 1 Maximum Value"
                    DEFVAL { 1000 }
                    ::= { analogObjects 18 }

        -- 1.3.6.1.4.1.9839.2.1.2.19
        opt-sns-1-ain-offs OBJECT-TYPE
                    SYNTAX Integer32 (-32768..32767)
                    UNITS "N/A"
                    MAX-ACCESS read-only
                    STATUS current
                    DESCRIPTION "Analog Sensor 1 Calibration"
                    DEFVAL { 0 }
                    ::= { analogObjects 19 }

        -- 1.3.6.1.4.1.9839.2.1.2.20
        opt-sns-2-y1 OBJECT-TYPE
                    SYNTAX Integer32 (-32768..32767)
                    UNITS "N/A"
                    MAX-ACCESS read-only
                    STATUS current
                    DESCRIPTION "Analog Sensor 2 Minimum Value"
                    DEFVAL { 0 }
                    ::= { analogObjects 20 }

        -- 1.3.6.1.4.1.9839.2.1.2.21
        opt-sns-2-y2 OBJECT-TYPE
                    SYNTAX Integer32 (-32768..32767)
                    UNITS "N/A"
                    MAX-ACCESS read-only
                    STATUS current
                    DESCRIPTION "Analog Sensor 2 Maximum Value"
                    DEFVAL { 1000 }
                    ::= { analogObjects 21 }

        -- 1.3.6.1.4.1.9839.2.1.2.22
        opt-sns-2-ain-offs OBJECT-TYPE
                    SYNTAX Integer32 (-32768..32767)
                    UNITS "N/A"
                    MAX-ACCESS read-only
                    STATUS current
                    DESCRIPTION "Analog Sensor 2 Calibration"
                    DEFVAL { 0 }
                    ::= { analogObjects 22 }

        -- 1.3.6.1.4.1.9839.2.1.2.23
        opt-sns-3-y1 OBJECT-TYPE
                    SYNTAX Integer32 (-32768..32767)
                    UNITS "N/A"
                    MAX-ACCESS read-only
                    STATUS current
                    DESCRIPTION "Analog Sensor 3 Minimum Value"
                    DEFVAL { 0 }
                    ::= { analogObjects 23 }

        -- 1.3.6.1.4.1.9839.2.1.2.24
        opt-sns-3-y2 OBJECT-TYPE
                    SYNTAX Integer32 (-32768..32767)
                    UNITS "N/A"
                    MAX-ACCESS read-only
                    STATUS current
                    DESCRIPTION "Analog Sensor 3 Maximum Value"
                    DEFVAL { 1000 }
                    ::= { analogObjects 24 }

        -- 1.3.6.1.4.1.9839.2.1.2.25
        opt-sns-3-ain-offs OBJECT-TYPE
                    SYNTAX Integer32 (-32768..32767)
                    UNITS "N/A"
                    MAX-ACCESS read-only
                    STATUS current
                    DESCRIPTION "Analog Sensor 3 Calibration"
                    DEFVAL { 0 }
                    ::= { analogObjects 25 }

        -- 1.3.6.1.4.1.9839.2.1.2.26
        opt-sns-4-y1 OBJECT-TYPE
                    SYNTAX Integer32 (-32768..32767)
                    UNITS "N/A"
                    MAX-ACCESS read-only
                    STATUS current
                    DESCRIPTION "Analog Sensor 4 Minimum Value"
                    DEFVAL { 0 }
                    ::= { analogObjects 26 }

        -- 1.3.6.1.4.1.9839.2.1.2.27
        opt-sns-4-y2 OBJECT-TYPE
                    SYNTAX Integer32 (-32768..32767)
                    UNITS "N/A"
                    MAX-ACCESS read-only
                    STATUS current
                    DESCRIPTION "Analog Sensor 4 Maximum Value"
                    DEFVAL { 1000 }
                    ::= { analogObjects 27 }

        -- 1.3.6.1.4.1.9839.2.1.2.28
        opt-sns-4-ain-offs OBJECT-TYPE
                    SYNTAX Integer32 (-32768..32767)
                    UNITS "N/A"
                    MAX-ACCESS read-only
                    STATUS current
                    DESCRIPTION "Analog Sensor 4 Calibration"
                    DEFVAL { 0 }
                    ::= { analogObjects 28 }



        -- 1.3.6.1.4.1.9839.2.1.3
        integerObjects OBJECT IDENTIFIER ::= { dap4-alMIB 3 }

        -- 1.3.6.1.4.1.9839.2.1.3.1
        disch-air-lo-sp OBJECT-TYPE
                    SYNTAX Integer32 (-32767..32767)
                    UNITS "N/A"
                    MAX-ACCESS read-write
                    STATUS current
                    DESCRIPTION "Lower Limit alarm of discharge air temp"
                    DEFVAL { 0 }
                    ::= { integerObjects 1 }

        -- 1.3.6.1.4.1.9839.2.1.3.2
        humidity-dis OBJECT-TYPE
                    SYNTAX Integer32 (-999..999)
                    UNITS "N/A"
                    MAX-ACCESS read-only
                    STATUS current
                    DESCRIPTION "Relative humidity displayed as xx%"
                    DEFVAL { 0 }
                    ::= { integerObjects 2 } 
  
        -- 1.3.6.1.4.1.9839.2.1.3.3
        stages-on OBJECT-TYPE
                    SYNTAX Integer32 (-32767..32767)
                    UNITS "N/A"
                    MAX-ACCESS read-only
                    STATUS current
                    DESCRIPTION "Cooling Stages On, DX only"
                    DEFVAL { 0 }
                    ::= { integerObjects 3 }    

        -- 1.3.6.1.4.1.9839.2.1.3.4
        heaters-on OBJECT-TYPE
                    SYNTAX Integer32 (-32768..32767)
                    UNITS "N/A"
                    MAX-ACCESS read-only
                    STATUS current
                    DESCRIPTION "Number of heat stages running"
                    DEFVAL { 0 }
                    ::= { integerObjects 4 }

        -- 1.3.6.1.4.1.9839.2.1.3.5
        minmax-24hr-hum-maximum OBJECT-TYPE
                    SYNTAX Integer32 (-32768..32767)
                    UNITS "N/A"
                    MAX-ACCESS read-only
                    STATUS current
                    DESCRIPTION "Maximum humidity in last 24hrs"
                    DEFVAL { 0 }
                    ::= { integerObjects 5 }

        -- 1.3.6.1.4.1.9839.2.1.3.6
        minmax-24hr-hum-minumum OBJECT-TYPE
                    SYNTAX Integer32 (-32768..32767)
                    UNITS "N/A"
                    MAX-ACCESS read-only
                    STATUS current
                    DESCRIPTION "Minimum humidity in last 24hrs"
                    DEFVAL { 0 }
                    ::= { integerObjects 6 }

        -- 1.3.6.1.4.1.9839.2.1.3.7
        comp-duty OBJECT-TYPE
                    SYNTAX Integer32 (0..999)
                    UNITS "N/A"
                    MAX-ACCESS read-only
                    STATUS current
                    DESCRIPTION "Cooling Utilization Over Last Hour -Percentage of cooling is used in the last hour of operation; this point applies to DX unit."
                    DEFVAL { 0 }
                    ::= { integerObjects 7 }

        -- 1.3.6.1.4.1.9839.2.1.3.8
        heat-duty OBJECT-TYPE
                    SYNTAX Integer32 (0..999)
                    UNITS "N/A"
                    MAX-ACCESS read-only
                    STATUS current
                    DESCRIPTION "Heating Utilization Over Last Hour -Percentage of heating is used in the last hour of operation"
                    DEFVAL { 0 }
                    ::= { integerObjects 8 }

        -- 1.3.6.1.4.1.9839.2.1.3.9
        hum-duty OBJECT-TYPE
                    SYNTAX Integer32 (0..999)
                    UNITS "N/A"
                    MAX-ACCESS read-only
                    STATUS current
                    DESCRIPTION "Humidifier Utilization Over Last Hour -Percentage of humidifier is used in the last hour of operation"
                    DEFVAL { 0 }
                    ::= { integerObjects 9 }

        -- 1.3.6.1.4.1.9839.2.1.3.10
        c1-hours-h OBJECT-TYPE
                    SYNTAX Integer32 (-32768..32767)
                    UNITS "N/A"
                    MAX-ACCESS read-only
                    STATUS current
                    DESCRIPTION "Compressor 1 Runtime -This point applies to DX unit with one compressor -high"
                    DEFVAL { 0 }
                    ::= { integerObjects 10 }

        -- 1.3.6.1.4.1.9839.2.1.3.11
        c1-hours-l OBJECT-TYPE
                    SYNTAX Integer32 (-32768..32767)
                    UNITS "hour"
                    MAX-ACCESS read-only
                    STATUS current
                    DESCRIPTION "Compressor 1 Runtime -This point applies to DX unit with one compressor -low"
                    DEFVAL { 0 }
                    ::= { integerObjects 11 }

        -- 1.3.6.1.4.1.9839.2.1.3.12
        c2-hours-h OBJECT-TYPE
                    SYNTAX Integer32 (-32768..32767)
                    UNITS "N/A"
                    MAX-ACCESS read-only
                    STATUS current
                    DESCRIPTION "Compressor 2 Runtime -This point applies to DX unit with dual compressor - high"
                    DEFVAL { 0 }
                    ::= { integerObjects 12 }

        -- 1.3.6.1.4.1.9839.2.1.3.13
        c2-hours-l OBJECT-TYPE
                    SYNTAX Integer32 (-32768..32767)
                    UNITS "hour"
                    MAX-ACCESS read-only
                    STATUS current
                    DESCRIPTION "Compressor 2 Runtime -This point applies to DX unit with dual compressor - low"
                    DEFVAL { 0 }
                    ::= { integerObjects 13 }

        -- 1.3.6.1.4.1.9839.2.1.3.14
        ht1-hours-h OBJECT-TYPE
                    SYNTAX Integer32 (-32768..32767)
                    UNITS "N/A"
                    MAX-ACCESS read-only
                    STATUS current
                    DESCRIPTION "Heater 1 Runtime - high"
                    DEFVAL { 0 }
                    ::= { integerObjects 14 }

        -- 1.3.6.1.4.1.9839.2.1.3.15
        ht1-hours-l OBJECT-TYPE
                    SYNTAX Integer32 (-32768..32767)
                    UNITS "hour"
                    MAX-ACCESS read-only
                    STATUS current
                    DESCRIPTION "Heater 1 Runtime - low"
                    DEFVAL { 0 }
                    ::= { integerObjects 15 }

        -- 1.3.6.1.4.1.9839.2.1.3.16
        current-second OBJECT-TYPE
                    SYNTAX Integer32 (0..59)
                    UNITS "sec"
                    MAX-ACCESS read-only
                    STATUS current
                    DESCRIPTION "Current second"
                    DEFVAL { 0 }
                    ::= { integerObjects 16 }

        -- 1.3.6.1.4.1.9839.2.1.3.17
        current-minute OBJECT-TYPE
                    SYNTAX Integer32 (0..59)
                    UNITS "N/A"
                    MAX-ACCESS read-only
                    STATUS current
                    DESCRIPTION "Current minute"
                    DEFVAL { 0 }
                    ::= { integerObjects 17 }

        -- 1.3.6.1.4.1.9839.2.1.3.18
        current-hour OBJECT-TYPE
                    SYNTAX Integer32 (0..23)
                    UNITS "hour"
                    MAX-ACCESS read-only
                    STATUS current
                    DESCRIPTION "Current hour"
                    DEFVAL { 0 }
                    ::= { integerObjects 18 }

        -- 1.3.6.1.4.1.9839.2.1.3.19
        current-day OBJECT-TYPE
                    SYNTAX Integer32 (1..31)
                    UNITS "N/A"
                    MAX-ACCESS read-only
                    STATUS current
                    DESCRIPTION "Current day"
                    DEFVAL { 1 }
                    ::= { integerObjects 19 }

        -- 1.3.6.1.4.1.9839.2.1.3.20
        current-month OBJECT-TYPE
                    SYNTAX Integer32 (1..12)
                    UNITS "N/A"
                    MAX-ACCESS read-only
                    STATUS current
                    DESCRIPTION "Current month"
                    DEFVAL { 1 }
                    ::= { integerObjects 20 }

        -- 1.3.6.1.4.1.9839.2.1.3.21
        current-year OBJECT-TYPE
                    SYNTAX Integer32 (0..99)
                    UNITS "N/A"
                    MAX-ACCESS read-only
                    STATUS current
                    DESCRIPTION "Current year"
                    DEFVAL { 0 }
                    ::= { integerObjects 21 }

        -- 1.3.6.1.4.1.9839.2.1.3.22
        firestat-sp OBJECT-TYPE
                    SYNTAX Integer32 (0..999)
                    UNITS "N/A"
                    MAX-ACCESS read-write
                    STATUS current
                    DESCRIPTION "Alarm settting of return air temp to determine there is a fire"
                    DEFVAL { 0 }
                    ::= { integerObjects 22 }

        -- 1.3.6.1.4.1.9839.2.1.3.23
        hum-hi-sp OBJECT-TYPE
                    SYNTAX Integer32 (0..99)
                    UNITS "N/A"
                    MAX-ACCESS read-write
                    STATUS current
                    DESCRIPTION "Humidity upper limit alarm"
                    DEFVAL { 0 }
                    ::= { integerObjects 23 }

        -- 1.3.6.1.4.1.9839.2.1.3.24
        ret-air-hi-sp OBJECT-TYPE
                    SYNTAX Integer32 (-32768..32767)
                    UNITS "N/A"
                    MAX-ACCESS read-write
                    STATUS current
                    DESCRIPTION "Upper limit alarm of return air temp"
                    DEFVAL { 0 }
                    ::= { integerObjects 24 }

        -- 1.3.6.1.4.1.9839.2.1.3.25
        hum-lo-sp OBJECT-TYPE
                    SYNTAX Integer32 (0..99)
                    UNITS "N/A"
                    MAX-ACCESS read-write
                    STATUS current
                    DESCRIPTION "Humidity lower  limit alarm"
                    DEFVAL { 0 }
                    ::= { integerObjects 25 }

        -- 1.3.6.1.4.1.9839.2.1.3.26
        ret-air-lo-sp OBJECT-TYPE
                    SYNTAX Integer32 (-32768..32767)
                    UNITS "N/A"
                    MAX-ACCESS read-write
                    STATUS current
                    DESCRIPTION "Lower limit alarm of return air temp"
                    DEFVAL { 0 }
                    ::= { integerObjects 26 }

        -- 1.3.6.1.4.1.9839.2.1.3.27
        hum-deadband OBJECT-TYPE
                    SYNTAX Integer32 (0..999)
                    UNITS "N/A"
                    MAX-ACCESS read-write
                    STATUS current
                    DESCRIPTION "amount hum must change from setpoint before acting"
                    DEFVAL { 0 }
                    ::= { integerObjects 27 }

        -- 1.3.6.1.4.1.9839.2.1.3.28
        hum-setpoint OBJECT-TYPE
                    SYNTAX Integer32 (0..999)
                    UNITS "N/A"
                    MAX-ACCESS read-write
                    STATUS current
                    DESCRIPTION "humidity setpoint"
                    DEFVAL { 0 }
                    ::= { integerObjects 28 }

        -- 1.3.6.1.4.1.9839.2.1.3.29
        start-dly OBJECT-TYPE
                    SYNTAX Integer32 (1..600)
                    UNITS "N/A"
                    MAX-ACCESS read-write
                    STATUS current
                    DESCRIPTION "Time before the system starts up"
                    DEFVAL { 10 }
                    ::= { integerObjects 29 }

        -- 1.3.6.1.4.1.9839.2.1.3.30
        alm1-del OBJECT-TYPE
                    SYNTAX Integer32 (0..32000)
                    UNITS "N/A"
                    MAX-ACCESS read-only
                    STATUS current
                    DESCRIPTION "Optional Alarm 1 Delay"
                    DEFVAL { 0 }
                    ::= { integerObjects 30 }

        -- 1.3.6.1.4.1.9839.2.1.3.31
        alm2-del OBJECT-TYPE
                    SYNTAX Integer32 (0..32000)
                    UNITS "N/A"
                    MAX-ACCESS read-only
                    STATUS current
                    DESCRIPTION "Optional Alarm 2 Delay"
                    DEFVAL { 0 }
                    ::= { integerObjects 31 }

        -- 1.3.6.1.4.1.9839.2.1.3.32
        alm3-del OBJECT-TYPE
                    SYNTAX Integer32 (0..32000)
                    UNITS "N/A"
                    MAX-ACCESS read-only
                    STATUS current
                    DESCRIPTION "Optional Alarm 3 Delay"
                    DEFVAL { 0 }
                    ::= { integerObjects 32 }

        -- 1.3.6.1.4.1.9839.2.1.3.33
        alarm1-txt OBJECT-TYPE
                    SYNTAX Integer32 (0..16)
                    UNITS "N/A"
                    MAX-ACCESS read-only
                    STATUS current
                    DESCRIPTION "Message on optional alarm screen, some also add function"
                    DEFVAL { 0 }
                    ::= { integerObjects 33 }

        -- 1.3.6.1.4.1.9839.2.1.3.34
        alarm2-txt OBJECT-TYPE
                    SYNTAX Integer32 (0..16)
                    UNITS "N/A"
                    MAX-ACCESS read-only
                    STATUS current
                    DESCRIPTION "Message on optional alarm screen, some also add function"
                    DEFVAL { 0 }
                    ::= { integerObjects 34 }

        -- 1.3.6.1.4.1.9839.2.1.3.35
        alarm3-txt OBJECT-TYPE
                    SYNTAX Integer32 (0..16)
                    UNITS "N/A"
                    MAX-ACCESS read-only
                    STATUS current
                    DESCRIPTION "Message on optional alarm screen, some also add function"
                    DEFVAL { 0 }
                    ::= { integerObjects 35 }

        -- 1.3.6.1.4.1.9839.2.1.3.36
        alarm4-txt OBJECT-TYPE
                    SYNTAX Integer32 (0..16)
                    UNITS "N/A"
                    MAX-ACCESS read-only
                    STATUS current
                    DESCRIPTION "Message on optional alarm screen, some also add function"
                    DEFVAL { 0 }
                    ::= { integerObjects 36 }

        -- 1.3.6.1.4.1.9839.2.1.3.37
        comp-sel OBJECT-TYPE
                    SYNTAX Integer32 (0..5)
                    UNITS "N/A"
                    MAX-ACCESS read-only
                    STATUS current
                    DESCRIPTION "Comps  0=none, 1=one, 2=one+UL, 3=two, 4=two+UL, 5=Four/two circuit"
                    DEFVAL { 0 }
                    ::= { integerObjects 37 }

        -- 1.3.6.1.4.1.9839.2.1.3.38
        dehum-mode OBJECT-TYPE
                    SYNTAX Integer32 (0..4)
                    UNITS "N/A"
                    MAX-ACCESS read-only
                    STATUS current
                    DESCRIPTION "0=none, 1= comp limited, 2=twocomp limited, 3= comp unlimited, 4=twocomp unlimited"
                    DEFVAL { 0 }
                    ::= { integerObjects 38 }

        -- 1.3.6.1.4.1.9839.2.1.3.39
        reheat-sel OBJECT-TYPE
                    SYNTAX Integer32 (0..3)
                    UNITS "N/A"
                    MAX-ACCESS read-only
                    STATUS current
                    DESCRIPTION "Number of heat stages"
                    DEFVAL { 0 }
                    ::= { integerObjects 39 }

        -- 1.3.6.1.4.1.9839.2.1.3.40
        hum-sel OBJECT-TYPE
                    SYNTAX Integer32 (0..4)
                    UNITS "N/A"
                    MAX-ACCESS read-only
                    STATUS current
                    DESCRIPTION "0=none, 1=comp mod, 2=comp non, 3= comf mod, 4= conf non mod"
                    DEFVAL { 0 }
                    ::= { integerObjects 40 }

        -- 1.3.6.1.4.1.9839.2.1.3.41
        alm-contact-msg OBJECT-TYPE
                    SYNTAX Integer32 (0..4)
                    UNITS "N/A"
                    MAX-ACCESS read-only
                    STATUS current
                    DESCRIPTION "Text displayed on all alarm screens"
                    DEFVAL { 0 }
                    ::= { integerObjects 41 }

        -- 1.3.6.1.4.1.9839.2.1.3.42
        powerup-sel OBJECT-TYPE
                    SYNTAX Integer32 (0..2)
                    UNITS "N/A"
                    MAX-ACCESS read-only
                    STATUS current
                    DESCRIPTION "0= start wo/alarm, 1= start w/alarm, 2= requires reset of alarm"
                    DEFVAL { 0 }
                    ::= { integerObjects 42 }

        -- 1.3.6.1.4.1.9839.2.1.3.43
        buzzer-select OBJECT-TYPE
                    SYNTAX Integer32 (0..3)
                    UNITS "N/A"
                    MAX-ACCESS read-only
                    STATUS current
                    DESCRIPTION "0=None, 1=short beeps, 2=long beep, 3=Constant"
                    DEFVAL { 0 }
                    ::= { integerObjects 43 }

        -- 1.3.6.1.4.1.9839.2.1.3.44
        cw-disp OBJECT-TYPE
                    SYNTAX Integer32 (0..999)
                    UNITS "N/A"
                    MAX-ACCESS read-only
                    STATUS current
                    DESCRIPTION "% of 10volts of analog output #1"
                    DEFVAL { 0 }
                    ::= { integerObjects 44 }

        -- 1.3.6.1.4.1.9839.2.1.3.45
        wtrvlv-duty OBJECT-TYPE
                    SYNTAX Integer32 (0..999)
                    UNITS "N/A"
                    MAX-ACCESS read-only
                    STATUS current
                    DESCRIPTION "Chilled Water Utilization Over Last Hour - This applies to Chilled water or Energy saver units. "
                    DEFVAL { 0 }
                    ::= { integerObjects 45 }

        -- 1.3.6.1.4.1.9839.2.1.3.46
        hum-hours-h OBJECT-TYPE
                    SYNTAX Integer32 (-32768..32767)
                    UNITS "N/A"
                    MAX-ACCESS read-only
                    STATUS current
                    DESCRIPTION "Humidifier Runtime - high"
                    DEFVAL { 0 }
                    ::= { integerObjects 46 }

        -- 1.3.6.1.4.1.9839.2.1.3.47
        hum-hours-l OBJECT-TYPE
                    SYNTAX Integer32 (-32768..32767)
                    UNITS "hour"
                    MAX-ACCESS read-only
                    STATUS current
                    DESCRIPTION "Humidifier Runtime - low"
                    DEFVAL { 0 }
                    ::= { integerObjects 47 }

        -- 1.3.6.1.4.1.9839.2.1.3.48
        blower-hours-h OBJECT-TYPE
                    SYNTAX Integer32 (-32768..32767)
                    UNITS "N/A"
                    MAX-ACCESS read-only
                    STATUS current
                    DESCRIPTION "Blower Runtime - high"
                    DEFVAL { 0 }
                    ::= { integerObjects 48 }

        -- 1.3.6.1.4.1.9839.2.1.3.49
        blower-hours-l OBJECT-TYPE
                    SYNTAX Integer32 (-32768..32767)
                    UNITS "hour"
                    MAX-ACCESS read-only
                    STATUS current
                    DESCRIPTION "Blower Runtime - low"
                    DEFVAL { 0 }
                    ::= { integerObjects 49 }

        -- 1.3.6.1.4.1.9839.2.1.3.50
        alm4-del OBJECT-TYPE
                    SYNTAX Integer32 (0..32000)
                    UNITS "N/A"
                    MAX-ACCESS read-only
                    STATUS current
                    DESCRIPTION "Optional Alarm 4 Delay"
                    DEFVAL { 0 }
                    ::= { integerObjects 50 }

        -- 1.3.6.1.4.1.9839.2.1.3.51
        assist-sel OBJECT-TYPE
                    SYNTAX Integer32 (0..5)
                    UNITS "N/A"
                    MAX-ACCESS read-only
                    STATUS current
                    DESCRIPTION "0= no comp assist, 1=one comp assist, 2= two comp assist, 3... 4..."
                    DEFVAL { 0 }
                    ::= { integerObjects 51 }

        -- 1.3.6.1.4.1.9839.2.1.3.52
        wtrvlv-sel OBJECT-TYPE
                    SYNTAX Integer32 (0..4)
                    UNITS "N/A"
                    MAX-ACCESS read-only
                    STATUS current
                    DESCRIPTION "Water valve type  0=none, 1=chill, 2=Engy, 3=Aux chill, 4=Disc Reg"
                    DEFVAL { 0 }
                    ::= { integerObjects 52 }

        -- 1.3.6.1.4.1.9839.2.1.3.53
        wtrvlv-volts-sel OBJECT-TYPE
                    SYNTAX Integer32 (0..4)
                    UNITS "N/A"
                    MAX-ACCESS read-only
                    STATUS current
                    DESCRIPTION "Water valve voltage  0= 0-10, 1=2-10, 2=7-10, 3=6-9, 4=4-7"
                    DEFVAL { 0 }
                    ::= { integerObjects 53 }

        -- 1.3.6.1.4.1.9839.2.1.3.54
        hum-volts OBJECT-TYPE
                    SYNTAX Integer32 (0..999)
                    UNITS "N/A"
                    MAX-ACCESS read-only
                    STATUS current
                    DESCRIPTION "% of 10volts of analog output #2"
                    DEFVAL { 0 }
                    ::= { integerObjects 54 }

        -- 1.3.6.1.4.1.9839.2.1.3.55
        dehum-hours-h OBJECT-TYPE
                    SYNTAX Integer32 (-32768..32767)
                    UNITS "N/A"
                    MAX-ACCESS read-only
                    STATUS current
                    DESCRIPTION "Dehumidifier Runtime - High"
                    DEFVAL { 0 }
                    ::= { integerObjects 55 }

        -- 1.3.6.1.4.1.9839.2.1.3.56
        dehum-hours-l OBJECT-TYPE
                    SYNTAX Integer32 (-32768..32767)
                    UNITS "hour"
                    MAX-ACCESS read-only
                    STATUS current
                    DESCRIPTION "Dehumidifier Runtime - Low"
                    DEFVAL { 0 }
                    ::= { integerObjects 56 }

        -- 1.3.6.1.4.1.9839.2.1.3.58
        autoflush-dly OBJECT-TYPE
                    SYNTAX Integer32 (0..99)
                    UNITS "hour"
                    MAX-ACCESS read-only
                    STATUS current
                    DESCRIPTION "Time between drain cycles 0=12hr, 1=24hr, 2=48hr, 3=96hr, 4=None"
                    DEFVAL { 0 }
                    ::= { integerObjects 58 }

        -- 1.3.6.1.4.1.9839.2.1.3.59
        y4-out OBJECT-TYPE
                    SYNTAX Integer32 (-32768..32767)
                    UNITS "N/A"
                    MAX-ACCESS read-only
                    STATUS current
                    DESCRIPTION "Value sent to optional analog output#1"
                    DEFVAL { 0 }
                    ::= { integerObjects 59 }

        -- 1.3.6.1.4.1.9839.2.1.3.60
        y5-out OBJECT-TYPE
                    SYNTAX Integer32 (-32768..32767)
                    UNITS "N/A"
                    MAX-ACCESS read-only
                    STATUS current
                    DESCRIPTION "Value sent to optional analog output#2"
                    DEFVAL { 0 }
                    ::= { integerObjects 60 }

        -- 1.3.6.1.4.1.9839.2.1.3.61
        air-flow OBJECT-TYPE
                    SYNTAX Integer32 (-32768..32767)
                    UNITS "N/A"
                    MAX-ACCESS read-only
                    STATUS current
                    DESCRIPTION "Current Fan Airflow - Based on calculated Pressure Diff formula"
                    DEFVAL { 0 }
                    ::= { integerObjects 61 }

        -- 1.3.6.1.4.1.9839.2.1.3.62
        opt-snsr1-name OBJECT-TYPE
                    SYNTAX Integer32 (-32768..32767)
                    UNITS "N/A"
                    MAX-ACCESS read-only
                    STATUS current
                    DESCRIPTION "Name of the sensor"
                    DEFVAL { 0 }
                    ::= { integerObjects 62 }

        -- 1.3.6.1.4.1.9839.2.1.3.63
        opt-sns-1-ain-type OBJECT-TYPE
                    SYNTAX Integer32 (0..9)
                    UNITS "N/A"
                    MAX-ACCESS read-only
                    STATUS current
                    DESCRIPTION "Analog Sensor 1 Type {0=NTC 1=PT1000 2=0-1VDC 3=0-10VDC 4=4-20mA 5=ON/OFF 6=0-5VDC 7=NTC HT 8=-50T90 9=10T170}"
                    DEFVAL { 0 }
                    ::= { integerObjects 63 }

        -- 1.3.6.1.4.1.9839.2.1.3.64
        opt-snsr2-name OBJECT-TYPE
                    SYNTAX Integer32 (-32768..32767)
                    UNITS "N/A"
                    MAX-ACCESS read-only
                    STATUS current
                    DESCRIPTION "Name of the sensor"
                    DEFVAL { 0 }
                    ::= { integerObjects 64 }

        -- 1.3.6.1.4.1.9839.2.1.3.65
        opt-sns-2-ain-type OBJECT-TYPE
                    SYNTAX Integer32 (0..9)
                    UNITS "N/A"
                    MAX-ACCESS read-only
                    STATUS current
                    DESCRIPTION "Analog Sensor 2 Type {0=NTC 1=PT1000 2=0-1VDC 3=0-10VDC 4=4-20mA 5=ON/OFF 6=0-5VDC 7=NTC HT 8=-50T90 9=10T170}"
                    DEFVAL { 0 }
                    ::= { integerObjects 65 }

        -- 1.3.6.1.4.1.9839.2.1.3.66
        opt-snsr3-name OBJECT-TYPE
                    SYNTAX Integer32 (-32768..32767)
                    UNITS "N/A"
                    MAX-ACCESS read-only
                    STATUS current
                    DESCRIPTION "Name of the sensor"
                    DEFVAL { 0 }
                    ::= { integerObjects 66 }

        -- 1.3.6.1.4.1.9839.2.1.3.67
        opt-sns-3-ain-type OBJECT-TYPE
                    SYNTAX Integer32 (0..9)
                    UNITS "N/A"
                    MAX-ACCESS read-only
                    STATUS current
                    DESCRIPTION "Analog Sensor 3 Type {0=NTC 1=PT1000 2=0-1VDC 3=0-10VDC 4=4-20mA 5=ON/OFF 6=0-5VDC 7=NTC HT 8=-50T90 9=10T170}"
                    DEFVAL { 0 }
                    ::= { integerObjects 67 }

        -- 1.3.6.1.4.1.9839.2.1.3.68
        opt-snsr4-name OBJECT-TYPE
                    SYNTAX Integer32 (-32768..32767)
                    UNITS "N/A"
                    MAX-ACCESS read-only
                    STATUS current
                    DESCRIPTION "Name of the sensor"
                    DEFVAL { 0 }
                    ::= { integerObjects 68 }

        -- 1.3.6.1.4.1.9839.2.1.3.69
        opt-sns-4-ain-type OBJECT-TYPE
                    SYNTAX Integer32 (0..9)
                    UNITS "N/A"
                    MAX-ACCESS read-only
                    STATUS current
                    DESCRIPTION "Analog Sensor 4 Type {0=NTC 1=PT1000 2=0-1VDC 3=0-10VDC 4=4-20mA 5=ON/OFF 6=0-5VDC 7=NTC HT 8=-50T90 9=10T170}"
                    DEFVAL { 0 }
                    ::= { integerObjects 69 }

        -- 1.3.6.1.4.1.9839.2.1.3.70
        cw-fan-speed-bms OBJECT-TYPE
                    SYNTAX Integer32 (0..100)
                    UNITS "N/A"
                    MAX-ACCESS read-write
                    STATUS current
                    DESCRIPTION "CW Fan speed (%) sent via BMS"
                    DEFVAL { 0 }
                    ::= { integerObjects 70 }

        -- 1.3.6.1.4.1.9839.2.1.3.71
        dx-fan-speed-bms OBJECT-TYPE
                    SYNTAX Integer32 (0..100)
                    UNITS "N/A"
                    MAX-ACCESS read-write
                    STATUS current
                    DESCRIPTION "DX Fan speed (%) sent via BMS"
                    DEFVAL { 0 }
                    ::= { integerObjects 71 }

        -- 1.3.6.1.4.1.9839.2.1.3.72
        fan-speed-max OBJECT-TYPE
                    SYNTAX Integer32 (70..100)
                    UNITS "N/A"
                    MAX-ACCESS read-write
                    STATUS current
                    DESCRIPTION "Maximum Fan speed (% of output) modulation."
                    DEFVAL { 100 }
                    ::= { integerObjects 72 }

        -- 1.3.6.1.4.1.9839.2.1.3.73
        fan-speed-min OBJECT-TYPE
                    SYNTAX Integer32 (40..100)
                    UNITS "N/A"
                    MAX-ACCESS read-write
                    STATUS current
                    DESCRIPTION "Minimum Fan speed (% of output) modulation from pressure."
                    DEFVAL { 40 }
                    ::= { integerObjects 73 }

        -- 1.3.6.1.4.1.9839.2.1.3.74
        fan-pr-sp OBJECT-TYPE
                    SYNTAX Integer32 (0..1001)
                    UNITS "N/A"
                    MAX-ACCESS read-write
                    STATUS current
                    DESCRIPTION "Fan pressure setpoint (0.01 inches of water)"
                    DEFVAL { 0 }
                    ::= { integerObjects 74 }

        -- 1.3.6.1.4.1.9839.2.1.3.75
        fan-pr-band OBJECT-TYPE
                    SYNTAX Integer32 (1..100)
                    UNITS "N/A"
                    MAX-ACCESS read-write
                    STATUS current
                    DESCRIPTION "Fan pressure band (0.01 inches of water)"
                    DEFVAL { 5 }
                    ::= { integerObjects 75 }

        -- 1.3.6.1.4.1.9839.2.1.3.76
        fan-af-max OBJECT-TYPE
                    SYNTAX Integer32 (0..32000)
                    UNITS "N/A"
                    MAX-ACCESS read-write
                    STATUS current
                    DESCRIPTION "Maximum air flow limit of setpoint from BMS or valve modulation."
                    DEFVAL { 1000 }
                    ::= { integerObjects 76 }

        -- 1.3.6.1.4.1.9839.2.1.3.77
        fan-af-min OBJECT-TYPE
                    SYNTAX Integer32 (0..32000)
                    UNITS "N/A"
                    MAX-ACCESS read-write
                    STATUS current
                    DESCRIPTION "Minimum air flow limit of setpoint from BMS or valve modulation."
                    DEFVAL { 1000 }
                    ::= { integerObjects 77 }

        -- 1.3.6.1.4.1.9839.2.1.3.78
        fan-kfactor OBJECT-TYPE
                    SYNTAX Integer32 (100..500)
                    UNITS "N/A"
                    MAX-ACCESS read-write
                    STATUS current
                    DESCRIPTION "Fan K Factor"
                    DEFVAL { 200 }
                    ::= { integerObjects 78 }

        -- 1.3.6.1.4.1.9839.2.1.3.79
        num-fans OBJECT-TYPE
                    SYNTAX Integer32 (1..3)
                    UNITS "N/A"
                    MAX-ACCESS read-write
                    STATUS current
                    DESCRIPTION "Number of fans installed in this unit"
                    DEFVAL { 1 }
                    ::= { integerObjects 79 }

        -- 1.3.6.1.4.1.9839.2.1.3.81
        ht2-hours-h OBJECT-TYPE
                    SYNTAX Integer32 (-32768..32767)
                    UNITS "N/A"
                    MAX-ACCESS read-only
                    STATUS current
                    DESCRIPTION "Heater 2 Runtime - high"
                    DEFVAL { 0 }
                    ::= { integerObjects 81 }

        -- 1.3.6.1.4.1.9839.2.1.3.82
        ht2-hours-l OBJECT-TYPE
                    SYNTAX Integer32 (-32768..32767)
                    UNITS "hour"
                    MAX-ACCESS read-only
                    STATUS current
                    DESCRIPTION "Heater 2 Runtime - low"
                    DEFVAL { 0 }
                    ::= { integerObjects 82 }

        -- 1.3.6.1.4.1.9839.2.1.3.83
        ht3-hours-h OBJECT-TYPE
                    SYNTAX Integer32 (-32768..32767)
                    UNITS "N/A"
                    MAX-ACCESS read-only
                    STATUS current
                    DESCRIPTION "Heater 3 Runtime - high"
                    DEFVAL { 0 }
                    ::= { integerObjects 83 }

        -- 1.3.6.1.4.1.9839.2.1.3.84
        ht3-hours-l OBJECT-TYPE
                    SYNTAX Integer32 (-32768..32767)
                    UNITS "hour"
                    MAX-ACCESS read-only
                    STATUS current
                    DESCRIPTION "Heater 3 Runtime - low"
                    DEFVAL { 0 }
                    ::= { integerObjects 84 }

        -- 1.3.6.1.4.1.9839.2.1.3.85
        engy-hours-h OBJECT-TYPE
                    SYNTAX Integer32 (-32768..32767)
                    UNITS "N/A"
                    MAX-ACCESS read-only
                    STATUS current
                    DESCRIPTION "Energy Saver Runtime - This optional point applies to energy saver units only -high"
                    DEFVAL { 0 }
                    ::= { integerObjects 85 }

        -- 1.3.6.1.4.1.9839.2.1.3.86
        engy-hours-l OBJECT-TYPE
                    SYNTAX Integer32 (-32768..32767)
                    UNITS "hour"
                    MAX-ACCESS read-only
                    STATUS current
                    DESCRIPTION "Energy Saver Runtime - This optional point applies to energy saver units only - low"
                    DEFVAL { 0 }
                    ::= { integerObjects 86 }

        -- 1.3.6.1.4.1.9839.2.1.3.87
        cw-hours-h OBJECT-TYPE
                    SYNTAX Integer32 (-32768..32767)
                    UNITS "N/A"
                    MAX-ACCESS read-only
                    STATUS current
                    DESCRIPTION "Chilled Water Runtime - This applies to chilled water units only - high"
                    DEFVAL { 0 }
                    ::= { integerObjects 87 }

        -- 1.3.6.1.4.1.9839.2.1.3.88
        cw-hours-l OBJECT-TYPE
                    SYNTAX Integer32 (-32768..32767)
                    UNITS "hour"
                    MAX-ACCESS read-only
                    STATUS current
                    DESCRIPTION "Chilled Water Runtime - This applies to chilled water units only - low"
                    DEFVAL { 0 }
                    ::= { integerObjects 88 }

        -- 1.3.6.1.4.1.9839.2.1.3.89
        c3-hours-h OBJECT-TYPE
                    SYNTAX Integer32 (-32768..32767)
                    UNITS "N/A"
                    MAX-ACCESS read-only
                    STATUS current
                    DESCRIPTION "Compressor 3 Runtime - This applies when unit has four stages tandem compressors - high"
                    DEFVAL { 0 }
                    ::= { integerObjects 89 }

        -- 1.3.6.1.4.1.9839.2.1.3.90
        c3-hours-l OBJECT-TYPE
                    SYNTAX Integer32 (-32768..32767)
                    UNITS "hour"
                    MAX-ACCESS read-only
                    STATUS current
                    DESCRIPTION "Compressor 3 Runtime - This applies when unit has four stages tandem compressors - low"
                    DEFVAL { 0 }
                    ::= { integerObjects 90 }

        -- 1.3.6.1.4.1.9839.2.1.3.91
        c4-hours-l OBJECT-TYPE
                    SYNTAX Integer32 (-32768..32767)
                    UNITS "hour"
                    MAX-ACCESS read-only
                    STATUS current
                    DESCRIPTION "Compressor 4 Runtime - This applies when unit has four stages tandem compressors. - high"
                    DEFVAL { 0 }
                    ::= { integerObjects 91 }

        -- 1.3.6.1.4.1.9839.2.1.3.92
        c4-hours-h OBJECT-TYPE
                    SYNTAX Integer32 (-32768..32767)
                    UNITS "N/A"
                    MAX-ACCESS read-only
                    STATUS current
                    DESCRIPTION "Compressor 4 Runtime - This applies when unit has four stages tandem compressors. - low"
                    DEFVAL { 0 }
                    ::= { integerObjects 92 }

        -- 1.3.6.1.4.1.9839.2.1.3.93
        cond-hours-h OBJECT-TYPE
                    SYNTAX Integer32 (-32768..32767)
                    UNITS "N/A"
                    MAX-ACCESS read-only
                    STATUS current
                    DESCRIPTION "Condenser Runtime - high"
                    DEFVAL { 0 }
                    ::= { integerObjects 93 }

        -- 1.3.6.1.4.1.9839.2.1.3.94
        cond-hours-l OBJECT-TYPE
                    SYNTAX Integer32 (-32768..32767)
                    UNITS "hour"
                    MAX-ACCESS read-only
                    STATUS current
                    DESCRIPTION "Condenser Runtime - low"
                    DEFVAL { 0 }
                    ::= { integerObjects 94 }

        -- 1.3.6.1.4.1.9839.2.1.3.95
        dx-fan-speed OBJECT-TYPE
                    SYNTAX Integer32 (60..100)
                    UNITS "N/A"
                    MAX-ACCESS read-only
                    STATUS current
                    DESCRIPTION "Fan speed (% of output) when compressor cooling."
                    DEFVAL { 85 }
                    ::= { integerObjects 95 }

        -- 1.3.6.1.4.1.9839.2.1.3.96
        cw-fan-speed OBJECT-TYPE
                    SYNTAX Integer32 (60..100)
                    UNITS "N/A"
                    MAX-ACCESS read-only
                    STATUS current
                    DESCRIPTION "Fan speed (% of output) when cold water cooling."
                    DEFVAL { 85 }
                    ::= { integerObjects 96 }

        -- 1.3.6.1.4.1.9839.2.1.3.97
        fan-af-dx-sp OBJECT-TYPE
                    SYNTAX Integer32 (0..32000)
                    UNITS "N/A"
                    MAX-ACCESS read-only
                    STATUS current
                    DESCRIPTION "Fan air flow setpoint for DX unit (cfm)"
                    DEFVAL { 0 }
                    ::= { integerObjects 97 }

        -- 1.3.6.1.4.1.9839.2.1.3.98
        fan-af-cw-sp OBJECT-TYPE
                    SYNTAX Integer32 (0..32000)
                    UNITS "N/A"
                    MAX-ACCESS read-only
                    STATUS current
                    DESCRIPTION "Fan air flow setpoint for CW unit (cfm)"
                    DEFVAL { 0 }
                    ::= { integerObjects 98 }

        -- 1.3.6.1.4.1.9839.2.1.3.99
        zm-airflow-sp OBJECT-TYPE
                    SYNTAX Integer32 (-32768..32767)
                    UNITS "N/A"
                    MAX-ACCESS read-write
                    STATUS current
                    DESCRIPTION "Zone Airflow Setpoint kcfm"
                    DEFVAL { 0 }
                    ::= { integerObjects 99 }


	
	END

--
-- DataAire-dap4-al.MIB
--
