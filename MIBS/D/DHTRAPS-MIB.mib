-- ------------------------------------------------------
-- Dot Hill Low Cost Array MIB for SNMP Traps
--
-- $Revision: 1.2 $
--
-- Copyright 2005 Dot Hill Systems Corp.
-- All rights reserved. Use is subject to license terms.
--
-- ------------------------------------------------------

DHTRAPS-MIB
-- Last edit date: Nov 11th, 2005
DEFINITIONS ::= BEGIN
  IMPORTS
    enterprises
        FROM RFC1155-SMI
    TRAP-TYPE
        FROM RFC-1215
    connUnitEventId, connUnitEventType, connUnitEventDescr
        FROM FCMGMT-MIB;


    --Textual conventions for this MIB

----------------------------------------------------------------------
    -- formerly Box Hill
    dothill    OBJECT IDENTIFIER ::= { enterprises 347 }


-- Related traps

    dhEventInfoTrap TRAP-TYPE
        ENTERPRISE dothill
        VARIABLES { connUnitEventId,
                    connUnitEventType,
                    connUnitEventDescr }
        DESCRIPTION
            "An event has been generated by the storage array.
            Recommended severity level (for filtering): info"

        -- Trap annotations are as follows:
		--#TYPE "Informational storage event"
		--#SUMMARY "Informational storage event # %d, type %d, description: %s"
		--#ARGUMENTS {0,1,2}
		--#SEVERITY INFORMATIONAL
		--#TIMEINDEX 6
        ::= 1

    dhEventWarningTrap TRAP-TYPE
        ENTERPRISE dothill
        VARIABLES { connUnitEventId,
                    connUnitEventType,
                    connUnitEventDescr }
        DESCRIPTION
            "An event has been generated by the storage array.
            Recommended severity level (for filtering): warning"

        -- Trap annotations are as follows:
		--#TYPE "Warning storage event"
		--#SUMMARY "Warning storage event # %d, type %d, description: %s"
		--#ARGUMENTS {0,1,2}
		--#SEVERITY MINOR
		--#TIMEINDEX 6
        ::= 2

    dhEventErrorTrap TRAP-TYPE
        ENTERPRISE dothill
        VARIABLES { connUnitEventId,
                    connUnitEventType,
                    connUnitEventDescr }
        DESCRIPTION
            "An event has been generated by the storage array.
            Recommended severity level (for filtering): error"

        -- Trap annotations are as follows:
		--#TYPE "Error storage event"
		--#SUMMARY "Error storage event # %d, type %d, description: %s"
		--#ARGUMENTS {0,1,2}
		--#SEVERITY MAJOR
		--#TIMEINDEX 6
        ::= 3

    dhEventCriticalTrap TRAP-TYPE
        ENTERPRISE dothill
        VARIABLES { connUnitEventId,
                    connUnitEventType,
                    connUnitEventDescr }
        DESCRIPTION
            "An event has been generated by the storage array.
            Recommended severity level (for filtering): critical"

        -- Trap annotations are as follows:
		--#TYPE "Critical storage event"
		--#SUMMARY "Critical storage event # %d, type %d, description: %s"
		--#ARGUMENTS {0,1,2}
		--#SEVERITY CRITICAL
		--#TIMEINDEX 6
        ::= 4


END
