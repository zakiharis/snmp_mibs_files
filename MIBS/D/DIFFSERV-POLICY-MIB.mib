-- extracted from draft-ietf-snmpconf-diffpolicy-04.txt
-- at Tue Mar  6 06:04:42 2001

   DIFFSERV-POLICY-MIB DEFINITIONS ::= BEGIN

   -- This version of the MIB is aligned with the DiffServ WG's MIB
   -- found in draft-ietf-diffserv-mib-06.txt.  This MIB module will
   -- remain aligned with that work as updates are made.

   -- Note that much of the content of the MIBs in previous versions
   -- of this document have been removed since they were used for
   -- creating "templates" that were not bound to interface
   -- instances.  That functionality now exists in the DIFF-SERV-MIB
   -- itself.

       IMPORTS

       Integer32, OBJECT-TYPE, MODULE-IDENTITY, zeroDotZero, mib-2
          FROM SNMPv2-SMI

       RowStatus, RowPointer, TestAndIncr, DateAndTime
          FROM SNMPv2-TC

       MODULE-COMPLIANCE, OBJECT-GROUP
          FROM SNMPv2-CONF

       SnmpAdminString
          FROM SNMP-FRAMEWORK-MIB;

   diffPolicyMib MODULE-IDENTITY
       LAST-UPDATED "200011130500Z" -- November 12, 2000, 20:00 San Francisco
       ORGANIZATION "SNMPCONF WG"
       CONTACT-INFO
          "SNMPCONF Working Group
           http://www.ietf.org/html.charters/snmpconf-charter.html
          Editors:

          Harrie Hazewinkel
          Postal: Covalent Technologies
                  706 Mission Street (2nd floor)
                  San Francisco, CA - 94133
                  United States
          Tel: +1 415 536 5221
          E-mail: harrie@covalent.net

          David Partain
          Postal: Ericsson Radio Systems
                  P.O. Box 1248
                  SE-581 12 Linkoping
                  Sweden
          Tel: +46 13 28 41 44
          E-mail: David.Partain@ericsson.com"

       DESCRIPTION
               "This MIB module contains differentiated services
               specific managed objects to perform policy-based
               configuration management. This MIB allows policies
               to use 'templates' to be used to instantiate
               diffserv datapath configurations to be assigned
               (associated with an interface and direction)
               when a policy is created and activated."
       ::= { mib-2 22222222 }  -- Needs to be assigned by IANA

   diffPolicyMIBObjects     OBJECT IDENTIFIER ::= { diffPolicyMib 1 }
   diffPolicyMIBConformance OBJECT IDENTIFIER ::= { diffPolicyMib 2 }

   --
   -- The DiffServ Policy Configuration objects
   --

   diffPolicyDPCUnique OBJECT-TYPE
       SYNTAX       TestAndIncr
       MAX-ACCESS   read-write
       STATUS       current
       DESCRIPTION
          "The diffPolicyDPCUnique object yields a unique new
          value for diffPolicyDPCId when read and subsequently
          set. This value must be tested for uniqueness."
       ::= { diffPolicyMIBObjects 1 }

   diffPolicyDPCTable OBJECT-TYPE
       SYNTAX       SEQUENCE OF DiffPolicyDPCEntry
       MAX-ACCESS   not-accessible
       STATUS       current
       DESCRIPTION
          "A table which defines the various per-hop-behaviors
          for which the system has default 'templates'."
       ::= { diffPolicyMIBObjects 2 }

   diffPolicyDPCEntry OBJECT-TYPE
       SYNTAX       DiffPolicyDPCEntry
       MAX-ACCESS   not-accessible
       STATUS       current
       DESCRIPTION
          "An entry defining a per-hop-behavior.  Each entry in
          this table combines the various parameters (entries)
          into a specific per-hop-behavior.  Entries in this
          table might be defined by a vendor (pre-configured)
          or defined by a management application."
       INDEX { diffPolicyDPCId }
       ::= { diffPolicyDPCTable 1 }

   DiffPolicyDPCEntry ::= SEQUENCE {
       diffPolicyDPCId               Integer32,
       diffPolicyDPCDescr            SnmpAdminString,
       diffPolicyDPCOwner            SnmpAdminString,
       diffPolicyDPCLastChange       DateAndTime,
       diffPolicyDPCConfiguration    RowPointer,
       diffPolicyDPCStatus           RowStatus
   }

   diffPolicyDPCId OBJECT-TYPE
       SYNTAX         Integer32 (1..2147483647)
       MAX-ACCESS     not-accessible
       STATUS         current
       DESCRIPTION
          "A unique id for the per-hop-behavior policy."
       ::= { diffPolicyDPCEntry 1 }

   diffPolicyDPCDescr OBJECT-TYPE
       SYNTAX         SnmpAdminString
       MAX-ACCESS     read-create
       STATUS         current
       DESCRIPTION
          "A human-readable description to identify this defined
          per-hop-behavior.  Note that this is an SnmpAdminString,
          which permits UTF-8 strings."
       ::= { diffPolicyDPCEntry 2 }

   diffPolicyDPCOwner OBJECT-TYPE
       SYNTAX         SnmpAdminString
       MAX-ACCESS     read-create
       STATUS         current
       DESCRIPTION
          "The owner who created this entry."
       ::= { diffPolicyDPCEntry 3 }

   diffPolicyDPCLastChange OBJECT-TYPE
       SYNTAX         DateAndTime
       MAX-ACCESS     read-only
       STATUS         current
       DESCRIPTION
          "The date and time when this entry was last changed."
       ::= { diffPolicyDPCEntry 4 }

   diffPolicyDPCConfiguration OBJECT-TYPE
       SYNTAX         RowPointer
       MAX-ACCESS     read-create
       STATUS         current
       DESCRIPTION
          "The pointer to a datapath configuration template as
          set up in the DIFFSERV-MIB.  This  RowPointer  should
          point to an instance of one of:
         diffServClfrElementEntry
            diffServClfrEntry
            diffServMeterEntry
            diffServActionEntry
            diffServAlgDropEntry
            diffServQEntry
          A value of zeroDotZero in this attribute indicates no
          further Diffserv treatment is performed on traffic of
          this datapath.

          If the row pointed to does not exist,  the  treatment
          is  as if this attribute contains a value of zero-
          DotZero."
       DEFVAL { zeroDotZero }
       ::= { diffPolicyDPCEntry 5 }

   diffPolicyDPCStatus OBJECT-TYPE
       SYNTAX         RowStatus
       MAX-ACCESS     read-create
       STATUS         current
       DESCRIPTION
          "RowStatus object used for creation and deletion of
          rows in this table."
       ::= { diffPolicyDPCEntry 11 }

   --
   -- MIB Compliance statements.
   --

   diffPolicyMIBCompliances OBJECT IDENTIFIER ::= { diffPolicyMIBConformance 1 }
   diffPolicyMIBGroups      OBJECT IDENTIFIER ::= { diffPolicyMIBConformance 2 }

   diffPolicyMIBFullCompliance MODULE-COMPLIANCE
       STATUS       current
       DESCRIPTION
          "The full compliance for this MIB module."
       MODULE  -- This module
       MANDATORY-GROUPS {  diffPolicyMIBDPCGroup }
       ::= { diffPolicyMIBCompliances 1 }

   diffPolicyMIBDPCGroup OBJECT-GROUP
       OBJECTS {  diffPolicyDPCUnique,
                  diffPolicyDPCDescr,
                  diffPolicyDPCOwner,
                  diffPolicyDPCLastChange,
                  diffPolicyDPCConfiguration,
                  diffPolicyDPCStatus
       }
       STATUS current
       DESCRIPTION
          "The per-hop-behavior Group defines the MIB Objects that
          describe the configuration template for the per-hop-behavior."
       ::= { diffPolicyMIBGroups 1 }

   END

-- 
-- 
--    Copyright (C) The Internet Society (2000).  All Rights Reserved.
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE."
-- 
--
