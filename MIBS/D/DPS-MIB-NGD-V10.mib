--  Title:    NGD_G42.MIB

--  Version:  v4.2

--

--  Copyright @ 1997-2004 DPS Inc. All Rights Reserved

--

--  This MIB defines supplemental objects for the DPS NetGuardian series.

--

--



DPS-MIB-NGD-V10 DEFINITIONS ::= BEGIN



IMPORTS

	dpsRTU

		FROM DPS-MIB-V38;



dpsRTUp8001Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 1 is set."

	::=  8001



dpsRTUp9001Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 1 clears."

	::=  9001



dpsRTUp8002Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 2 is set."

	::=  8002



dpsRTUp9002Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 2 clears."

	::=  9002



dpsRTUp8003Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 3 is set."

	::=  8003



dpsRTUp9003Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 3 clears."

	::=  9003



dpsRTUp8004Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 4 is set."

	::=  8004



dpsRTUp9004Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 4 clears."

	::=  9004



dpsRTUp8005Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 5 is set."

	::=  8005



dpsRTUp9005Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 5 clears."

	::=  9005



dpsRTUp8006Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 6 is set."

	::=  8006



dpsRTUp9006Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 6 clears."

	::=  9006



dpsRTUp8007Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 7 is set."

	::=  8007



dpsRTUp9007Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 7 clears."

	::=  9007



dpsRTUp8008Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 8 is set."

	::=  8008



dpsRTUp9008Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 8 clears."

	::=  9008



dpsRTUp8009Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 9 is set."

	::=  8009



dpsRTUp9009Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 9 clears."

	::=  9009



dpsRTUp8010Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 10 is set."

	::=  8010



dpsRTUp9010Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 10 clears."

	::=  9010



dpsRTUp8011Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 11 is set."

	::=  8011



dpsRTUp9011Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 11 clears."

	::=  9011



dpsRTUp8012Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 12 is set."

	::=  8012



dpsRTUp9012Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 12 clears."

	::=  9012



dpsRTUp8013Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 13 is set."

	::=  8013



dpsRTUp9013Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 13 clears."

	::=  9013



dpsRTUp8014Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 14 is set."

	::=  8014



dpsRTUp9014Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 14 clears."

	::=  9014



dpsRTUp8015Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 15 is set."

	::=  8015



dpsRTUp9015Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 15 clears."

	::=  9015



dpsRTUp8016Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 16 is set."

	::=  8016



dpsRTUp9016Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 16 clears."

	::=  9016



dpsRTUp8017Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 17 is set."

	::=  8017



dpsRTUp9017Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 17 clears."

	::=  9017



dpsRTUp8018Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 18 is set."

	::=  8018



dpsRTUp9018Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 18 clears."

	::=  9018



dpsRTUp8019Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 19 is set."

	::=  8019



dpsRTUp9019Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 19 clears."

	::=  9019



dpsRTUp8020Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 20 is set."

	::=  8020



dpsRTUp9020Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 20 clears."

	::=  9020



dpsRTUp8021Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 21 is set."

	::=  8021



dpsRTUp9021Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 21 clears."

	::=  9021



dpsRTUp8022Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 22 is set."

	::=  8022



dpsRTUp9022Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 22 clears."

	::=  9022



dpsRTUp8023Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 23 is set."

	::=  8023



dpsRTUp9023Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 23 clears."

	::=  9023



dpsRTUp8024Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 24 is set."

	::=  8024



dpsRTUp9024Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 24 clears."

	::=  9024



dpsRTUp8025Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 25 is set."

	::=  8025



dpsRTUp9025Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 25 clears."

	::=  9025



dpsRTUp8026Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 26 is set."

	::=  8026



dpsRTUp9026Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 26 clears."

	::=  9026



dpsRTUp8027Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 27 is set."

	::=  8027



dpsRTUp9027Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 27 clears."

	::=  9027



dpsRTUp8028Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 28 is set."

	::=  8028



dpsRTUp9028Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 28 clears."

	::=  9028



dpsRTUp8029Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 29 is set."

	::=  8029



dpsRTUp9029Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 29 clears."

	::=  9029



dpsRTUp8030Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 30 is set."

	::=  8030



dpsRTUp9030Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 30 clears."

	::=  9030



dpsRTUp8031Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 31 is set."

	::=  8031



dpsRTUp9031Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 31 clears."

	::=  9031



dpsRTUp8032Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 32 is set."

	::=  8032



dpsRTUp9032Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 32 clears."

	::=  9032

dpsRTUp8033Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 33 is set."

	::=  8033



dpsRTUp9033Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 33 clears."

	::=  9033

dpsRTUp8034Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 34 is set."

	::=  8034



dpsRTUp9034Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 34 clears."

	::=  9034

dpsRTUp8035Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 35 is set."

	::=  8035



dpsRTUp9035Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 35 clears."

	::=  9035

dpsRTUp8036Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 36 is set."

	::=  8036



dpsRTUp9036Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 36 clears."

	::=  9036



dpsRTUp8037Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 37 is set."

	::=  8037



dpsRTUp9037Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 37 clears."

	::=  9037



dpsRTUp8038Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 38 is set."

	::=  8038



dpsRTUp9038Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 38 clears."

	::=  9038



dpsRTUp8039Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 39 is set."

	::=  8039



dpsRTUp9039Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 39 clears."

	::=  9039



dpsRTUp8040Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 40 is set."

	::=  8040



dpsRTUp9040Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 40 clears."

	::=  9040

dpsRTUp8041Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 41 is set."

	::=  8041



dpsRTUp9041Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 41 clears."

	::=  9041



dpsRTUp8042Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 42 is set."

	::=  8042



dpsRTUp9042Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 42 clears."

	::=  9042



dpsRTUp8043Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 43 is set."

	::=  8043



dpsRTUp9043Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 43 clears."

	::=  9043



dpsRTUp8044Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 44 is set."

	::=  8044



dpsRTUp9044Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 44 clears."

	::=  9044



dpsRTUp8045Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 45 is set."

	::=  8045



dpsRTUp9045Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 45 clears."

	::=  9045



dpsRTUp8046Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 46 is set."

	::=  8046



dpsRTUp9046Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 46 clears."

	::=  9046



dpsRTUp8047Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 47 is set."

	::=  8047



dpsRTUp9047Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 47 clears."

	::=  9047



dpsRTUp8048Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 48 is set."

	::=  8048



dpsRTUp9048Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 48 clears."

	::=  9048



dpsRTUp8049Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 49 is set."

	::=  8049



dpsRTUp9049Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 49 clears."

	::=  9049



dpsRTUp8050Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 50 is set."

	::=  8050



dpsRTUp9050Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 50 clears."

	::=  9050





dpsRTUp8051Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 51 is set."

	::=  8051



dpsRTUp9051Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 51 clears."

	::=  9051



dpsRTUp8052Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 52 is set."

	::=  8052



dpsRTUp9052Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 52 clears."

	::=  9052



dpsRTUp8053Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 53 is set."

	::=  8053



dpsRTUp9053Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 53 clears."

	::=  9053



dpsRTUp8054Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 54 is set."

	::=  8054



dpsRTUp9054Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 54 clears."

	::=  9054



dpsRTUp8055Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 55 is set."

	::=  8055



dpsRTUp9055Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 55 clears."

	::=  9055



dpsRTUp8056Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 56 is set."

	::=  8056



dpsRTUp9056Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 56 clears."

	::=  9056



dpsRTUp8057Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 57 is set."

	::=  8057



dpsRTUp9057Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 57 clears."

	::=  9057



dpsRTUp8058Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 58 is set."

	::=  8058



dpsRTUp9058Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 58 clears."

	::=  9058



dpsRTUp8059Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 59 is set."

	::=  8059



dpsRTUp9059Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 59 clears."

	::=  9059



dpsRTUp8060Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 60 is set."

	::=  8060



dpsRTUp9060Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 60 clears."

	::=  9060

dpsRTUp8061Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 61 is set."

	::=  8061



dpsRTUp9061Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 61 clears."

	::=  9061



dpsRTUp8062Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 62 is set."

	::=  8062



dpsRTUp9062Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 62 clears."

	::=  9062



dpsRTUp8063Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 63 is set."

	::=  8063



dpsRTUp9063Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 63 clears."

	::=  9063



dpsRTUp8064Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 64 is set."

	::=  8064



dpsRTUp9064Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 64 clears."

	::=  9064





dpsRTUp8065Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 1 fails."

	::=  8065



dpsRTUp9065Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 1 reappears."

	::=  9065



dpsRTUp8066Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 2 fails."

	::=  8066



dpsRTUp9066Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 2 reappears."

	::=  9066



dpsRTUp8067Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 3 fails."

	::=  8067



dpsRTUp9067Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 3 reappears."

	::=  9067



dpsRTUp8068Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 4 fails."

	::=  8068



dpsRTUp9068Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 4 reappears."

	::=  9068



dpsRTUp8069Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 5 fails."

	::=  8069



dpsRTUp9069Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 5 reappears."

	::=  9069



dpsRTUp8070Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 6 fails."

	::=  8070



dpsRTUp9070Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 6 reappears."

	::=  9070



dpsRTUp8071Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 7 fails."

	::=  8071



dpsRTUp9071Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 7 reappears."

	::=  9071



dpsRTUp8072Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 8 fails."

	::=  8072



dpsRTUp9072Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 8 reappears."

	::=  9072



dpsRTUp8073Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 9 fails."

	::=  8073



dpsRTUp9073Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 9 reappears."

	::=  9073



dpsRTUp8074Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 10 fails."

	::=  8074



dpsRTUp9074Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 10 reappears."

	::=  9074



dpsRTUp8075Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 11 fails."

	::=  8075



dpsRTUp9075Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 11 reappears."

	::=  9075



dpsRTUp8076Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 12 fails."

	::=  8076



dpsRTUp9076Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 12 reappears."

	::=  9076



dpsRTUp8077Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 13 fails."

	::=  8077



dpsRTUp9077Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 13 reappears."

	::=  9077



dpsRTUp8078Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 14 fails."

	::=  8078



dpsRTUp9078Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 14 reappears."

	::=  9078



dpsRTUp8079Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 15 fails."

	::=  8079



dpsRTUp9079Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 15 reappears."

	::=  9079



dpsRTUp8080Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 16 fails."

	::=  8080



dpsRTUp9080Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 16 reappears."

	::=  9080



dpsRTUp8081Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 17 fails."

	::=  8081



dpsRTUp9081Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 17 reappears."

	::=  9081



dpsRTUp8082Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 18 fails."

	::=  8082



dpsRTUp9082Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 18 reappears."

	::=  9082



dpsRTUp8083Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 19 fails."

	::=  8083



dpsRTUp9083Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 19 reappears."

	::=  9083



dpsRTUp8084Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 20 fails."

	::=  8084



dpsRTUp9084Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 20 reappears."

	::=  9084



dpsRTUp8085Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 21 fails."

	::=  8085



dpsRTUp9085Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 21 reappears."

	::=  9085



dpsRTUp8086Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 22 fails."

	::=  8086



dpsRTUp9086Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 22 reappears."

	::=  9086



dpsRTUp8087Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 23 fails."

	::=  8087



dpsRTUp9087Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 23 reappears."

	::=  9087



dpsRTUp8088Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 24 fails."

	::=  8088



dpsRTUp9088Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 24 reappears."

	::=  9088



dpsRTUp8089Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 25 fails."

	::=  8089



dpsRTUp9089Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 25 reappears."

	::=  9089



dpsRTUp8090Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 26 fails."

	::=  8090



dpsRTUp9090Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 26 reappears."

	::=  9090



dpsRTUp8091Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 27 fails."

	::=  8091



dpsRTUp9091Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 27 reappears."

	::=  9091



dpsRTUp8092Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 28 fails."

	::=  8092



dpsRTUp9092Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 28 reappears."

	::=  9092



dpsRTUp8093Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 29 fails."

	::=  8093



dpsRTUp9093Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 29 reappears."

	::=  9093



dpsRTUp8094Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 30 fails."

	::=  8094



dpsRTUp9094Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 30 reappears."

	::=  9094



dpsRTUp8095Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 31 fails."

	::=  8095



dpsRTUp9095Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 31 reappears."

	::=  9095



dpsRTUp8096Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 32 fails."

	::=  8096



dpsRTUp9096Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when ping target 32 reappears."

	::=  9096

dpsRTUp8097Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 97 is set."

	::=  8097



dpsRTUp9097Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 97 clears."

	::=  9097



dpsRTUp8098Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 98 is set."

	::=  8098



dpsRTUp9098Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 98 clears."

	::=  9098



dpsRTUp8099Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 99 is set."

	::=  8099



dpsRTUp9099Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 99 clears."

	::=  9099



dpsRTUp8100Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 64 is set."

	::=  8100



dpsRTUp9100Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 64 clears."

	::=  9100



dpsRTUp8101Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 101 is set."

	::=  8101



dpsRTUp9101Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 101 clears."

	::=  9101



dpsRTUp8102Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 102 is set."

	::=  8102



dpsRTUp9102Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 102 clears."

	::=  9102



dpsRTUp8103Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 103 is set."

	::=  8103



dpsRTUp9103Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 103 clears."

	::=  9103



dpsRTUp8104Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 104 is set."

	::=  8104



dpsRTUp9104Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 104 clears."

	::=  9104



dpsRTUp8105Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 105 is set."

	::=  8105



dpsRTUp9105Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 105 clears."

	::=  9105



dpsRTUp8106Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 106 is set."

	::=  8106



dpsRTUp9106Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 106 clears."

	::=  9106



dpsRTUp8107Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 107 is set."

	::=  8107



dpsRTUp9107Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 107 clears."

	::=  9107



dpsRTUp8108Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 108 is set."

	::=  8108



dpsRTUp9108Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 108 clears."

	::=  9108



dpsRTUp8109Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 109 is set."

	::=  8109



dpsRTUp9109Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 109 clears."

	::=  9109



dpsRTUp8110Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 110 is set."

	::=  8110



dpsRTUp9110Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 110 clears."

	::=  9110





dpsRTUp8111Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 111 is set."

	::=  8111



dpsRTUp9111Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 111 clears."

	::=  9111



dpsRTUp8112Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 112 is set."

	::=  8112



dpsRTUp9112Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 112 clears."

	::=  9112



dpsRTUp8113Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 113 is set."

	::=  8113



dpsRTUp9113Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 113 clears."

	::=  9113



dpsRTUp8114Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 114 is set."

	::=  8114



dpsRTUp9114Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 114 clears."

	::=  9114



dpsRTUp8115Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 115 is set."

	::=  8115



dpsRTUp9115Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 115 clears."

	::=  9115



dpsRTUp8116Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 116 is set."

	::=  8116



dpsRTUp9116Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 116 clears."

	::=  9116



dpsRTUp8117Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 117 is set."

	::=  8117



dpsRTUp9117Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 117 clears."

	::=  9117



dpsRTUp8118Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 118 is set."

	::=  8118



dpsRTUp9118Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 118 clears."

	::=  9118



dpsRTUp8119Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 119 is set."

	::=  8119



dpsRTUp9119Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 119 clears."

	::=  9119



dpsRTUp8120Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 120 is set."

	::=  8120



dpsRTUp9120Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 120 clears."

	::=  9120

dpsRTUp8121Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 121 is set."

	::=  8121



dpsRTUp9121Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 121 clears."

	::=  9121



dpsRTUp8122Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 122 is set."

	::=  8122



dpsRTUp9122Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 122 clears."

	::=  9122



dpsRTUp8123Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 123 is set."

	::=  8123



dpsRTUp9123Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 123 clears."

	::=  9123



dpsRTUp8124Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 124 is set."

	::=  8124



dpsRTUp9124Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 124 clears."

	::=  9124



dpsRTUp8125Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 125 is set."

	::=  8125



dpsRTUp9125Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 125 clears."

	::=  9125



dpsRTUp8126Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 126 is set."

	::=  8126



dpsRTUp9126Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 126 clears."

	::=  9126



dpsRTUp8127Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 127 is set."

	::=  8127



dpsRTUp9127Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 127 clears."

	::=  9127



dpsRTUp8128Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 128 is set."

	::=  8128



dpsRTUp9128Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 128 clears."

	::=  9128



dpsRTUp8129Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 minor under threshold is violated"

	::=  8129



dpsRTUp9129Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 minor under threshold is restored"

	::=  9129



dpsRTUp8130Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 minor over threshold is violated"

	::=  8130



dpsRTUp9130Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 minor over threshold is restored"

	::=  9130



dpsRTUp8131Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 major under threshold is violated"

	::=  8131



dpsRTUp9131Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 major under threshold is restored"

	::=  9131



dpsRTUp8132Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 major over threshold is violated"

	::=  8132



dpsRTUp9132Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 1 major over threshold is restored"

	::=  9132



dpsRTUp8133Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 133 is set."

	::=  8133



dpsRTUp9133Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 133 clears."

	::=  9133

	   

dpsRTUp8134Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 134 is set."

	::=  8134



dpsRTUp9134Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 134 clears."

	::=  9134

	   

dpsRTUp8135Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 135 is set."

	::=  8135



dpsRTUp9135Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 135 clears."

	::=  9135

	   

dpsRTUp8136Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 136 is set."

	::=  8136



dpsRTUp9136Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 136 clears."

	::=  9136

	   

dpsRTUp8137Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 137 is set."

	::=  8137



dpsRTUp9137Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 137 clears."

	::=  9137

	   

dpsRTUp8138Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 138 is set."

	::=  8138



dpsRTUp9138Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 138 clears."

	::=  9138

	   

dpsRTUp8139Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 139 is set."

	::=  8139



dpsRTUp9139Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 139 clears."

	::=  9139

	   

dpsRTUp8140Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 140 is set."

	::=  8140



dpsRTUp9140Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 140 clears."

	::=  9140

	   

dpsRTUp8141Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 141 is set."

	::=  8141



dpsRTUp9141Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 141 clears."

	::=  9141

	   

dpsRTUp8142Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 142 is set."

	::=  8142



dpsRTUp9142Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 142 clears."

	::=  9142

	   

dpsRTUp8143Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 143 is set."

	::=  8143



dpsRTUp9143Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 143 clears."

	::=  9143

	   

dpsRTUp8144Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 144 is set."

	::=  8144



dpsRTUp9144Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 144 clears."

	::=  9144

	   

dpsRTUp8145Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 145 is set."

	::=  8145



dpsRTUp9145Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 145 clears."

	::=  9145

	   

dpsRTUp8146Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 146 is set."

	::=  8146



dpsRTUp9146Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 146 clears."

	::=  9146

	   

dpsRTUp8147Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 147 is set."

	::=  8147



dpsRTUp9147Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 147 clears."

	::=  9147

	   

dpsRTUp8148Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 148 is set."

	::=  8148



dpsRTUp9148Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 148 clears."

	::=  9148

	   

dpsRTUp8149Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 149 is set."

	::=  8149



dpsRTUp9149Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 149 clears."

	::=  9149

	   

dpsRTUp8150Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 150 is set."

	::=  8150



dpsRTUp9150Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 150 clears."

	::=  9150

	   

dpsRTUp8151Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 151 is set."

	::=  8151



dpsRTUp9151Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 151 clears."

	::=  9151

	   

dpsRTUp8152Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 152 is set."

	::=  8152



dpsRTUp9152Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 152 clears."

	::=  9152

	   

dpsRTUp8153Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 153 is set."

	::=  8153



dpsRTUp9153Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 153 clears."

	::=  9153

	   

dpsRTUp8154Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 154 is set."

	::=  8154



dpsRTUp9154Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 154 clears."

	::=  9154

	   

dpsRTUp8155Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 155 is set."

	::=  8155



dpsRTUp9155Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 155 clears."

	::=  9155

	   

dpsRTUp8156Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 156 is set."

	::=  8156



dpsRTUp9156Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 156 clears."

	::=  9156

	   

dpsRTUp8157Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 157 is set."

	::=  8157



dpsRTUp9157Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 157 clears."

	::=  9157

	   

dpsRTUp8158Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 158 is set."

	::=  8158



dpsRTUp9158Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 158 clears."

	::=  9158

	   

dpsRTUp8159Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 159 is set."

	::=  8159



dpsRTUp9159Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 159 clears."

	::=  9159

	   

dpsRTUp8160Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 160 is set."

	::=  8160



dpsRTUp9160Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 160 clears."

	::=  9160

	   

dpsRTUp8161Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 161 is set."

	::=  8161



dpsRTUp9161Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 161 clears."

	::=  9161

	   

dpsRTUp8162Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 162 is set."

	::=  8162



dpsRTUp9162Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 162 clears."

	::=  9162

	   

dpsRTUp8163Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 163 is set."

	::=  8163



dpsRTUp9163Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 163 clears."

	::=  9163

	   

dpsRTUp8164Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 164 is set."

	::=  8164



dpsRTUp9164Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 164 clears."

	::=  9164

	   

dpsRTUp8165Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 165 is set."

	::=  8165



dpsRTUp9165Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 165 clears."

	::=  9165

	   

dpsRTUp8166Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 166 is set."

	::=  8166



dpsRTUp9166Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 166 clears."

	::=  9166

	   

dpsRTUp8167Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 167 is set."

	::=  8167



dpsRTUp9167Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 167 clears."

	::=  9167

	   

dpsRTUp8168Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 168 is set."

	::=  8168



dpsRTUp9168Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 168 clears."

	::=  9168

	   

dpsRTUp8169Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 169 is set."

	::=  8169



dpsRTUp9169Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 169 clears."

	::=  9169

	   

dpsRTUp8170Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 170 is set."

	::=  8170



dpsRTUp9170Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 170 clears."

	::=  9170

	   

dpsRTUp8171Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 171 is set."

	::=  8171



dpsRTUp9171Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 171 clears."

	::=  9171

	   

dpsRTUp8172Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 172 is set."

	::=  8172



dpsRTUp9172Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 172 clears."

	::=  9172

	   

dpsRTUp8173Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 173 is set."

	::=  8173



dpsRTUp9173Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 173 clears."

	::=  9173

	   

dpsRTUp8174Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 174 is set."

	::=  8174



dpsRTUp9174Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 174 clears."

	::=  9174

	   

dpsRTUp8175Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 175 is set."

	::=  8175



dpsRTUp9175Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 175 clears."

	::=  9175

	   

dpsRTUp8176Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 176 is set."

	::=  8176



dpsRTUp9176Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 176 clears."

	::=  9176



dpsRTUp8193Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 minor under threshold is violated"

	::=  8193



dpsRTUp9193Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 minor under threshold is restored"

	::=  9193



dpsRTUp8194Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 minor over threshold is violated"

	::=  8194



dpsRTUp9194Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 minor over threshold is restored"

	::=  9194



dpsRTUp8195Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 major under threshold is violated"

	::=  8195



dpsRTUp9195Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 major under threshold is restored"

	::=  9195



dpsRTUp8196Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 major over threshold is violated"

	::=  8196



dpsRTUp9196Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 2 major over threshold is restored"

	::=  9196



dpsRTUp8197Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 197 is set."

	::=  8197



dpsRTUp9197Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 197 clears."

	::=  9197



dpsRTUp8198Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 198 is set."

	::=  8198



dpsRTUp9198Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 198 clears."

	::=  9198



dpsRTUp8199Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 199 is set."

	::=  8199



dpsRTUp9199Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 199 clears."

	::=  9199



dpsRTUp8200Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 200 is set."

	::=  8200



dpsRTUp9200Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 200 clears."

	::=  9200



dpsRTUp8201Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 201 is set."

	::=  8201



dpsRTUp9201Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 201 clears."

	::=  9201



dpsRTUp8202Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 202 is set."

	::=  8202



dpsRTUp9202Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 202 clears."

	::=  9202



dpsRTUp8203Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 203 is set."

	::=  8203



dpsRTUp9203Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 203 clears."

	::=  9203



dpsRTUp8204Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 204 is set."

	::=  8204



dpsRTUp9204Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 204 clears."

	::=  9204



dpsRTUp8205Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 205 is set."

	::=  8205



dpsRTUp9205Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 205 clears."

	::=  9205



dpsRTUp8206Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 206 is set."

	::=  8206



dpsRTUp9206Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 206 clears."

	::=  9206



dpsRTUp8207Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 207 is set."

	::=  8207



dpsRTUp9207Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 207 clears."

	::=  9207



dpsRTUp8208Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 208 is set."

	::=  8208



dpsRTUp9208Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 208 clears."

	::=  9208



dpsRTUp8209Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 209 is set."

	::=  8209



dpsRTUp9209Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 209 clears."

	::=  9209



dpsRTUp8210Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 210 is set."

	::=  8210



dpsRTUp9210Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 210 clears."

	::=  9210





dpsRTUp8211Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 211 is set."

	::=  8211



dpsRTUp9211Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 211 clears."

	::=  9211



dpsRTUp8212Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 212 is set."

	::=  8212



dpsRTUp9212Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 212 clears."

	::=  9212



dpsRTUp8213Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 213 is set."

	::=  8213



dpsRTUp9213Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 213 clears."

	::=  9213



dpsRTUp8214Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 214 is set."

	::=  8214



dpsRTUp9214Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 214 clears."

	::=  9214



dpsRTUp8215Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 215 is set."

	::=  8215



dpsRTUp9215Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 215 clears."

	::=  9215



dpsRTUp8216Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 216 is set."

	::=  8216



dpsRTUp9216Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 216 clears."

	::=  9216



dpsRTUp8217Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 217 is set."

	::=  8217



dpsRTUp9217Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 217 clears."

	::=  9217



dpsRTUp8218Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 218 is set."

	::=  8218



dpsRTUp9218Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 218 clears."

	::=  9218



dpsRTUp8219Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 219 is set."

	::=  8219



dpsRTUp9219Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 219 clears."

	::=  9219



dpsRTUp8220Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 220 is set."

	::=  8220



dpsRTUp9220Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 220 clears."

	::=  9220



dpsRTUp8221Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 221 is set."

	::=  8221



dpsRTUp9221Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 221 clears."

	::=  9221



dpsRTUp8222Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 222 is set."

	::=  8222



dpsRTUp9222Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 222 clears."

	::=  9222



dpsRTUp8223Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 223 is set."

	::=  8223



dpsRTUp9223Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 223 clears."

	::=  9223



dpsRTUp8224Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 224 is set."

	::=  8224



dpsRTUp9224Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 224 clears."

	::=  9224



dpsRTUp8225Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 225 is set."

	::=  8225



dpsRTUp9225Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 225 clears."

	::=  9225



dpsRTUp8226Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 226 is set."

	::=  8226



dpsRTUp9226Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 226 clears."

	::=  9226



dpsRTUp8227Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 227 is set."

	::=  8227



dpsRTUp9227Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 227 clears."

	::=  9227



dpsRTUp8228Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 228 is set."

	::=  8228



dpsRTUp9228Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 228 clears."

	::=  9228



dpsRTUp8229Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 229 is set."

	::=  8229



dpsRTUp9229Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 229 clears."

	::=  9229



dpsRTUp8230Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 230 is set."

	::=  8230



dpsRTUp9230Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 230 clears."

	::=  9230





dpsRTUp8231Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 231 is set."

	::=  8231



dpsRTUp9231Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 231 clears."

	::=  9231



dpsRTUp8232Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 232 is set."

	::=  8232



dpsRTUp9232Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 232 clears."

	::=  9232



dpsRTUp8233Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 233 is set."

	::=  8233



dpsRTUp9233Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 233 clears."

	::=  9233



dpsRTUp8234Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 234 is set."

	::=  8234



dpsRTUp9234Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 234 clears."

	::=  9234



dpsRTUp8235Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 235 is set."

	::=  8235



dpsRTUp9235Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 235 clears."

	::=  9235



dpsRTUp8236Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 236 is set."

	::=  8236



dpsRTUp9236Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 236 clears."

	::=  9236



dpsRTUp8237Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 237 is set."

	::=  8237



dpsRTUp9237Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 237 clears."

	::=  9237



dpsRTUp8238Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 238 is set."

	::=  8238



dpsRTUp9238Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 238 clears."

	::=  9238



dpsRTUp8239Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 239 is set."

	::=  8239



dpsRTUp9239Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 239 clears."

	::=  9239



dpsRTUp8240Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 240 is set."

	::=  8240



dpsRTUp9240Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 240 clears."

	::=  9240





dpsRTUp8241Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 241 is set."

	::=  8241



dpsRTUp9241Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 241 clears."

	::=  9241



dpsRTUp8242Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 242 is set."

	::=  8242



dpsRTUp9242Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 242 clears."

	::=  9242



dpsRTUp8243Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 243 is set."

	::=  8243



dpsRTUp9243Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 243 clears."

	::=  9243



dpsRTUp8244Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 244 is set."

	::=  8244



dpsRTUp9244Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 244 clears."

	::=  9244



dpsRTUp8245Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 245 is set."

	::=  8245



dpsRTUp9245Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 245 clears."

	::=  9245



dpsRTUp8246Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 246 is set."

	::=  8246



dpsRTUp9246Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 246 clears."

	::=  9246



dpsRTUp8247Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 247 is set."

	::=  8247



dpsRTUp9247Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 247 clears."

	::=  9247



dpsRTUp8248Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 248 is set."

	::=  8248



dpsRTUp9248Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 248 clears."

	::=  9248



dpsRTUp8249Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 249 is set."

	::=  8249



dpsRTUp9249Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 249 clears."

	::=  9249



dpsRTUp8250Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 250 is set."

	::=  8250



dpsRTUp9250Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 250 clears."

	::=  9250



dpsRTUp8251Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 251 is set."

	::=  8251



dpsRTUp9251Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 251 clears."

	::=  9251



dpsRTUp8252Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 252 is set."

	::=  8252



dpsRTUp9252Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 252 clears."

	::=  9252



dpsRTUp8253Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 253 is set."

	::=  8253



dpsRTUp9253Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 253 clears."

	::=  9253



dpsRTUp8254Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 254 is set."

	::=  8254



dpsRTUp9254Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 254 clears."

	::=  9254



dpsRTUp8255Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 255 is set."

	::=  8255



dpsRTUp9255Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 255 clears."

	::=  9255



dpsRTUp8256Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 256 is set."

	::=  8256



dpsRTUp9256Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when discrete point 256 clears."

	::=  9256





dpsRTUp8257Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 minor under threshold is violated"

	::=  8257



dpsRTUp9257Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 minor under threshold is restored"

	::=  9257



dpsRTUp8258Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 minor over threshold is violated"

	::=  8258



dpsRTUp9258Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 minor over threshold is restored"

	::=  9258



dpsRTUp8259Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 major under threshold is violated"

	::=  8259



dpsRTUp9259Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 major under threshold is restored"

	::=  9259



dpsRTUp8260Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 major over threshold is violated"

	::=  8260



dpsRTUp9260Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 3 major over threshold is restored"

	::=  9260



dpsRTUp8321Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 minor under threshold is violated"

	::=  8321



dpsRTUp9321Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 minor under threshold is restored"

	::=  9321



dpsRTUp8322Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 minor over threshold is violated"

	::=  8322



dpsRTUp9322Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 minor over threshold is restored"

	::=  9322



dpsRTUp8323Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 major under threshold is violated"

	::=  8323



dpsRTUp9323Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 major under threshold is restored"

	::=  9323



dpsRTUp8324Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 major over threshold is violated"

	::=  8324



dpsRTUp9324Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 4 major over threshold is restored"

	::=  9324



dpsRTUp8385Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 minor under threshold is violated"

	::=  8385



dpsRTUp9385Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 minor under threshold is restored"

	::=  9385



dpsRTUp8386Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 minor over threshold is violated"

	::=  8386



dpsRTUp9386Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 minor over threshold is restored"

	::=  9386



dpsRTUp8387Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 major under threshold is violated"

	::=  8387



dpsRTUp9387Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 major under threshold is restored"

	::=  9387



dpsRTUp8388Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 major over threshold is violated"

	::=  8388



dpsRTUp9388Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 5 major over threshold is restored"

	::=  9388



dpsRTUp8449Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 minor under threshold is violated"

	::=  8449



dpsRTUp9449Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 minor under threshold is restored"

	::=  9449



dpsRTUp8450Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 minor over threshold is violated"

	::=  8450



dpsRTUp9450Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 minor over threshold is restored"

	::=  9450



dpsRTUp8451Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 major under threshold is violated"

	::=  8451



dpsRTUp9451Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 major under threshold is restored"

	::=  9451



dpsRTUp8452Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 major over threshold is violated"

	::=  8452



dpsRTUp9452Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 6 major over threshold is restored"

	::=  9452



dpsRTUp8513Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 minor under threshold is violated"

	::=  8513



dpsRTUp9513Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 minor under threshold is restored"

	::=  9513



dpsRTUp8514Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 minor over threshold is violated"

	::=  8514



dpsRTUp9514Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 minor over threshold is restored"

	::=  9514



dpsRTUp8515Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 major under threshold is violated"

	::=  8515



dpsRTUp9515Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 major under threshold is restored"

	::=  9515



dpsRTUp8516Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 major over threshold is violated"

	::=  8516



dpsRTUp9516Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 7 major over threshold is restored"

	::=  9516



dpsRTUp8577Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 minor under threshold is violated"

	::=  8577



dpsRTUp9577Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 minor under threshold is restored"

	::=  9577



dpsRTUp8578Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 minor over threshold is violated"

	::=  8578



dpsRTUp9578Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 minor over threshold is restored"

	::=  9578



dpsRTUp8579Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 major under threshold is violated"

	::=  8579



dpsRTUp9579Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 major under threshold is restored"

	::=  9579



dpsRTUp8580Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 major over threshold is violated"

	::=  8580



dpsRTUp9580Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when channel 8 major over threshold is restored"

	::=  9580



dpsRTUp8641Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 1 is latched."

	::=  8641



dpsRTUp9641Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 1 is released."

	::=  9641



dpsRTUp8642Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 2 is latched."

	::=  8642



dpsRTUp9642Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 2 is released."

	::=  9642



dpsRTUp8643Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 3 is latched."

	::=  8643



dpsRTUp9643Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 3 is released."

	::=  9643



dpsRTUp8644Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 4 is latched."

	::=  8644



dpsRTUp9644Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 4 is released."

	::=  9644



dpsRTUp8645Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 5 is latched."

	::=  8645



dpsRTUp9645Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 5 is released."

	::=  9645



dpsRTUp8646Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 6 is latched."

	::=  8646



dpsRTUp9646Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 6 is released."

	::=  9646



dpsRTUp8647Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 7 is latched."

	::=  8647



dpsRTUp9647Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 7 is released."

	::=  9647



dpsRTUp8648Set TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 8 is latched."

	::=  8648



dpsRTUp9648Clr TRAP-TYPE

	ENTERPRISE  dpsRTU

	VARIABLES {	sysDescr, sysLocation, dpsRTUDateTime,

					dpsRTUAPort, dpsRTUCAddress, dpsRTUADisplay, dpsRTUAPoint,

					dpsRTUAPntDesc, dpsRTUAState }

	DESCRIPTION "Generated when control 8 is released."

	::=  9648



dpsRTUp8657Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Timed Tick: set."

	::= 8657



dpsRTUp9657Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Timed Tick: cleared."

	::= 9657



dpsRTUp8658Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Exp.Module Callout: set."

	::= 8658



dpsRTUp9658Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Exp.Module Callout: cleared."

	::= 9658



dpsRTUp8659Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Network Time Server: set."

	::= 8659



dpsRTUp9659Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Network Time Server: cleared."

	::= 9659



dpsRTUp8673Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Power Up: set."

	::= 8673



dpsRTUp9673Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Power Up: cleared."

	::= 9673





dpsRTUp8676Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Lost Provisioning: set."

	::= 8676



dpsRTUp9676Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Lost Provisioning: cleared."

	::= 9676





dpsRTUp8677Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "DCP Poller Inactive: set."

	::= 8677



dpsRTUp9677Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "DCP Poller Inactive: cleared."

	::= 9677





dpsRTUp8678Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "LAN Not Active: set."

	::= 8678



dpsRTUp9678Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "LAN Not Active: cleared."

	::= 9678





dpsRTUp8681Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Modem Not Responding: set."

	::= 8681



dpsRTUp9681Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Modem Not Responding: cleared."

	::= 9681





dpsRTUp8682Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "No Dialtone: set."

	::= 8682



dpsRTUp9682Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "No Dialtone: cleared."

	::= 9682



dpsRTUp8683Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "SNMP Trap not Sent: set."

	::= 8683



dpsRTUp9683Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "SNMP Trap not Sent: cleared."

	::= 9683



dpsRTUp8684Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Pager Que Overflow: set."

	::= 8684



dpsRTUp9684Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Pager Que Overflow: cleared."

	::= 9684





dpsRTUp8685Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Notification Failed: set."

	::= 8685



dpsRTUp9685Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Notification Failed: cleared."

	::= 9685





dpsRTUp8686Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Craft RcvQ full: set."

	::= 8686



dpsRTUp9686Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Craft RcvQ full: cleared."

	::= 9686





dpsRTUp8687Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Modem RcvQ full: set."

	::= 8687



dpsRTUp9687Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Modem RcvQ full: cleared."

	::= 9687





dpsRTUp8688Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 1 RcvQ full: set."

	::= 8688



dpsRTUp9688Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 1 RcvQ full: cleared."

	::= 9688





dpsRTUp8689Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 2 RcvQ full: set."

	::= 8689



dpsRTUp9689Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 2 RcvQ full: cleared."

	::= 9689





dpsRTUp8690Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 3 RcvQ full: set."

	::= 8690



dpsRTUp9690Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 3 RcvQ full: cleared."

	::= 9690





dpsRTUp8691Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 4 RcvQ full: set."

	::= 8691



dpsRTUp9691Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 4 RcvQ full: cleared."

	::= 9691





dpsRTUp8692Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 5 RcvQ full: set."

	::= 8692



dpsRTUp9692Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 5 RcvQ full: cleared."

	::= 9692





dpsRTUp8693Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 6 RcvQ full: set."

	::= 8693



dpsRTUp9693Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 6 RcvQ full: cleared."

	::= 9693





dpsRTUp8694Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 7 RcvQ full: set."

	::= 8694



dpsRTUp9694Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 7 RcvQ full: cleared."

	::= 9694





dpsRTUp8695Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 8 RcvQ full: set."

	::= 8695



dpsRTUp9695Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Data 8 RcvQ full: cleared."

	::= 9695



dpsRTUp8696Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 1 Fail: set."

	::= 8696



dpsRTUp9696Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 1 Fail: cleared."

	::= 9696



dpsRTUp8697Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 2 Fail: set."

	::= 8697



dpsRTUp9697Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 2 Fail: cleared."

	::= 9697



dpsRTUp8698Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 3 Fail: set."

	::= 8698



dpsRTUp9698Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "NGDdx 3 Fail: cleared."

	::= 9698



dpsRTUp8699Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 1 Fail: set."

	::= 8699



dpsRTUp9699Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 1 Fail: cleared."

	::= 9699



dpsRTUp8700Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 2 Fail: set."

	::= 8700



dpsRTUp9700Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 2 Fail: cleared."

	::= 9700



dpsRTUp8701Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 3 Fail: set."

	::= 8701



dpsRTUp9701Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "GLD 3 Fail: cleared."

	::= 9701



dpsRTUp8702Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Chan. Port Timeout: set."

	::= 8702



dpsRTUp9702Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Chan. Port Timeout: cleared."

	::= 9702



dpsRTUp8703Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Craft Timeout: set."

	::= 8703



dpsRTUp9703Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Craft Timeout: cleared."

	::= 9703



dpsRTUp8704Set TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Event Que Full: set."

	::= 8704



dpsRTUp9704Clr TRAP-TYPE

	ENTERPRISE  dpsRTU

	VARIABLES {	sysDescr, sysLocation, dpsRTUDateTime,

			dpsRTUAPort, dpsRTUCAddress, dpsRTUADisplay, dpsRTUAPoint,

			dpsRTUAPntDesc, dpsRTUAState }

	DESCRIPTION "Event Que Full: cleared."

	::= 9704



END
