-- extracted from draft-ranjith-dpnss-mib-00.txt
-- at Tue Dec  5 10:05:27 2000

DPNSS-MIB DEFINITIONS ::= BEGIN

   IMPORTS
        MODULE-IDENTITY,
        NOTIFICATION-TYPE,
        OBJECT-TYPE,
        Counter32,
        Integer32,
        transmission
                FROM SNMPv2-SMI
        DisplayString,
        TimeStamp
                 FROM SNMPv2-TC
        MODULE-COMPLIANCE,
        OBJECT-GROUP,
        NOTIFICATION-GROUP
                FROM SNMPv2-CONF
        ifIndex,
        InterfaceIndex
                FROM IF-MIB
        IANAifType
                FROM IANAifType-MIB;

   dpnssMib MODULE-IDENTITY
        LAST-UPDATED    "200008090000Z" -- August 23, 2000
        ORGANIZATION    "IETF Interfaces Working Group"
        CONTACT-INFO
            "       DPNSS MIB Team : Ranjith Mukundan
                                     Sudarshan Naganathan
                                     Narsimuloo Mangalpally
                                     Vaidyanathan Anantharaman

              DPNSS MIB Team email : mdragon@nortelnetworks.com

                            Postal : Nortel Networks plc
                                     Concorde Road,
                                     Maidenhead, Berkshire SL6 4AG
                                     United Kingdom
                            Phone  : +44 (0)1628434388         "


        DESCRIPTION
            "The MIB module to describe the
             management of DPNSS interfaces."
        ::= { transmission 999 }            -- IANA will be requested
                                            -- to assign a value

      -- The DPNSS hardware interface is represented
      -- by a media specific ifEntry.
      --
      -- The media specifics are defined in the ds0 (81)
      -- MIB ds1(18) MIB.

      -- Each DPNSS signaling channel is represented by an entry
      -- in the dpnssSigTable.
      --
      -- Each DPNSS trunk is also represented as an entry
      -- in the ifTable. The DPNSS trunks will have an ifType value
      -- of ds0(81).
      -- This model is used while defining      objects and tables
      -- for management.
      --
      -- The DPNSS Signaling channel is modeled as a single interface
      -- sublayer.Separate ifEntries for DPNSS Layer 2 and Layer 3 is
      -- not provided.
      --
      -- The DPNSS DLC information is maintained in the dpnssDLCTable.
      -- Information relating to each of the 30 Real and 30 Virtual
      -- DLCs is maintained in this table. These Virtual Connections do
      -- not have ifEntries.

      -- The DPNSS Signaling Group consists of 2 tables
      -- DPNSS Signaling Table and
      -- DPNSS DLC Table

      -- The dpnssSigTable contains configuration and statistical
      -- information required for DPNSS signaling channel

      dpnssSigTable OBJECT-TYPE
              SYNTAX      SEQUENCE OF DpnssSigEntry
              MAX-ACCESS  not-accessible
              STATUS      current
           DESCRIPTION
                "DPNSS Signaling Table containing configuration and
                statistical parameters for all DPNSS signaling channel
                interfaces on this managed device."
           ::= { dpnssMib 1 }

      dpnssSigEntry OBJECT-TYPE
           SYNTAX      DpnssSigEntry
           MAX-ACCESS  not-accessible
           STATUS      current

           DESCRIPTION
               "An entry in the DPNSS Signaling Channel Table."
           INDEX { dpnssSigIndex }
           ::= { dpnssSigTable 1 }

      DpnssSigEntry ::= SEQUENCE {
               dpnssSigIndex                   INTEGER,
               dpnssSigIfIndex                 InterfaceIndex,
               dpnssSigTrkCount                Integer32,
               dpnssSigInfoTrapEnable          INTEGER,
               dpnssSigEndPtType               INTEGER,
               dpnssSigL2ReTxns                Integer32,
               dpnssSigL2ReTxnTimeout          Integer32,
               dpnssSigL2ReTxnAckTimeout       Integer32,
               dpnssSigLinkOperStatus          INTEGER,
               dpnssSigL2InCallsConn           Counter32,
               dpnssSigL3InCallsConn           Counter32,
               dpnssSigL2OutCallsConn          Counter32,
               dpnssSigL3OutCallsConn          Counter32,
               dpnssSigL2AttemptedConns        Counter32,
               dpnssSigUnprocessedUIs          Counter32
         }

      dpnssSigIndex OBJECT-TYPE
           SYNTAX      INTEGER (1..2147483647)
           MAX-ACCESS  not-accessible
           STATUS      current
           DESCRIPTION
               "The index value which uniquely identifies an entry
                in the dpnssSigTable."
           ::= { dpnssSigEntry 1 }

      dpnssSigIfIndex OBJECT-TYPE
           SYNTAX      InterfaceIndex
           MAX-ACCESS  read-only
           STATUS      current
           DESCRIPTION
               "The ifIndex value of the interface associated with this
                signaling channel."
           ::= { dpnssSigEntry 2 }

      dpnssSigTrkCount OBJECT-TYPE
           SYNTAX      Integer32 (1..65535)
           MAX-ACCESS  read-only
           STATUS      current
           DESCRIPTION
               "The total number of DPNSS Trunks(bearer channels)
                managed by this signaling channel. For E1 this will
                be 30 and for T1 it will be 24."
           ::= { dpnssSigEntry 3 }

      dpnssSigInfoTrapEnable    OBJECT-TYPE

           SYNTAX      INTEGER {
               enabled(1),
               disabled(2)
           }
           MAX-ACCESS  read-write
           STATUS      current
           DESCRIPTION
               "Indicates whether dpnssMibCallInformation traps
                should be generated for calls on this signaling
                channel."
           DEFVAL      { disabled }
           ::= { dpnssSigEntry 4 }


      dpnssSigEndPtType OBJECT-TYPE
           SYNTAX      INTEGER {
               a(1),
               b(2)
           }
           MAX-ACCESS  read-write
           STATUS      current
           DESCRIPTION
               "This object shall be used such that the two PBXs at
                each end of the transmission link shall be designated A
                & B by arrangement at configuration as specified in
                BTNR 188."
           ::= { dpnssSigEntry 5 }

      dpnssSigL2ReTxns OBJECT-TYPE
           SYNTAX      Integer32 (-32768..32767)
           MAX-ACCESS  read-write
           STATUS      current
           DESCRIPTION
               "This is the minimum retransmission count limit
                designated as 'NL' in BTNR 188. This is the minimum
                number of retransmissions of a command frame, which
                must take place if the correct acknowledgment is not
                received. BTNR recommends a value of 64 for this
                parameter. If set to a value of -1 (or any other
                negative value) this parameter is rendered redundant.
                In such cases the NL value should be set/read on a per
                DLC basis from the dpnssDLCTable. If set to a value
                other than -1 (or any other negative value) it will be
                applicable to all the DLCs."
           DEFVAL {64}
           ::= { dpnssSigEntry 6 }

      dpnssSigL2ReTxnTimeout OBJECT-TYPE
           SYNTAX      Integer32 (-32768..32767)
           MAX-ACCESS  read-write
           STATUS      current
           DESCRIPTION

               "This is the minimum retransmission period designated as
                'NT1' in BTNR 188. This is the minimum period of time
                for which a command frame must be retransmitted if not
                acknowledged. BTNR 188 recommends this value to be
                500ms. If set to a value of -1 (or any other negative
                value) this paramter is rendered redundant. In such
                cases the NT1 value should be set/read on a per DLC
                basis from the dpnssDLCTable. If set to a value other
                than -1 (or any other negative value) it will be
                applicable to all the DLCs."
           DEFVAL {500}
             ::= { dpnssSigEntry 7 }

      dpnssSigL2ReTxnAckTimeout OBJECT-TYPE
           SYNTAX      Integer32 (-32768..32767)
           MAX-ACCESS  read-write
           STATUS      current
           DESCRIPTION
               "This is the minimum post retransmission acknowledgment
                delay designated as 'NT2' in BTNR 188. This is the
                minimum period of time after the expiry of NL and NT1
                during which an acknowledgement is awaited before
                reporting a retransmission failure to DPNSS Layer 3.
                When DPNSS is used via a satellite link, BTNR 188
                recommends a value of 520ms for NT2 and 0 otherwise.
                If set to a value of -1 (or any other negative value)
                this parameter is rendered redundant. In such cases the
                NT2 value should be set/read on a per DLC basis from
                dpnssDLCTable. If set to a value other than -1 (or any
                other negative value) it will be applicable to all the
                DLCs."
           DEFVAL {0}
           ::= { dpnssSigEntry 8 }

      dpnssSigLinkOperStatus   OBJECT-TYPE
           SYNTAX      INTEGER {
                    oos(1),
                    idle(2),
                    resetAttempted(3),
                    resetComplete (4),
                    infoTransfer (5),
                    recvOverrun(6),
                    babbling(7),
                    crptMsg(8),
                    overload (9),
                    bsy(10),
                    lockout(11),
                    inb(12),
                    offLine(13),
                    pInSv (14),
                    pOverload (15)
                   }

           MAX-ACCESS  read-write
           STATUS      current
           DESCRIPTION
               "Parameter specifying the different DPNSS Signaling
                channel states.

                The maintenance states - bsy, inb and offline does not
                directly correspond to a DLC state in the DLC table. In
                this state the DLCs state should be either one of oos
                or resetAttempt.

                oos - Out Of Service
                This State can be entered immediately following power
                up or due to a maintenance action, eg following reset
                failure. It is the state in which all DLCs exist before
                activation of the Data Link Layer. A DLC remains in the
                'Out of Service' state if it is not being used across a
                particular physical link. In this state all received
                frames are ignored. The oos status in the dpnssSigTable
                indicates that all the corresponding DLCs are in oos
                state.

                idle
                This is the state which a DLC enters from the OOS state
                while awaiting to be started. In this state reset
                requests from the remote PBX are not ignored, as in the
                Out of service state. If a DLC is reset remotely the
                local data link layer does not need to reset it. When a
                DLC is started up locally it moves from this state to
                Reset Attempted. The idle status in the dpnssSigTable
                indicates that all the corresponding DLCs are idle
                state.

                resetAttempted
                This is the state which a DLC enters when a reset
                request is sent on it. The DLC enters the Reset
                Complete state on completion of the reset procedure.
                The resetAttempted status in the dpnssSigTable
                indicates that all the corresponding DLCs are in
                resetAttempted state.

                resetComplete
                This is the state of a DLC which has just been
                successfuly reset. In this state, all the state
                variables are set to 0. The resetComplete status in the
                dpnssSigTable indicates that all the corresponding DLCs
                are in resetComplete state

                overload
                This indicates that a DLC is not able to process the L2
                messages due to various overload reasons which can
                result for example when the layer 2 peer DLC is sending

                messages at a rate faster than the what the near-end
                can handle. The overload status in the dpnssSigTable
                indicates that all the corresponding DLCs are in
                overload state.

                recvOverrun - receive overrun
                This indicates that the DLC is receiving layer 2
                messages from a peer at a rate faster than it can
                buffer/process. The recvOverrun status in the
                dpnssSigTable indicates that all the corresponding DLCs
                are in recvOverrun state.

                babbling
                This indicates the receipt of an unexpected 'glitch-
                message' on all the DLCs.

                crptMsg - corrupt message
                This indicates the receipt of a corrupt (but correctly
                framed) DPNSS Layer 2 message on all the DLCs catered
                by this DPNSS signaling channel.

                The states - oos, idle, resetAttempted,
                resetComplete, infoTransfer and overload of this table
                is applicable to all the DLCs & reflects the status of
                all the DLCs. This value should match the corresponding
                OperStatus of the DLC Table. This option is provided so
                that the implentors have the flexibility of
                setting/reading the states of all DLCs in one shot
                rather than walking through all the entries of the DLC
                table.

                bsy - busy
                Indicates a maintenance operation status of the
                signaling channel during which this link will not be
                used for signaling. Generally this is the value
                during some maintenance actions on the DPNSS link.

                inB - installation Busy
                Indicates a maintenance operation of the signaling
                channel during which, apart from this channel not being
                available for signaling, the configuration parameters
                (mostly ds0 characteristics of this interface) can be
                changed. The implementor may chose to just use the bsy
                state as a superset state instead of inB in which case
                this state will be rendered redundant.

                offLine -
                Indicates a maintenance operation of this signaling
                channel  during which, apart from this channel not
                being available for call processing, the dpnss link
                interface configuration parameters also cannot be
                changed. This state is used to completely delete this

                interface and configure it as some interface or re-
                configure this interface. The vendor may just chose to
                just use the inB state as a superset state instead of
                offline in which case this state will be rendered
                redundant.

                pInSv - Partial Inservice
                This indicates that some DLCs (atleast 1 DLC) are

                in Reset Complete, Information Transfer or Idle state.

                pOverload - Partial Overload
                This indicates that some DLCs (atleast 1 DLC) is in
                overload state."

        ::= { dpnssSigEntry 9 }

      dpnssSigL2InCallsConn OBJECT-TYPE
           SYNTAX      Counter32
           MAX-ACCESS  read-only
           STATUS      current
           DESCRIPTION
               "The number of peer SABMR frames successfully received
                on this interface. This is the number of peer-initiated
                new connections on this interface. This does not
                include the SABMR frames that were received but were
                not processed."
           ::= { dpnssSigEntry 10 }

      dpnssSigL3InCallsConn OBJECT-TYPE
           SYNTAX      Counter32
           MAX-ACCESS  read-only
           STATUS      current
           DESCRIPTION
               "The number of incoming calls on this interface which
                were actually connected."
           ::= { dpnssSigEntry 11 }

      dpnssSigL2OutCallsConn OBJECT-TYPE
           SYNTAX      Counter32
           MAX-ACCESS  read-only
           STATUS      current
           DESCRIPTION
               "The number of SABMR frames sent from this
                interface. This is the number of new connections
                initiated from this interface."
           ::= { dpnssSigEntry 12 }

      dpnssSigL3OutCallsConn OBJECT-TYPE
           SYNTAX      Counter32
           MAX-ACCESS  read-only
           STATUS      current

           DESCRIPTION
               "The number of outgoing calls on this interface which
                were actually connected."
           ::= { dpnssSigEntry 13 }

      dpnssSigL2AttemptedConns OBJECT-TYPE
           SYNTAX      Counter32
           MAX-ACCESS  read-only
           STATUS      current
           DESCRIPTION
               "The number of peer SABMR frames received on this
                interface. This is the number of peer-initiated
                new connections on this interface. This also includes
                the SABMR frames that were received but could not be
                procesed resulting in unsuccessful Layer 2 connection
                attempts. This count gives the SABMR frames received
                for on all the DLCs."
           ::= { dpnssSigEntry 14}

      dpnssSigUnprocessedUIs OBJECT-TYPE
           SYNTAX      Counter32
           MAX-ACCESS  read-only
           STATUS      current
           DESCRIPTION
               "The number of peer UI frames received on this
                interface but could not be processed successfully (e.g.
                due to layer 2 overload). This count gives the
                unsuccessful UI frame count for on all the DLCs."
           ::= { dpnssSigEntry 15}

      -- The dpnssDLCTable contains DPNSS DLC related information
      -- required for a DPNSS signaling channel

      dpnssDLCTable OBJECT-TYPE
           SYNTAX      SEQUENCE OF DpnssDLCEntry
           MAX-ACCESS  not-accessible
           STATUS      current
           DESCRIPTION
               "DPNSS DLC table containing configuration and DLC
                characteristic parameters for all DPNSS DLCs on this
                managed device. One Entry for each Lap (total of 60
                Entries). There is no ifEntry for a DPNSS DLC in the
                IfTable."
           ::= { dpnssMib 2 }

      dpnssDLCEntry OBJECT-TYPE
           SYNTAX      DpnssDLCEntry
           MAX-ACCESS  not-accessible
           STATUS      current
           DESCRIPTION
               "An entry in the DPNSS DLC Table."
           INDEX { dpnssDLCSigIfIndex }

           ::= { dpnssDLCTable 1 }

      DpnssDLCEntry ::= SEQUENCE {
               dpnssDLCSigIfIndex           InterfaceIndex,
               dpnssDLCNum                  INTEGER,
               dpnssDLCInfoTrapEnable       INTEGER,
               dpnssDLCReTxns               Integer32,
               dpnssDLCReTxnTimeout         Integer32,
               dpnssDLCReTxnAckTimeout      Integer32,
               dpnssDLCOperStatus           INTEGER,
               dpnssDLCType                 INTEGER,
               dpnssDLCFrmErrs              Counter32,
               dpnssDLCUnprocessedUIs       Counter32
                    }

      dpnssDLCSigIfIndex         OBJECT-TYPE
           SYNTAX      InterfaceIndex
           MAX-ACCESS  read-only
           STATUS      current
           DESCRIPTION
               "The ifIndex value corresponding to the DPNSS signaling
                channel that is responsible for this DLC. It is
                important to note that this is also the index for the
                dpnssDLCTable. Since the DLC does not have a
                corresponding ifEntry, this is the only link between
                the DPNSS DLC table and the DPNSS Signaling table
                provided by this MIB"
           ::= { dpnssDLCEntry 1 }

      dpnssDLCNum         OBJECT-TYPE
           SYNTAX      INTEGER (1..60)
           MAX-ACCESS  read-only
           STATUS      current
           DESCRIPTION
               "The identifier being used by the signaling protocol
                to identify this DLC, also referred to as
                'Link Access Protocol (LAP) Number'."
           ::= { dpnssDLCEntry 2 }

      dpnssDLCInfoTrapEnable    OBJECT-TYPE
           SYNTAX      INTEGER {
               enabled(1),
               disabled(2)
           }
           MAX-ACCESS  read-write
           STATUS      current
           DESCRIPTION
               "Indicates whether dpnssMibCallInformation traps
                should be generated for calls on this DLC."
           DEFVAL      { disabled }
           ::= { dpnssDLCEntry 3 }


      dpnssDLCReTxns OBJECT-TYPE
           SYNTAX      Integer32 (-32768..32767)
           MAX-ACCESS  read-write
           STATUS      current
           DESCRIPTION
               "This is the minimum retransmission count limit
                designated as 'NL' in BTNR 188. This is the minimum
                number of retransmissions of a command frame which must
                take place if the correct acknowledgment is not
                received. BTNR recommends a value of 64 for this
                parameter. If set to a value of -1 (or any other
                negative value) this parameter is rendered redundant.
                In such cases the NL value should be set/read from the
                dpnssSigTable. This value should not be -1 in the
                dpnssSigTable and dpnssDLCTable at the same time."
           DEFVAL {64}
           ::= { dpnssDLCEntry 4 }

      dpnssDLCReTxnTimeout OBJECT-TYPE
           SYNTAX      Integer32 (-32768..32767)
           MAX-ACCESS  read-write
           STATUS      current
           DESCRIPTION
               "This is the minimum retransmission period designated as
                'NT1' in BTNR 188. This is the minimum period of time
                for which a command frame must be retransmitted if not
                acknowledged. BTNR 188 recommends this value to be
                500ms. If set to a value of -1 (or any other negative
                value) this paramter is rendered redundant. In such
                cases the NT1 value should be set/read from the
                dpnssSigTable. This value should not be -1 in the
                dpnssSigTable and dpnssDLCTable at the same time."
           DEFVAL {500}
             ::= { dpnssDLCEntry 5 }

      dpnssDLCReTxnAckTimeout OBJECT-TYPE
           SYNTAX      Integer32 (-32768..32767)
           MAX-ACCESS  read-write
           STATUS      current
           DESCRIPTION
               "This is the minimum post retransmission acknowledgment
                delay designated as 'NT2' in BTNR 188. This is the
                minimum period of time after the expiry of NL and NT1
                during which an acknowledgement is awaited before
                reporting a retransmission failure to DPNSS Layer 3.
                When DPNSS is used via a satellite link, BTNR 188
                recommends a value of 520ms for NT2 and 0 otherwise.
                If set to a value of -1 (or any other negative value)
                this parameter is rendered redundant. In such cases the
                NT2 value should be set/read from dpnssSigTable. This
                value should not be -1 in the dpnssSigTable and
                dpnssDLCTable at the same time."

           DEFVAL {0}
           ::= { dpnssDLCEntry 6 }

      dpnssDLCOperStatus        OBJECT-TYPE
           SYNTAX      INTEGER {
                    oos(1),
                    idle(2),
                    resetAttempted(3),
                    resetComplete(4),
                    infoTransfer(5),
                    overload(6),
                    recvOverrun(7),
                    babbling(8),
                    crptMessage(9)
                            }
           MAX-ACCESS  read-write
           STATUS      current
           DESCRIPTION
               "Parameter specifying the different DPNSS Layer 2 DLC
                states.

                oos - Out Of Service
                This State can be entered immediately following power
                up or due to a maintenance action, eg following reset
                failure. It is the state in which all DLCs exist before
                activation of the Data Link Layer. A DLC remains in the
                'Out of Service' state if it is not being used across a
                particular physical link. In this state all received
                frames are ignored.

                idle
                This is the state which a DLC enters from the OOS state
                while awaiting to be started. In this state reset
                requests from the remote PBX are not ignored, as in the
                Out of service state. If a DLC is reset remotely the
                local data link layer does not need to reset it. When a
                DLC is started up locally it moves from this state to
                Reset Attempted.

                resetAttempted
                This is the state which a DLC enters when a reset
                request is sent on it. The DLC enters the Reset
                Complete state on completion of the reset procedure.

                resetComplete
                This is the state of a DLC which has just been
                successfuly reset. In this state, all the state
                variables are set to 0.

                overload
                This indicates that a DLC is not able to process the L2
                messages due to various overload reasons which can

                result for example when the layer 2 peer DLC is sending
                messages at a rate faster than the what the near-end
                can handle.

                recvOverrun - receive overrun
                This indicates that the DLC is receiving layer 2
                messages from a peer at a rate faster than it can
                buffer/process.

                babbling
                This indicates the receipt of an unexpected 'glitch-
                message' on all this DLC.

                crptMsg - corrupt message
                This indicates the receipt of a corrupt (but correctly
                framed) DPNSS Layer 2 message on this DLC."
                ::= { dpnssDLCEntry 7 }

      dpnssDLCType   OBJECT-TYPE
           SYNTAX      INTEGER {
               real(1),
               virtual(2)
           }
           MAX-ACCESS  read-only
           STATUS      current
           DESCRIPTION
               "Indicates whether it is a real or virtual DLC."
           ::= { dpnssDLCEntry 8 }

      dpnssDLCFrmErrs OBJECT-TYPE
           SYNTAX      Counter32
           MAX-ACCESS  read-only
           STATUS      current
           DESCRIPTION
               "Number of L2 Framing Errors."
           ::= { dpnssDLCEntry 9 }

      dpnssDLCUnprocessedUIs OBJECT-TYPE
           SYNTAX      Counter32
           MAX-ACCESS  read-only
           STATUS      current
           DESCRIPTION
               "The number of peer UI frames received on this
                interface but could not be processed successfully (e.g.
                due to layer 2 overload). This count gives the
                unsuccessful UI frame count for on all the DLCs."
           ::= { dpnssDLCEntry 10}


      -- The DPNSS Trunk Group. This Group consists of just two tables.
      --             the dpnss trunk table and
      --             the dpnss trunk mapping table.

      -- The dpnssTrkTable contains configuration and statistical
      -- information required for DPNSS trunks.

      dpnssTrkTable OBJECT-TYPE
           SYNTAX      SEQUENCE OF DpnssTrkEntry
           MAX-ACCESS  not-accessible
           STATUS      current
           DESCRIPTION
               "This table defines port specific operational,
                statistics and active call data for DPNSS Trunks.
                Each entry in this table describes one DPNSS Trunk
                channel."
           ::= { dpnssMib 3}

      dpnssTrkEntry OBJECT-TYPE
           SYNTAX      DpnssTrkEntry
           MAX-ACCESS  not-accessible
           STATUS      current
           DESCRIPTION
               "Operational and statistics information relating to
                one port. A port is a single DPNSS (Trunk)."
           INDEX { ifIndex }
           ::= { dpnssTrkTable 1 }

      DpnssTrkEntry ::=
           SEQUENCE {
               dpnssTrkIfIndex            INTEGER,
               dpnssTrkSigIfIndex         InterfaceIndex,
               dpnssTrkNum                INTEGER,
               dpnssTrkInfoTrapEnable     INTEGER,
               dpnssTrkOperStatus         INTEGER,
               dpnssTrkOpulseType         INTEGER,
               dpnssTrkDir                INTEGER,
               dpnssTrkIfAddress          DisplayString,
               dpnssTrkCallSetupTime      TimeStamp,
               dpnssTrkCallConnectTime    TimeStamp
                       }

      dpnssTrkIfIndex    OBJECT-TYPE
           SYNTAX      INTEGER (1..2147483647)
           MAX-ACCESS  read-only
           STATUS      current
           DESCRIPTION
               "The index value which uniquely identifies an entry
                in the dpnssTrkTable."
           ::= { dpnssTrkEntry 1 }


      dpnssTrkSigIfIndex    OBJECT-TYPE
           SYNTAX      InterfaceIndex
           MAX-ACCESS  read-only

           STATUS      current
           DESCRIPTION
               "The ifIndex value corresponding to the DPNSS signaling
                channel that serves as the signaling channel for this
                trunk."
           ::= { dpnssTrkEntry 2 }

      dpnssTrkNum    OBJECT-TYPE
           SYNTAX INTEGER (1..30)
           MAX-ACCESS  read-only
           STATUS      current
           DESCRIPTION
               "The identifier being used by a signaling protocol
                to identify this trunk, also referred to as
                trunk number. If the Agent also supports the DS0
                MIB, the values of dpnssTrkNum and dsx0Ds0Number
                must be identical for a given DPNSS Trunk."
           ::= { dpnssTrkEntry 3 }

      dpnssTrkInfoTrapEnable    OBJECT-TYPE
           SYNTAX      INTEGER {
               enabled(1),
               disabled(2)
           }
           MAX-ACCESS  read-write
           STATUS      current
           DESCRIPTION
               "Indicates whether dpnssMibCallInformation traps
                should be generated for calls over this Trunk."
           DEFVAL      { disabled }
           ::= { dpnssTrkEntry 4 }

      dpnssTrkOperStatus   OBJECT-TYPE
           SYNTAX INTEGER {
                 icSetupReq(1),
                 ogSetupReq(2),
                 icSetupComp(3),
                 ogSetupComp(4),
                 icSetupCompBuf(5),
                 ogSetupCompBuf(6),
                 icAns(7),
                 ogAns(8),
                 clearing(9),
                 idle(10),
                 bsy(11),
                 lockout(12),
                 inb(13),
                 offLine(14)
           }
           MAX-ACCESS  read-write
           STATUS      current
           DESCRIPTION

               "The Different DPNSS DPNSS trunk States as specified by
                BTNR 188. Also incorporates maintenance operation
                states that.

                icSetupReq - Incoming Setup Request
                Indicates that there is an incoming setup request (ISRM
                receipt).

                ogSetupReq - Outgoing Setup Request
                Indicates that there is an outgoing setup request
                outgoing ISRM).

                icSetupComp - Incoming Setup Complete
                Indicates that the trunk in inSetupReq state has
                sent a successful Ack (sending of DPNSS Number
                Acknowledge (NAM) message).

                ogSetupComp - Outgoing Setup Complete
                Indicates that the trunk in ogSetupReq state has
                received a successful acknowledgement(incoming NAM).

                inSetupCompBuf - Incoming Setup Complete Buffer
                Indicates the receipt of a message received on a trunk
                in inSetupComp state and being buffered (example, the
                received EEM(I)s may be buffered till the receipt of
                EEM(C)s before being processed.

                ogSetupCompBuf - Outgoing Setup Complete Buffer
                Indicates the receipt of a message received on a trunk
                in ogSetupComp state.

                inAns - Incoming Answer
                Indicates the sending of an of an answer message
                (incoming DPNSS Call Connected Message (CCM)).

                ogAns - Outgoing Answer
                Indicates the receipt of an answer message on a trunk
                that is in ogSetupComp state(outgoing CCM).

                Clearing
                Indicates the sending of an clearing message
                (outgoing DPNSS Clear Request Message (CRM). The trunk
                will return to idle state or the receipt of a DPNSS
                Clear Indication Message from the peer PBX in response
                to the CRM.

                idle
                Default working state when no call attempt or call in
                progress on this trunk.

                bsy - busy
                Indicates a maintenance operation status of the trunk

                during which this trunk will not be used for call
                processing. Generally done to perform some maintenance
                on the DPNSS trunk.

                LockOut
                Indicates that the corresponding Layer 2 DLC is Out Of-
                Service.

                inB - installation Busy
                Indicates a maintenance operation of the trunk during
                which, apart from this trunk not being available for
                call processing, the configuration parameters (like
                dpnssTrkDir etc) of the trunk can be changed. The
                implementor may chose to just use the bsy state as a
                superset state instead of inB in which case this state
                will be rendered redundant.

                offLine -
                Indicates a maintenance operation of the trunk during
                which, apart from this trunk not being available for
                call processing, the trunk interface configuration
                parameters also cannot be changed. This state is used
                normally to completely delete this interface and
                reconfigure as some other interface. The vendor may
                just chose to just use the inB state as a superset
                state instead of offline in which case this state will
                be rendered redundant. Further, the DS1 interface over
                which the DPNSS trunks and signaling channel is
                configured cannot be shared across another protocol
                (e.g. ISDN - Primary Rate Interface) interface - this
                further reduces the usefulness of this state but the
                parameter is provided in favour of implementation
                flexibility."
           ::= { dpnssTrkEntry 5}

      dpnssTrkOpulseType    OBJECT-TYPE
           SYNTAX      INTEGER {
               enblock(1),
               overlap(2)
           }
           MAX-ACCESS  read-write
           STATUS      current
           DESCRIPTION
               "Indicates the type of digit outpulsing that will be
                done for a call-setup over this trunk."
           ::= { dpnssTrkEntry 6 }

      dpnssTrkDir     OBJECT-TYPE
           SYNTAX      INTEGER {
               ic(1),
               og(2),
               twoW(3)

           }
           MAX-ACCESS  read-write
           STATUS      current
           DESCRIPTION
               "The direction of the trunk call that will be supported
                over this trunk.

                ic   - Allow only       Incoming calls over this trunk
                og   - Allow only       Outgoing calls over this trunk
                twoW - Allow both       incoming and outgoing calls
                                        over this trunk."
           ::= { dpnssTrkEntry 7 }


      dpnssTrkIfAddress   OBJECT-TYPE
           SYNTAX       DisplayString
           MAX-ACCESS   read-write
           STATUS       current
           DESCRIPTION
               "Interface address if any, in IA5 format of the DPNSS
                trunk Interface"
           ::= { dpnssTrkEntry 8 }

      dpnssTrkCallSetupTime   OBJECT-TYPE
           SYNTAX      TimeStamp
           MAX-ACCESS  read-only
           STATUS      current
           DESCRIPTION
               "The value of sysUpTime when the DPNSS setup message
                [DPNSS Initial Service Request Message (ISRM)] for the
                current or last call was sent or received. If since
                system startup there has been no call on this
                interface, this object has a value of zero."
           ::= { dpnssTrkEntry 9 }

      dpnssTrkCallConnectTime    OBJECT-TYPE
           SYNTAX      TimeStamp
           MAX-ACCESS  read-only
           STATUS      current
           DESCRIPTION
               "The value of sysUpTime when the DPNSS connect message
                [DPNSS Call Connect Message (CCM)] for the current or
                last call was sent or received. If since system startup
                there has been no call on this interface, this object
                has a value of zero."
           ::= { dpnssTrkEntry 10 }

      -- The dpnssTrkMappingTable is used for quick look-up to
      -- associate a dpnss trunk with the corresponding dpnss signaling
      -- channel

      dpnssTrkMappingTable     OBJECT-TYPE

           SYNTAX      SEQUENCE OF DpnssTrkMappingEntry
           MAX-ACCESS  not-accessible
           STATUS      current
           DESCRIPTION
               " The dpnssTrkMappingTable is used for quick look-up to
                    associate a dpnss trunk with the corresponding
                    dpnss signaling channel."
           ::= { dpnssMib 4 }

      dpnssTrkMappingEntry      OBJECT-TYPE
           SYNTAX      DpnssTrkMappingEntry
           MAX-ACCESS  not-accessible
           STATUS      current
           DESCRIPTION
               "This is an entry in the DPNSS Trunk Mapping table.
                There is a entry in this table corresponding to each
                DPNSS trunk ifEntry. This table is intended to
                facilitate mapping from DPNSS signaling channel
                ifEntry/DPNSS trunk number to the DPNSS trunk ifEntry.
                (e.g. mapping (DPNSS signaling channel ifIndex, DPNSS
                trunk number) -> DPNSS trunk ifIndex.

                 While this table provides information that can also be
                 indirectly derived from the ifStackTable using the ds0
                 & ds1 MIBs, it provides the same information with a
                 single table lookup, rather than by walking through
                 the ifStackTable to find the various constituent ds0
                 ifTable entries, and testing various ifEntry leaf
                 nodes like ifName etc."
           INDEX { ifIndex, dpnssTrkNum }
           ::= { dpnssTrkMappingTable 1 }

      DpnssTrkMappingEntry      ::=
           SEQUENCE {
               dpnssTrkMappingIfIndex  InterfaceIndex
      }

      dpnssTrkMappingIfIndex  OBJECT-TYPE
           SYNTAX  InterfaceIndex
           MAX-ACCESS  read-only
           STATUS  current
           DESCRIPTION
                  "This object indicates the ifIndex value assigned
                  by the agent for the individual dpnss trunk ifEntry
                  that corresponds to the given dpnss trunk number
                  (specified by the INDEX element dpnssTrkNum) of the
                  associated dpnss signaling interface (specified by
                  INDEX element ifIndex)."
           ::= {  dpnssTrkMappingEntry 1 }

      -- Traps


      dpnssMibTraps OBJECT      IDENTIFIER ::= { dpnssMib 5 }

      dpnssMibLinkInformation NOTIFICATION-TYPE
           OBJECTS { dpnssSigIndex,
                     dpnssSigLinkOperStatus,
                     dpnssSigUnprocessedUIs
                   }
           STATUS      current
           DESCRIPTION
               "This trap/information is sent to the manager under the
                following conditions:
                    - The dpnssSigLinkOperStatus goes to one of oos,
                      resetAttempted, overload, recvOverrun, babbling,
                      or crptMsg.
                    - the dpnssSigUnprocessedUIs exceeds a preset
                      threshold. The exact value of the threshold is
                      implementor specific. If a threshold is not
                      implemented in the agent, this trap will be
                      generated for any positive value of
                      dpnssSigUnprocessedUIs."
           ::= { dpnssMibTraps 0 1 }

      dpnssMibDLCSigInformation NOTIFICATION-TYPE
           OBJECTS { dpnssDLCSigIfIndex,
                     dpnssDLCNum,
                     dpnssDLCOperStatus,
                     dpnssDLCType,
                     dpnssDLCFrmErrs,
                     dpnssDLCUnprocessedUIs
                                     }
           STATUS    current
           DESCRIPTION
               "This trap/information is sent to the manager under the
                following conditions:
                    - the dpnssDLCOperStatus goes to one of
                      overload, recvOverrun, babbling, or crptMsg.
                    - the dpnssDLCUnprocessedUIs exceeds a preset
                      threshold. The exact value of the threshold is
                      implementor specific. If a threshold is not
                      implemented in the agent, this trap will be
                      generated for any positive value of
                      dpnssSigUnprocessedUIs. It is recommended that a
                      different thresholds be implemented for
                      dpnssSigUnprocessedUIs and
                      dpnssDLCUnprocessedUIs.
                    - the dpnssDLCL2FrameErrs exceeds a preset
                      threshold. The exact value of the threshold is
                      implementor specific. If a threshold is not
                      implemented in the agent, the trap will be
                      generated for any positive value of
                      dpnssDLCL2FrameErrs."
           ::= { dpnssMibTraps 0 2 }


      dpnssMibTrkInformation NOTIFICATION-TYPE
           OBJECTS { dpnssTrkSigIfIndex,
                     dpnssTrkNum,
                     dpnssTrkOperStatus,
                     dpnssTrkCallSetupTime
                        }
           STATUS    current
           DESCRIPTION
               "This trap/information is sent to the manager under the
                following conditions:
                    - the dpnssTrkOperStatus goes to one of lockout,
                      inb or offLine."
           ::= { dpnssMibTraps 0 3 }

      --
      -- conformance information
      --

      dpnssMibConformance OBJECT IDENTIFIER ::= { dpnssMib    6 }
      dpnssMibCompliances OBJECT IDENTIFIER ::=
                                         { dpnssMibConformance 1 }
      dpnssMibGroups      OBJECT IDENTIFIER ::=
                                         { dpnssMibConformance 2 }

      -- compliance statements

      dpnssMibCompliances MODULE-COMPLIANCE
           STATUS      current
           DESCRIPTION
               "The compliance statement for entities which implement
                the DPNSS MIB."
           MODULE        -- this module

      -- mandatory      groups

              MANDATORY-GROUPS {
                dpnssMibSigGroup,
                dpnssMibTrkGroup }

           OBJECT dpnssSigL2InCallsConn
           MIN-ACCESS  read-only
           DESCRIPTION
               "The number of peer SABMR frames successfully received
                on a DPNSS signaling channel interface is not
                required."

           OBJECT dpnssSigL3InCallsConn
           MIN-ACCESS  read-only
           DESCRIPTION
                "The number of incoming calls on the DPNSS signaling
                 channel interface which were actually connected."


           OBJECT dpnssSigL2OutCallsConn
           MIN-ACCESS  read-only
           DESCRIPTION
                "The number of SABMR frames sent on a DPNSS signaling
                 channel interface is not required."

           OBJECT dpnssSigL3OutCallsConn
           MIN-ACCESS  read-only
           DESCRIPTION
                "The number of outgoing calls on a DPNSS signaling
                 channel interface which were actually connected is not
                 required."

           OBJECT dpnssSigL2AttemptedConns
           MIN-ACCESS  read-only
           DESCRIPTION
                "The number of peer SABMR frames received on a DPNSS
                 signaling channel interface is not required."

           OBJECT dpnssSigUnprocessedUIs
           MIN-ACCESS  read-only
           DESCRIPTION
               "The number of peer UI frames received on the signaling
                channel interface but could not be processed
                successfully is not required."

           OBJECT dpnssDLCUnprocessedUIs
           MIN-ACCESS  read-only
           DESCRIPTION
               "The number of peer UI frames received on a DLC but
                could not be processed successfully is not
           required."

           OBJECT dpnssTrkOpulseType
           MIN-ACCESS  read-only
           DESCRIPTION
               "The number of peer UI frames received on a DLC but
                could not be processed successfully is not
                required."

           OBJECT dpnssTrkDir
           MIN-ACCESS  read-only
           DESCRIPTION
               "The direction of the trunk call that will be supported
                over a trunk is not required."

           OBJECT dpnssTrkIfAddr
           MIN-ACCESS  read-only
           DESCRIPTION
               "Interface address if any, in IA5 format of the DPNSS
                trunk Interface is not required."

           ::= { dpnssMibCompliances 1  }

   -- units of conformance

         dpnssMibSigGroup OBJECT-GROUP
            OBJECTS {
               dpnssSigIndex,
               dpnssSigIfIndex,
               dpnssTrkNum,
               dpnssSigInfoTrapEnable,
               dpnssSigEndPtType,
               dpnssSigL2ReTxns,
               dpnssSigL2ReTxnTimeout,
               dpnssSigL2ReTxnAckTimeout,
               dpnssDLCReTxns,
               dpnssDLCReTxnTimeout,
               dpnssDLCReTxnAckTimeout,
               dpnssSigLinkOperStatus,
               dpnssSigL2InCallsConn,
               dpnssSigL3InCallsConn,
               dpnssSigL2OutCallsConn,
               dpnssSigL3OutCallsConn,
               dpnssSigL2AttemptedConns,
               dpnssSigUnprocessedUIs,
               dpnssDLCSigIfIndex,
               dpnssDLCNum,
               dpnssDLCInfoTrapEnable,
               dpnssDLCReTxns,
               dpnssDLCReTxnTimeout,
               dpnssDLCReTxnAckTimeout,
               dpnssDLCOperStatus,
               dpnssDLCType,
               dpnssDLCFrmErrs,
               dpnssDLCUnprocessedUIs }
           STATUS current
           DESCRIPTION
               "A collection of objects providing configuration and
                statistical information applicable to all DPNSS
                signaling channel interfaces."
           ::={ dpnssMibGroups 1}

        dpnssMibTrkGroup OBJECT-GROUP
            OBJECTS {
               dpnssTrkIfIndex,
               dpnssTrkSigIfIndex,
               dpnssTrkNum,
               dpnssTrkInfoTrapEnable,
               dpnssTrkOperStatus,
               dpnssTrkOpulseType,
               dpnssTrkDir,
               dpnssTrkIfAddress,
               dpnssTrkCallSetupTime,

               dpnssTrkCallConnectTime,
               dpnssTrkMappingIfIndex }
            STATUS current
            DESCRIPTION
               "A collection of objects providing configuration,
                statistical & signaling channel - trunk mapping
                information applicable to all DPNSS trunk interfaces."
            ::={ dpnssMibGroups 2}

   END
