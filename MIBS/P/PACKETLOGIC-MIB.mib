PACKETLOGIC-MIB DEFINITIONS ::= BEGIN

IMPORTS
	NOTIFICATION-TYPE,
	MODULE-IDENTITY, OBJECT-TYPE, Integer32, Counter64,
	Unsigned32, TimeTicks FROM SNMPv2-SMI
	enterprises FROM SNMPv2-SMI
	DisplayString, DateAndTime FROM SNMPv2-TC
	CounterBasedGauge64 FROM HCNUM-TC;

procera MODULE-IDENTITY
	LAST-UPDATED "201209261248Z"
	ORGANIZATION "Procera Networks, Inc."
	CONTACT-INFO "support@proceranetworks.com"
	DESCRIPTION "MIB for PacketLogic2"
	REVISION "201209261248Z"
	DESCRIPTION " Latest version at the revision date for version GET VERSION HERE"

	::={enterprises 15397}
packetlogic2	OBJECT IDENTIFIER ::={procera 2}

psm	OBJECT IDENTIFIER ::={procera 3}

pbs	OBJECT IDENTIFIER ::={procera 4}

sysdiag	OBJECT IDENTIFIER ::={packetlogic2 1}

channelstats	OBJECT IDENTIFIER ::={packetlogic2 2}

pl2Trap	OBJECT IDENTIFIER ::={packetlogic2 8}

snoopers	OBJECT IDENTIFIER ::={packetlogic2 10}

dynamiczones	OBJECT IDENTIFIER ::={packetlogic2 20}

packetprocessing	OBJECT IDENTIFIER ::={sysdiag 8}

packetprocessingRx	OBJECT IDENTIFIER ::={packetprocessing 1}

packetprocessingRxVal	OBJECT-TYPE
	SYNTAX	 Counter64
	MAX-ACCESS read-only
	STATUS current
	DESCRIPTION "RX packets"

	::={packetprocessingRx 1}

packetprocessingRxMom	OBJECT-TYPE
	SYNTAX	 CounterBasedGauge64
	MAX-ACCESS read-only
	STATUS current
	DESCRIPTION "RX packets"

	::={packetprocessingRx 2}

packetprocessingRxMax	OBJECT-TYPE
	SYNTAX	 CounterBasedGauge64
	MAX-ACCESS read-only
	STATUS current
	DESCRIPTION "RX packets"

	::={packetprocessingRx 3}

packetprocessingRxDrops	OBJECT IDENTIFIER ::={packetprocessing 2}

packetprocessingRxDropsVal	OBJECT-TYPE
	SYNTAX	 Counter64
	MAX-ACCESS read-only
	STATUS current
	DESCRIPTION "RX drops"

	::={packetprocessingRxDrops 1}

packetprocessingRxDropsMom	OBJECT-TYPE
	SYNTAX	 CounterBasedGauge64
	MAX-ACCESS read-only
	STATUS current
	DESCRIPTION "RX drops"

	::={packetprocessingRxDrops 2}

packetprocessingRxDropsMax	OBJECT-TYPE
	SYNTAX	 CounterBasedGauge64
	MAX-ACCESS read-only
	STATUS current
	DESCRIPTION "RX drops"

	::={packetprocessingRxDrops 3}

packetprocessingTx	OBJECT IDENTIFIER ::={packetprocessing 6}

packetprocessingTxVal	OBJECT-TYPE
	SYNTAX	 Counter64
	MAX-ACCESS read-only
	STATUS current
	DESCRIPTION "TX packets"

	::={packetprocessingTx 1}

packetprocessingTxMom	OBJECT-TYPE
	SYNTAX	 CounterBasedGauge64
	MAX-ACCESS read-only
	STATUS current
	DESCRIPTION "TX packets"

	::={packetprocessingTx 2}

packetprocessingTxMax	OBJECT-TYPE
	SYNTAX	 CounterBasedGauge64
	MAX-ACCESS read-only
	STATUS current
	DESCRIPTION "TX packets"

	::={packetprocessingTx 3}

packetprocessingTxDrops	OBJECT IDENTIFIER ::={packetprocessing 7}

packetprocessingTxDropsVal	OBJECT-TYPE
	SYNTAX	 Counter64
	MAX-ACCESS read-only
	STATUS current
	DESCRIPTION "TX drops"

	::={packetprocessingTxDrops 1}

packetprocessingTxDropsMom	OBJECT-TYPE
	SYNTAX	 CounterBasedGauge64
	MAX-ACCESS read-only
	STATUS current
	DESCRIPTION "TX drops"

	::={packetprocessingTxDrops 2}

packetprocessingTxDropsMax	OBJECT-TYPE
	SYNTAX	 CounterBasedGauge64
	MAX-ACCESS read-only
	STATUS current
	DESCRIPTION "TX drops"

	::={packetprocessingTxDrops 3}

packetprocessingPacketPoolSize	OBJECT IDENTIFIER ::={packetprocessing 10}

packetprocessingPacketPoolSizeVal	OBJECT-TYPE
	SYNTAX	 CounterBasedGauge64
	MAX-ACCESS read-only
	STATUS current
	DESCRIPTION "Packets left in pool"

	::={packetprocessingPacketPoolSize 1}

packetprocessingPacketPoolSizeMax	OBJECT-TYPE
	SYNTAX	 CounterBasedGauge64
	MAX-ACCESS read-only
	STATUS current
	DESCRIPTION "Packets left in pool"

	::={packetprocessingPacketPoolSize 3}

packetprocessingDmaAllocs	OBJECT IDENTIFIER ::={packetprocessing 13}

packetprocessingDmaAllocsVal	OBJECT-TYPE
	SYNTAX	 CounterBasedGauge64
	MAX-ACCESS read-only
	STATUS current
	DESCRIPTION "DMA-allocated packets"

	::={packetprocessingDmaAllocs 1}

packetprocessingDmaAllocsMax	OBJECT-TYPE
	SYNTAX	 CounterBasedGauge64
	MAX-ACCESS read-only
	STATUS current
	DESCRIPTION "DMA-allocated packets"

	::={packetprocessingDmaAllocs 3}

packetprocessingOverLoad	OBJECT IDENTIFIER ::={packetprocessing 27}

packetprocessingOverLoadVal	OBJECT-TYPE
	SYNTAX	 CounterBasedGauge64
	MAX-ACCESS read-only
	STATUS current
	DESCRIPTION "Overload mode"

	::={packetprocessingOverLoad 1}

packetprocessingOverLoadMax	OBJECT-TYPE
	SYNTAX	 CounterBasedGauge64
	MAX-ACCESS read-only
	STATUS current
	DESCRIPTION "Overload mode"

	::={packetprocessingOverLoad 3}

packetprocessingLoad	OBJECT IDENTIFIER ::={packetprocessing 15}

packetprocessingLoadVal	OBJECT-TYPE
	SYNTAX	 Unsigned32
	MAX-ACCESS read-only
	STATUS current
	DESCRIPTION "CPU Load"

	::={packetprocessingLoad 1}

packetprocessingLoadMax	OBJECT-TYPE
	SYNTAX	 Unsigned32
	MAX-ACCESS read-only
	STATUS current
	DESCRIPTION "CPU Load"

	::={packetprocessingLoad 3}

packetprocessingUptime	OBJECT IDENTIFIER ::={packetprocessing 17}

packetprocessingUptimeVal	OBJECT-TYPE
	SYNTAX	 TimeTicks
	MAX-ACCESS read-only
	STATUS current
	DESCRIPTION "CPU uptime"

	::={packetprocessingUptime 1}

packetprocessingHeapfree	OBJECT IDENTIFIER ::={packetprocessing 16}

packetprocessingHeapfreeVal	OBJECT-TYPE
	SYNTAX	 CounterBasedGauge64
	MAX-ACCESS read-only
	STATUS current
	DESCRIPTION "Free memory"

	::={packetprocessingHeapfree 1}

packetprocessingHeapfreeMax	OBJECT-TYPE
	SYNTAX	 CounterBasedGauge64
	MAX-ACCESS read-only
	STATUS current
	DESCRIPTION "Free memory"

	::={packetprocessingHeapfree 3}

packetprocessingPushbackQueueFull	OBJECT IDENTIFIER ::={packetprocessing 18}

packetprocessingPushbackQueueFullVal	OBJECT-TYPE
	SYNTAX	 Counter64
	MAX-ACCESS read-only
	STATUS obsolete
	DESCRIPTION "Push back queue full"

	::={packetprocessingPushbackQueueFull 1}

packetprocessingPushbackQueueFullMom	OBJECT-TYPE
	SYNTAX	 CounterBasedGauge64
	MAX-ACCESS read-only
	STATUS obsolete
	DESCRIPTION "Push back queue full"

	::={packetprocessingPushbackQueueFull 2}

packetprocessingPushbackQueueFullMax	OBJECT-TYPE
	SYNTAX	 CounterBasedGauge64
	MAX-ACCESS read-only
	STATUS obsolete
	DESCRIPTION "Push back queue full"

	::={packetprocessingPushbackQueueFull 3}

packetprocessingPushbackPackets	OBJECT IDENTIFIER ::={packetprocessing 19}

packetprocessingPushbackPacketsVal	OBJECT-TYPE
	SYNTAX	 Counter64
	MAX-ACCESS read-only
	STATUS obsolete
	DESCRIPTION "Push back packets"

	::={packetprocessingPushbackPackets 1}

packetprocessingPushbackPacketsMom	OBJECT-TYPE
	SYNTAX	 CounterBasedGauge64
	MAX-ACCESS read-only
	STATUS obsolete
	DESCRIPTION "Push back packets"

	::={packetprocessingPushbackPackets 2}

packetprocessingPushbackPacketsMax	OBJECT-TYPE
	SYNTAX	 CounterBasedGauge64
	MAX-ACCESS read-only
	STATUS obsolete
	DESCRIPTION "Push back packets"

	::={packetprocessingPushbackPackets 3}

packetprocessingPushbackQueueSize	OBJECT IDENTIFIER ::={packetprocessing 20}

packetprocessingPushbackQueueSizeVal	OBJECT-TYPE
	SYNTAX	 CounterBasedGauge64
	MAX-ACCESS read-only
	STATUS obsolete
	DESCRIPTION "Push back queue size"

	::={packetprocessingPushbackQueueSize 1}

packetprocessingPushbackQueueSizeMax	OBJECT-TYPE
	SYNTAX	 CounterBasedGauge64
	MAX-ACCESS read-only
	STATUS obsolete
	DESCRIPTION "Push back queue size"

	::={packetprocessingPushbackQueueSize 3}

packetprocessingPushbackRequeues	OBJECT IDENTIFIER ::={packetprocessing 21}

packetprocessingPushbackRequeuesVal	OBJECT-TYPE
	SYNTAX	 Counter64
	MAX-ACCESS read-only
	STATUS obsolete
	DESCRIPTION "Push back requeues"

	::={packetprocessingPushbackRequeues 1}

packetprocessingPushbackRequeuesMom	OBJECT-TYPE
	SYNTAX	 CounterBasedGauge64
	MAX-ACCESS read-only
	STATUS obsolete
	DESCRIPTION "Push back requeues"

	::={packetprocessingPushbackRequeues 2}

packetprocessingPushbackRequeuesMax	OBJECT-TYPE
	SYNTAX	 CounterBasedGauge64
	MAX-ACCESS read-only
	STATUS obsolete
	DESCRIPTION "Push back requeues"

	::={packetprocessingPushbackRequeues 3}

packetprocessingBalancerDrops	OBJECT IDENTIFIER ::={packetprocessing 22}

packetprocessingBalancerDropsVal	OBJECT-TYPE
	SYNTAX	 Counter64
	MAX-ACCESS read-only
	STATUS current
	DESCRIPTION "Load balancer drops"

	::={packetprocessingBalancerDrops 1}

packetprocessingBalancerDropsMom	OBJECT-TYPE
	SYNTAX	 CounterBasedGauge64
	MAX-ACCESS read-only
	STATUS current
	DESCRIPTION "Load balancer drops"

	::={packetprocessingBalancerDrops 2}

packetprocessingBalancerDropsMax	OBJECT-TYPE
	SYNTAX	 CounterBasedGauge64
	MAX-ACCESS read-only
	STATUS current
	DESCRIPTION "Load balancer drops"

	::={packetprocessingBalancerDrops 3}

packetprocessingNICRXDrops	OBJECT IDENTIFIER ::={packetprocessing 23}

packetprocessingNICRXDropsVal	OBJECT-TYPE
	SYNTAX	 Counter64
	MAX-ACCESS read-only
	STATUS current
	DESCRIPTION "NIC RX drops"

	::={packetprocessingNICRXDrops 1}

packetprocessingNICRXDropsMom	OBJECT-TYPE
	SYNTAX	 CounterBasedGauge64
	MAX-ACCESS read-only
	STATUS current
	DESCRIPTION "NIC RX drops"

	::={packetprocessingNICRXDrops 2}

packetprocessingNICRXDropsMax	OBJECT-TYPE
	SYNTAX	 CounterBasedGauge64
	MAX-ACCESS read-only
	STATUS current
	DESCRIPTION "NIC RX drops"

	::={packetprocessingNICRXDrops 3}

packetprocessingBalancerQueueLength	OBJECT IDENTIFIER ::={packetprocessing 24}

packetprocessingBalancerQueueLengthVal	OBJECT-TYPE
	SYNTAX	 CounterBasedGauge64
	MAX-ACCESS read-only
	STATUS current
	DESCRIPTION "Load balancer queue length"

	::={packetprocessingBalancerQueueLength 1}

packetprocessingBalancerQueueLengthMax	OBJECT-TYPE
	SYNTAX	 CounterBasedGauge64
	MAX-ACCESS read-only
	STATUS current
	DESCRIPTION "Load balancer queue length"

	::={packetprocessingBalancerQueueLength 3}

drdl	OBJECT IDENTIFIER ::={sysdiag 24}

drdlWaitingChildren	OBJECT IDENTIFIER ::={drdl 1}

drdlWaitingChildrenVal	OBJECT-TYPE
	SYNTAX	 CounterBasedGauge64
	MAX-ACCESS read-only
	STATUS current
	DESCRIPTION "Waiting childconnections"

	::={drdlWaitingChildren 1}

drdlWaitingChildrenMax	OBJECT-TYPE
	SYNTAX	 CounterBasedGauge64
	MAX-ACCESS read-only
	STATUS current
	DESCRIPTION "Waiting childconnections"

	::={drdlWaitingChildren 3}

drdlAddedChildren	OBJECT IDENTIFIER ::={drdl 2}

drdlAddedChildrenVal	OBJECT-TYPE
	SYNTAX	 Counter64
	MAX-ACCESS read-only
	STATUS current
	DESCRIPTION "New childconnections"

	::={drdlAddedChildren 1}

drdlAddedChildrenMom	OBJECT-TYPE
	SYNTAX	 CounterBasedGauge64
	MAX-ACCESS read-only
	STATUS current
	DESCRIPTION "New childconnections"

	::={drdlAddedChildren 2}

drdlAddedChildrenMax	OBJECT-TYPE
	SYNTAX	 CounterBasedGauge64
	MAX-ACCESS read-only
	STATUS current
	DESCRIPTION "New childconnections"

	::={drdlAddedChildren 3}

drdlChildAbuses	OBJECT IDENTIFIER ::={drdl 3}

drdlChildAbusesVal	OBJECT-TYPE
	SYNTAX	 Counter64
	MAX-ACCESS read-only
	STATUS current
	DESCRIPTION "LRU child allocations"

	::={drdlChildAbuses 1}

drdlChildAbusesMom	OBJECT-TYPE
	SYNTAX	 CounterBasedGauge64
	MAX-ACCESS read-only
	STATUS current
	DESCRIPTION "LRU child allocations"

	::={drdlChildAbuses 2}

drdlChildAbusesMax	OBJECT-TYPE
	SYNTAX	 CounterBasedGauge64
	MAX-ACCESS read-only
	STATUS current
	DESCRIPTION "LRU child allocations"

	::={drdlChildAbuses 3}

drdlChildEmpty	OBJECT IDENTIFIER ::={drdl 4}

drdlChildEmptyVal	OBJECT-TYPE
	SYNTAX	 Counter64
	MAX-ACCESS read-only
	STATUS current
	DESCRIPTION "Child allocation failures"

	::={drdlChildEmpty 1}

drdlChildEmptyMom	OBJECT-TYPE
	SYNTAX	 CounterBasedGauge64
	MAX-ACCESS read-only
	STATUS current
	DESCRIPTION "Child allocation failures"

	::={drdlChildEmpty 2}

drdlChildEmptyMax	OBJECT-TYPE
	SYNTAX	 CounterBasedGauge64
	MAX-ACCESS read-only
	STATUS current
	DESCRIPTION "Child allocation failures"

	::={drdlChildEmpty 3}

drdlProp32Fail	OBJECT IDENTIFIER ::={drdl 5}

drdlProp32FailVal	OBJECT-TYPE
	SYNTAX	 Counter64
	MAX-ACCESS read-only
	STATUS current
	DESCRIPTION "Property allocation failures (32)"

	::={drdlProp32Fail 1}

drdlProp32FailMom	OBJECT-TYPE
	SYNTAX	 CounterBasedGauge64
	MAX-ACCESS read-only
	STATUS current
	DESCRIPTION "Property allocation failures (32)"

	::={drdlProp32Fail 2}

drdlProp32FailMax	OBJECT-TYPE
	SYNTAX	 CounterBasedGauge64
	MAX-ACCESS read-only
	STATUS current
	DESCRIPTION "Property allocation failures (32)"

	::={drdlProp32Fail 3}

drdlProp64Fail	OBJECT IDENTIFIER ::={drdl 6}

drdlProp64FailVal	OBJECT-TYPE
	SYNTAX	 Counter64
	MAX-ACCESS read-only
	STATUS obsolete
	DESCRIPTION "Unused"

	::={drdlProp64Fail 1}

drdlProp64FailMom	OBJECT-TYPE
	SYNTAX	 CounterBasedGauge64
	MAX-ACCESS read-only
	STATUS obsolete
	DESCRIPTION "Unused"

	::={drdlProp64Fail 2}

drdlProp64FailMax	OBJECT-TYPE
	SYNTAX	 CounterBasedGauge64
	MAX-ACCESS read-only
	STATUS obsolete
	DESCRIPTION "Unused"

	::={drdlProp64Fail 3}

drdlProp256Fail	OBJECT IDENTIFIER ::={drdl 7}

drdlProp256FailVal	OBJECT-TYPE
	SYNTAX	 Counter64
	MAX-ACCESS read-only
	STATUS current
	DESCRIPTION "Property allocation failures (256)"

	::={drdlProp256Fail 1}

drdlProp256FailMom	OBJECT-TYPE
	SYNTAX	 CounterBasedGauge64
	MAX-ACCESS read-only
	STATUS current
	DESCRIPTION "Property allocation failures (256)"

	::={drdlProp256Fail 2}

drdlProp256FailMax	OBJECT-TYPE
	SYNTAX	 CounterBasedGauge64
	MAX-ACCESS read-only
	STATUS current
	DESCRIPTION "Property allocation failures (256)"

	::={drdlProp256Fail 3}

drdlProp32Used	OBJECT IDENTIFIER ::={drdl 8}

drdlProp32UsedVal	OBJECT-TYPE
	SYNTAX	 CounterBasedGauge64
	MAX-ACCESS read-only
	STATUS current
	DESCRIPTION "Properties used (32)"

	::={drdlProp32Used 1}

drdlProp32UsedMax	OBJECT-TYPE
	SYNTAX	 CounterBasedGauge64
	MAX-ACCESS read-only
	STATUS current
	DESCRIPTION "Properties used (32)"

	::={drdlProp32Used 3}

drdlProp64Used	OBJECT IDENTIFIER ::={drdl 9}

drdlProp64UsedVal	OBJECT-TYPE
	SYNTAX	 Counter64
	MAX-ACCESS read-only
	STATUS obsolete
	DESCRIPTION "Unused"

	::={drdlProp64Used 1}

drdlProp64UsedMom	OBJECT-TYPE
	SYNTAX	 CounterBasedGauge64
	MAX-ACCESS read-only
	STATUS obsolete
	DESCRIPTION "Unused"

	::={drdlProp64Used 2}

drdlProp64UsedMax	OBJECT-TYPE
	SYNTAX	 CounterBasedGauge64
	MAX-ACCESS read-only
	STATUS obsolete
	DESCRIPTION "Unused"

	::={drdlProp64Used 3}

drdlProp256Used	OBJECT IDENTIFIER ::={drdl 10}

drdlProp256UsedVal	OBJECT-TYPE
	SYNTAX	 CounterBasedGauge64
	MAX-ACCESS read-only
	STATUS current
	DESCRIPTION "Properties used (256)"

	::={drdlProp256Used 1}

drdlProp256UsedMax	OBJECT-TYPE
	SYNTAX	 CounterBasedGauge64
	MAX-ACCESS read-only
	STATUS current
	DESCRIPTION "Properties used (256)"

	::={drdlProp256Used 3}

drdlAnalyzerChecks	OBJECT IDENTIFIER ::={drdl 11}

drdlAnalyzerChecksVal	OBJECT-TYPE
	SYNTAX	 Counter64
	MAX-ACCESS read-only
	STATUS current
	DESCRIPTION "Analyzer packet checks"

	::={drdlAnalyzerChecks 1}

drdlAnalyzerChecksMom	OBJECT-TYPE
	SYNTAX	 CounterBasedGauge64
	MAX-ACCESS read-only
	STATUS current
	DESCRIPTION "Analyzer packet checks"

	::={drdlAnalyzerChecks 2}

drdlAnalyzerChecksMax	OBJECT-TYPE
	SYNTAX	 CounterBasedGauge64
	MAX-ACCESS read-only
	STATUS current
	DESCRIPTION "Analyzer packet checks"

	::={drdlAnalyzerChecks 3}

drdlAnalyzerCheckedBytes	OBJECT IDENTIFIER ::={drdl 12}

drdlAnalyzerCheckedBytesVal	OBJECT-TYPE
	SYNTAX	 Counter64
	MAX-ACCESS read-only
	STATUS current
	DESCRIPTION "Analyzed bytes"

	::={drdlAnalyzerCheckedBytes 1}

drdlAnalyzerCheckedBytesMom	OBJECT-TYPE
	SYNTAX	 CounterBasedGauge64
	MAX-ACCESS read-only
	STATUS current
	DESCRIPTION "Analyzed bytes"

	::={drdlAnalyzerCheckedBytes 2}

drdlAnalyzerCheckedBytesMax	OBJECT-TYPE
	SYNTAX	 CounterBasedGauge64
	MAX-ACCESS read-only
	STATUS current
	DESCRIPTION "Analyzed bytes"

	::={drdlAnalyzerCheckedBytes 3}

drdlAnalyzerSkippedBytes	OBJECT IDENTIFIER ::={drdl 13}

drdlAnalyzerSkippedBytesVal	OBJECT-TYPE
	SYNTAX	 Counter64
	MAX-ACCESS read-only
	STATUS current
	DESCRIPTION "Skipped bytes"

	::={drdlAnalyzerSkippedBytes 1}

drdlAnalyzerSkippedBytesMom	OBJECT-TYPE
	SYNTAX	 CounterBasedGauge64
	MAX-ACCESS read-only
	STATUS current
	DESCRIPTION "Skipped bytes"

	::={drdlAnalyzerSkippedBytes 2}

drdlAnalyzerSkippedBytesMax	OBJECT-TYPE
	SYNTAX	 CounterBasedGauge64
	MAX-ACCESS read-only
	STATUS current
	DESCRIPTION "Skipped bytes"

	::={drdlAnalyzerSkippedBytes 3}

drdlAnalyzerActions	OBJECT IDENTIFIER ::={drdl 14}

drdlAnalyzerActionsVal	OBJECT-TYPE
	SYNTAX	 Counter64
	MAX-ACCESS read-only
	STATUS current
	DESCRIPTION "Analyzer actions called"

	::={drdlAnalyzerActions 1}

drdlAnalyzerActionsMom	OBJECT-TYPE
	SYNTAX	 CounterBasedGauge64
	MAX-ACCESS read-only
	STATUS current
	DESCRIPTION "Analyzer actions called"

	::={drdlAnalyzerActions 2}

drdlAnalyzerActionsMax	OBJECT-TYPE
	SYNTAX	 CounterBasedGauge64
	MAX-ACCESS read-only
	STATUS current
	DESCRIPTION "Analyzer actions called"

	::={drdlAnalyzerActions 3}

drdlPropertySet	OBJECT IDENTIFIER ::={drdl 15}

drdlPropertySetVal	OBJECT-TYPE
	SYNTAX	 Counter64
	MAX-ACCESS read-only
	STATUS current
	DESCRIPTION "Analyzer properties set"

	::={drdlPropertySet 1}

drdlPropertySetMom	OBJECT-TYPE
	SYNTAX	 CounterBasedGauge64
	MAX-ACCESS read-only
	STATUS current
	DESCRIPTION "Analyzer properties set"

	::={drdlPropertySet 2}

drdlPropertySetMax	OBJECT-TYPE
	SYNTAX	 CounterBasedGauge64
	MAX-ACCESS read-only
	STATUS current
	DESCRIPTION "Analyzer properties set"

	::={drdlPropertySet 3}

drdlOrphans	OBJECT IDENTIFIER ::={drdl 18}

drdlOrphansVal	OBJECT-TYPE
	SYNTAX	 Counter64
	MAX-ACCESS read-only
	STATUS current
	DESCRIPTION "Orphaned childconnections"

	::={drdlOrphans 1}

drdlOrphansMom	OBJECT-TYPE
	SYNTAX	 CounterBasedGauge64
	MAX-ACCESS read-only
	STATUS current
	DESCRIPTION "Orphaned childconnections"

	::={drdlOrphans 2}

drdlOrphansMax	OBJECT-TYPE
	SYNTAX	 CounterBasedGauge64
	MAX-ACCESS read-only
	STATUS current
	DESCRIPTION "Orphaned childconnections"

	::={drdlOrphans 3}

drdlAutoAccepts	OBJECT IDENTIFIER ::={drdl 21}

drdlAutoAcceptsVal	OBJECT-TYPE
	SYNTAX	 Counter64
	MAX-ACCESS read-only
	STATUS current
	DESCRIPTION "Number of automatic accepts"

	::={drdlAutoAccepts 1}

drdlAutoAcceptsMom	OBJECT-TYPE
	SYNTAX	 CounterBasedGauge64
	MAX-ACCESS read-only
	STATUS current
	DESCRIPTION "Number of automatic accepts"

	::={drdlAutoAccepts 2}

drdlAutoAcceptsMax	OBJECT-TYPE
	SYNTAX	 CounterBasedGauge64
	MAX-ACCESS read-only
	STATUS current
	DESCRIPTION "Number of automatic accepts"

	::={drdlAutoAccepts 3}

drdlBuffersUsed	OBJECT IDENTIFIER ::={drdl 22}

drdlBuffersUsedVal	OBJECT-TYPE
	SYNTAX	 CounterBasedGauge64
	MAX-ACCESS read-only
	STATUS current
	DESCRIPTION "Number of buffers used"

	::={drdlBuffersUsed 1}

drdlBuffersUsedMax	OBJECT-TYPE
	SYNTAX	 CounterBasedGauge64
	MAX-ACCESS read-only
	STATUS current
	DESCRIPTION "Number of buffers used"

	::={drdlBuffersUsed 3}

drdlBufferAllocationFailures	OBJECT IDENTIFIER ::={drdl 23}

drdlBufferAllocationFailuresVal	OBJECT-TYPE
	SYNTAX	 Counter64
	MAX-ACCESS read-only
	STATUS current
	DESCRIPTION "Number of buffer allocation failures"

	::={drdlBufferAllocationFailures 1}

drdlBufferAllocationFailuresMom	OBJECT-TYPE
	SYNTAX	 CounterBasedGauge64
	MAX-ACCESS read-only
	STATUS current
	DESCRIPTION "Number of buffer allocation failures"

	::={drdlBufferAllocationFailures 2}

drdlBufferAllocationFailuresMax	OBJECT-TYPE
	SYNTAX	 CounterBasedGauge64
	MAX-ACCESS read-only
	STATUS current
	DESCRIPTION "Number of buffer allocation failures"

	::={drdlBufferAllocationFailures 3}

drdlFullPackets	OBJECT IDENTIFIER ::={drdl 24}

drdlFullPacketsVal	OBJECT-TYPE
	SYNTAX	 Counter64
	MAX-ACCESS read-only
	STATUS current
	DESCRIPTION "Number of full run packets"

	::={drdlFullPackets 1}

drdlFullPacketsMom	OBJECT-TYPE
	SYNTAX	 CounterBasedGauge64
	MAX-ACCESS read-only
	STATUS current
	DESCRIPTION "Number of full run packets"

	::={drdlFullPackets 2}

drdlFullPacketsMax	OBJECT-TYPE
	SYNTAX	 CounterBasedGauge64
	MAX-ACCESS read-only
	STATUS current
	DESCRIPTION "Number of full run packets"

	::={drdlFullPackets 3}

drdlProp0Fail	OBJECT IDENTIFIER ::={drdl 25}

drdlProp0FailVal	OBJECT-TYPE
	SYNTAX	 CounterBasedGauge64
	MAX-ACCESS read-only
	STATUS obsolete
	DESCRIPTION "Unused"

	::={drdlProp0Fail 1}

drdlProp0FailMax	OBJECT-TYPE
	SYNTAX	 CounterBasedGauge64
	MAX-ACCESS read-only
	STATUS obsolete
	DESCRIPTION "Unused"

	::={drdlProp0Fail 3}

drdlProp0Used	OBJECT IDENTIFIER ::={drdl 26}

drdlProp0UsedVal	OBJECT-TYPE
	SYNTAX	 CounterBasedGauge64
	MAX-ACCESS read-only
	STATUS obsolete
	DESCRIPTION "Unused"

	::={drdlProp0Used 1}

drdlProp0UsedMax	OBJECT-TYPE
	SYNTAX	 CounterBasedGauge64
	MAX-ACCESS read-only
	STATUS obsolete
	DESCRIPTION "Unused"

	::={drdlProp0Used 3}

drdlSliceStateUsed	OBJECT IDENTIFIER ::={drdl 27}

drdlSliceStateUsedVal	OBJECT-TYPE
	SYNTAX	 CounterBasedGauge64
	MAX-ACCESS read-only
	STATUS current
	DESCRIPTION "Number of slice state structures used"

	::={drdlSliceStateUsed 1}

drdlSliceStateUsedMax	OBJECT-TYPE
	SYNTAX	 CounterBasedGauge64
	MAX-ACCESS read-only
	STATUS current
	DESCRIPTION "Number of slice state structures used"

	::={drdlSliceStateUsed 3}

drdlSliceStateFail	OBJECT IDENTIFIER ::={drdl 28}

drdlSliceStateFailVal	OBJECT-TYPE
	SYNTAX	 Counter64
	MAX-ACCESS read-only
	STATUS current
	DESCRIPTION "Number of slice state structure allocation failures"

	::={drdlSliceStateFail 1}

drdlSliceStateFailMom	OBJECT-TYPE
	SYNTAX	 CounterBasedGauge64
	MAX-ACCESS read-only
	STATUS current
	DESCRIPTION "Number of slice state structure allocation failures"

	::={drdlSliceStateFail 2}

drdlSliceStateFailMax	OBJECT-TYPE
	SYNTAX	 CounterBasedGauge64
	MAX-ACCESS read-only
	STATUS current
	DESCRIPTION "Number of slice state structure allocation failures"

	::={drdlSliceStateFail 3}

drdlLiteralSet	OBJECT IDENTIFIER ::={drdl 29}

drdlLiteralSetVal	OBJECT-TYPE
	SYNTAX	 Counter64
	MAX-ACCESS read-only
	STATUS current
	DESCRIPTION "Analyzer literals set"

	::={drdlLiteralSet 1}

drdlLiteralSetMom	OBJECT-TYPE
	SYNTAX	 CounterBasedGauge64
	MAX-ACCESS read-only
	STATUS current
	DESCRIPTION "Analyzer literals set"

	::={drdlLiteralSet 2}

drdlLiteralSetMax	OBJECT-TYPE
	SYNTAX	 CounterBasedGauge64
	MAX-ACCESS read-only
	STATUS current
	DESCRIPTION "Analyzer literals set"

	::={drdlLiteralSet 3}

drdlPropertyFail	OBJECT IDENTIFIER ::={drdl 30}

drdlPropertyFailVal	OBJECT-TYPE
	SYNTAX	 Counter64
	MAX-ACCESS read-only
	STATUS current
	DESCRIPTION "Analyzer properties that could not be set"

	::={drdlPropertyFail 1}

drdlPropertyFailMom	OBJECT-TYPE
	SYNTAX	 CounterBasedGauge64
	MAX-ACCESS read-only
	STATUS current
	DESCRIPTION "Analyzer properties that could not be set"

	::={drdlPropertyFail 2}

drdlPropertyFailMax	OBJECT-TYPE
	SYNTAX	 CounterBasedGauge64
	MAX-ACCESS read-only
	STATUS current
	DESCRIPTION "Analyzer properties that could not be set"

	::={drdlPropertyFail 3}

drdlVsRangeTests	OBJECT IDENTIFIER ::={drdl 45}

drdlVsRangeTestsVal	OBJECT-TYPE
	SYNTAX	 Counter64
	MAX-ACCESS read-only
	STATUS current
	DESCRIPTION "Virtual services range tests"

	::={drdlVsRangeTests 1}

drdlVsRangeTestsMom	OBJECT-TYPE
	SYNTAX	 CounterBasedGauge64
	MAX-ACCESS read-only
	STATUS current
	DESCRIPTION "Virtual services range tests"

	::={drdlVsRangeTests 2}

drdlVsRangeTestsMax	OBJECT-TYPE
	SYNTAX	 CounterBasedGauge64
	MAX-ACCESS read-only
	STATUS current
	DESCRIPTION "Virtual services range tests"

	::={drdlVsRangeTests 3}

drdlVsRangeSteps	OBJECT IDENTIFIER ::={drdl 46}

drdlVsRangeStepsVal	OBJECT-TYPE
	SYNTAX	 Counter64
	MAX-ACCESS read-only
	STATUS current
	DESCRIPTION "Virtual services range steps"

	::={drdlVsRangeSteps 1}

drdlVsRangeStepsMom	OBJECT-TYPE
	SYNTAX	 CounterBasedGauge64
	MAX-ACCESS read-only
	STATUS current
	DESCRIPTION "Virtual services range steps"

	::={drdlVsRangeSteps 2}

drdlVsRangeStepsMax	OBJECT-TYPE
	SYNTAX	 CounterBasedGauge64
	MAX-ACCESS read-only
	STATUS current
	DESCRIPTION "Virtual services range steps"

	::={drdlVsRangeSteps 3}

drdlVsRegexTests	OBJECT IDENTIFIER ::={drdl 47}

drdlVsRegexTestsVal	OBJECT-TYPE
	SYNTAX	 Counter64
	MAX-ACCESS read-only
	STATUS current
	DESCRIPTION "Virtual services regex tests"

	::={drdlVsRegexTests 1}

drdlVsRegexTestsMom	OBJECT-TYPE
	SYNTAX	 CounterBasedGauge64
	MAX-ACCESS read-only
	STATUS current
	DESCRIPTION "Virtual services regex tests"

	::={drdlVsRegexTests 2}

drdlVsRegexTestsMax	OBJECT-TYPE
	SYNTAX	 CounterBasedGauge64
	MAX-ACCESS read-only
	STATUS current
	DESCRIPTION "Virtual services regex tests"

	::={drdlVsRegexTests 3}

drdlVsRegexSteps	OBJECT IDENTIFIER ::={drdl 48}

drdlVsRegexStepsVal	OBJECT-TYPE
	SYNTAX	 Counter64
	MAX-ACCESS read-only
	STATUS current
	DESCRIPTION "Virtual services regex steps"

	::={drdlVsRegexSteps 1}

drdlVsRegexStepsMom	OBJECT-TYPE
	SYNTAX	 CounterBasedGauge64
	MAX-ACCESS read-only
	STATUS current
	DESCRIPTION "Virtual services regex steps"

	::={drdlVsRegexSteps 2}

drdlVsRegexStepsMax	OBJECT-TYPE
	SYNTAX	 CounterBasedGauge64
	MAX-ACCESS read-only
	STATUS current
	DESCRIPTION "Virtual services regex steps"

	::={drdlVsRegexSteps 3}

drdlTaintFill	OBJECT IDENTIFIER ::={drdl 49}

drdlTaintFillVal	OBJECT-TYPE
	SYNTAX	 CounterBasedGauge64
	MAX-ACCESS read-only
	STATUS current
	DESCRIPTION "Buckets used in taint store"

	::={drdlTaintFill 1}

drdlTaintFillMax	OBJECT-TYPE
	SYNTAX	 CounterBasedGauge64
	MAX-ACCESS read-only
	STATUS current
	DESCRIPTION "Buckets used in taint store"

	::={drdlTaintFill 3}

drdlChildIterateMax	OBJECT IDENTIFIER ::={drdl 33}

drdlChildIterateMaxVal	OBJECT-TYPE
	SYNTAX	 CounterBasedGauge64
	MAX-ACCESS read-only
	STATUS current
	DESCRIPTION "Childconnection iterations during search (max)"

	::={drdlChildIterateMax 1}

drdlChildIterateMaxMax	OBJECT-TYPE
	SYNTAX	 CounterBasedGauge64
	MAX-ACCESS read-only
	STATUS current
	DESCRIPTION "Childconnection iterations during search (max)"

	::={drdlChildIterateMax 3}

drdlTaintFillPercent	OBJECT IDENTIFIER ::={drdl 54}

drdlTaintFillPercentVal	OBJECT-TYPE
	SYNTAX	 Unsigned32
	MAX-ACCESS read-only
	STATUS current
	DESCRIPTION "Port tainting data structure usage"

	::={drdlTaintFillPercent 1}

drdlTaintFillPercentMax	OBJECT-TYPE
	SYNTAX	 Unsigned32
	MAX-ACCESS read-only
	STATUS current
	DESCRIPTION "Port tainting data structure usage"

	::={drdlTaintFillPercent 3}

ethernet	OBJECT IDENTIFIER ::={sysdiag 28}

ethernetUnicast	OBJECT IDENTIFIER ::={ethernet 1}

ethernetUnicastVal	OBJECT-TYPE
	SYNTAX	 Counter64
	MAX-ACCESS read-only
	STATUS current
	DESCRIPTION "Unicast packets"

	::={ethernetUnicast 1}

ethernetUnicastMom	OBJECT-TYPE
	SYNTAX	 CounterBasedGauge64
	MAX-ACCESS read-only
	STATUS current
	DESCRIPTION "Unicast packets"

	::={ethernetUnicast 2}

ethernetUnicastMax	OBJECT-TYPE
	SYNTAX	 CounterBasedGauge64
	MAX-ACCESS read-only
	STATUS current
	DESCRIPTION "Unicast packets"

	::={ethernetUnicast 3}

ethernetBroadcast	OBJECT IDENTIFIER ::={ethernet 2}

ethernetBroadcastVal	OBJECT-TYPE
	SYNTAX	 Counter64
	MAX-ACCESS read-only
	STATUS current
	DESCRIPTION "Broadcast packets"

	::={ethernetBroadcast 1}

ethernetBroadcastMom	OBJECT-TYPE
	SYNTAX	 CounterBasedGauge64
	MAX-ACCESS read-only
	STATUS current
	DESCRIPTION "Broadcast packets"

	::={ethernetBroadcast 2}

ethernetBroadcastMax	OBJECT-TYPE
	SYNTAX	 CounterBasedGauge64
	MAX-ACCESS read-only
	STATUS current
	DESCRIPTION "Broadcast packets"

	::={ethernetBroadcast 3}

ethernetMulticast	OBJECT IDENTIFIER ::={ethernet 3}

ethernetMulticastVal	OBJECT-TYPE
	SYNTAX	 Counter64
	MAX-ACCESS read-only
	STATUS current
	DESCRIPTION "Multicast packets"

	::={ethernetMulticast 1}

ethernetMulticastMom	OBJECT-TYPE
	SYNTAX	 CounterBasedGauge64
	MAX-ACCESS read-only
	STATUS current
	DESCRIPTION "Multicast packets"

	::={ethernetMulticast 2}

ethernetMulticastMax	OBJECT-TYPE
	SYNTAX	 CounterBasedGauge64
	MAX-ACCESS read-only
	STATUS current
	DESCRIPTION "Multicast packets"

	::={ethernetMulticast 3}

ethernet8021q	OBJECT IDENTIFIER ::={ethernet 4}

ethernet8021qVal	OBJECT-TYPE
	SYNTAX	 Counter64
	MAX-ACCESS read-only
	STATUS current
	DESCRIPTION "802.1q encapsulated packets"

	::={ethernet8021q 1}

ethernet8021qMom	OBJECT-TYPE
	SYNTAX	 CounterBasedGauge64
	MAX-ACCESS read-only
	STATUS current
	DESCRIPTION "802.1q encapsulated packets"

	::={ethernet8021q 2}

ethernet8021qMax	OBJECT-TYPE
	SYNTAX	 CounterBasedGauge64
	MAX-ACCESS read-only
	STATUS current
	DESCRIPTION "802.1q encapsulated packets"

	::={ethernet8021q 3}

ethernetMpls	OBJECT IDENTIFIER ::={ethernet 5}

ethernetMplsVal	OBJECT-TYPE
	SYNTAX	 Counter64
	MAX-ACCESS read-only
	STATUS current
	DESCRIPTION "MPLS over Ethernet frames"

	::={ethernetMpls 1}

ethernetMplsMom	OBJECT-TYPE
	SYNTAX	 CounterBasedGauge64
	MAX-ACCESS read-only
	STATUS current
	DESCRIPTION "MPLS over Ethernet frames"

	::={ethernetMpls 2}

ethernetMplsMax	OBJECT-TYPE
	SYNTAX	 CounterBasedGauge64
	MAX-ACCESS read-only
	STATUS current
	DESCRIPTION "MPLS over Ethernet frames"

	::={ethernetMpls 3}

ethernetMplsOoh	OBJECT IDENTIFIER ::={ethernet 6}

ethernetMplsOohVal	OBJECT-TYPE
	SYNTAX	 Counter64
	MAX-ACCESS read-only
	STATUS current
	DESCRIPTION "Invalid MPLS frames"

	::={ethernetMplsOoh 1}

ethernetMplsOohMom	OBJECT-TYPE
	SYNTAX	 CounterBasedGauge64
	MAX-ACCESS read-only
	STATUS current
	DESCRIPTION "Invalid MPLS frames"

	::={ethernetMplsOoh 2}

ethernetMplsOohMax	OBJECT-TYPE
	SYNTAX	 CounterBasedGauge64
	MAX-ACCESS read-only
	STATUS current
	DESCRIPTION "Invalid MPLS frames"

	::={ethernetMplsOoh 3}

ethernetNonIp	OBJECT IDENTIFIER ::={ethernet 7}

ethernetNonIpVal	OBJECT-TYPE
	SYNTAX	 Counter64
	MAX-ACCESS read-only
	STATUS current
	DESCRIPTION "Non IP packets"

	::={ethernetNonIp 1}

ethernetNonIpMom	OBJECT-TYPE
	SYNTAX	 CounterBasedGauge64
	MAX-ACCESS read-only
	STATUS current
	DESCRIPTION "Non IP packets"

	::={ethernetNonIp 2}

ethernetNonIpMax	OBJECT-TYPE
	SYNTAX	 CounterBasedGauge64
	MAX-ACCESS read-only
	STATUS current
	DESCRIPTION "Non IP packets"

	::={ethernetNonIp 3}

ethernetDivert	OBJECT IDENTIFIER ::={ethernet 8}

ethernetDivertVal	OBJECT-TYPE
	SYNTAX	 Counter64
	MAX-ACCESS read-only
	STATUS current
	DESCRIPTION "Divert packets"

	::={ethernetDivert 1}

ethernetDivertMom	OBJECT-TYPE
	SYNTAX	 CounterBasedGauge64
	MAX-ACCESS read-only
	STATUS current
	DESCRIPTION "Divert packets"

	::={ethernetDivert 2}

ethernetDivertMax	OBJECT-TYPE
	SYNTAX	 CounterBasedGauge64
	MAX-ACCESS read-only
	STATUS current
	DESCRIPTION "Divert packets"

	::={ethernetDivert 3}

ethernetHBResetDrops	OBJECT IDENTIFIER ::={ethernet 21}

ethernetHBResetDropsVal	OBJECT-TYPE
	SYNTAX	 Counter64
	MAX-ACCESS read-only
	STATUS current
	DESCRIPTION "Dropped packets because of HB Reset"

	::={ethernetHBResetDrops 1}

ethernetHBResetDropsMom	OBJECT-TYPE
	SYNTAX	 CounterBasedGauge64
	MAX-ACCESS read-only
	STATUS current
	DESCRIPTION "Dropped packets because of HB Reset"

	::={ethernetHBResetDrops 2}

ethernetHBResetDropsMax	OBJECT-TYPE
	SYNTAX	 CounterBasedGauge64
	MAX-ACCESS read-only
	STATUS current
	DESCRIPTION "Dropped packets because of HB Reset"

	::={ethernetHBResetDrops 3}

ethernetShuntEthertypePackets	OBJECT IDENTIFIER ::={ethernet 22}

ethernetShuntEthertypePacketsVal	OBJECT-TYPE
	SYNTAX	 Counter64
	MAX-ACCESS read-only
	STATUS current
	DESCRIPTION "Shunted packets (ethertype)"

	::={ethernetShuntEthertypePackets 1}

ethernetShuntEthertypePacketsMom	OBJECT-TYPE
	SYNTAX	 CounterBasedGauge64
	MAX-ACCESS read-only
	STATUS current
	DESCRIPTION "Shunted packets (ethertype)"

	::={ethernetShuntEthertypePackets 2}

ethernetShuntEthertypePacketsMax	OBJECT-TYPE
	SYNTAX	 CounterBasedGauge64
	MAX-ACCESS read-only
	STATUS current
	DESCRIPTION "Shunted packets (ethertype)"

	::={ethernetShuntEthertypePackets 3}

ethernetShuntEthertypeBytes	OBJECT IDENTIFIER ::={ethernet 23}

ethernetShuntEthertypeBytesVal	OBJECT-TYPE
	SYNTAX	 Counter64
	MAX-ACCESS read-only
	STATUS current
	DESCRIPTION "Shunted bytes (ethertype)"

	::={ethernetShuntEthertypeBytes 1}

ethernetShuntEthertypeBytesMom	OBJECT-TYPE
	SYNTAX	 CounterBasedGauge64
	MAX-ACCESS read-only
	STATUS current
	DESCRIPTION "Shunted bytes (ethertype)"

	::={ethernetShuntEthertypeBytes 2}

ethernetShuntEthertypeBytesMax	OBJECT-TYPE
	SYNTAX	 CounterBasedGauge64
	MAX-ACCESS read-only
	STATUS current
	DESCRIPTION "Shunted bytes (ethertype)"

	::={ethernetShuntEthertypeBytes 3}

ethernetShuntMplsPackets	OBJECT IDENTIFIER ::={ethernet 24}

ethernetShuntMplsPacketsVal	OBJECT-TYPE
	SYNTAX	 Counter64
	MAX-ACCESS read-only
	STATUS current
	DESCRIPTION "Shunted packets (MPLS)"

	::={ethernetShuntMplsPackets 1}

ethernetShuntMplsPacketsMom	OBJECT-TYPE
	SYNTAX	 CounterBasedGauge64
	MAX-ACCESS read-only
	STATUS current
	DESCRIPTION "Shunted packets (MPLS)"

	::={ethernetShuntMplsPackets 2}

ethernetShuntMplsPacketsMax	OBJECT-TYPE
	SYNTAX	 CounterBasedGauge64
	MAX-ACCESS read-only
	STATUS current
	DESCRIPTION "Shunted packets (MPLS)"

	::={ethernetShuntMplsPackets 3}

ethernetShuntMplsBytes	OBJECT IDENTIFIER ::={ethernet 25}

ethernetShuntMplsBytesVal	OBJECT-TYPE
	SYNTAX	 Counter64
	MAX-ACCESS read-only
	STATUS current
	DESCRIPTION "Shunted bytes (MPLS)"

	::={ethernetShuntMplsBytes 1}

ethernetShuntMplsBytesMom	OBJECT-TYPE
	SYNTAX	 CounterBasedGauge64
	MAX-ACCESS read-only
	STATUS current
	DESCRIPTION "Shunted bytes (MPLS)"

	::={ethernetShuntMplsBytes 2}

ethernetShuntMplsBytesMax	OBJECT-TYPE
	SYNTAX	 CounterBasedGauge64
	MAX-ACCESS read-only
	STATUS current
	DESCRIPTION "Shunted bytes (MPLS)"

	::={ethernetShuntMplsBytes 3}

ethernetShuntEoMplsPackets	OBJECT IDENTIFIER ::={ethernet 26}

ethernetShuntEoMplsPacketsVal	OBJECT-TYPE
	SYNTAX	 Counter64
	MAX-ACCESS read-only
	STATUS current
	DESCRIPTION "Shunted packets (EoMPLS)"

	::={ethernetShuntEoMplsPackets 1}

ethernetShuntEoMplsPacketsMom	OBJECT-TYPE
	SYNTAX	 CounterBasedGauge64
	MAX-ACCESS read-only
	STATUS current
	DESCRIPTION "Shunted packets (EoMPLS)"

	::={ethernetShuntEoMplsPackets 2}

ethernetShuntEoMplsPacketsMax	OBJECT-TYPE
	SYNTAX	 CounterBasedGauge64
	MAX-ACCESS read-only
	STATUS current
	DESCRIPTION "Shunted packets (EoMPLS)"

	::={ethernetShuntEoMplsPackets 3}

ethernetShuntEoMplsBytes	OBJECT IDENTIFIER ::={ethernet 27}

ethernetShuntEoMplsBytesVal	OBJECT-TYPE
	SYNTAX	 Counter64
	MAX-ACCESS read-only
	STATUS current
	DESCRIPTION "Shunted bytes (EoMPLS)"

	::={ethernetShuntEoMplsBytes 1}

ethernetShuntEoMplsBytesMom	OBJECT-TYPE
	SYNTAX	 CounterBasedGauge64
	MAX-ACCESS read-only
	STATUS current
	DESCRIPTION "Shunted bytes (EoMPLS)"

	::={ethernetShuntEoMplsBytes 2}

ethernetShuntEoMplsBytesMax	OBJECT-TYPE
	SYNTAX	 CounterBasedGauge64
	MAX-ACCESS read-only
	STATUS current
	DESCRIPTION "Shunted bytes (EoMPLS)"

	::={ethernetShuntEoMplsBytes 3}

ethernetShuntDot1qPackets	OBJECT IDENTIFIER ::={ethernet 28}

ethernetShuntDot1qPacketsVal	OBJECT-TYPE
	SYNTAX	 Counter64
	MAX-ACCESS read-only
	STATUS current
	DESCRIPTION "Shunted packets (Dot1q)"

	::={ethernetShuntDot1qPackets 1}

ethernetShuntDot1qPacketsMom	OBJECT-TYPE
	SYNTAX	 CounterBasedGauge64
	MAX-ACCESS read-only
	STATUS current
	DESCRIPTION "Shunted packets (Dot1q)"

	::={ethernetShuntDot1qPackets 2}

ethernetShuntDot1qPacketsMax	OBJECT-TYPE
	SYNTAX	 CounterBasedGauge64
	MAX-ACCESS read-only
	STATUS current
	DESCRIPTION "Shunted packets (Dot1q)"

	::={ethernetShuntDot1qPackets 3}

ethernetShuntDot1qBytes	OBJECT IDENTIFIER ::={ethernet 29}

ethernetShuntDot1qBytesVal	OBJECT-TYPE
	SYNTAX	 Counter64
	MAX-ACCESS read-only
	STATUS current
	DESCRIPTION "Shunted bytes (Dot1q)"

	::={ethernetShuntDot1qBytes 1}

ethernetShuntDot1qBytesMom	OBJECT-TYPE
	SYNTAX	 CounterBasedGauge64
	MAX-ACCESS read-only
	STATUS current
	DESCRIPTION "Shunted bytes (Dot1q)"

	::={ethernetShuntDot1qBytes 2}

ethernetShuntDot1qBytesMax	OBJECT-TYPE
	SYNTAX	 CounterBasedGauge64
	MAX-ACCESS read-only
	STATUS current
	DESCRIPTION "Shunted bytes (Dot1q)"

	::={ethernetShuntDot1qBytes 3}

ethernetCountBytesIPv4IPv6	OBJECT IDENTIFIER ::={ethernet 30}

ethernetCountBytesIPv4IPv6Val	OBJECT-TYPE
	SYNTAX	 Counter64
	MAX-ACCESS read-only
	STATUS current
	DESCRIPTION "Ethernet bytes (IPv4 and IPv6)"

	::={ethernetCountBytesIPv4IPv6 1}

ethernetCountBytesIPv4IPv6Mom	OBJECT-TYPE
	SYNTAX	 CounterBasedGauge64
	MAX-ACCESS read-only
	STATUS current
	DESCRIPTION "Ethernet bytes (IPv4 and IPv6)"

	::={ethernetCountBytesIPv4IPv6 2}

ethernetCountBytesIPv4IPv6Max	OBJECT-TYPE
	SYNTAX	 CounterBasedGauge64
	MAX-ACCESS read-only
	STATUS current
	DESCRIPTION "Ethernet bytes (IPv4 and IPv6)"

	::={ethernetCountBytesIPv4IPv6 3}

ipv4	OBJECT IDENTIFIER ::={sysdiag 32}

ipv4Packets	OBJECT IDENTIFIER ::={ipv4 1}

ipv4PacketsVal	OBJECT-TYPE
	SYNTAX	 Counter64
	MAX-ACCESS read-only
	STATUS current
	DESCRIPTION "RX packets"

	::={ipv4Packets 1}

ipv4PacketsMom	OBJECT-TYPE
	SYNTAX	 CounterBasedGauge64
	MAX-ACCESS read-only
	STATUS current
	DESCRIPTION "RX packets"

	::={ipv4Packets 2}

ipv4PacketsMax	OBJECT-TYPE
	SYNTAX	 CounterBasedGauge64
	MAX-ACCESS read-only
	STATUS current
	DESCRIPTION "RX packets"

	::={ipv4Packets 3}

ipv4Bytes	OBJECT IDENTIFIER ::={ipv4 2}

ipv4BytesVal	OBJECT-TYPE
	SYNTAX	 Counter64
	MAX-ACCESS read-only
	STATUS current
	DESCRIPTION "RX data"

	::={ipv4Bytes 1}

ipv4BytesMom	OBJECT-TYPE
	SYNTAX	 CounterBasedGauge64
	MAX-ACCESS read-only
	STATUS current
	DESCRIPTION "RX data"

	::={ipv4Bytes 2}

ipv4BytesMax	OBJECT-TYPE
	SYNTAX	 CounterBasedGauge64
	MAX-ACCESS read-only
	STATUS current
	DESCRIPTION "RX data"

	::={ipv4Bytes 3}

ipv4RefusedShort	OBJECT IDENTIFIER ::={ipv4 3}

ipv4RefusedShortVal	OBJECT-TYPE
	SYNTAX	 Counter64
	MAX-ACCESS read-only
	STATUS current
	DESCRIPTION "Refused (packet is too short)"

	::={ipv4RefusedShort 1}

ipv4RefusedShortMom	OBJECT-TYPE
	SYNTAX	 CounterBasedGauge64
	MAX-ACCESS read-only
	STATUS current
	DESCRIPTION "Refused (packet is too short)"

	::={ipv4RefusedShort 2}

ipv4RefusedShortMax	OBJECT-TYPE
	SYNTAX	 CounterBasedGauge64
	MAX-ACCESS read-only
	STATUS current
	DESCRIPTION "Refused (packet is too short)"

	::={ipv4RefusedShort 3}

ipv4RefusedVersion	OBJECT IDENTIFIER ::={ipv4 4}

ipv4RefusedVersionVal	OBJECT-TYPE
	SYNTAX	 Counter64
	MAX-ACCESS read-only
	STATUS current
	DESCRIPTION "Refused (invalid version)"

	::={ipv4RefusedVersion 1}

ipv4RefusedVersionMom	OBJECT-TYPE
	SYNTAX	 CounterBasedGauge64
	MAX-ACCESS read-only
	STATUS current
	DESCRIPTION "Refused (invalid version)"

	::={ipv4RefusedVersion 2}

ipv4RefusedVersionMax	OBJECT-TYPE
	SYNTAX	 CounterBasedGauge64
	MAX-ACCESS read-only
	STATUS current
	DESCRIPTION "Refused (invalid version)"

	::={ipv4RefusedVersion 3}

ipv4RefusedSelf	OBJECT IDENTIFIER ::={ipv4 5}

ipv4RefusedSelfVal	OBJECT-TYPE
	SYNTAX	 Counter64
	MAX-ACCESS read-only
	STATUS current
	DESCRIPTION "Refused (src == dest)"

	::={ipv4RefusedSelf 1}

ipv4RefusedSelfMom	OBJECT-TYPE
	SYNTAX	 CounterBasedGauge64
	MAX-ACCESS read-only
	STATUS current
	DESCRIPTION "Refused (src == dest)"

	::={ipv4RefusedSelf 2}

ipv4RefusedSelfMax	OBJECT-TYPE
	SYNTAX	 CounterBasedGauge64
	MAX-ACCESS read-only
	STATUS current
	DESCRIPTION "Refused (src == dest)"

	::={ipv4RefusedSelf 3}

ipv4Unfragmented	OBJECT IDENTIFIER ::={ipv4 6}

ipv4UnfragmentedVal	OBJECT-TYPE
	SYNTAX	 Counter64
	MAX-ACCESS read-only
	STATUS current
	DESCRIPTION "Unfragmented packets"

	::={ipv4Unfragmented 1}

ipv4UnfragmentedMom	OBJECT-TYPE
	SYNTAX	 CounterBasedGauge64
	MAX-ACCESS read-only
	STATUS current
	DESCRIPTION "Unfragmented packets"

	::={ipv4Unfragmented 2}

ipv4UnfragmentedMax	OBJECT-TYPE
	SYNTAX	 CounterBasedGauge64
	MAX-ACCESS read-only
	STATUS current
	DESCRIPTION "Unfragmented packets"

	::={ipv4Unfragmented 3}

ipv4Fragmented	OBJECT IDENTIFIER ::={ipv4 7}

ipv4FragmentedVal	OBJECT-TYPE
	SYNTAX	 Counter64
	MAX-ACCESS read-only
	STATUS current
	DESCRIPTION "Packet fragments"

	::={ipv4Fragmented 1}

ipv4FragmentedMom	OBJECT-TYPE
	SYNTAX	 CounterBasedGauge64
	MAX-ACCESS read-only
	STATUS current
	DESCRIPTION "Packet fragments"

	::={ipv4Fragmented 2}

ipv4FragmentedMax	OBJECT-TYPE
	SYNTAX	 CounterBasedGauge64
	MAX-ACCESS read-only
	STATUS current
	DESCRIPTION "Packet fragments"

	::={ipv4Fragmented 3}

ipv4FragmentedIds	OBJECT IDENTIFIER ::={ipv4 10}

ipv4FragmentedIdsVal	OBJECT-TYPE
	SYNTAX	 CounterBasedGauge64
	MAX-ACCESS read-only
	STATUS current
	DESCRIPTION "Fragment ids"

	::={ipv4FragmentedIds 1}

ipv4FragmentedIdsMax	OBJECT-TYPE
	SYNTAX	 CounterBasedGauge64
	MAX-ACCESS read-only
	STATUS current
	DESCRIPTION "Fragment ids"

	::={ipv4FragmentedIds 3}

ipv4Fragments	OBJECT IDENTIFIER ::={ipv4 11}

ipv4FragmentsVal	OBJECT-TYPE
	SYNTAX	 CounterBasedGauge64
	MAX-ACCESS read-only
	STATUS current
	DESCRIPTION "Fragments in queue"

	::={ipv4Fragments 1}

ipv4FragmentsMax	OBJECT-TYPE
	SYNTAX	 CounterBasedGauge64
	MAX-ACCESS read-only
	STATUS current
	DESCRIPTION "Fragments in queue"

	::={ipv4Fragments 3}

ipv4RefusedOof	OBJECT IDENTIFIER ::={ipv4 14}

ipv4RefusedOofVal	OBJECT-TYPE
	SYNTAX	 Counter64
	MAX-ACCESS read-only
	STATUS current
	DESCRIPTION "Refused (out of fragments)"

	::={ipv4RefusedOof 1}

ipv4RefusedOofMom	OBJECT-TYPE
	SYNTAX	 CounterBasedGauge64
	MAX-ACCESS read-only
	STATUS current
	DESCRIPTION "Refused (out of fragments)"

	::={ipv4RefusedOof 2}

ipv4RefusedOofMax	OBJECT-TYPE
	SYNTAX	 CounterBasedGauge64
	MAX-ACCESS read-only
	STATUS current
	DESCRIPTION "Refused (out of fragments)"

	::={ipv4RefusedOof 3}

ipv4FragmentAllocationFailures	OBJECT IDENTIFIER ::={ipv4 15}

ipv4FragmentAllocationFailuresVal	OBJECT-TYPE
	SYNTAX	 Counter64
	MAX-ACCESS read-only
	STATUS current
	DESCRIPTION "Fragment allocation failures"

	::={ipv4FragmentAllocationFailures 1}

ipv4FragmentAllocationFailuresMom	OBJECT-TYPE
	SYNTAX	 CounterBasedGauge64
	MAX-ACCESS read-only
	STATUS current
	DESCRIPTION "Fragment allocation failures"

	::={ipv4FragmentAllocationFailures 2}

ipv4FragmentAllocationFailuresMax	OBJECT-TYPE
	SYNTAX	 CounterBasedGauge64
	MAX-ACCESS read-only
	STATUS current
	DESCRIPTION "Fragment allocation failures"

	::={ipv4FragmentAllocationFailures 3}

ipv4FragmentReassFail	OBJECT IDENTIFIER ::={ipv4 16}

ipv4FragmentReassFailVal	OBJECT-TYPE
	SYNTAX	 Counter64
	MAX-ACCESS read-only
	STATUS current
	DESCRIPTION "Fragment reassembly failures"

	::={ipv4FragmentReassFail 1}

ipv4FragmentReassFailMom	OBJECT-TYPE
	SYNTAX	 CounterBasedGauge64
	MAX-ACCESS read-only
	STATUS current
	DESCRIPTION "Fragment reassembly failures"

	::={ipv4FragmentReassFail 2}

ipv4FragmentReassFailMax	OBJECT-TYPE
	SYNTAX	 CounterBasedGauge64
	MAX-ACCESS read-only
	STATUS current
	DESCRIPTION "Fragment reassembly failures"

	::={ipv4FragmentReassFail 3}

ipv4RefusedFilter	OBJECT IDENTIFIER ::={ipv4 17}

ipv4RefusedFilterVal	OBJECT-TYPE
	SYNTAX	 Counter64
	MAX-ACCESS read-only
	STATUS current
	DESCRIPTION "Packets refused by lowlevel filter"

	::={ipv4RefusedFilter 1}

ipv4RefusedFilterMom	OBJECT-TYPE
	SYNTAX	 CounterBasedGauge64
	MAX-ACCESS read-only
	STATUS current
	DESCRIPTION "Packets refused by lowlevel filter"

	::={ipv4RefusedFilter 2}

ipv4RefusedFilterMax	OBJECT-TYPE
	SYNTAX	 CounterBasedGauge64
	MAX-ACCESS read-only
	STATUS current
	DESCRIPTION "Packets refused by lowlevel filter"

	::={ipv4RefusedFilter 3}

ipv4FragmentTooNoisy	OBJECT IDENTIFIER ::={ipv4 19}

ipv4FragmentTooNoisyVal	OBJECT-TYPE
	SYNTAX	 Counter64
	MAX-ACCESS read-only
	STATUS current
	DESCRIPTION "Packets refused (too many fragments)"

	::={ipv4FragmentTooNoisy 1}

ipv4FragmentTooNoisyMom	OBJECT-TYPE
	SYNTAX	 CounterBasedGauge64
	MAX-ACCESS read-only
	STATUS current
	DESCRIPTION "Packets refused (too many fragments)"

	::={ipv4FragmentTooNoisy 2}

ipv4FragmentTooNoisyMax	OBJECT-TYPE
	SYNTAX	 CounterBasedGauge64
	MAX-ACCESS read-only
	STATUS current
	DESCRIPTION "Packets refused (too many fragments)"

	::={ipv4FragmentTooNoisy 3}

ipv4Reassembled	OBJECT IDENTIFIER ::={ipv4 20}

ipv4ReassembledVal	OBJECT-TYPE
	SYNTAX	 Counter64
	MAX-ACCESS read-only
	STATUS current
	DESCRIPTION "Reassembled packets"

	::={ipv4Reassembled 1}

ipv4ReassembledMom	OBJECT-TYPE
	SYNTAX	 CounterBasedGauge64
	MAX-ACCESS read-only
	STATUS current
	DESCRIPTION "Reassembled packets"

	::={ipv4Reassembled 2}

ipv4ReassembledMax	OBJECT-TYPE
	SYNTAX	 CounterBasedGauge64
	MAX-ACCESS read-only
	STATUS current
	DESCRIPTION "Reassembled packets"

	::={ipv4Reassembled 3}

ipv4FragmentDrops	OBJECT IDENTIFIER ::={ipv4 21}

ipv4FragmentDropsVal	OBJECT-TYPE
	SYNTAX	 Counter64
	MAX-ACCESS read-only
	STATUS current
	DESCRIPTION "Dropped fragments (timeout/LRU)"

	::={ipv4FragmentDrops 1}

ipv4FragmentDropsMom	OBJECT-TYPE
	SYNTAX	 CounterBasedGauge64
	MAX-ACCESS read-only
	STATUS current
	DESCRIPTION "Dropped fragments (timeout/LRU)"

	::={ipv4FragmentDrops 2}

ipv4FragmentDropsMax	OBJECT-TYPE
	SYNTAX	 CounterBasedGauge64
	MAX-ACCESS read-only
	STATUS current
	DESCRIPTION "Dropped fragments (timeout/LRU)"

	::={ipv4FragmentDrops 3}

ipv4ShuntAddressPackets	OBJECT IDENTIFIER ::={ipv4 35}

ipv4ShuntAddressPacketsVal	OBJECT-TYPE
	SYNTAX	 Counter64
	MAX-ACCESS read-only
	STATUS current
	DESCRIPTION "Shunted packets (address)"

	::={ipv4ShuntAddressPackets 1}

ipv4ShuntAddressPacketsMom	OBJECT-TYPE
	SYNTAX	 CounterBasedGauge64
	MAX-ACCESS read-only
	STATUS current
	DESCRIPTION "Shunted packets (address)"

	::={ipv4ShuntAddressPackets 2}

ipv4ShuntAddressPacketsMax	OBJECT-TYPE
	SYNTAX	 CounterBasedGauge64
	MAX-ACCESS read-only
	STATUS current
	DESCRIPTION "Shunted packets (address)"

	::={ipv4ShuntAddressPackets 3}

ipv4ShuntAddressBytes	OBJECT IDENTIFIER ::={ipv4 36}

ipv4ShuntAddressBytesVal	OBJECT-TYPE
	SYNTAX	 Counter64
	MAX-ACCESS read-only
	STATUS current
	DESCRIPTION "Shunted bytes (address)"

	::={ipv4ShuntAddressBytes 1}

ipv4ShuntAddressBytesMom	OBJECT-TYPE
	SYNTAX	 CounterBasedGauge64
	MAX-ACCESS read-only
	STATUS current
	DESCRIPTION "Shunted bytes (address)"

	::={ipv4ShuntAddressBytes 2}

ipv4ShuntAddressBytesMax	OBJECT-TYPE
	SYNTAX	 CounterBasedGauge64
	MAX-ACCESS read-only
	STATUS current
	DESCRIPTION "Shunted bytes (address)"

	::={ipv4ShuntAddressBytes 3}

ipv4ShuntProtoPackets	OBJECT IDENTIFIER ::={ipv4 37}

ipv4ShuntProtoPacketsVal	OBJECT-TYPE
	SYNTAX	 Counter64
	MAX-ACCESS read-only
	STATUS current
	DESCRIPTION "Shunted packets (protocol)"

	::={ipv4ShuntProtoPackets 1}

ipv4ShuntProtoPacketsMom	OBJECT-TYPE
	SYNTAX	 CounterBasedGauge64
	MAX-ACCESS read-only
	STATUS current
	DESCRIPTION "Shunted packets (protocol)"

	::={ipv4ShuntProtoPackets 2}

ipv4ShuntProtoPacketsMax	OBJECT-TYPE
	SYNTAX	 CounterBasedGauge64
	MAX-ACCESS read-only
	STATUS current
	DESCRIPTION "Shunted packets (protocol)"

	::={ipv4ShuntProtoPackets 3}

ipv4ShuntProtoBytes	OBJECT IDENTIFIER ::={ipv4 38}

ipv4ShuntProtoBytesVal	OBJECT-TYPE
	SYNTAX	 Counter64
	MAX-ACCESS read-only
	STATUS current
	DESCRIPTION "Shunted bytes (protocol)"

	::={ipv4ShuntProtoBytes 1}

ipv4ShuntProtoBytesMom	OBJECT-TYPE
	SYNTAX	 CounterBasedGauge64
	MAX-ACCESS read-only
	STATUS current
	DESCRIPTION "Shunted bytes (protocol)"

	::={ipv4ShuntProtoBytes 2}

ipv4ShuntProtoBytesMax	OBJECT-TYPE
	SYNTAX	 CounterBasedGauge64
	MAX-ACCESS read-only
	STATUS current
	DESCRIPTION "Shunted bytes (protocol)"

	::={ipv4ShuntProtoBytes 3}

ipv4EcnEct0	OBJECT IDENTIFIER ::={ipv4 39}

ipv4EcnEct0Val	OBJECT-TYPE
	SYNTAX	 Counter64
	MAX-ACCESS read-only
	STATUS current
	DESCRIPTION "ECN Capable Packets ECT(0)"

	::={ipv4EcnEct0 1}

ipv4EcnEct0Mom	OBJECT-TYPE
	SYNTAX	 CounterBasedGauge64
	MAX-ACCESS read-only
	STATUS current
	DESCRIPTION "ECN Capable Packets ECT(0)"

	::={ipv4EcnEct0 2}

ipv4EcnEct0Max	OBJECT-TYPE
	SYNTAX	 CounterBasedGauge64
	MAX-ACCESS read-only
	STATUS current
	DESCRIPTION "ECN Capable Packets ECT(0)"

	::={ipv4EcnEct0 3}

ipv4EcnEct1	OBJECT IDENTIFIER ::={ipv4 40}

ipv4EcnEct1Val	OBJECT-TYPE
	SYNTAX	 Counter64
	MAX-ACCESS read-only
	STATUS current
	DESCRIPTION "ECN Capable Packets ECT(1)"

	::={ipv4EcnEct1 1}

ipv4EcnEct1Mom	OBJECT-TYPE
	SYNTAX	 CounterBasedGauge64
	MAX-ACCESS read-only
	STATUS current
	DESCRIPTION "ECN Capable Packets ECT(1)"

	::={ipv4EcnEct1 2}

ipv4EcnEct1Max	OBJECT-TYPE
	SYNTAX	 CounterBasedGauge64
	MAX-ACCESS read-only
	STATUS current
	DESCRIPTION "ECN Capable Packets ECT(1)"

	::={ipv4EcnEct1 3}

ipv4EcnCn	OBJECT IDENTIFIER ::={ipv4 41}

ipv4EcnCnVal	OBJECT-TYPE
	SYNTAX	 Counter64
	MAX-ACCESS read-only
	STATUS current
	DESCRIPTION "ECN Packets Congestion Experienced"

	::={ipv4EcnCn 1}

ipv4EcnCnMom	OBJECT-TYPE
	SYNTAX	 CounterBasedGauge64
	MAX-ACCESS read-only
	STATUS current
	DESCRIPTION "ECN Packets Congestion Experienced"

	::={ipv4EcnCn 2}

ipv4EcnCnMax	OBJECT-TYPE
	SYNTAX	 CounterBasedGauge64
	MAX-ACCESS read-only
	STATUS current
	DESCRIPTION "ECN Packets Congestion Experienced"

	::={ipv4EcnCn 3}

ipv6	OBJECT IDENTIFIER ::={sysdiag 126}

ipv6Packets	OBJECT IDENTIFIER ::={ipv6 1}

ipv6PacketsVal	OBJECT-TYPE
	SYNTAX	 Counter64
	MAX-ACCESS read-only
	STATUS current
	DESCRIPTION "RX packets"

	::={ipv6Packets 1}

ipv6PacketsMom	OBJECT-TYPE
	SYNTAX	 CounterBasedGauge64
	MAX-ACCESS read-only
	STATUS current
	DESCRIPTION "RX packets"

	::={ipv6Packets 2}

ipv6PacketsMax	OBJECT-TYPE
	SYNTAX	 CounterBasedGauge64
	MAX-ACCESS read-only
	STATUS current
	DESCRIPTION "RX packets"

	::={ipv6Packets 3}

ipv6Bytes	OBJECT IDENTIFIER ::={ipv6 2}

ipv6BytesVal	OBJECT-TYPE
	SYNTAX	 Counter64
	MAX-ACCESS read-only
	STATUS current
	DESCRIPTION "RX data"

	::={ipv6Bytes 1}

ipv6BytesMom	OBJECT-TYPE
	SYNTAX	 CounterBasedGauge64
	MAX-ACCESS read-only
	STATUS current
	DESCRIPTION "RX data"

	::={ipv6Bytes 2}

ipv6BytesMax	OBJECT-TYPE
	SYNTAX	 CounterBasedGauge64
	MAX-ACCESS read-only
	STATUS current
	DESCRIPTION "RX data"

	::={ipv6Bytes 3}

ipv6RefusedShort	OBJECT IDENTIFIER ::={ipv6 3}

ipv6RefusedShortVal	OBJECT-TYPE
	SYNTAX	 Counter64
	MAX-ACCESS read-only
	STATUS current
	DESCRIPTION "Refused (packet is too short)"

	::={ipv6RefusedShort 1}

ipv6RefusedShortMom	OBJECT-TYPE
	SYNTAX	 CounterBasedGauge64
	MAX-ACCESS read-only
	STATUS current
	DESCRIPTION "Refused (packet is too short)"

	::={ipv6RefusedShort 2}

ipv6RefusedShortMax	OBJECT-TYPE
	SYNTAX	 CounterBasedGauge64
	MAX-ACCESS read-only
	STATUS current
	DESCRIPTION "Refused (packet is too short)"

	::={ipv6RefusedShort 3}

ipv6RefusedVersion	OBJECT IDENTIFIER ::={ipv6 4}

ipv6RefusedVersionVal	OBJECT-TYPE
	SYNTAX	 Counter64
	MAX-ACCESS read-only
	STATUS current
	DESCRIPTION "Refused (invalid version)"

	::={ipv6RefusedVersion 1}

ipv6RefusedVersionMom	OBJECT-TYPE
	SYNTAX	 CounterBasedGauge64
	MAX-ACCESS read-only
	STATUS current
	DESCRIPTION "Refused (invalid version)"

	::={ipv6RefusedVersion 2}

ipv6RefusedVersionMax	OBJECT-TYPE
	SYNTAX	 CounterBasedGauge64
	MAX-ACCESS read-only
	STATUS current
	DESCRIPTION "Refused (invalid version)"

	::={ipv6RefusedVersion 3}

ipv6RefusedSelf	OBJECT IDENTIFIER ::={ipv6 5}

ipv6RefusedSelfVal	OBJECT-TYPE
	SYNTAX	 Counter64
	MAX-ACCESS read-only
	STATUS current
	DESCRIPTION "Refused (src == dest)"

	::={ipv6RefusedSelf 1}

ipv6RefusedSelfMom	OBJECT-TYPE
	SYNTAX	 CounterBasedGauge64
	MAX-ACCESS read-only
	STATUS current
	DESCRIPTION "Refused (src == dest)"

	::={ipv6RefusedSelf 2}

ipv6RefusedSelfMax	OBJECT-TYPE
	SYNTAX	 CounterBasedGauge64
	MAX-ACCESS read-only
	STATUS current
	DESCRIPTION "Refused (src == dest)"

	::={ipv6RefusedSelf 3}

ipv6Fragmented	OBJECT IDENTIFIER ::={ipv6 7}

ipv6FragmentedVal	OBJECT-TYPE
	SYNTAX	 Counter64
	MAX-ACCESS read-only
	STATUS current
	DESCRIPTION "Packet fragments"

	::={ipv6Fragmented 1}

ipv6FragmentedMom	OBJECT-TYPE
	SYNTAX	 CounterBasedGauge64
	MAX-ACCESS read-only
	STATUS current
	DESCRIPTION "Packet fragments"

	::={ipv6Fragmented 2}

ipv6FragmentedMax	OBJECT-TYPE
	SYNTAX	 CounterBasedGauge64
	MAX-ACCESS read-only
	STATUS current
	DESCRIPTION "Packet fragments"

	::={ipv6Fragmented 3}

ipv6FragmentedIds	OBJECT IDENTIFIER ::={ipv6 10}

ipv6FragmentedIdsVal	OBJECT-TYPE
	SYNTAX	 CounterBasedGauge64
	MAX-ACCESS read-only
	STATUS current
	DESCRIPTION "Fragment ids"

	::={ipv6FragmentedIds 1}

ipv6FragmentedIdsMax	OBJECT-TYPE
	SYNTAX	 CounterBasedGauge64
	MAX-ACCESS read-only
	STATUS current
	DESCRIPTION "Fragment ids"

	::={ipv6FragmentedIds 3}

ipv6Fragments	OBJECT IDENTIFIER ::={ipv6 11}

ipv6FragmentsVal	OBJECT-TYPE
	SYNTAX	 CounterBasedGauge64
	MAX-ACCESS read-only
	STATUS current
	DESCRIPTION "Fragments in queue"

	::={ipv6Fragments 1}

ipv6FragmentsMax	OBJECT-TYPE
	SYNTAX	 CounterBasedGauge64
	MAX-ACCESS read-only
	STATUS current
	DESCRIPTION "Fragments in queue"

	::={ipv6Fragments 3}

ipv6RefusedOof	OBJECT IDENTIFIER ::={ipv6 14}

ipv6RefusedOofVal	OBJECT-TYPE
	SYNTAX	 Counter64
	MAX-ACCESS read-only
	STATUS current
	DESCRIPTION "Refused (out of fragments)"

	::={ipv6RefusedOof 1}

ipv6RefusedOofMom	OBJECT-TYPE
	SYNTAX	 CounterBasedGauge64
	MAX-ACCESS read-only
	STATUS current
	DESCRIPTION "Refused (out of fragments)"

	::={ipv6RefusedOof 2}

ipv6RefusedOofMax	OBJECT-TYPE
	SYNTAX	 CounterBasedGauge64
	MAX-ACCESS read-only
	STATUS current
	DESCRIPTION "Refused (out of fragments)"

	::={ipv6RefusedOof 3}

ipv6FragmentAllocationFailures	OBJECT IDENTIFIER ::={ipv6 15}

ipv6FragmentAllocationFailuresVal	OBJECT-TYPE
	SYNTAX	 Counter64
	MAX-ACCESS read-only
	STATUS current
	DESCRIPTION "Fragment allocation failures"

	::={ipv6FragmentAllocationFailures 1}

ipv6FragmentAllocationFailuresMom	OBJECT-TYPE
	SYNTAX	 CounterBasedGauge64
	MAX-ACCESS read-only
	STATUS current
	DESCRIPTION "Fragment allocation failures"

	::={ipv6FragmentAllocationFailures 2}

ipv6FragmentAllocationFailuresMax	OBJECT-TYPE
	SYNTAX	 CounterBasedGauge64
	MAX-ACCESS read-only
	STATUS current
	DESCRIPTION "Fragment allocation failures"

	::={ipv6FragmentAllocationFailures 3}

ipv6FragmentReassFail	OBJECT IDENTIFIER ::={ipv6 16}

ipv6FragmentReassFailVal	OBJECT-TYPE
	SYNTAX	 Counter64
	MAX-ACCESS read-only
	STATUS current
	DESCRIPTION "Fragment reassembly failures"

	::={ipv6FragmentReassFail 1}

ipv6FragmentReassFailMom	OBJECT-TYPE
	SYNTAX	 CounterBasedGauge64
	MAX-ACCESS read-only
	STATUS current
	DESCRIPTION "Fragment reassembly failures"

	::={ipv6FragmentReassFail 2}

ipv6FragmentReassFailMax	OBJECT-TYPE
	SYNTAX	 CounterBasedGauge64
	MAX-ACCESS read-only
	STATUS current
	DESCRIPTION "Fragment reassembly failures"

	::={ipv6FragmentReassFail 3}

ipv6FragmentTooNoisy	OBJECT IDENTIFIER ::={ipv6 19}

ipv6FragmentTooNoisyVal	OBJECT-TYPE
	SYNTAX	 Counter64
	MAX-ACCESS read-only
	STATUS current
	DESCRIPTION "Packets refused (too many fragments)"

	::={ipv6FragmentTooNoisy 1}

ipv6FragmentTooNoisyMom	OBJECT-TYPE
	SYNTAX	 CounterBasedGauge64
	MAX-ACCESS read-only
	STATUS current
	DESCRIPTION "Packets refused (too many fragments)"

	::={ipv6FragmentTooNoisy 2}

ipv6FragmentTooNoisyMax	OBJECT-TYPE
	SYNTAX	 CounterBasedGauge64
	MAX-ACCESS read-only
	STATUS current
	DESCRIPTION "Packets refused (too many fragments)"

	::={ipv6FragmentTooNoisy 3}

ipv6Reassembled	OBJECT IDENTIFIER ::={ipv6 20}

ipv6ReassembledVal	OBJECT-TYPE
	SYNTAX	 Counter64
	MAX-ACCESS read-only
	STATUS current
	DESCRIPTION "Reassembled packets"

	::={ipv6Reassembled 1}

ipv6ReassembledMom	OBJECT-TYPE
	SYNTAX	 CounterBasedGauge64
	MAX-ACCESS read-only
	STATUS current
	DESCRIPTION "Reassembled packets"

	::={ipv6Reassembled 2}

ipv6ReassembledMax	OBJECT-TYPE
	SYNTAX	 CounterBasedGauge64
	MAX-ACCESS read-only
	STATUS current
	DESCRIPTION "Reassembled packets"

	::={ipv6Reassembled 3}

ipv6FragmentOverlap	OBJECT IDENTIFIER ::={ipv6 21}

ipv6FragmentOverlapVal	OBJECT-TYPE
	SYNTAX	 Counter64
	MAX-ACCESS read-only
	STATUS current
	DESCRIPTION "Overlapping Fragments"

	::={ipv6FragmentOverlap 1}

ipv6FragmentOverlapMom	OBJECT-TYPE
	SYNTAX	 CounterBasedGauge64
	MAX-ACCESS read-only
	STATUS current
	DESCRIPTION "Overlapping Fragments"

	::={ipv6FragmentOverlap 2}

ipv6FragmentOverlapMax	OBJECT-TYPE
	SYNTAX	 CounterBasedGauge64
	MAX-ACCESS read-only
	STATUS current
	DESCRIPTION "Overlapping Fragments"

	::={ipv6FragmentOverlap 3}

ipv6ExtDest	OBJECT IDENTIFIER ::={ipv6 22}

ipv6ExtDestVal	OBJECT-TYPE
	SYNTAX	 Counter64
	MAX-ACCESS read-only
	STATUS current
	DESCRIPTION "Destination Ext. Headers"

	::={ipv6ExtDest 1}

ipv6ExtDestMom	OBJECT-TYPE
	SYNTAX	 CounterBasedGauge64
	MAX-ACCESS read-only
	STATUS current
	DESCRIPTION "Destination Ext. Headers"

	::={ipv6ExtDest 2}

ipv6ExtDestMax	OBJECT-TYPE
	SYNTAX	 CounterBasedGauge64
	MAX-ACCESS read-only
	STATUS current
	DESCRIPTION "Destination Ext. Headers"

	::={ipv6ExtDest 3}

ipv6ExtHbh	OBJECT IDENTIFIER ::={ipv6 23}

ipv6ExtHbhVal	OBJECT-TYPE
	SYNTAX	 Counter64
	MAX-ACCESS read-only
	STATUS current
	DESCRIPTION "Hob-by-hop Ext. Headers"

	::={ipv6ExtHbh 1}

ipv6ExtHbhMom	OBJECT-TYPE
	SYNTAX	 CounterBasedGauge64
	MAX-ACCESS read-only
	STATUS current
	DESCRIPTION "Hob-by-hop Ext. Headers"

	::={ipv6ExtHbh 2}

ipv6ExtHbhMax	OBJECT-TYPE
	SYNTAX	 CounterBasedGauge64
	MAX-ACCESS read-only
	STATUS current
	DESCRIPTION "Hob-by-hop Ext. Headers"

	::={ipv6ExtHbh 3}

ipv6ExtRoute	OBJECT IDENTIFIER ::={ipv6 24}

ipv6ExtRouteVal	OBJECT-TYPE
	SYNTAX	 Counter64
	MAX-ACCESS read-only
	STATUS current
	DESCRIPTION "Route Ext, Headers"

	::={ipv6ExtRoute 1}

ipv6ExtRouteMom	OBJECT-TYPE
	SYNTAX	 CounterBasedGauge64
	MAX-ACCESS read-only
	STATUS current
	DESCRIPTION "Route Ext, Headers"

	::={ipv6ExtRoute 2}

ipv6ExtRouteMax	OBJECT-TYPE
	SYNTAX	 CounterBasedGauge64
	MAX-ACCESS read-only
	STATUS current
	DESCRIPTION "Route Ext, Headers"

	::={ipv6ExtRoute 3}

ipv6ExtInvl	OBJECT IDENTIFIER ::={ipv6 25}

ipv6ExtInvlVal	OBJECT-TYPE
	SYNTAX	 Counter64
	MAX-ACCESS read-only
	STATUS current
	DESCRIPTION "Invalid Ext. Headers"

	::={ipv6ExtInvl 1}

ipv6ExtInvlMom	OBJECT-TYPE
	SYNTAX	 CounterBasedGauge64
	MAX-ACCESS read-only
	STATUS current
	DESCRIPTION "Invalid Ext. Headers"

	::={ipv6ExtInvl 2}

ipv6ExtInvlMax	OBJECT-TYPE
	SYNTAX	 CounterBasedGauge64
	MAX-ACCESS read-only
	STATUS current
	DESCRIPTION "Invalid Ext. Headers"

	::={ipv6ExtInvl 3}

ipv6FragnentTimeout	OBJECT IDENTIFIER ::={ipv6 26}

ipv6FragnentTimeoutVal	OBJECT-TYPE
	SYNTAX	 Counter64
	MAX-ACCESS read-only
	STATUS current
	DESCRIPTION "Reassembly Timeout"

	::={ipv6FragnentTimeout 1}

ipv6FragnentTimeoutMom	OBJECT-TYPE
	SYNTAX	 CounterBasedGauge64
	MAX-ACCESS read-only
	STATUS current
	DESCRIPTION "Reassembly Timeout"

	::={ipv6FragnentTimeout 2}

ipv6FragnentTimeoutMax	OBJECT-TYPE
	SYNTAX	 CounterBasedGauge64
	MAX-ACCESS read-only
	STATUS current
	DESCRIPTION "Reassembly Timeout"

	::={ipv6FragnentTimeout 3}

ipv6FragmentDrops	OBJECT IDENTIFIER ::={ipv6 27}

ipv6FragmentDropsVal	OBJECT-TYPE
	SYNTAX	 Counter64
	MAX-ACCESS read-only
	STATUS current
	DESCRIPTION "Dropped fragments (timeout/LRU)"

	::={ipv6FragmentDrops 1}

ipv6FragmentDropsMom	OBJECT-TYPE
	SYNTAX	 CounterBasedGauge64
	MAX-ACCESS read-only
	STATUS current
	DESCRIPTION "Dropped fragments (timeout/LRU)"

	::={ipv6FragmentDrops 2}

ipv6FragmentDropsMax	OBJECT-TYPE
	SYNTAX	 CounterBasedGauge64
	MAX-ACCESS read-only
	STATUS current
	DESCRIPTION "Dropped fragments (timeout/LRU)"

	::={ipv6FragmentDrops 3}

ipv6ShuntAddressPackets	OBJECT IDENTIFIER ::={ipv6 28}

ipv6ShuntAddressPacketsVal	OBJECT-TYPE
	SYNTAX	 Counter64
	MAX-ACCESS read-only
	STATUS current
	DESCRIPTION "Shunted packets (address)"

	::={ipv6ShuntAddressPackets 1}

ipv6ShuntAddressPacketsMom	OBJECT-TYPE
	SYNTAX	 CounterBasedGauge64
	MAX-ACCESS read-only
	STATUS current
	DESCRIPTION "Shunted packets (address)"

	::={ipv6ShuntAddressPackets 2}

ipv6ShuntAddressPacketsMax	OBJECT-TYPE
	SYNTAX	 CounterBasedGauge64
	MAX-ACCESS read-only
	STATUS current
	DESCRIPTION "Shunted packets (address)"

	::={ipv6ShuntAddressPackets 3}

ipv6ShuntAddressBytes	OBJECT IDENTIFIER ::={ipv6 29}

ipv6ShuntAddressBytesVal	OBJECT-TYPE
	SYNTAX	 Counter64
	MAX-ACCESS read-only
	STATUS current
	DESCRIPTION "Shunted bytes (address)"

	::={ipv6ShuntAddressBytes 1}

ipv6ShuntAddressBytesMom	OBJECT-TYPE
	SYNTAX	 CounterBasedGauge64
	MAX-ACCESS read-only
	STATUS current
	DESCRIPTION "Shunted bytes (address)"

	::={ipv6ShuntAddressBytes 2}

ipv6ShuntAddressBytesMax	OBJECT-TYPE
	SYNTAX	 CounterBasedGauge64
	MAX-ACCESS read-only
	STATUS current
	DESCRIPTION "Shunted bytes (address)"

	::={ipv6ShuntAddressBytes 3}

ipv6ShuntProtoPackets	OBJECT IDENTIFIER ::={ipv6 30}

ipv6ShuntProtoPacketsVal	OBJECT-TYPE
	SYNTAX	 Counter64
	MAX-ACCESS read-only
	STATUS current
	DESCRIPTION "Shunted packets (protocol)"

	::={ipv6ShuntProtoPackets 1}

ipv6ShuntProtoPacketsMom	OBJECT-TYPE
	SYNTAX	 CounterBasedGauge64
	MAX-ACCESS read-only
	STATUS current
	DESCRIPTION "Shunted packets (protocol)"

	::={ipv6ShuntProtoPackets 2}

ipv6ShuntProtoPacketsMax	OBJECT-TYPE
	SYNTAX	 CounterBasedGauge64
	MAX-ACCESS read-only
	STATUS current
	DESCRIPTION "Shunted packets (protocol)"

	::={ipv6ShuntProtoPackets 3}

ipv6ShuntProtoBytes	OBJECT IDENTIFIER ::={ipv6 31}

ipv6ShuntProtoBytesVal	OBJECT-TYPE
	SYNTAX	 Counter64
	MAX-ACCESS read-only
	STATUS current
	DESCRIPTION "Shunted bytes (protocol)"

	::={ipv6ShuntProtoBytes 1}

ipv6ShuntProtoBytesMom	OBJECT-TYPE
	SYNTAX	 CounterBasedGauge64
	MAX-ACCESS read-only
	STATUS current
	DESCRIPTION "Shunted bytes (protocol)"

	::={ipv6ShuntProtoBytes 2}

ipv6ShuntProtoBytesMax	OBJECT-TYPE
	SYNTAX	 CounterBasedGauge64
	MAX-ACCESS read-only
	STATUS current
	DESCRIPTION "Shunted bytes (protocol)"

	::={ipv6ShuntProtoBytes 3}

ipv6FragInFrag	OBJECT IDENTIFIER ::={ipv6 32}

ipv6FragInFragVal	OBJECT-TYPE
	SYNTAX	 Counter64
	MAX-ACCESS read-only
	STATUS current
	DESCRIPTION "Fragments in Fragments"

	::={ipv6FragInFrag 1}

ipv6FragInFragMom	OBJECT-TYPE
	SYNTAX	 CounterBasedGauge64
	MAX-ACCESS read-only
	STATUS current
	DESCRIPTION "Fragments in Fragments"

	::={ipv6FragInFrag 2}

ipv6FragInFragMax	OBJECT-TYPE
	SYNTAX	 CounterBasedGauge64
	MAX-ACCESS read-only
	STATUS current
	DESCRIPTION "Fragments in Fragments"

	::={ipv6FragInFrag 3}

ipv6EcnEct0	OBJECT IDENTIFIER ::={ipv6 33}

ipv6EcnEct0Val	OBJECT-TYPE
	SYNTAX	 Counter64
	MAX-ACCESS read-only
	STATUS current
	DESCRIPTION "ECN Capable Packets ECT(0)"

	::={ipv6EcnEct0 1}

ipv6EcnEct0Mom	OBJECT-TYPE
	SYNTAX	 CounterBasedGauge64
	MAX-ACCESS read-only
	STATUS current
	DESCRIPTION "ECN Capable Packets ECT(0)"

	::={ipv6EcnEct0 2}

ipv6EcnEct0Max	OBJECT-TYPE
	SYNTAX	 CounterBasedGauge64
	MAX-ACCESS read-only
	STATUS current
	DESCRIPTION "ECN Capable Packets ECT(0)"

	::={ipv6EcnEct0 3}

ipv6EcnEct1	OBJECT IDENTIFIER ::={ipv6 34}

ipv6EcnEct1Val	OBJECT-TYPE
	SYNTAX	 Counter64
	MAX-ACCESS read-only
	STATUS current
	DESCRIPTION "ECN Capable Packets ECT(1)"

	::={ipv6EcnEct1 1}

ipv6EcnEct1Mom	OBJECT-TYPE
	SYNTAX	 CounterBasedGauge64
	MAX-ACCESS read-only
	STATUS current
	DESCRIPTION "ECN Capable Packets ECT(1)"

	::={ipv6EcnEct1 2}

ipv6EcnEct1Max	OBJECT-TYPE
	SYNTAX	 CounterBasedGauge64
	MAX-ACCESS read-only
	STATUS current
	DESCRIPTION "ECN Capable Packets ECT(1)"

	::={ipv6EcnEct1 3}

ipv6EcnCn	OBJECT IDENTIFIER ::={ipv6 35}

ipv6EcnCnVal	OBJECT-TYPE
	SYNTAX	 Counter64
	MAX-ACCESS read-only
	STATUS current
	DESCRIPTION "ECN Packets Congestion Experienced"

	::={ipv6EcnCn 1}

ipv6EcnCnMom	OBJECT-TYPE
	SYNTAX	 CounterBasedGauge64
	MAX-ACCESS read-only
	STATUS current
	DESCRIPTION "ECN Packets Congestion Experienced"

	::={ipv6EcnCn 2}

ipv6EcnCnMax	OBJECT-TYPE
	SYNTAX	 CounterBasedGauge64
	MAX-ACCESS read-only
	STATUS current
	DESCRIPTION "ECN Packets Congestion Experienced"

	::={ipv6EcnCn 3}

tcpv4	OBJECT IDENTIFIER ::={sysdiag 48}

tcpv4Packets	OBJECT IDENTIFIER ::={tcpv4 1}

tcpv4PacketsVal	OBJECT-TYPE
	SYNTAX	 Counter64
	MAX-ACCESS read-only
	STATUS current
	DESCRIPTION "RX packets"

	::={tcpv4Packets 1}

tcpv4PacketsMom	OBJECT-TYPE
	SYNTAX	 CounterBasedGauge64
	MAX-ACCESS read-only
	STATUS current
	DESCRIPTION "RX packets"

	::={tcpv4Packets 2}

tcpv4PacketsMax	OBJECT-TYPE
	SYNTAX	 CounterBasedGauge64
	MAX-ACCESS read-only
	STATUS current
	DESCRIPTION "RX packets"

	::={tcpv4Packets 3}

tcpv4Bytes	OBJECT IDENTIFIER ::={tcpv4 2}

tcpv4BytesVal	OBJECT-TYPE
	SYNTAX	 Counter64
	MAX-ACCESS read-only
	STATUS current
	DESCRIPTION "RX bytes"

	::={tcpv4Bytes 1}

tcpv4BytesMom	OBJECT-TYPE
	SYNTAX	 CounterBasedGauge64
	MAX-ACCESS read-only
	STATUS current
	DESCRIPTION "RX bytes"

	::={tcpv4Bytes 2}

tcpv4BytesMax	OBJECT-TYPE
	SYNTAX	 CounterBasedGauge64
	MAX-ACCESS read-only
	STATUS current
	DESCRIPTION "RX bytes"

	::={tcpv4Bytes 3}

tcpv4CreateAttempts	OBJECT IDENTIFIER ::={tcpv4 4}

tcpv4CreateAttemptsVal	OBJECT-TYPE
	SYNTAX	 Counter64
	MAX-ACCESS read-only
	STATUS current
	DESCRIPTION "Connection create attempts"

	::={tcpv4CreateAttempts 1}

tcpv4CreateAttemptsMom	OBJECT-TYPE
	SYNTAX	 CounterBasedGauge64
	MAX-ACCESS read-only
	STATUS current
	DESCRIPTION "Connection create attempts"

	::={tcpv4CreateAttempts 2}

tcpv4CreateAttemptsMax	OBJECT-TYPE
	SYNTAX	 CounterBasedGauge64
	MAX-ACCESS read-only
	STATUS current
	DESCRIPTION "Connection create attempts"

	::={tcpv4CreateAttempts 3}

tcpv4Created	OBJECT IDENTIFIER ::={tcpv4 5}

tcpv4CreatedVal	OBJECT-TYPE
	SYNTAX	 Counter64
	MAX-ACCESS read-only
	STATUS current
	DESCRIPTION "Connections created"

	::={tcpv4Created 1}

tcpv4CreatedMom	OBJECT-TYPE
	SYNTAX	 CounterBasedGauge64
	MAX-ACCESS read-only
	STATUS current
	DESCRIPTION "Connections created"

	::={tcpv4Created 2}

tcpv4CreatedMax	OBJECT-TYPE
	SYNTAX	 CounterBasedGauge64
	MAX-ACCESS read-only
	STATUS current
	DESCRIPTION "Connections created"

	::={tcpv4Created 3}

tcpv4RefusedRuleset	OBJECT IDENTIFIER ::={tcpv4 6}

tcpv4RefusedRulesetVal	OBJECT-TYPE
	SYNTAX	 Counter64
	MAX-ACCESS read-only
	STATUS current
	DESCRIPTION "Refused (ruleset)"

	::={tcpv4RefusedRuleset 1}

tcpv4RefusedRulesetMom	OBJECT-TYPE
	SYNTAX	 CounterBasedGauge64
	MAX-ACCESS read-only
	STATUS current
	DESCRIPTION "Refused (ruleset)"

	::={tcpv4RefusedRuleset 2}

tcpv4RefusedRulesetMax	OBJECT-TYPE
	SYNTAX	 CounterBasedGauge64
	MAX-ACCESS read-only
	STATUS current
	DESCRIPTION "Refused (ruleset)"

	::={tcpv4RefusedRuleset 3}

tcpv4RefusedShort	OBJECT IDENTIFIER ::={tcpv4 7}

tcpv4RefusedShortVal	OBJECT-TYPE
	SYNTAX	 Counter64
	MAX-ACCESS read-only
	STATUS current
	DESCRIPTION "Refused (short)"

	::={tcpv4RefusedShort 1}

tcpv4RefusedShortMom	OBJECT-TYPE
	SYNTAX	 CounterBasedGauge64
	MAX-ACCESS read-only
	STATUS current
	DESCRIPTION "Refused (short)"

	::={tcpv4RefusedShort 2}

tcpv4RefusedShortMax	OBJECT-TYPE
	SYNTAX	 CounterBasedGauge64
	MAX-ACCESS read-only
	STATUS current
	DESCRIPTION "Refused (short)"

	::={tcpv4RefusedShort 3}

tcpv4RefusedBroadcast	OBJECT IDENTIFIER ::={tcpv4 8}

tcpv4RefusedBroadcastVal	OBJECT-TYPE
	SYNTAX	 Counter64
	MAX-ACCESS read-only
	STATUS current
	DESCRIPTION "Refused (broadcast)"

	::={tcpv4RefusedBroadcast 1}

tcpv4RefusedBroadcastMom	OBJECT-TYPE
	SYNTAX	 CounterBasedGauge64
	MAX-ACCESS read-only
	STATUS current
	DESCRIPTION "Refused (broadcast)"

	::={tcpv4RefusedBroadcast 2}

tcpv4RefusedBroadcastMax	OBJECT-TYPE
	SYNTAX	 CounterBasedGauge64
	MAX-ACCESS read-only
	STATUS current
	DESCRIPTION "Refused (broadcast)"

	::={tcpv4RefusedBroadcast 3}

tcpv4RefusedOffset	OBJECT IDENTIFIER ::={tcpv4 9}

tcpv4RefusedOffsetVal	OBJECT-TYPE
	SYNTAX	 Counter64
	MAX-ACCESS read-only
	STATUS current
	DESCRIPTION "Refused (offset)"

	::={tcpv4RefusedOffset 1}

tcpv4RefusedOffsetMom	OBJECT-TYPE
	SYNTAX	 CounterBasedGauge64
	MAX-ACCESS read-only
	STATUS current
	DESCRIPTION "Refused (offset)"

	::={tcpv4RefusedOffset 2}

tcpv4RefusedOffsetMax	OBJECT-TYPE
	SYNTAX	 CounterBasedGauge64
	MAX-ACCESS read-only
	STATUS current
	DESCRIPTION "Refused (offset)"

	::={tcpv4RefusedOffset 3}

tcpv4Rejected	OBJECT IDENTIFIER ::={tcpv4 10}

tcpv4RejectedVal	OBJECT-TYPE
	SYNTAX	 Counter64
	MAX-ACCESS read-only
	STATUS current
	DESCRIPTION "Rejected packets"

	::={tcpv4Rejected 1}

tcpv4RejectedMom	OBJECT-TYPE
	SYNTAX	 CounterBasedGauge64
	MAX-ACCESS read-only
	STATUS current
	DESCRIPTION "Rejected packets"

	::={tcpv4Rejected 2}

tcpv4RejectedMax	OBJECT-TYPE
	SYNTAX	 CounterBasedGauge64
	MAX-ACCESS read-only
	STATUS current
	DESCRIPTION "Rejected packets"

	::={tcpv4Rejected 3}

tcpv4Lostsync	OBJECT IDENTIFIER ::={tcpv4 12}

tcpv4LostsyncVal	OBJECT-TYPE
	SYNTAX	 CounterBasedGauge64
	MAX-ACCESS read-only
	STATUS current
	DESCRIPTION "Out-of-sync connections"

	::={tcpv4Lostsync 1}

tcpv4LostsyncMax	OBJECT-TYPE
	SYNTAX	 CounterBasedGauge64
	MAX-ACCESS read-only
	STATUS current
	DESCRIPTION "Out-of-sync connections"

	::={tcpv4Lostsync 3}

tcpv4UntrackedPackets	OBJECT IDENTIFIER ::={tcpv4 13}

tcpv4UntrackedPacketsVal	OBJECT-TYPE
	SYNTAX	 Counter64
	MAX-ACCESS read-only
	STATUS current
	DESCRIPTION "Untracked packets"

	::={tcpv4UntrackedPackets 1}

tcpv4UntrackedPacketsMom	OBJECT-TYPE
	SYNTAX	 CounterBasedGauge64
	MAX-ACCESS read-only
	STATUS current
	DESCRIPTION "Untracked packets"

	::={tcpv4UntrackedPackets 2}

tcpv4UntrackedPacketsMax	OBJECT-TYPE
	SYNTAX	 CounterBasedGauge64
	MAX-ACCESS read-only
	STATUS current
	DESCRIPTION "Untracked packets"

	::={tcpv4UntrackedPackets 3}

tcpv4GoodputPackets	OBJECT IDENTIFIER ::={tcpv4 14}

tcpv4GoodputPacketsVal	OBJECT-TYPE
	SYNTAX	 Counter64
	MAX-ACCESS read-only
	STATUS current
	DESCRIPTION "Goodput packets"

	::={tcpv4GoodputPackets 1}

tcpv4GoodputPacketsMom	OBJECT-TYPE
	SYNTAX	 CounterBasedGauge64
	MAX-ACCESS read-only
	STATUS current
	DESCRIPTION "Goodput packets"

	::={tcpv4GoodputPackets 2}

tcpv4GoodputPacketsMax	OBJECT-TYPE
	SYNTAX	 CounterBasedGauge64
	MAX-ACCESS read-only
	STATUS current
	DESCRIPTION "Goodput packets"

	::={tcpv4GoodputPackets 3}

tcpv4GoodputBytes	OBJECT IDENTIFIER ::={tcpv4 15}

tcpv4GoodputBytesVal	OBJECT-TYPE
	SYNTAX	 Counter64
	MAX-ACCESS read-only
	STATUS current
	DESCRIPTION "Goodput bytes"

	::={tcpv4GoodputBytes 1}

tcpv4GoodputBytesMom	OBJECT-TYPE
	SYNTAX	 CounterBasedGauge64
	MAX-ACCESS read-only
	STATUS current
	DESCRIPTION "Goodput bytes"

	::={tcpv4GoodputBytes 2}

tcpv4GoodputBytesMax	OBJECT-TYPE
	SYNTAX	 CounterBasedGauge64
	MAX-ACCESS read-only
	STATUS current
	DESCRIPTION "Goodput bytes"

	::={tcpv4GoodputBytes 3}

tcpv4Segments	OBJECT IDENTIFIER ::={tcpv4 16}

tcpv4SegmentsVal	OBJECT-TYPE
	SYNTAX	 CounterBasedGauge64
	MAX-ACCESS read-only
	STATUS current
	DESCRIPTION "Saved segments"

	::={tcpv4Segments 1}

tcpv4SegmentsMax	OBJECT-TYPE
	SYNTAX	 CounterBasedGauge64
	MAX-ACCESS read-only
	STATUS current
	DESCRIPTION "Saved segments"

	::={tcpv4Segments 3}

tcpv4SegmentsPayload	OBJECT IDENTIFIER ::={tcpv4 17}

tcpv4SegmentsPayloadVal	OBJECT-TYPE
	SYNTAX	 CounterBasedGauge64
	MAX-ACCESS read-only
	STATUS current
	DESCRIPTION "Saved segments with payload"

	::={tcpv4SegmentsPayload 1}

tcpv4SegmentsPayloadMax	OBJECT-TYPE
	SYNTAX	 CounterBasedGauge64
	MAX-ACCESS read-only
	STATUS current
	DESCRIPTION "Saved segments with payload"

	::={tcpv4SegmentsPayload 3}

tcpv4SegmentsDropped	OBJECT IDENTIFIER ::={tcpv4 18}

tcpv4SegmentsDroppedVal	OBJECT-TYPE
	SYNTAX	 Counter64
	MAX-ACCESS read-only
	STATUS current
	DESCRIPTION "Ignored segments"

	::={tcpv4SegmentsDropped 1}

tcpv4SegmentsDroppedMom	OBJECT-TYPE
	SYNTAX	 CounterBasedGauge64
	MAX-ACCESS read-only
	STATUS current
	DESCRIPTION "Ignored segments"

	::={tcpv4SegmentsDropped 2}

tcpv4SegmentsDroppedMax	OBJECT-TYPE
	SYNTAX	 CounterBasedGauge64
	MAX-ACCESS read-only
	STATUS current
	DESCRIPTION "Ignored segments"

	::={tcpv4SegmentsDropped 3}

tcpv4PacketAllocFail	OBJECT IDENTIFIER ::={tcpv4 19}

tcpv4PacketAllocFailVal	OBJECT-TYPE
	SYNTAX	 Counter64
	MAX-ACCESS read-only
	STATUS current
	DESCRIPTION "Packet allocation failures"

	::={tcpv4PacketAllocFail 1}

tcpv4PacketAllocFailMom	OBJECT-TYPE
	SYNTAX	 CounterBasedGauge64
	MAX-ACCESS read-only
	STATUS current
	DESCRIPTION "Packet allocation failures"

	::={tcpv4PacketAllocFail 2}

tcpv4PacketAllocFailMax	OBJECT-TYPE
	SYNTAX	 CounterBasedGauge64
	MAX-ACCESS read-only
	STATUS current
	DESCRIPTION "Packet allocation failures"

	::={tcpv4PacketAllocFail 3}

tcpv4UntrackedGoodput	OBJECT IDENTIFIER ::={tcpv4 23}

tcpv4UntrackedGoodputVal	OBJECT-TYPE
	SYNTAX	 Counter64
	MAX-ACCESS read-only
	STATUS current
	DESCRIPTION "Untracked bytes (goodput)"

	::={tcpv4UntrackedGoodput 1}

tcpv4UntrackedGoodputMom	OBJECT-TYPE
	SYNTAX	 CounterBasedGauge64
	MAX-ACCESS read-only
	STATUS current
	DESCRIPTION "Untracked bytes (goodput)"

	::={tcpv4UntrackedGoodput 2}

tcpv4UntrackedGoodputMax	OBJECT-TYPE
	SYNTAX	 CounterBasedGauge64
	MAX-ACCESS read-only
	STATUS current
	DESCRIPTION "Untracked bytes (goodput)"

	::={tcpv4UntrackedGoodput 3}

tcpv4UntrackedBytes	OBJECT IDENTIFIER ::={tcpv4 24}

tcpv4UntrackedBytesVal	OBJECT-TYPE
	SYNTAX	 Counter64
	MAX-ACCESS read-only
	STATUS current
	DESCRIPTION "Untracked bytes"

	::={tcpv4UntrackedBytes 1}

tcpv4UntrackedBytesMom	OBJECT-TYPE
	SYNTAX	 CounterBasedGauge64
	MAX-ACCESS read-only
	STATUS current
	DESCRIPTION "Untracked bytes"

	::={tcpv4UntrackedBytes 2}

tcpv4UntrackedBytesMax	OBJECT-TYPE
	SYNTAX	 CounterBasedGauge64
	MAX-ACCESS read-only
	STATUS current
	DESCRIPTION "Untracked bytes"

	::={tcpv4UntrackedBytes 3}

tcpv4CorruptOptions	OBJECT IDENTIFIER ::={tcpv4 25}

tcpv4CorruptOptionsVal	OBJECT-TYPE
	SYNTAX	 Counter64
	MAX-ACCESS read-only
	STATUS current
	DESCRIPTION "Packets with corrupt options"

	::={tcpv4CorruptOptions 1}

tcpv4CorruptOptionsMom	OBJECT-TYPE
	SYNTAX	 CounterBasedGauge64
	MAX-ACCESS read-only
	STATUS current
	DESCRIPTION "Packets with corrupt options"

	::={tcpv4CorruptOptions 2}

tcpv4CorruptOptionsMax	OBJECT-TYPE
	SYNTAX	 CounterBasedGauge64
	MAX-ACCESS read-only
	STATUS current
	DESCRIPTION "Packets with corrupt options"

	::={tcpv4CorruptOptions 3}

tcpv4CorruptConn	OBJECT IDENTIFIER ::={tcpv4 26}

tcpv4CorruptConnVal	OBJECT-TYPE
	SYNTAX	 Counter64
	MAX-ACCESS read-only
	STATUS current
	DESCRIPTION "Packets with corrupt conn"

	::={tcpv4CorruptConn 1}

tcpv4CorruptConnMom	OBJECT-TYPE
	SYNTAX	 CounterBasedGauge64
	MAX-ACCESS read-only
	STATUS current
	DESCRIPTION "Packets with corrupt conn"

	::={tcpv4CorruptConn 2}

tcpv4CorruptConnMax	OBJECT-TYPE
	SYNTAX	 CounterBasedGauge64
	MAX-ACCESS read-only
	STATUS current
	DESCRIPTION "Packets with corrupt conn"

	::={tcpv4CorruptConn 3}

tcpv4SegmentedConnections	OBJECT IDENTIFIER ::={tcpv4 27}

tcpv4SegmentedConnectionsVal	OBJECT-TYPE
	SYNTAX	 CounterBasedGauge64
	MAX-ACCESS read-only
	STATUS current
	DESCRIPTION "Connections with segments"

	::={tcpv4SegmentedConnections 1}

tcpv4SegmentedConnectionsMax	OBJECT-TYPE
	SYNTAX	 CounterBasedGauge64
	MAX-ACCESS read-only
	STATUS current
	DESCRIPTION "Connections with segments"

	::={tcpv4SegmentedConnections 3}

tcpv4OutOfWindowPackets	OBJECT IDENTIFIER ::={tcpv4 28}

tcpv4OutOfWindowPacketsVal	OBJECT-TYPE
	SYNTAX	 Counter64
	MAX-ACCESS read-only
	STATUS current
	DESCRIPTION "Out of window packets (ignored)"

	::={tcpv4OutOfWindowPackets 1}

tcpv4OutOfWindowPacketsMom	OBJECT-TYPE
	SYNTAX	 CounterBasedGauge64
	MAX-ACCESS read-only
	STATUS current
	DESCRIPTION "Out of window packets (ignored)"

	::={tcpv4OutOfWindowPackets 2}

tcpv4OutOfWindowPacketsMax	OBJECT-TYPE
	SYNTAX	 CounterBasedGauge64
	MAX-ACCESS read-only
	STATUS current
	DESCRIPTION "Out of window packets (ignored)"

	::={tcpv4OutOfWindowPackets 3}

tcpv4RefusedFilter	OBJECT IDENTIFIER ::={tcpv4 29}

tcpv4RefusedFilterVal	OBJECT-TYPE
	SYNTAX	 Counter64
	MAX-ACCESS read-only
	STATUS current
	DESCRIPTION "Packets refused by lowlevel filter"

	::={tcpv4RefusedFilter 1}

tcpv4RefusedFilterMom	OBJECT-TYPE
	SYNTAX	 CounterBasedGauge64
	MAX-ACCESS read-only
	STATUS current
	DESCRIPTION "Packets refused by lowlevel filter"

	::={tcpv4RefusedFilter 2}

tcpv4RefusedFilterMax	OBJECT-TYPE
	SYNTAX	 CounterBasedGauge64
	MAX-ACCESS read-only
	STATUS current
	DESCRIPTION "Packets refused by lowlevel filter"

	::={tcpv4RefusedFilter 3}

tcpv4SynExisting	OBJECT IDENTIFIER ::={tcpv4 32}

tcpv4SynExistingVal	OBJECT-TYPE
	SYNTAX	 Counter64
	MAX-ACCESS read-only
	STATUS current
	DESCRIPTION "SYN packets for existing connections"

	::={tcpv4SynExisting 1}

tcpv4SynExistingMom	OBJECT-TYPE
	SYNTAX	 CounterBasedGauge64
	MAX-ACCESS read-only
	STATUS current
	DESCRIPTION "SYN packets for existing connections"

	::={tcpv4SynExisting 2}

tcpv4SynExistingMax	OBJECT-TYPE
	SYNTAX	 CounterBasedGauge64
	MAX-ACCESS read-only
	STATUS current
	DESCRIPTION "SYN packets for existing connections"

	::={tcpv4SynExisting 3}

tcpv4SegmentAllocFail	OBJECT IDENTIFIER ::={tcpv4 33}

tcpv4SegmentAllocFailVal	OBJECT-TYPE
	SYNTAX	 Counter64
	MAX-ACCESS read-only
	STATUS current
	DESCRIPTION "Segment allocation failures"

	::={tcpv4SegmentAllocFail 1}

tcpv4SegmentAllocFailMom	OBJECT-TYPE
	SYNTAX	 CounterBasedGauge64
	MAX-ACCESS read-only
	STATUS current
	DESCRIPTION "Segment allocation failures"

	::={tcpv4SegmentAllocFail 2}

tcpv4SegmentAllocFailMax	OBJECT-TYPE
	SYNTAX	 CounterBasedGauge64
	MAX-ACCESS read-only
	STATUS current
	DESCRIPTION "Segment allocation failures"

	::={tcpv4SegmentAllocFail 3}

tcpv4EnqueuedSegments	OBJECT IDENTIFIER ::={tcpv4 34}

tcpv4EnqueuedSegmentsVal	OBJECT-TYPE
	SYNTAX	 Counter64
	MAX-ACCESS read-only
	STATUS current
	DESCRIPTION "Enqueued segments"

	::={tcpv4EnqueuedSegments 1}

tcpv4EnqueuedSegmentsMom	OBJECT-TYPE
	SYNTAX	 CounterBasedGauge64
	MAX-ACCESS read-only
	STATUS current
	DESCRIPTION "Enqueued segments"

	::={tcpv4EnqueuedSegments 2}

tcpv4EnqueuedSegmentsMax	OBJECT-TYPE
	SYNTAX	 CounterBasedGauge64
	MAX-ACCESS read-only
	STATUS current
	DESCRIPTION "Enqueued segments"

	::={tcpv4EnqueuedSegments 3}

tcpv4DequeuedSegments	OBJECT IDENTIFIER ::={tcpv4 35}

tcpv4DequeuedSegmentsVal	OBJECT-TYPE
	SYNTAX	 Counter64
	MAX-ACCESS read-only
	STATUS current
	DESCRIPTION "Dequeued segments"

	::={tcpv4DequeuedSegments 1}

tcpv4DequeuedSegmentsMom	OBJECT-TYPE
	SYNTAX	 CounterBasedGauge64
	MAX-ACCESS read-only
	STATUS current
	DESCRIPTION "Dequeued segments"

	::={tcpv4DequeuedSegments 2}

tcpv4DequeuedSegmentsMax	OBJECT-TYPE
	SYNTAX	 CounterBasedGauge64
	MAX-ACCESS read-only
	STATUS current
	DESCRIPTION "Dequeued segments"

	::={tcpv4DequeuedSegments 3}

tcpv4DiscardedSegments	OBJECT IDENTIFIER ::={tcpv4 36}

tcpv4DiscardedSegmentsVal	OBJECT-TYPE
	SYNTAX	 Counter64
	MAX-ACCESS read-only
	STATUS current
	DESCRIPTION "Discarded segments"

	::={tcpv4DiscardedSegments 1}

tcpv4DiscardedSegmentsMom	OBJECT-TYPE
	SYNTAX	 CounterBasedGauge64
	MAX-ACCESS read-only
	STATUS current
	DESCRIPTION "Discarded segments"

	::={tcpv4DiscardedSegments 2}

tcpv4DiscardedSegmentsMax	OBJECT-TYPE
	SYNTAX	 CounterBasedGauge64
	MAX-ACCESS read-only
	STATUS current
	DESCRIPTION "Discarded segments"

	::={tcpv4DiscardedSegments 3}

tcpv4EmptyPackets	OBJECT IDENTIFIER ::={tcpv4 37}

tcpv4EmptyPacketsVal	OBJECT-TYPE
	SYNTAX	 Counter64
	MAX-ACCESS read-only
	STATUS current
	DESCRIPTION "Packets without payload"

	::={tcpv4EmptyPackets 1}

tcpv4EmptyPacketsMom	OBJECT-TYPE
	SYNTAX	 CounterBasedGauge64
	MAX-ACCESS read-only
	STATUS current
	DESCRIPTION "Packets without payload"

	::={tcpv4EmptyPackets 2}

tcpv4EmptyPacketsMax	OBJECT-TYPE
	SYNTAX	 CounterBasedGauge64
	MAX-ACCESS read-only
	STATUS current
	DESCRIPTION "Packets without payload"

	::={tcpv4EmptyPackets 3}

tcpv4OosPackets	OBJECT IDENTIFIER ::={tcpv4 38}

tcpv4OosPacketsVal	OBJECT-TYPE
	SYNTAX	 Counter64
	MAX-ACCESS read-only
	STATUS current
	DESCRIPTION "Out-of-sync packets"

	::={tcpv4OosPackets 1}

tcpv4OosPacketsMom	OBJECT-TYPE
	SYNTAX	 CounterBasedGauge64
	MAX-ACCESS read-only
	STATUS current
	DESCRIPTION "Out-of-sync packets"

	::={tcpv4OosPackets 2}

tcpv4OosPacketsMax	OBJECT-TYPE
	SYNTAX	 CounterBasedGauge64
	MAX-ACCESS read-only
	STATUS current
	DESCRIPTION "Out-of-sync packets"

	::={tcpv4OosPackets 3}

tcpv4OosBytes	OBJECT IDENTIFIER ::={tcpv4 39}

tcpv4OosBytesVal	OBJECT-TYPE
	SYNTAX	 Counter64
	MAX-ACCESS read-only
	STATUS current
	DESCRIPTION "Out-of-sync bytes"

	::={tcpv4OosBytes 1}

tcpv4OosBytesMom	OBJECT-TYPE
	SYNTAX	 CounterBasedGauge64
	MAX-ACCESS read-only
	STATUS current
	DESCRIPTION "Out-of-sync bytes"

	::={tcpv4OosBytes 2}

tcpv4OosBytesMax	OBJECT-TYPE
	SYNTAX	 CounterBasedGauge64
	MAX-ACCESS read-only
	STATUS current
	DESCRIPTION "Out-of-sync bytes"

	::={tcpv4OosBytes 3}

tcpv4Retransmits	OBJECT IDENTIFIER ::={tcpv4 40}

tcpv4RetransmitsVal	OBJECT-TYPE
	SYNTAX	 Counter64
	MAX-ACCESS read-only
	STATUS current
	DESCRIPTION "Retransmitted packets"

	::={tcpv4Retransmits 1}

tcpv4RetransmitsMom	OBJECT-TYPE
	SYNTAX	 CounterBasedGauge64
	MAX-ACCESS read-only
	STATUS current
	DESCRIPTION "Retransmitted packets"

	::={tcpv4Retransmits 2}

tcpv4RetransmitsMax	OBJECT-TYPE
	SYNTAX	 CounterBasedGauge64
	MAX-ACCESS read-only
	STATUS current
	DESCRIPTION "Retransmitted packets"

	::={tcpv4Retransmits 3}

tcpv4Cwr	OBJECT IDENTIFIER ::={tcpv4 41}

tcpv4CwrVal	OBJECT-TYPE
	SYNTAX	 Counter64
	MAX-ACCESS read-only
	STATUS current
	DESCRIPTION "Congestion Window Reduced Packets"

	::={tcpv4Cwr 1}

tcpv4CwrMom	OBJECT-TYPE
	SYNTAX	 CounterBasedGauge64
	MAX-ACCESS read-only
	STATUS current
	DESCRIPTION "Congestion Window Reduced Packets"

	::={tcpv4Cwr 2}

tcpv4CwrMax	OBJECT-TYPE
	SYNTAX	 CounterBasedGauge64
	MAX-ACCESS read-only
	STATUS current
	DESCRIPTION "Congestion Window Reduced Packets"

	::={tcpv4Cwr 3}

tcpv4Ecne	OBJECT IDENTIFIER ::={tcpv4 42}

tcpv4EcneVal	OBJECT-TYPE
	SYNTAX	 Counter64
	MAX-ACCESS read-only
	STATUS current
	DESCRIPTION "Explicit Congestion Notification Echo Packets"

	::={tcpv4Ecne 1}

tcpv4EcneMom	OBJECT-TYPE
	SYNTAX	 CounterBasedGauge64
	MAX-ACCESS read-only
	STATUS current
	DESCRIPTION "Explicit Congestion Notification Echo Packets"

	::={tcpv4Ecne 2}

tcpv4EcneMax	OBJECT-TYPE
	SYNTAX	 CounterBasedGauge64
	MAX-ACCESS read-only
	STATUS current
	DESCRIPTION "Explicit Congestion Notification Echo Packets"

	::={tcpv4Ecne 3}

tcpv4SimOpen	OBJECT IDENTIFIER ::={tcpv4 43}

tcpv4SimOpenVal	OBJECT-TYPE
	SYNTAX	 Counter64
	MAX-ACCESS read-only
	STATUS current
	DESCRIPTION "Simultaneous Open"

	::={tcpv4SimOpen 1}

tcpv4SimOpenMom	OBJECT-TYPE
	SYNTAX	 CounterBasedGauge64
	MAX-ACCESS read-only
	STATUS current
	DESCRIPTION "Simultaneous Open"

	::={tcpv4SimOpen 2}

tcpv4SimOpenMax	OBJECT-TYPE
	SYNTAX	 CounterBasedGauge64
	MAX-ACCESS read-only
	STATUS current
	DESCRIPTION "Simultaneous Open"

	::={tcpv4SimOpen 3}

tcpv6	OBJECT IDENTIFIER ::={sysdiag 127}

tcpv6Packets	OBJECT IDENTIFIER ::={tcpv6 1}

tcpv6PacketsVal	OBJECT-TYPE
	SYNTAX	 Counter64
	MAX-ACCESS read-only
	STATUS current
	DESCRIPTION "RX packets"

	::={tcpv6Packets 1}

tcpv6PacketsMom	OBJECT-TYPE
	SYNTAX	 CounterBasedGauge64
	MAX-ACCESS read-only
	STATUS current
	DESCRIPTION "RX packets"

	::={tcpv6Packets 2}

tcpv6PacketsMax	OBJECT-TYPE
	SYNTAX	 CounterBasedGauge64
	MAX-ACCESS read-only
	STATUS current
	DESCRIPTION "RX packets"

	::={tcpv6Packets 3}

tcpv6Bytes	OBJECT IDENTIFIER ::={tcpv6 2}

tcpv6BytesVal	OBJECT-TYPE
	SYNTAX	 Counter64
	MAX-ACCESS read-only
	STATUS current
	DESCRIPTION "RX bytes"

	::={tcpv6Bytes 1}

tcpv6BytesMom	OBJECT-TYPE
	SYNTAX	 CounterBasedGauge64
	MAX-ACCESS read-only
	STATUS current
	DESCRIPTION "RX bytes"

	::={tcpv6Bytes 2}

tcpv6BytesMax	OBJECT-TYPE
	SYNTAX	 CounterBasedGauge64
	MAX-ACCESS read-only
	STATUS current
	DESCRIPTION "RX bytes"

	::={tcpv6Bytes 3}

tcpv6CreateAttempts	OBJECT IDENTIFIER ::={tcpv6 4}

tcpv6CreateAttemptsVal	OBJECT-TYPE
	SYNTAX	 Counter64
	MAX-ACCESS read-only
	STATUS current
	DESCRIPTION "Connection create attempts"

	::={tcpv6CreateAttempts 1}

tcpv6CreateAttemptsMom	OBJECT-TYPE
	SYNTAX	 CounterBasedGauge64
	MAX-ACCESS read-only
	STATUS current
	DESCRIPTION "Connection create attempts"

	::={tcpv6CreateAttempts 2}

tcpv6CreateAttemptsMax	OBJECT-TYPE
	SYNTAX	 CounterBasedGauge64
	MAX-ACCESS read-only
	STATUS current
	DESCRIPTION "Connection create attempts"

	::={tcpv6CreateAttempts 3}

tcpv6Created	OBJECT IDENTIFIER ::={tcpv6 5}

tcpv6CreatedVal	OBJECT-TYPE
	SYNTAX	 Counter64
	MAX-ACCESS read-only
	STATUS current
	DESCRIPTION "Connections created"

	::={tcpv6Created 1}

tcpv6CreatedMom	OBJECT-TYPE
	SYNTAX	 CounterBasedGauge64
	MAX-ACCESS read-only
	STATUS current
	DESCRIPTION "Connections created"

	::={tcpv6Created 2}

tcpv6CreatedMax	OBJECT-TYPE
	SYNTAX	 CounterBasedGauge64
	MAX-ACCESS read-only
	STATUS current
	DESCRIPTION "Connections created"

	::={tcpv6Created 3}

tcpv6RefusedRuleset	OBJECT IDENTIFIER ::={tcpv6 6}

tcpv6RefusedRulesetVal	OBJECT-TYPE
	SYNTAX	 Counter64
	MAX-ACCESS read-only
	STATUS current
	DESCRIPTION "Refused (ruleset)"

	::={tcpv6RefusedRuleset 1}

tcpv6RefusedRulesetMom	OBJECT-TYPE
	SYNTAX	 CounterBasedGauge64
	MAX-ACCESS read-only
	STATUS current
	DESCRIPTION "Refused (ruleset)"

	::={tcpv6RefusedRuleset 2}

tcpv6RefusedRulesetMax	OBJECT-TYPE
	SYNTAX	 CounterBasedGauge64
	MAX-ACCESS read-only
	STATUS current
	DESCRIPTION "Refused (ruleset)"

	::={tcpv6RefusedRuleset 3}

tcpv6RefusedShort	OBJECT IDENTIFIER ::={tcpv6 7}

tcpv6RefusedShortVal	OBJECT-TYPE
	SYNTAX	 Counter64
	MAX-ACCESS read-only
	STATUS current
	DESCRIPTION "Refused (short)"

	::={tcpv6RefusedShort 1}

tcpv6RefusedShortMom	OBJECT-TYPE
	SYNTAX	 CounterBasedGauge64
	MAX-ACCESS read-only
	STATUS current
	DESCRIPTION "Refused (short)"

	::={tcpv6RefusedShort 2}

tcpv6RefusedShortMax	OBJECT-TYPE
	SYNTAX	 CounterBasedGauge64
	MAX-ACCESS read-only
	STATUS current
	DESCRIPTION "Refused (short)"

	::={tcpv6RefusedShort 3}

tcpv6RefusedBroadcast	OBJECT IDENTIFIER ::={tcpv6 8}

tcpv6RefusedBroadcastVal	OBJECT-TYPE
	SYNTAX	 Counter64
	MAX-ACCESS read-only
	STATUS current
	DESCRIPTION "Refused (broadcast)"

	::={tcpv6RefusedBroadcast 1}

tcpv6RefusedBroadcastMom	OBJECT-TYPE
	SYNTAX	 CounterBasedGauge64
	MAX-ACCESS read-only
	STATUS current
	DESCRIPTION "Refused (broadcast)"

	::={tcpv6RefusedBroadcast 2}

tcpv6RefusedBroadcastMax	OBJECT-TYPE
	SYNTAX	 CounterBasedGauge64
	MAX-ACCESS read-only
	STATUS current
	DESCRIPTION "Refused (broadcast)"

	::={tcpv6RefusedBroadcast 3}

tcpv6RefusedOffset	OBJECT IDENTIFIER ::={tcpv6 9}

tcpv6RefusedOffsetVal	OBJECT-TYPE
	SYNTAX	 Counter64
	MAX-ACCESS read-only
	STATUS current
	DESCRIPTION "Refused (offset)"

	::={tcpv6RefusedOffset 1}

tcpv6RefusedOffsetMom	OBJECT-TYPE
	SYNTAX	 CounterBasedGauge64
	MAX-ACCESS read-only
	STATUS current
	DESCRIPTION "Refused (offset)"

	::={tcpv6RefusedOffset 2}

tcpv6RefusedOffsetMax	OBJECT-TYPE
	SYNTAX	 CounterBasedGauge64
	MAX-ACCESS read-only
	STATUS current
	DESCRIPTION "Refused (offset)"

	::={tcpv6RefusedOffset 3}

tcpv6Rejected	OBJECT IDENTIFIER ::={tcpv6 10}

tcpv6RejectedVal	OBJECT-TYPE
	SYNTAX	 Counter64
	MAX-ACCESS read-only
	STATUS current
	DESCRIPTION "Rejected packets"

	::={tcpv6Rejected 1}

tcpv6RejectedMom	OBJECT-TYPE
	SYNTAX	 CounterBasedGauge64
	MAX-ACCESS read-only
	STATUS current
	DESCRIPTION "Rejected packets"

	::={tcpv6Rejected 2}

tcpv6RejectedMax	OBJECT-TYPE
	SYNTAX	 CounterBasedGauge64
	MAX-ACCESS read-only
	STATUS current
	DESCRIPTION "Rejected packets"

	::={tcpv6Rejected 3}

tcpv6Lostsync	OBJECT IDENTIFIER ::={tcpv6 12}

tcpv6LostsyncVal	OBJECT-TYPE
	SYNTAX	 CounterBasedGauge64
	MAX-ACCESS read-only
	STATUS current
	DESCRIPTION "Out-of-sync connections"

	::={tcpv6Lostsync 1}

tcpv6LostsyncMax	OBJECT-TYPE
	SYNTAX	 CounterBasedGauge64
	MAX-ACCESS read-only
	STATUS current
	DESCRIPTION "Out-of-sync connections"

	::={tcpv6Lostsync 3}

tcpv6UntrackedPackets	OBJECT IDENTIFIER ::={tcpv6 13}

tcpv6UntrackedPacketsVal	OBJECT-TYPE
	SYNTAX	 Counter64
	MAX-ACCESS read-only
	STATUS current
	DESCRIPTION "Untracked packets"

	::={tcpv6UntrackedPackets 1}

tcpv6UntrackedPacketsMom	OBJECT-TYPE
	SYNTAX	 CounterBasedGauge64
	MAX-ACCESS read-only
	STATUS current
	DESCRIPTION "Untracked packets"

	::={tcpv6UntrackedPackets 2}

tcpv6UntrackedPacketsMax	OBJECT-TYPE
	SYNTAX	 CounterBasedGauge64
	MAX-ACCESS read-only
	STATUS current
	DESCRIPTION "Untracked packets"

	::={tcpv6UntrackedPackets 3}

tcpv6GoodputPackets	OBJECT IDENTIFIER ::={tcpv6 14}

tcpv6GoodputPacketsVal	OBJECT-TYPE
	SYNTAX	 Counter64
	MAX-ACCESS read-only
	STATUS current
	DESCRIPTION "Goodput packets"

	::={tcpv6GoodputPackets 1}

tcpv6GoodputPacketsMom	OBJECT-TYPE
	SYNTAX	 CounterBasedGauge64
	MAX-ACCESS read-only
	STATUS current
	DESCRIPTION "Goodput packets"

	::={tcpv6GoodputPackets 2}

tcpv6GoodputPacketsMax	OBJECT-TYPE
	SYNTAX	 CounterBasedGauge64
	MAX-ACCESS read-only
	STATUS current
	DESCRIPTION "Goodput packets"

	::={tcpv6GoodputPackets 3}

tcpv6GoodputBytes	OBJECT IDENTIFIER ::={tcpv6 15}

tcpv6GoodputBytesVal	OBJECT-TYPE
	SYNTAX	 Counter64
	MAX-ACCESS read-only
	STATUS current
	DESCRIPTION "Goodput bytes"

	::={tcpv6GoodputBytes 1}

tcpv6GoodputBytesMom	OBJECT-TYPE
	SYNTAX	 CounterBasedGauge64
	MAX-ACCESS read-only
	STATUS current
	DESCRIPTION "Goodput bytes"

	::={tcpv6GoodputBytes 2}

tcpv6GoodputBytesMax	OBJECT-TYPE
	SYNTAX	 CounterBasedGauge64
	MAX-ACCESS read-only
	STATUS current
	DESCRIPTION "Goodput bytes"

	::={tcpv6GoodputBytes 3}

tcpv6Segments	OBJECT IDENTIFIER ::={tcpv6 16}

tcpv6SegmentsVal	OBJECT-TYPE
	SYNTAX	 CounterBasedGauge64
	MAX-ACCESS read-only
	STATUS current
	DESCRIPTION "Saved segments"

	::={tcpv6Segments 1}

tcpv6SegmentsMax	OBJECT-TYPE
	SYNTAX	 CounterBasedGauge64
	MAX-ACCESS read-only
	STATUS current
	DESCRIPTION "Saved segments"

	::={tcpv6Segments 3}

tcpv6SegmentsPayload	OBJECT IDENTIFIER ::={tcpv6 17}

tcpv6SegmentsPayloadVal	OBJECT-TYPE
	SYNTAX	 CounterBasedGauge64
	MAX-ACCESS read-only
	STATUS current
	DESCRIPTION "Saved segments with payload"

	::={tcpv6SegmentsPayload 1}

tcpv6SegmentsPayloadMax	OBJECT-TYPE
	SYNTAX	 CounterBasedGauge64
	MAX-ACCESS read-only
	STATUS current
	DESCRIPTION "Saved segments with payload"

	::={tcpv6SegmentsPayload 3}

tcpv6SegmentsDropped	OBJECT IDENTIFIER ::={tcpv6 18}

tcpv6SegmentsDroppedVal	OBJECT-TYPE
	SYNTAX	 Counter64
	MAX-ACCESS read-only
	STATUS current
	DESCRIPTION "Ignored segments"

	::={tcpv6SegmentsDropped 1}

tcpv6SegmentsDroppedMom	OBJECT-TYPE
	SYNTAX	 CounterBasedGauge64
	MAX-ACCESS read-only
	STATUS current
	DESCRIPTION "Ignored segments"

	::={tcpv6SegmentsDropped 2}

tcpv6SegmentsDroppedMax	OBJECT-TYPE
	SYNTAX	 CounterBasedGauge64
	MAX-ACCESS read-only
	STATUS current
	DESCRIPTION "Ignored segments"

	::={tcpv6SegmentsDropped 3}

tcpv6PacketAllocFail	OBJECT IDENTIFIER ::={tcpv6 19}

tcpv6PacketAllocFailVal	OBJECT-TYPE
	SYNTAX	 Counter64
	MAX-ACCESS read-only
	STATUS current
	DESCRIPTION "Packet allocation failures"

	::={tcpv6PacketAllocFail 1}

tcpv6PacketAllocFailMom	OBJECT-TYPE
	SYNTAX	 CounterBasedGauge64
	MAX-ACCESS read-only
	STATUS current
	DESCRIPTION "Packet allocation failures"

	::={tcpv6PacketAllocFail 2}

tcpv6PacketAllocFailMax	OBJECT-TYPE
	SYNTAX	 CounterBasedGauge64
	MAX-ACCESS read-only
	STATUS current
	DESCRIPTION "Packet allocation failures"

	::={tcpv6PacketAllocFail 3}

tcpv6UntrackedGoodput	OBJECT IDENTIFIER ::={tcpv6 23}

tcpv6UntrackedGoodputVal	OBJECT-TYPE
	SYNTAX	 Counter64
	MAX-ACCESS read-only
	STATUS current
	DESCRIPTION "Untracked bytes (goodput)"

	::={tcpv6UntrackedGoodput 1}

tcpv6UntrackedGoodputMom	OBJECT-TYPE
	SYNTAX	 CounterBasedGauge64
	MAX-ACCESS read-only
	STATUS current
	DESCRIPTION "Untracked bytes (goodput)"

	::={tcpv6UntrackedGoodput 2}

tcpv6UntrackedGoodputMax	OBJECT-TYPE
	SYNTAX	 CounterBasedGauge64
	MAX-ACCESS read-only
	STATUS current
	DESCRIPTION "Untracked bytes (goodput)"

	::={tcpv6UntrackedGoodput 3}

tcpv6UntrackedBytes	OBJECT IDENTIFIER ::={tcpv6 24}

tcpv6UntrackedBytesVal	OBJECT-TYPE
	SYNTAX	 Counter64
	MAX-ACCESS read-only
	STATUS current
	DESCRIPTION "Untracked bytes"

	::={tcpv6UntrackedBytes 1}

tcpv6UntrackedBytesMom	OBJECT-TYPE
	SYNTAX	 CounterBasedGauge64
	MAX-ACCESS read-only
	STATUS current
	DESCRIPTION "Untracked bytes"

	::={tcpv6UntrackedBytes 2}

tcpv6UntrackedBytesMax	OBJECT-TYPE
	SYNTAX	 CounterBasedGauge64
	MAX-ACCESS read-only
	STATUS current
	DESCRIPTION "Untracked bytes"

	::={tcpv6UntrackedBytes 3}

tcpv6CorruptOptions	OBJECT IDENTIFIER ::={tcpv6 25}

tcpv6CorruptOptionsVal	OBJECT-TYPE
	SYNTAX	 Counter64
	MAX-ACCESS read-only
	STATUS current
	DESCRIPTION "Packets with corrupt options"

	::={tcpv6CorruptOptions 1}

tcpv6CorruptOptionsMom	OBJECT-TYPE
	SYNTAX	 CounterBasedGauge64
	MAX-ACCESS read-only
	STATUS current
	DESCRIPTION "Packets with corrupt options"

	::={tcpv6CorruptOptions 2}

tcpv6CorruptOptionsMax	OBJECT-TYPE
	SYNTAX	 CounterBasedGauge64
	MAX-ACCESS read-only
	STATUS current
	DESCRIPTION "Packets with corrupt options"

	::={tcpv6CorruptOptions 3}

tcpv6CorruptConn	OBJECT IDENTIFIER ::={tcpv6 26}

tcpv6CorruptConnVal	OBJECT-TYPE
	SYNTAX	 Counter64
	MAX-ACCESS read-only
	STATUS current
	DESCRIPTION "Packets with corrupt conn"

	::={tcpv6CorruptConn 1}

tcpv6CorruptConnMom	OBJECT-TYPE
	SYNTAX	 CounterBasedGauge64
	MAX-ACCESS read-only
	STATUS current
	DESCRIPTION "Packets with corrupt conn"

	::={tcpv6CorruptConn 2}

tcpv6CorruptConnMax	OBJECT-TYPE
	SYNTAX	 CounterBasedGauge64
	MAX-ACCESS read-only
	STATUS current
	DESCRIPTION "Packets with corrupt conn"

	::={tcpv6CorruptConn 3}

tcpv6SegmentedConnections	OBJECT IDENTIFIER ::={tcpv6 27}

tcpv6SegmentedConnectionsVal	OBJECT-TYPE
	SYNTAX	 CounterBasedGauge64
	MAX-ACCESS read-only
	STATUS current
	DESCRIPTION "Connections with segments"

	::={tcpv6SegmentedConnections 1}

tcpv6SegmentedConnectionsMax	OBJECT-TYPE
	SYNTAX	 CounterBasedGauge64
	MAX-ACCESS read-only
	STATUS current
	DESCRIPTION "Connections with segments"

	::={tcpv6SegmentedConnections 3}

tcpv6OutOfWindowPackets	OBJECT IDENTIFIER ::={tcpv6 28}

tcpv6OutOfWindowPacketsVal	OBJECT-TYPE
	SYNTAX	 Counter64
	MAX-ACCESS read-only
	STATUS current
	DESCRIPTION "Out of window packets (ignored)"

	::={tcpv6OutOfWindowPackets 1}

tcpv6OutOfWindowPacketsMom	OBJECT-TYPE
	SYNTAX	 CounterBasedGauge64
	MAX-ACCESS read-only
	STATUS current
	DESCRIPTION "Out of window packets (ignored)"

	::={tcpv6OutOfWindowPackets 2}

tcpv6OutOfWindowPacketsMax	OBJECT-TYPE
	SYNTAX	 CounterBasedGauge64
	MAX-ACCESS read-only
	STATUS current
	DESCRIPTION "Out of window packets (ignored)"

	::={tcpv6OutOfWindowPackets 3}

tcpv6RefusedFilter	OBJECT IDENTIFIER ::={tcpv6 29}

tcpv6RefusedFilterVal	OBJECT-TYPE
	SYNTAX	 Counter64
	MAX-ACCESS read-only
	STATUS current
	DESCRIPTION "Packets refused by lowlevel filter"

	::={tcpv6RefusedFilter 1}

tcpv6RefusedFilterMom	OBJECT-TYPE
	SYNTAX	 CounterBasedGauge64
	MAX-ACCESS read-only
	STATUS current
	DESCRIPTION "Packets refused by lowlevel filter"

	::={tcpv6RefusedFilter 2}

tcpv6RefusedFilterMax	OBJECT-TYPE
	SYNTAX	 CounterBasedGauge64
	MAX-ACCESS read-only
	STATUS current
	DESCRIPTION "Packets refused by lowlevel filter"

	::={tcpv6RefusedFilter 3}

tcpv6SynExisting	OBJECT IDENTIFIER ::={tcpv6 32}

tcpv6SynExistingVal	OBJECT-TYPE
	SYNTAX	 Counter64
	MAX-ACCESS read-only
	STATUS current
	DESCRIPTION "SYN packets for existing connections"

	::={tcpv6SynExisting 1}

tcpv6SynExistingMom	OBJECT-TYPE
	SYNTAX	 CounterBasedGauge64
	MAX-ACCESS read-only
	STATUS current
	DESCRIPTION "SYN packets for existing connections"

	::={tcpv6SynExisting 2}

tcpv6SynExistingMax	OBJECT-TYPE
	SYNTAX	 CounterBasedGauge64
	MAX-ACCESS read-only
	STATUS current
	DESCRIPTION "SYN packets for existing connections"

	::={tcpv6SynExisting 3}

tcpv6SegmentAllocFail	OBJECT IDENTIFIER ::={tcpv6 33}

tcpv6SegmentAllocFailVal	OBJECT-TYPE
	SYNTAX	 Counter64
	MAX-ACCESS read-only
	STATUS current
	DESCRIPTION "Segment allocation failures"

	::={tcpv6SegmentAllocFail 1}

tcpv6SegmentAllocFailMom	OBJECT-TYPE
	SYNTAX	 CounterBasedGauge64
	MAX-ACCESS read-only
	STATUS current
	DESCRIPTION "Segment allocation failures"

	::={tcpv6SegmentAllocFail 2}

tcpv6SegmentAllocFailMax	OBJECT-TYPE
	SYNTAX	 CounterBasedGauge64
	MAX-ACCESS read-only
	STATUS current
	DESCRIPTION "Segment allocation failures"

	::={tcpv6SegmentAllocFail 3}

tcpv6EnqueuedSegments	OBJECT IDENTIFIER ::={tcpv6 34}

tcpv6EnqueuedSegmentsVal	OBJECT-TYPE
	SYNTAX	 Counter64
	MAX-ACCESS read-only
	STATUS current
	DESCRIPTION "Enqueued segments"

	::={tcpv6EnqueuedSegments 1}

tcpv6EnqueuedSegmentsMom	OBJECT-TYPE
	SYNTAX	 CounterBasedGauge64
	MAX-ACCESS read-only
	STATUS current
	DESCRIPTION "Enqueued segments"

	::={tcpv6EnqueuedSegments 2}

tcpv6EnqueuedSegmentsMax	OBJECT-TYPE
	SYNTAX	 CounterBasedGauge64
	MAX-ACCESS read-only
	STATUS current
	DESCRIPTION "Enqueued segments"

	::={tcpv6EnqueuedSegments 3}

tcpv6DequeuedSegments	OBJECT IDENTIFIER ::={tcpv6 35}

tcpv6DequeuedSegmentsVal	OBJECT-TYPE
	SYNTAX	 Counter64
	MAX-ACCESS read-only
	STATUS current
	DESCRIPTION "Dequeued segments"

	::={tcpv6DequeuedSegments 1}

tcpv6DequeuedSegmentsMom	OBJECT-TYPE
	SYNTAX	 CounterBasedGauge64
	MAX-ACCESS read-only
	STATUS current
	DESCRIPTION "Dequeued segments"

	::={tcpv6DequeuedSegments 2}

tcpv6DequeuedSegmentsMax	OBJECT-TYPE
	SYNTAX	 CounterBasedGauge64
	MAX-ACCESS read-only
	STATUS current
	DESCRIPTION "Dequeued segments"

	::={tcpv6DequeuedSegments 3}

tcpv6DiscardedSegments	OBJECT IDENTIFIER ::={tcpv6 36}

tcpv6DiscardedSegmentsVal	OBJECT-TYPE
	SYNTAX	 Counter64
	MAX-ACCESS read-only
	STATUS current
	DESCRIPTION "Discarded segments"

	::={tcpv6DiscardedSegments 1}

tcpv6DiscardedSegmentsMom	OBJECT-TYPE
	SYNTAX	 CounterBasedGauge64
	MAX-ACCESS read-only
	STATUS current
	DESCRIPTION "Discarded segments"

	::={tcpv6DiscardedSegments 2}

tcpv6DiscardedSegmentsMax	OBJECT-TYPE
	SYNTAX	 CounterBasedGauge64
	MAX-ACCESS read-only
	STATUS current
	DESCRIPTION "Discarded segments"

	::={tcpv6DiscardedSegments 3}

tcpv6EmptyPackets	OBJECT IDENTIFIER ::={tcpv6 37}

tcpv6EmptyPacketsVal	OBJECT-TYPE
	SYNTAX	 Counter64
	MAX-ACCESS read-only
	STATUS current
	DESCRIPTION "Packets without payload"

	::={tcpv6EmptyPackets 1}

tcpv6EmptyPacketsMom	OBJECT-TYPE
	SYNTAX	 CounterBasedGauge64
	MAX-ACCESS read-only
	STATUS current
	DESCRIPTION "Packets without payload"

	::={tcpv6EmptyPackets 2}

tcpv6EmptyPacketsMax	OBJECT-TYPE
	SYNTAX	 CounterBasedGauge64
	MAX-ACCESS read-only
	STATUS current
	DESCRIPTION "Packets without payload"

	::={tcpv6EmptyPackets 3}

tcpv6OosPackets	OBJECT IDENTIFIER ::={tcpv6 38}

tcpv6OosPacketsVal	OBJECT-TYPE
	SYNTAX	 Counter64
	MAX-ACCESS read-only
	STATUS current
	DESCRIPTION "Out-of-sync packets"

	::={tcpv6OosPackets 1}

tcpv6OosPacketsMom	OBJECT-TYPE
	SYNTAX	 CounterBasedGauge64
	MAX-ACCESS read-only
	STATUS current
	DESCRIPTION "Out-of-sync packets"

	::={tcpv6OosPackets 2}

tcpv6OosPacketsMax	OBJECT-TYPE
	SYNTAX	 CounterBasedGauge64
	MAX-ACCESS read-only
	STATUS current
	DESCRIPTION "Out-of-sync packets"

	::={tcpv6OosPackets 3}

tcpv6OosBytes	OBJECT IDENTIFIER ::={tcpv6 39}

tcpv6OosBytesVal	OBJECT-TYPE
	SYNTAX	 Counter64
	MAX-ACCESS read-only
	STATUS current
	DESCRIPTION "Out-of-sync bytes"

	::={tcpv6OosBytes 1}

tcpv6OosBytesMom	OBJECT-TYPE
	SYNTAX	 CounterBasedGauge64
	MAX-ACCESS read-only
	STATUS current
	DESCRIPTION "Out-of-sync bytes"

	::={tcpv6OosBytes 2}

tcpv6OosBytesMax	OBJECT-TYPE
	SYNTAX	 CounterBasedGauge64
	MAX-ACCESS read-only
	STATUS current
	DESCRIPTION "Out-of-sync bytes"

	::={tcpv6OosBytes 3}

tcpv6Retransmits	OBJECT IDENTIFIER ::={tcpv6 40}

tcpv6RetransmitsVal	OBJECT-TYPE
	SYNTAX	 Counter64
	MAX-ACCESS read-only
	STATUS current
	DESCRIPTION "Retransmitted packets"

	::={tcpv6Retransmits 1}

tcpv6RetransmitsMom	OBJECT-TYPE
	SYNTAX	 CounterBasedGauge64
	MAX-ACCESS read-only
	STATUS current
	DESCRIPTION "Retransmitted packets"

	::={tcpv6Retransmits 2}

tcpv6RetransmitsMax	OBJECT-TYPE
	SYNTAX	 CounterBasedGauge64
	MAX-ACCESS read-only
	STATUS current
	DESCRIPTION "Retransmitted packets"

	::={tcpv6Retransmits 3}

tcpv6Cwr	OBJECT IDENTIFIER ::={tcpv6 41}

tcpv6CwrVal	OBJECT-TYPE
	SYNTAX	 Counter64
	MAX-ACCESS read-only
	STATUS current
	DESCRIPTION "Congestion Window Reduced Packets"

	::={tcpv6Cwr 1}

tcpv6CwrMom	OBJECT-TYPE
	SYNTAX	 CounterBasedGauge64
	MAX-ACCESS read-only
	STATUS current
	DESCRIPTION "Congestion Window Reduced Packets"

	::={tcpv6Cwr 2}

tcpv6CwrMax	OBJECT-TYPE
	SYNTAX	 CounterBasedGauge64
	MAX-ACCESS read-only
	STATUS current
	DESCRIPTION "Congestion Window Reduced Packets"

	::={tcpv6Cwr 3}

tcpv6Ecne	OBJECT IDENTIFIER ::={tcpv6 42}

tcpv6EcneVal	OBJECT-TYPE
	SYNTAX	 Counter64
	MAX-ACCESS read-only
	STATUS current
	DESCRIPTION "Explicit Congestion Notification Echo Packets"

	::={tcpv6Ecne 1}

tcpv6EcneMom	OBJECT-TYPE
	SYNTAX	 CounterBasedGauge64
	MAX-ACCESS read-only
	STATUS current
	DESCRIPTION "Explicit Congestion Notification Echo Packets"

	::={tcpv6Ecne 2}

tcpv6EcneMax	OBJECT-TYPE
	SYNTAX	 CounterBasedGauge64
	MAX-ACCESS read-only
	STATUS current
	DESCRIPTION "Explicit Congestion Notification Echo Packets"

	::={tcpv6Ecne 3}

tcpv6SimOpen	OBJECT IDENTIFIER ::={tcpv6 43}

tcpv6SimOpenVal	OBJECT-TYPE
	SYNTAX	 Counter64
	MAX-ACCESS read-only
	STATUS current
	DESCRIPTION "Simultaneous Open"

	::={tcpv6SimOpen 1}

tcpv6SimOpenMom	OBJECT-TYPE
	SYNTAX	 CounterBasedGauge64
	MAX-ACCESS read-only
	STATUS current
	DESCRIPTION "Simultaneous Open"

	::={tcpv6SimOpen 2}

tcpv6SimOpenMax	OBJECT-TYPE
	SYNTAX	 CounterBasedGauge64
	MAX-ACCESS read-only
	STATUS current
	DESCRIPTION "Simultaneous Open"

	::={tcpv6SimOpen 3}

connection	OBJECT IDENTIFIER ::={sysdiag 56}

connectionCount	OBJECT IDENTIFIER ::={connection 1}

connectionCountVal	OBJECT-TYPE
	SYNTAX	 CounterBasedGauge64
	MAX-ACCESS read-only
	STATUS current
	DESCRIPTION "Current count"

	::={connectionCount 1}

connectionCountMax	OBJECT-TYPE
	SYNTAX	 CounterBasedGauge64
	MAX-ACCESS read-only
	STATUS current
	DESCRIPTION "Current count"

	::={connectionCount 3}

connectionEstCount	OBJECT IDENTIFIER ::={connection 2}

connectionEstCountVal	OBJECT-TYPE
	SYNTAX	 CounterBasedGauge64
	MAX-ACCESS read-only
	STATUS current
	DESCRIPTION "Current established count"

	::={connectionEstCount 1}

connectionEstCountMax	OBJECT-TYPE
	SYNTAX	 CounterBasedGauge64
	MAX-ACCESS read-only
	STATUS current
	DESCRIPTION "Current established count"

	::={connectionEstCount 3}

connectionCreateAttemptsInbound	OBJECT IDENTIFIER ::={connection 3}

connectionCreateAttemptsInboundVal	OBJECT-TYPE
	SYNTAX	 Counter64
	MAX-ACCESS read-only
	STATUS current
	DESCRIPTION "Create attempts inbound"

	::={connectionCreateAttemptsInbound 1}

connectionCreateAttemptsInboundMom	OBJECT-TYPE
	SYNTAX	 CounterBasedGauge64
	MAX-ACCESS read-only
	STATUS current
	DESCRIPTION "Create attempts inbound"

	::={connectionCreateAttemptsInbound 2}

connectionCreateAttemptsInboundMax	OBJECT-TYPE
	SYNTAX	 CounterBasedGauge64
	MAX-ACCESS read-only
	STATUS current
	DESCRIPTION "Create attempts inbound"

	::={connectionCreateAttemptsInbound 3}

connectionCreateAttemptsOutbound	OBJECT IDENTIFIER ::={connection 4}

connectionCreateAttemptsOutboundVal	OBJECT-TYPE
	SYNTAX	 Counter64
	MAX-ACCESS read-only
	STATUS current
	DESCRIPTION "Create attempts outbound"

	::={connectionCreateAttemptsOutbound 1}

connectionCreateAttemptsOutboundMom	OBJECT-TYPE
	SYNTAX	 CounterBasedGauge64
	MAX-ACCESS read-only
	STATUS current
	DESCRIPTION "Create attempts outbound"

	::={connectionCreateAttemptsOutbound 2}

connectionCreateAttemptsOutboundMax	OBJECT-TYPE
	SYNTAX	 CounterBasedGauge64
	MAX-ACCESS read-only
	STATUS current
	DESCRIPTION "Create attempts outbound"

	::={connectionCreateAttemptsOutbound 3}

connectionRefusedProt	OBJECT IDENTIFIER ::={connection 5}

connectionRefusedProtVal	OBJECT-TYPE
	SYNTAX	 Counter64
	MAX-ACCESS read-only
	STATUS current
	DESCRIPTION "Attempts refused (connprot)"

	::={connectionRefusedProt 1}

connectionRefusedProtMom	OBJECT-TYPE
	SYNTAX	 CounterBasedGauge64
	MAX-ACCESS read-only
	STATUS current
	DESCRIPTION "Attempts refused (connprot)"

	::={connectionRefusedProt 2}

connectionRefusedProtMax	OBJECT-TYPE
	SYNTAX	 CounterBasedGauge64
	MAX-ACCESS read-only
	STATUS current
	DESCRIPTION "Attempts refused (connprot)"

	::={connectionRefusedProt 3}

connectionRefusedFull	OBJECT IDENTIFIER ::={connection 6}

connectionRefusedFullVal	OBJECT-TYPE
	SYNTAX	 Counter64
	MAX-ACCESS read-only
	STATUS current
	DESCRIPTION "Attempts refused (resources)"

	::={connectionRefusedFull 1}

connectionRefusedFullMom	OBJECT-TYPE
	SYNTAX	 CounterBasedGauge64
	MAX-ACCESS read-only
	STATUS current
	DESCRIPTION "Attempts refused (resources)"

	::={connectionRefusedFull 2}

connectionRefusedFullMax	OBJECT-TYPE
	SYNTAX	 CounterBasedGauge64
	MAX-ACCESS read-only
	STATUS current
	DESCRIPTION "Attempts refused (resources)"

	::={connectionRefusedFull 3}

connectionCreatedInbound	OBJECT IDENTIFIER ::={connection 7}

connectionCreatedInboundVal	OBJECT-TYPE
	SYNTAX	 Counter64
	MAX-ACCESS read-only
	STATUS current
	DESCRIPTION "Created inbound"

	::={connectionCreatedInbound 1}

connectionCreatedInboundMom	OBJECT-TYPE
	SYNTAX	 CounterBasedGauge64
	MAX-ACCESS read-only
	STATUS current
	DESCRIPTION "Created inbound"

	::={connectionCreatedInbound 2}

connectionCreatedInboundMax	OBJECT-TYPE
	SYNTAX	 CounterBasedGauge64
	MAX-ACCESS read-only
	STATUS current
	DESCRIPTION "Created inbound"

	::={connectionCreatedInbound 3}

connectionCreatedOutbound	OBJECT IDENTIFIER ::={connection 8}

connectionCreatedOutboundVal	OBJECT-TYPE
	SYNTAX	 Counter64
	MAX-ACCESS read-only
	STATUS current
	DESCRIPTION "Created outbound"

	::={connectionCreatedOutbound 1}

connectionCreatedOutboundMom	OBJECT-TYPE
	SYNTAX	 CounterBasedGauge64
	MAX-ACCESS read-only
	STATUS current
	DESCRIPTION "Created outbound"

	::={connectionCreatedOutbound 2}

connectionCreatedOutboundMax	OBJECT-TYPE
	SYNTAX	 CounterBasedGauge64
	MAX-ACCESS read-only
	STATUS current
	DESCRIPTION "Created outbound"

	::={connectionCreatedOutbound 3}

connectionLruAllocs	OBJECT IDENTIFIER ::={connection 9}

connectionLruAllocsVal	OBJECT-TYPE
	SYNTAX	 Counter64
	MAX-ACCESS read-only
	STATUS current
	DESCRIPTION "Connections allocated from LRU"

	::={connectionLruAllocs 1}

connectionLruAllocsMom	OBJECT-TYPE
	SYNTAX	 CounterBasedGauge64
	MAX-ACCESS read-only
	STATUS current
	DESCRIPTION "Connections allocated from LRU"

	::={connectionLruAllocs 2}

connectionLruAllocsMax	OBJECT-TYPE
	SYNTAX	 CounterBasedGauge64
	MAX-ACCESS read-only
	STATUS current
	DESCRIPTION "Connections allocated from LRU"

	::={connectionLruAllocs 3}

connectionLookups	OBJECT IDENTIFIER ::={connection 10}

connectionLookupsVal	OBJECT-TYPE
	SYNTAX	 Counter64
	MAX-ACCESS read-only
	STATUS current
	DESCRIPTION "Lookups"

	::={connectionLookups 1}

connectionLookupsMom	OBJECT-TYPE
	SYNTAX	 CounterBasedGauge64
	MAX-ACCESS read-only
	STATUS current
	DESCRIPTION "Lookups"

	::={connectionLookups 2}

connectionLookupsMax	OBJECT-TYPE
	SYNTAX	 CounterBasedGauge64
	MAX-ACCESS read-only
	STATUS current
	DESCRIPTION "Lookups"

	::={connectionLookups 3}

connectionEstablished	OBJECT IDENTIFIER ::={connection 11}

connectionEstablishedVal	OBJECT-TYPE
	SYNTAX	 Counter64
	MAX-ACCESS read-only
	STATUS current
	DESCRIPTION "Made established"

	::={connectionEstablished 1}

connectionEstablishedMom	OBJECT-TYPE
	SYNTAX	 CounterBasedGauge64
	MAX-ACCESS read-only
	STATUS current
	DESCRIPTION "Made established"

	::={connectionEstablished 2}

connectionEstablishedMax	OBJECT-TYPE
	SYNTAX	 CounterBasedGauge64
	MAX-ACCESS read-only
	STATUS current
	DESCRIPTION "Made established"

	::={connectionEstablished 3}

connectionUpdates	OBJECT IDENTIFIER ::={connection 12}

connectionUpdatesVal	OBJECT-TYPE
	SYNTAX	 Counter64
	MAX-ACCESS read-only
	STATUS current
	DESCRIPTION "Updates sent"

	::={connectionUpdates 1}

connectionUpdatesMom	OBJECT-TYPE
	SYNTAX	 CounterBasedGauge64
	MAX-ACCESS read-only
	STATUS current
	DESCRIPTION "Updates sent"

	::={connectionUpdates 2}

connectionUpdatesMax	OBJECT-TYPE
	SYNTAX	 CounterBasedGauge64
	MAX-ACCESS read-only
	STATUS current
	DESCRIPTION "Updates sent"

	::={connectionUpdates 3}

connectionTtlTimeouts	OBJECT IDENTIFIER ::={connection 13}

connectionTtlTimeoutsVal	OBJECT-TYPE
	SYNTAX	 Counter64
	MAX-ACCESS read-only
	STATUS current
	DESCRIPTION "TTL timeouts"

	::={connectionTtlTimeouts 1}

connectionTtlTimeoutsMom	OBJECT-TYPE
	SYNTAX	 CounterBasedGauge64
	MAX-ACCESS read-only
	STATUS current
	DESCRIPTION "TTL timeouts"

	::={connectionTtlTimeouts 2}

connectionTtlTimeoutsMax	OBJECT-TYPE
	SYNTAX	 CounterBasedGauge64
	MAX-ACCESS read-only
	STATUS current
	DESCRIPTION "TTL timeouts"

	::={connectionTtlTimeouts 3}

connectionProtEnables	OBJECT IDENTIFIER ::={connection 14}

connectionProtEnablesVal	OBJECT-TYPE
	SYNTAX	 Counter64
	MAX-ACCESS read-only
	STATUS current
	DESCRIPTION "Protection enabled"

	::={connectionProtEnables 1}

connectionProtEnablesMom	OBJECT-TYPE
	SYNTAX	 CounterBasedGauge64
	MAX-ACCESS read-only
	STATUS current
	DESCRIPTION "Protection enabled"

	::={connectionProtEnables 2}

connectionProtEnablesMax	OBJECT-TYPE
	SYNTAX	 CounterBasedGauge64
	MAX-ACCESS read-only
	STATUS current
	DESCRIPTION "Protection enabled"

	::={connectionProtEnables 3}

connectionNotFound	OBJECT IDENTIFIER ::={connection 15}

connectionNotFoundVal	OBJECT-TYPE
	SYNTAX	 Counter64
	MAX-ACCESS read-only
	STATUS current
	DESCRIPTION "Failed lookups"

	::={connectionNotFound 1}

connectionNotFoundMom	OBJECT-TYPE
	SYNTAX	 CounterBasedGauge64
	MAX-ACCESS read-only
	STATUS current
	DESCRIPTION "Failed lookups"

	::={connectionNotFound 2}

connectionNotFoundMax	OBJECT-TYPE
	SYNTAX	 CounterBasedGauge64
	MAX-ACCESS read-only
	STATUS current
	DESCRIPTION "Failed lookups"

	::={connectionNotFound 3}

connectionRefusedExisting	OBJECT IDENTIFIER ::={connection 18}

connectionRefusedExistingVal	OBJECT-TYPE
	SYNTAX	 Counter64
	MAX-ACCESS read-only
	STATUS current
	DESCRIPTION "Attempts refused (already existed)"

	::={connectionRefusedExisting 1}

connectionRefusedExistingMom	OBJECT-TYPE
	SYNTAX	 CounterBasedGauge64
	MAX-ACCESS read-only
	STATUS current
	DESCRIPTION "Attempts refused (already existed)"

	::={connectionRefusedExisting 2}

connectionRefusedExistingMax	OBJECT-TYPE
	SYNTAX	 CounterBasedGauge64
	MAX-ACCESS read-only
	STATUS current
	DESCRIPTION "Attempts refused (already existed)"

	::={connectionRefusedExisting 3}

connectionRefusedRuleset	OBJECT IDENTIFIER ::={connection 19}

connectionRefusedRulesetVal	OBJECT-TYPE
	SYNTAX	 Counter64
	MAX-ACCESS read-only
	STATUS current
	DESCRIPTION "Attempts refused (ruleset)"

	::={connectionRefusedRuleset 1}

connectionRefusedRulesetMom	OBJECT-TYPE
	SYNTAX	 CounterBasedGauge64
	MAX-ACCESS read-only
	STATUS current
	DESCRIPTION "Attempts refused (ruleset)"

	::={connectionRefusedRuleset 2}

connectionRefusedRulesetMax	OBJECT-TYPE
	SYNTAX	 CounterBasedGauge64
	MAX-ACCESS read-only
	STATUS current
	DESCRIPTION "Attempts refused (ruleset)"

	::={connectionRefusedRuleset 3}

connectionRedirected	OBJECT IDENTIFIER ::={connection 20}

connectionRedirectedVal	OBJECT-TYPE
	SYNTAX	 CounterBasedGauge64
	MAX-ACCESS read-only
	STATUS current
	DESCRIPTION "Redirected"

	::={connectionRedirected 1}

connectionRedirectedMax	OBJECT-TYPE
	SYNTAX	 CounterBasedGauge64
	MAX-ACCESS read-only
	STATUS current
	DESCRIPTION "Redirected"

	::={connectionRedirected 3}

connectionRedirectCollisions	OBJECT IDENTIFIER ::={connection 21}

connectionRedirectCollisionsVal	OBJECT-TYPE
	SYNTAX	 CounterBasedGauge64
	MAX-ACCESS read-only
	STATUS current
	DESCRIPTION "Refused redirects (collision)"

	::={connectionRedirectCollisions 1}

connectionRedirectCollisionsMax	OBJECT-TYPE
	SYNTAX	 CounterBasedGauge64
	MAX-ACCESS read-only
	STATUS current
	DESCRIPTION "Refused redirects (collision)"

	::={connectionRedirectCollisions 3}

connectionUnestablished	OBJECT IDENTIFIER ::={connection 24}

connectionUnestablishedVal	OBJECT-TYPE
	SYNTAX	 Counter64
	MAX-ACCESS read-only
	STATUS current
	DESCRIPTION "Made unestablished"

	::={connectionUnestablished 1}

connectionUnestablishedMom	OBJECT-TYPE
	SYNTAX	 CounterBasedGauge64
	MAX-ACCESS read-only
	STATUS current
	DESCRIPTION "Made unestablished"

	::={connectionUnestablished 2}

connectionUnestablishedMax	OBJECT-TYPE
	SYNTAX	 CounterBasedGauge64
	MAX-ACCESS read-only
	STATUS current
	DESCRIPTION "Made unestablished"

	::={connectionUnestablished 3}

connectionDestroyedEst	OBJECT IDENTIFIER ::={connection 25}

connectionDestroyedEstVal	OBJECT-TYPE
	SYNTAX	 CounterBasedGauge64
	MAX-ACCESS read-only
	STATUS current
	DESCRIPTION "Destroyed established"

	::={connectionDestroyedEst 1}

connectionDestroyedEstMax	OBJECT-TYPE
	SYNTAX	 CounterBasedGauge64
	MAX-ACCESS read-only
	STATUS current
	DESCRIPTION "Destroyed established"

	::={connectionDestroyedEst 3}

connectionInvalidRulesetUpdate	OBJECT IDENTIFIER ::={connection 26}

connectionInvalidRulesetUpdateVal	OBJECT-TYPE
	SYNTAX	 Counter64
	MAX-ACCESS read-only
	STATUS current
	DESCRIPTION "Updates with invalid ruleset"

	::={connectionInvalidRulesetUpdate 1}

connectionInvalidRulesetUpdateMom	OBJECT-TYPE
	SYNTAX	 CounterBasedGauge64
	MAX-ACCESS read-only
	STATUS current
	DESCRIPTION "Updates with invalid ruleset"

	::={connectionInvalidRulesetUpdate 2}

connectionInvalidRulesetUpdateMax	OBJECT-TYPE
	SYNTAX	 CounterBasedGauge64
	MAX-ACCESS read-only
	STATUS current
	DESCRIPTION "Updates with invalid ruleset"

	::={connectionInvalidRulesetUpdate 3}

connectionOrphaned	OBJECT IDENTIFIER ::={connection 27}

connectionOrphanedVal	OBJECT-TYPE
	SYNTAX	 CounterBasedGauge64
	MAX-ACCESS read-only
	STATUS current
	DESCRIPTION "Connections without timer"

	::={connectionOrphaned 1}

connectionOrphanedMax	OBJECT-TYPE
	SYNTAX	 CounterBasedGauge64
	MAX-ACCESS read-only
	STATUS current
	DESCRIPTION "Connections without timer"

	::={connectionOrphaned 3}

connectionFailureShuntPackets	OBJECT IDENTIFIER ::={connection 40}

connectionFailureShuntPacketsVal	OBJECT-TYPE
	SYNTAX	 Counter64
	MAX-ACCESS read-only
	STATUS current
	DESCRIPTION "Shunted packets (connection create failure)"

	::={connectionFailureShuntPackets 1}

connectionFailureShuntPacketsMom	OBJECT-TYPE
	SYNTAX	 CounterBasedGauge64
	MAX-ACCESS read-only
	STATUS current
	DESCRIPTION "Shunted packets (connection create failure)"

	::={connectionFailureShuntPackets 2}

connectionFailureShuntPacketsMax	OBJECT-TYPE
	SYNTAX	 CounterBasedGauge64
	MAX-ACCESS read-only
	STATUS current
	DESCRIPTION "Shunted packets (connection create failure)"

	::={connectionFailureShuntPackets 3}

connectionFailureShuntBytes	OBJECT IDENTIFIER ::={connection 41}

connectionFailureShuntBytesVal	OBJECT-TYPE
	SYNTAX	 Counter64
	MAX-ACCESS read-only
	STATUS current
	DESCRIPTION "Shunted bytes (connection create failure)"

	::={connectionFailureShuntBytes 1}

connectionFailureShuntBytesMom	OBJECT-TYPE
	SYNTAX	 CounterBasedGauge64
	MAX-ACCESS read-only
	STATUS current
	DESCRIPTION "Shunted bytes (connection create failure)"

	::={connectionFailureShuntBytes 2}

connectionFailureShuntBytesMax	OBJECT-TYPE
	SYNTAX	 CounterBasedGauge64
	MAX-ACCESS read-only
	STATUS current
	DESCRIPTION "Shunted bytes (connection create failure)"

	::={connectionFailureShuntBytes 3}

connsync	OBJECT IDENTIFIER ::={sysdiag 60}

connsyncSeenSnt	OBJECT IDENTIFIER ::={connsync 1}

connsyncSeenSntVal	OBJECT-TYPE
	SYNTAX	 Counter64
	MAX-ACCESS read-only
	STATUS current
	DESCRIPTION "Seen sent"

	::={connsyncSeenSnt 1}

connsyncSeenSntMom	OBJECT-TYPE
	SYNTAX	 CounterBasedGauge64
	MAX-ACCESS read-only
	STATUS current
	DESCRIPTION "Seen sent"

	::={connsyncSeenSnt 2}

connsyncSeenSntMax	OBJECT-TYPE
	SYNTAX	 CounterBasedGauge64
	MAX-ACCESS read-only
	STATUS current
	DESCRIPTION "Seen sent"

	::={connsyncSeenSnt 3}

connsyncSeenRcv	OBJECT IDENTIFIER ::={connsync 2}

connsyncSeenRcvVal	OBJECT-TYPE
	SYNTAX	 Counter64
	MAX-ACCESS read-only
	STATUS current
	DESCRIPTION "Seen received"

	::={connsyncSeenRcv 1}

connsyncSeenRcvMom	OBJECT-TYPE
	SYNTAX	 CounterBasedGauge64
	MAX-ACCESS read-only
	STATUS current
	DESCRIPTION "Seen received"

	::={connsyncSeenRcv 2}

connsyncSeenRcvMax	OBJECT-TYPE
	SYNTAX	 CounterBasedGauge64
	MAX-ACCESS read-only
	STATUS current
	DESCRIPTION "Seen received"

	::={connsyncSeenRcv 3}

connsyncUpdateSnt	OBJECT IDENTIFIER ::={connsync 3}

connsyncUpdateSntVal	OBJECT-TYPE
	SYNTAX	 Counter64
	MAX-ACCESS read-only
	STATUS current
	DESCRIPTION "Updates Sent"

	::={connsyncUpdateSnt 1}

connsyncUpdateSntMom	OBJECT-TYPE
	SYNTAX	 CounterBasedGauge64
	MAX-ACCESS read-only
	STATUS current
	DESCRIPTION "Updates Sent"

	::={connsyncUpdateSnt 2}

connsyncUpdateSntMax	OBJECT-TYPE
	SYNTAX	 CounterBasedGauge64
	MAX-ACCESS read-only
	STATUS current
	DESCRIPTION "Updates Sent"

	::={connsyncUpdateSnt 3}

connsyncSeenackRcv	OBJECT IDENTIFIER ::={connsync 4}

connsyncSeenackRcvVal	OBJECT-TYPE
	SYNTAX	 Counter64
	MAX-ACCESS read-only
	STATUS current
	DESCRIPTION "First updates received"

	::={connsyncSeenackRcv 1}

connsyncSeenackRcvMom	OBJECT-TYPE
	SYNTAX	 CounterBasedGauge64
	MAX-ACCESS read-only
	STATUS current
	DESCRIPTION "First updates received"

	::={connsyncSeenackRcv 2}

connsyncSeenackRcvMax	OBJECT-TYPE
	SYNTAX	 CounterBasedGauge64
	MAX-ACCESS read-only
	STATUS current
	DESCRIPTION "First updates received"

	::={connsyncSeenackRcv 3}

connsyncUpdateRcv	OBJECT IDENTIFIER ::={connsync 5}

connsyncUpdateRcvVal	OBJECT-TYPE
	SYNTAX	 Counter64
	MAX-ACCESS read-only
	STATUS current
	DESCRIPTION "Updates received"

	::={connsyncUpdateRcv 1}

connsyncUpdateRcvMom	OBJECT-TYPE
	SYNTAX	 CounterBasedGauge64
	MAX-ACCESS read-only
	STATUS current
	DESCRIPTION "Updates received"

	::={connsyncUpdateRcv 2}

connsyncUpdateRcvMax	OBJECT-TYPE
	SYNTAX	 CounterBasedGauge64
	MAX-ACCESS read-only
	STATUS current
	DESCRIPTION "Updates received"

	::={connsyncUpdateRcv 3}

connsyncUnknownUpdateRcv	OBJECT IDENTIFIER ::={connsync 6}

connsyncUnknownUpdateRcvVal	OBJECT-TYPE
	SYNTAX	 Counter64
	MAX-ACCESS read-only
	STATUS current
	DESCRIPTION "Updates for unknown connections received"

	::={connsyncUnknownUpdateRcv 1}

connsyncUnknownUpdateRcvMom	OBJECT-TYPE
	SYNTAX	 CounterBasedGauge64
	MAX-ACCESS read-only
	STATUS current
	DESCRIPTION "Updates for unknown connections received"

	::={connsyncUnknownUpdateRcv 2}

connsyncUnknownUpdateRcvMax	OBJECT-TYPE
	SYNTAX	 CounterBasedGauge64
	MAX-ACCESS read-only
	STATUS current
	DESCRIPTION "Updates for unknown connections received"

	::={connsyncUnknownUpdateRcv 3}

connsyncOutofsync	OBJECT IDENTIFIER ::={connsync 7}

connsyncOutofsyncVal	OBJECT-TYPE
	SYNTAX	 Counter64
	MAX-ACCESS read-only
	STATUS current
	DESCRIPTION "Out of syncs"

	::={connsyncOutofsync 1}

connsyncOutofsyncMom	OBJECT-TYPE
	SYNTAX	 CounterBasedGauge64
	MAX-ACCESS read-only
	STATUS current
	DESCRIPTION "Out of syncs"

	::={connsyncOutofsync 2}

connsyncOutofsyncMax	OBJECT-TYPE
	SYNTAX	 CounterBasedGauge64
	MAX-ACCESS read-only
	STATUS current
	DESCRIPTION "Out of syncs"

	::={connsyncOutofsync 3}

connsyncSynced	OBJECT IDENTIFIER ::={connsync 8}

connsyncSyncedVal	OBJECT-TYPE
	SYNTAX	 CounterBasedGauge64
	MAX-ACCESS read-only
	STATUS current
	DESCRIPTION "Connections actively syncing"

	::={connsyncSynced 1}

connsyncSyncedMax	OBJECT-TYPE
	SYNTAX	 CounterBasedGauge64
	MAX-ACCESS read-only
	STATUS current
	DESCRIPTION "Connections actively syncing"

	::={connsyncSynced 3}

connsyncDoubleSeen	OBJECT IDENTIFIER ::={connsync 9}

connsyncDoubleSeenVal	OBJECT-TYPE
	SYNTAX	 Counter64
	MAX-ACCESS read-only
	STATUS current
	DESCRIPTION "Double seen"

	::={connsyncDoubleSeen 1}

connsyncDoubleSeenMom	OBJECT-TYPE
	SYNTAX	 CounterBasedGauge64
	MAX-ACCESS read-only
	STATUS current
	DESCRIPTION "Double seen"

	::={connsyncDoubleSeen 2}

connsyncDoubleSeenMax	OBJECT-TYPE
	SYNTAX	 CounterBasedGauge64
	MAX-ACCESS read-only
	STATUS current
	DESCRIPTION "Double seen"

	::={connsyncDoubleSeen 3}

connsyncHelloRcv	OBJECT IDENTIFIER ::={connsync 10}

connsyncHelloRcvVal	OBJECT-TYPE
	SYNTAX	 Counter64
	MAX-ACCESS read-only
	STATUS current
	DESCRIPTION "Hello received"

	::={connsyncHelloRcv 1}

connsyncHelloRcvMom	OBJECT-TYPE
	SYNTAX	 CounterBasedGauge64
	MAX-ACCESS read-only
	STATUS current
	DESCRIPTION "Hello received"

	::={connsyncHelloRcv 2}

connsyncHelloRcvMax	OBJECT-TYPE
	SYNTAX	 CounterBasedGauge64
	MAX-ACCESS read-only
	STATUS current
	DESCRIPTION "Hello received"

	::={connsyncHelloRcv 3}

connsyncOutofsyncMissedRcv	OBJECT IDENTIFIER ::={connsync 11}

connsyncOutofsyncMissedRcvVal	OBJECT-TYPE
	SYNTAX	 Counter64
	MAX-ACCESS read-only
	STATUS current
	DESCRIPTION "Out of sync - missed rcv/late collision"

	::={connsyncOutofsyncMissedRcv 1}

connsyncOutofsyncMissedRcvMom	OBJECT-TYPE
	SYNTAX	 CounterBasedGauge64
	MAX-ACCESS read-only
	STATUS current
	DESCRIPTION "Out of sync - missed rcv/late collision"

	::={connsyncOutofsyncMissedRcv 2}

connsyncOutofsyncMissedRcvMax	OBJECT-TYPE
	SYNTAX	 CounterBasedGauge64
	MAX-ACCESS read-only
	STATUS current
	DESCRIPTION "Out of sync - missed rcv/late collision"

	::={connsyncOutofsyncMissedRcv 3}

connsyncOutofsyncCollision	OBJECT IDENTIFIER ::={connsync 12}

connsyncOutofsyncCollisionVal	OBJECT-TYPE
	SYNTAX	 Counter64
	MAX-ACCESS read-only
	STATUS current
	DESCRIPTION "Out of sync - collision"

	::={connsyncOutofsyncCollision 1}

connsyncOutofsyncCollisionMom	OBJECT-TYPE
	SYNTAX	 CounterBasedGauge64
	MAX-ACCESS read-only
	STATUS current
	DESCRIPTION "Out of sync - collision"

	::={connsyncOutofsyncCollision 2}

connsyncOutofsyncCollisionMax	OBJECT-TYPE
	SYNTAX	 CounterBasedGauge64
	MAX-ACCESS read-only
	STATUS current
	DESCRIPTION "Out of sync - collision"

	::={connsyncOutofsyncCollision 3}

connsyncBadAdler	OBJECT IDENTIFIER ::={connsync 13}

connsyncBadAdlerVal	OBJECT-TYPE
	SYNTAX	 Counter64
	MAX-ACCESS read-only
	STATUS current
	DESCRIPTION "Updates for mismatching ARM"

	::={connsyncBadAdler 1}

connsyncBadAdlerMom	OBJECT-TYPE
	SYNTAX	 CounterBasedGauge64
	MAX-ACCESS read-only
	STATUS current
	DESCRIPTION "Updates for mismatching ARM"

	::={connsyncBadAdler 2}

connsyncBadAdlerMax	OBJECT-TYPE
	SYNTAX	 CounterBasedGauge64
	MAX-ACCESS read-only
	STATUS current
	DESCRIPTION "Updates for mismatching ARM"

	::={connsyncBadAdler 3}

connsyncPktOverflow	OBJECT IDENTIFIER ::={connsync 14}

connsyncPktOverflowVal	OBJECT-TYPE
	SYNTAX	 Counter64
	MAX-ACCESS read-only
	STATUS current
	DESCRIPTION "Update packet overflow"

	::={connsyncPktOverflow 1}

connsyncPktOverflowMom	OBJECT-TYPE
	SYNTAX	 CounterBasedGauge64
	MAX-ACCESS read-only
	STATUS current
	DESCRIPTION "Update packet overflow"

	::={connsyncPktOverflow 2}

connsyncPktOverflowMax	OBJECT-TYPE
	SYNTAX	 CounterBasedGauge64
	MAX-ACCESS read-only
	STATUS current
	DESCRIPTION "Update packet overflow"

	::={connsyncPktOverflow 3}

connsyncCorruptPkt	OBJECT IDENTIFIER ::={connsync 15}

connsyncCorruptPktVal	OBJECT-TYPE
	SYNTAX	 Counter64
	MAX-ACCESS read-only
	STATUS current
	DESCRIPTION "Corrupt packet received"

	::={connsyncCorruptPkt 1}

connsyncCorruptPktMom	OBJECT-TYPE
	SYNTAX	 CounterBasedGauge64
	MAX-ACCESS read-only
	STATUS current
	DESCRIPTION "Corrupt packet received"

	::={connsyncCorruptPkt 2}

connsyncCorruptPktMax	OBJECT-TYPE
	SYNTAX	 CounterBasedGauge64
	MAX-ACCESS read-only
	STATUS current
	DESCRIPTION "Corrupt packet received"

	::={connsyncCorruptPkt 3}

connsyncConnNotfound	OBJECT IDENTIFIER ::={connsync 16}

connsyncConnNotfoundVal	OBJECT-TYPE
	SYNTAX	 Counter64
	MAX-ACCESS read-only
	STATUS current
	DESCRIPTION "Connection not found"

	::={connsyncConnNotfound 1}

connsyncConnNotfoundMom	OBJECT-TYPE
	SYNTAX	 CounterBasedGauge64
	MAX-ACCESS read-only
	STATUS current
	DESCRIPTION "Connection not found"

	::={connsyncConnNotfound 2}

connsyncConnNotfoundMax	OBJECT-TYPE
	SYNTAX	 CounterBasedGauge64
	MAX-ACCESS read-only
	STATUS current
	DESCRIPTION "Connection not found"

	::={connsyncConnNotfound 3}

connsyncBadVer	OBJECT IDENTIFIER ::={connsync 17}

connsyncBadVerVal	OBJECT-TYPE
	SYNTAX	 Counter64
	MAX-ACCESS read-only
	STATUS current
	DESCRIPTION "Received packets with incompatible version"

	::={connsyncBadVer 1}

connsyncBadVerMom	OBJECT-TYPE
	SYNTAX	 CounterBasedGauge64
	MAX-ACCESS read-only
	STATUS current
	DESCRIPTION "Received packets with incompatible version"

	::={connsyncBadVer 2}

connsyncBadVerMax	OBJECT-TYPE
	SYNTAX	 CounterBasedGauge64
	MAX-ACCESS read-only
	STATUS current
	DESCRIPTION "Received packets with incompatible version"

	::={connsyncBadVer 3}

connsyncBadType	OBJECT IDENTIFIER ::={connsync 18}

connsyncBadTypeVal	OBJECT-TYPE
	SYNTAX	 Counter64
	MAX-ACCESS read-only
	STATUS current
	DESCRIPTION "Received packets with incorrect ethernet type"

	::={connsyncBadType 1}

connsyncBadTypeMom	OBJECT-TYPE
	SYNTAX	 CounterBasedGauge64
	MAX-ACCESS read-only
	STATUS current
	DESCRIPTION "Received packets with incorrect ethernet type"

	::={connsyncBadType 2}

connsyncBadTypeMax	OBJECT-TYPE
	SYNTAX	 CounterBasedGauge64
	MAX-ACCESS read-only
	STATUS current
	DESCRIPTION "Received packets with incorrect ethernet type"

	::={connsyncBadType 3}

connsyncBadEngineid	OBJECT IDENTIFIER ::={connsync 19}

connsyncBadEngineidVal	OBJECT-TYPE
	SYNTAX	 Counter64
	MAX-ACCESS read-only
	STATUS current
	DESCRIPTION "Received packets with own engine-id"

	::={connsyncBadEngineid 1}

connsyncBadEngineidMom	OBJECT-TYPE
	SYNTAX	 CounterBasedGauge64
	MAX-ACCESS read-only
	STATUS current
	DESCRIPTION "Received packets with own engine-id"

	::={connsyncBadEngineid 2}

connsyncBadEngineidMax	OBJECT-TYPE
	SYNTAX	 CounterBasedGauge64
	MAX-ACCESS read-only
	STATUS current
	DESCRIPTION "Received packets with own engine-id"

	::={connsyncBadEngineid 3}

connsyncUdpSnt	OBJECT IDENTIFIER ::={connsync 20}

connsyncUdpSntVal	OBJECT-TYPE
	SYNTAX	 Counter64
	MAX-ACCESS read-only
	STATUS current
	DESCRIPTION "UDP sent"

	::={connsyncUdpSnt 1}

connsyncUdpSntMom	OBJECT-TYPE
	SYNTAX	 CounterBasedGauge64
	MAX-ACCESS read-only
	STATUS current
	DESCRIPTION "UDP sent"

	::={connsyncUdpSnt 2}

connsyncUdpSntMax	OBJECT-TYPE
	SYNTAX	 CounterBasedGauge64
	MAX-ACCESS read-only
	STATUS current
	DESCRIPTION "UDP sent"

	::={connsyncUdpSnt 3}

connsyncUdpRcv	OBJECT IDENTIFIER ::={connsync 21}

connsyncUdpRcvVal	OBJECT-TYPE
	SYNTAX	 Counter64
	MAX-ACCESS read-only
	STATUS current
	DESCRIPTION "UDP received"

	::={connsyncUdpRcv 1}

connsyncUdpRcvMom	OBJECT-TYPE
	SYNTAX	 CounterBasedGauge64
	MAX-ACCESS read-only
	STATUS current
	DESCRIPTION "UDP received"

	::={connsyncUdpRcv 2}

connsyncUdpRcvMax	OBJECT-TYPE
	SYNTAX	 CounterBasedGauge64
	MAX-ACCESS read-only
	STATUS current
	DESCRIPTION "UDP received"

	::={connsyncUdpRcv 3}

ruleset	OBJECT IDENTIFIER ::={sysdiag 64}

rulesetReceived	OBJECT IDENTIFIER ::={ruleset 1}

rulesetReceivedVal	OBJECT-TYPE
	SYNTAX	 Counter64
	MAX-ACCESS read-only
	STATUS current
	DESCRIPTION "RX packets"

	::={rulesetReceived 1}

rulesetReceivedMom	OBJECT-TYPE
	SYNTAX	 CounterBasedGauge64
	MAX-ACCESS read-only
	STATUS current
	DESCRIPTION "RX packets"

	::={rulesetReceived 2}

rulesetReceivedMax	OBJECT-TYPE
	SYNTAX	 CounterBasedGauge64
	MAX-ACCESS read-only
	STATUS current
	DESCRIPTION "RX packets"

	::={rulesetReceived 3}

rulesetFwrules	OBJECT IDENTIFIER ::={ruleset 5}

rulesetFwrulesVal	OBJECT-TYPE
	SYNTAX	 CounterBasedGauge64
	MAX-ACCESS read-only
	STATUS current
	DESCRIPTION "FW rules loaded"

	::={rulesetFwrules 1}

rulesetFwrulesMax	OBJECT-TYPE
	SYNTAX	 CounterBasedGauge64
	MAX-ACCESS read-only
	STATUS current
	DESCRIPTION "FW rules loaded"

	::={rulesetFwrules 3}

rulesetShapingrules	OBJECT IDENTIFIER ::={ruleset 6}

rulesetShapingrulesVal	OBJECT-TYPE
	SYNTAX	 CounterBasedGauge64
	MAX-ACCESS read-only
	STATUS current
	DESCRIPTION "Shaping rules loaded"

	::={rulesetShapingrules 1}

rulesetShapingrulesMax	OBJECT-TYPE
	SYNTAX	 CounterBasedGauge64
	MAX-ACCESS read-only
	STATUS current
	DESCRIPTION "Shaping rules loaded"

	::={rulesetShapingrules 3}

rulesetClienttreeSize	OBJECT IDENTIFIER ::={ruleset 7}

rulesetClienttreeSizeVal	OBJECT-TYPE
	SYNTAX	 CounterBasedGauge64
	MAX-ACCESS read-only
	STATUS current
	DESCRIPTION "Nodes in Client IP-tree"

	::={rulesetClienttreeSize 1}

rulesetClienttreeSizeMax	OBJECT-TYPE
	SYNTAX	 CounterBasedGauge64
	MAX-ACCESS read-only
	STATUS current
	DESCRIPTION "Nodes in Client IP-tree"

	::={rulesetClienttreeSize 3}

rulesetServertreeSize	OBJECT IDENTIFIER ::={ruleset 8}

rulesetServertreeSizeVal	OBJECT-TYPE
	SYNTAX	 CounterBasedGauge64
	MAX-ACCESS read-only
	STATUS current
	DESCRIPTION "Nodes in Server IP-tree"

	::={rulesetServertreeSize 1}

rulesetServertreeSizeMax	OBJECT-TYPE
	SYNTAX	 CounterBasedGauge64
	MAX-ACCESS read-only
	STATUS current
	DESCRIPTION "Nodes in Server IP-tree"

	::={rulesetServertreeSize 3}

rulesetBgpNumpaths	OBJECT IDENTIFIER ::={ruleset 9}

rulesetBgpNumpathsVal	OBJECT-TYPE
	SYNTAX	 CounterBasedGauge64
	MAX-ACCESS read-only
	STATUS current
	DESCRIPTION "Number of ASPaths"

	::={rulesetBgpNumpaths 1}

rulesetBgpNumpathsMax	OBJECT-TYPE
	SYNTAX	 CounterBasedGauge64
	MAX-ACCESS read-only
	STATUS current
	DESCRIPTION "Number of ASPaths"

	::={rulesetBgpNumpaths 3}

rulesetBgpTreesize	OBJECT IDENTIFIER ::={ruleset 10}

rulesetBgpTreesizeVal	OBJECT-TYPE
	SYNTAX	 CounterBasedGauge64
	MAX-ACCESS read-only
	STATUS current
	DESCRIPTION "Nodes in BGP-tree"

	::={rulesetBgpTreesize 1}

rulesetBgpTreesizeMax	OBJECT-TYPE
	SYNTAX	 CounterBasedGauge64
	MAX-ACCESS read-only
	STATUS current
	DESCRIPTION "Nodes in BGP-tree"

	::={rulesetBgpTreesize 3}

rulesetBgpNumLookup	OBJECT IDENTIFIER ::={ruleset 12}

rulesetBgpNumLookupVal	OBJECT-TYPE
	SYNTAX	 Counter64
	MAX-ACCESS read-only
	STATUS current
	DESCRIPTION "BGP path lookups"

	::={rulesetBgpNumLookup 1}

rulesetBgpNumLookupMom	OBJECT-TYPE
	SYNTAX	 CounterBasedGauge64
	MAX-ACCESS read-only
	STATUS current
	DESCRIPTION "BGP path lookups"

	::={rulesetBgpNumLookup 2}

rulesetBgpNumLookupMax	OBJECT-TYPE
	SYNTAX	 CounterBasedGauge64
	MAX-ACCESS read-only
	STATUS current
	DESCRIPTION "BGP path lookups"

	::={rulesetBgpNumLookup 3}

rulesetPropChecks	OBJECT IDENTIFIER ::={ruleset 13}

rulesetPropChecksVal	OBJECT-TYPE
	SYNTAX	 Counter64
	MAX-ACCESS read-only
	STATUS current
	DESCRIPTION "Property checks"

	::={rulesetPropChecks 1}

rulesetPropChecksMom	OBJECT-TYPE
	SYNTAX	 CounterBasedGauge64
	MAX-ACCESS read-only
	STATUS current
	DESCRIPTION "Property checks"

	::={rulesetPropChecks 2}

rulesetPropChecksMax	OBJECT-TYPE
	SYNTAX	 CounterBasedGauge64
	MAX-ACCESS read-only
	STATUS current
	DESCRIPTION "Property checks"

	::={rulesetPropChecks 3}

rulesetBitmasksAvg	OBJECT IDENTIFIER ::={ruleset 15}

rulesetBitmasksAvgVal	OBJECT-TYPE
	SYNTAX	 CounterBasedGauge64
	MAX-ACCESS read-only
	STATUS current
	DESCRIPTION "Bitmask average number of words"

	::={rulesetBitmasksAvg 1}

rulesetBitmasksAvgMax	OBJECT-TYPE
	SYNTAX	 CounterBasedGauge64
	MAX-ACCESS read-only
	STATUS current
	DESCRIPTION "Bitmask average number of words"

	::={rulesetBitmasksAvg 3}

rulesetBitmasksMax	OBJECT IDENTIFIER ::={ruleset 16}

rulesetBitmasksMaxVal	OBJECT-TYPE
	SYNTAX	 CounterBasedGauge64
	MAX-ACCESS read-only
	STATUS current
	DESCRIPTION "Bitmask max number of words"

	::={rulesetBitmasksMax 1}

rulesetBitmasksMaxMax	OBJECT-TYPE
	SYNTAX	 CounterBasedGauge64
	MAX-ACCESS read-only
	STATUS current
	DESCRIPTION "Bitmask max number of words"

	::={rulesetBitmasksMax 3}

rulesetDynipAdd	OBJECT IDENTIFIER ::={ruleset 17}

rulesetDynipAddVal	OBJECT-TYPE
	SYNTAX	 Counter64
	MAX-ACCESS read-only
	STATUS current
	DESCRIPTION "Dynamic ips added"

	::={rulesetDynipAdd 1}

rulesetDynipAddMom	OBJECT-TYPE
	SYNTAX	 CounterBasedGauge64
	MAX-ACCESS read-only
	STATUS current
	DESCRIPTION "Dynamic ips added"

	::={rulesetDynipAdd 2}

rulesetDynipAddMax	OBJECT-TYPE
	SYNTAX	 CounterBasedGauge64
	MAX-ACCESS read-only
	STATUS current
	DESCRIPTION "Dynamic ips added"

	::={rulesetDynipAdd 3}

rulesetDynipRemove	OBJECT IDENTIFIER ::={ruleset 18}

rulesetDynipRemoveVal	OBJECT-TYPE
	SYNTAX	 Counter64
	MAX-ACCESS read-only
	STATUS current
	DESCRIPTION "Dynamic ips removed"

	::={rulesetDynipRemove 1}

rulesetDynipRemoveMom	OBJECT-TYPE
	SYNTAX	 CounterBasedGauge64
	MAX-ACCESS read-only
	STATUS current
	DESCRIPTION "Dynamic ips removed"

	::={rulesetDynipRemove 2}

rulesetDynipRemoveMax	OBJECT-TYPE
	SYNTAX	 CounterBasedGauge64
	MAX-ACCESS read-only
	STATUS current
	DESCRIPTION "Dynamic ips removed"

	::={rulesetDynipRemove 3}

rulesetLastUpdate	OBJECT IDENTIFIER ::={ruleset 22}

rulesetLastUpdateVal	OBJECT-TYPE
	SYNTAX	 DateAndTime
	MAX-ACCESS read-only
	STATUS current
	DESCRIPTION "Last ruleset reload"

	::={rulesetLastUpdate 1}

rulesetDynipNum	OBJECT IDENTIFIER ::={ruleset 23}

rulesetDynipNumVal	OBJECT-TYPE
	SYNTAX	 CounterBasedGauge64
	MAX-ACCESS read-only
	STATUS current
	DESCRIPTION "Dynamic ips current"

	::={rulesetDynipNum 1}

rulesetDynipNumMax	OBJECT-TYPE
	SYNTAX	 CounterBasedGauge64
	MAX-ACCESS read-only
	STATUS current
	DESCRIPTION "Dynamic ips current"

	::={rulesetDynipNum 3}

rulesetStatisticsrules	OBJECT IDENTIFIER ::={ruleset 24}

rulesetStatisticsrulesVal	OBJECT-TYPE
	SYNTAX	 CounterBasedGauge64
	MAX-ACCESS read-only
	STATUS current
	DESCRIPTION "Statistics rules loaded"

	::={rulesetStatisticsrules 1}

rulesetStatisticsrulesMax	OBJECT-TYPE
	SYNTAX	 CounterBasedGauge64
	MAX-ACCESS read-only
	STATUS current
	DESCRIPTION "Statistics rules loaded"

	::={rulesetStatisticsrules 3}

rulesetLocaltreeSize	OBJECT IDENTIFIER ::={ruleset 25}

rulesetLocaltreeSizeVal	OBJECT-TYPE
	SYNTAX	 CounterBasedGauge64
	MAX-ACCESS read-only
	STATUS current
	DESCRIPTION "Nodes in Local IP-tree"

	::={rulesetLocaltreeSize 1}

rulesetLocaltreeSizeMax	OBJECT-TYPE
	SYNTAX	 CounterBasedGauge64
	MAX-ACCESS read-only
	STATUS current
	DESCRIPTION "Nodes in Local IP-tree"

	::={rulesetLocaltreeSize 3}

rulesetStatisticsRuleOverflow	OBJECT IDENTIFIER ::={ruleset 26}

rulesetStatisticsRuleOverflowVal	OBJECT-TYPE
	SYNTAX	 Counter64
	MAX-ACCESS read-only
	STATUS current
	DESCRIPTION "Too many matching statistics rules"

	::={rulesetStatisticsRuleOverflow 1}

rulesetStatisticsRuleOverflowMom	OBJECT-TYPE
	SYNTAX	 CounterBasedGauge64
	MAX-ACCESS read-only
	STATUS current
	DESCRIPTION "Too many matching statistics rules"

	::={rulesetStatisticsRuleOverflow 2}

rulesetStatisticsRuleOverflowMax	OBJECT-TYPE
	SYNTAX	 CounterBasedGauge64
	MAX-ACCESS read-only
	STATUS current
	DESCRIPTION "Too many matching statistics rules"

	::={rulesetStatisticsRuleOverflow 3}

rulesetConnStatechange	OBJECT IDENTIFIER ::={ruleset 27}

rulesetConnStatechangeVal	OBJECT-TYPE
	SYNTAX	 Counter64
	MAX-ACCESS read-only
	STATUS current
	DESCRIPTION "Flow ruleset statechanges"

	::={rulesetConnStatechange 1}

rulesetConnStatechangeMom	OBJECT-TYPE
	SYNTAX	 CounterBasedGauge64
	MAX-ACCESS read-only
	STATUS current
	DESCRIPTION "Flow ruleset statechanges"

	::={rulesetConnStatechange 2}

rulesetConnStatechangeMax	OBJECT-TYPE
	SYNTAX	 CounterBasedGauge64
	MAX-ACCESS read-only
	STATUS current
	DESCRIPTION "Flow ruleset statechanges"

	::={rulesetConnStatechange 3}

rulesetConnStatechangeProp	OBJECT IDENTIFIER ::={ruleset 28}

rulesetConnStatechangePropVal	OBJECT-TYPE
	SYNTAX	 Counter64
	MAX-ACCESS read-only
	STATUS current
	DESCRIPTION "Flow ruleset statechanges (prop)"

	::={rulesetConnStatechangeProp 1}

rulesetConnStatechangePropMom	OBJECT-TYPE
	SYNTAX	 CounterBasedGauge64
	MAX-ACCESS read-only
	STATUS current
	DESCRIPTION "Flow ruleset statechanges (prop)"

	::={rulesetConnStatechangeProp 2}

rulesetConnStatechangePropMax	OBJECT-TYPE
	SYNTAX	 CounterBasedGauge64
	MAX-ACCESS read-only
	STATUS current
	DESCRIPTION "Flow ruleset statechanges (prop)"

	::={rulesetConnStatechangeProp 3}

rulesetConnStatechangeService	OBJECT IDENTIFIER ::={ruleset 29}

rulesetConnStatechangeServiceVal	OBJECT-TYPE
	SYNTAX	 Counter64
	MAX-ACCESS read-only
	STATUS current
	DESCRIPTION "Flow ruleset statechanges (service)"

	::={rulesetConnStatechangeService 1}

rulesetConnStatechangeServiceMom	OBJECT-TYPE
	SYNTAX	 CounterBasedGauge64
	MAX-ACCESS read-only
	STATUS current
	DESCRIPTION "Flow ruleset statechanges (service)"

	::={rulesetConnStatechangeService 2}

rulesetConnStatechangeServiceMax	OBJECT-TYPE
	SYNTAX	 CounterBasedGauge64
	MAX-ACCESS read-only
	STATUS current
	DESCRIPTION "Flow ruleset statechanges (service)"

	::={rulesetConnStatechangeService 3}

rulesetConnStatechangeFlags	OBJECT IDENTIFIER ::={ruleset 30}

rulesetConnStatechangeFlagsVal	OBJECT-TYPE
	SYNTAX	 Counter64
	MAX-ACCESS read-only
	STATUS current
	DESCRIPTION "Flow ruleset statechanges (flags)"

	::={rulesetConnStatechangeFlags 1}

rulesetConnStatechangeFlagsMom	OBJECT-TYPE
	SYNTAX	 CounterBasedGauge64
	MAX-ACCESS read-only
	STATUS current
	DESCRIPTION "Flow ruleset statechanges (flags)"

	::={rulesetConnStatechangeFlags 2}

rulesetConnStatechangeFlagsMax	OBJECT-TYPE
	SYNTAX	 CounterBasedGauge64
	MAX-ACCESS read-only
	STATUS current
	DESCRIPTION "Flow ruleset statechanges (flags)"

	::={rulesetConnStatechangeFlags 3}

rulesetConnStatechangeAspath	OBJECT IDENTIFIER ::={ruleset 31}

rulesetConnStatechangeAspathVal	OBJECT-TYPE
	SYNTAX	 Counter64
	MAX-ACCESS read-only
	STATUS current
	DESCRIPTION "Flow ruleset statechanges (aspath)"

	::={rulesetConnStatechangeAspath 1}

rulesetConnStatechangeAspathMom	OBJECT-TYPE
	SYNTAX	 CounterBasedGauge64
	MAX-ACCESS read-only
	STATUS current
	DESCRIPTION "Flow ruleset statechanges (aspath)"

	::={rulesetConnStatechangeAspath 2}

rulesetConnStatechangeAspathMax	OBJECT-TYPE
	SYNTAX	 CounterBasedGauge64
	MAX-ACCESS read-only
	STATUS current
	DESCRIPTION "Flow ruleset statechanges (aspath)"

	::={rulesetConnStatechangeAspath 3}

rulesetRecalcVersion	OBJECT IDENTIFIER ::={ruleset 32}

rulesetRecalcVersionVal	OBJECT-TYPE
	SYNTAX	 Counter64
	MAX-ACCESS read-only
	STATUS current
	DESCRIPTION "Flow ruleset recalcs from version"

	::={rulesetRecalcVersion 1}

rulesetRecalcVersionMom	OBJECT-TYPE
	SYNTAX	 CounterBasedGauge64
	MAX-ACCESS read-only
	STATUS current
	DESCRIPTION "Flow ruleset recalcs from version"

	::={rulesetRecalcVersion 2}

rulesetRecalcVersionMax	OBJECT-TYPE
	SYNTAX	 CounterBasedGauge64
	MAX-ACCESS read-only
	STATUS current
	DESCRIPTION "Flow ruleset recalcs from version"

	::={rulesetRecalcVersion 3}

rulesetRecalcTime	OBJECT IDENTIFIER ::={ruleset 33}

rulesetRecalcTimeVal	OBJECT-TYPE
	SYNTAX	 Counter64
	MAX-ACCESS read-only
	STATUS current
	DESCRIPTION "Flow ruleset recalcs from time"

	::={rulesetRecalcTime 1}

rulesetRecalcTimeMom	OBJECT-TYPE
	SYNTAX	 CounterBasedGauge64
	MAX-ACCESS read-only
	STATUS current
	DESCRIPTION "Flow ruleset recalcs from time"

	::={rulesetRecalcTime 2}

rulesetRecalcTimeMax	OBJECT-TYPE
	SYNTAX	 CounterBasedGauge64
	MAX-ACCESS read-only
	STATUS current
	DESCRIPTION "Flow ruleset recalcs from time"

	::={rulesetRecalcTime 3}

rulesetRecalcBgp	OBJECT IDENTIFIER ::={ruleset 34}

rulesetRecalcBgpVal	OBJECT-TYPE
	SYNTAX	 Counter64
	MAX-ACCESS read-only
	STATUS current
	DESCRIPTION "Flow ruleset recalcs from bgp"

	::={rulesetRecalcBgp 1}

rulesetRecalcBgpMom	OBJECT-TYPE
	SYNTAX	 CounterBasedGauge64
	MAX-ACCESS read-only
	STATUS current
	DESCRIPTION "Flow ruleset recalcs from bgp"

	::={rulesetRecalcBgp 2}

rulesetRecalcBgpMax	OBJECT-TYPE
	SYNTAX	 CounterBasedGauge64
	MAX-ACCESS read-only
	STATUS current
	DESCRIPTION "Flow ruleset recalcs from bgp"

	::={rulesetRecalcBgp 3}

rulesetRecalcUnknown	OBJECT IDENTIFIER ::={ruleset 35}

rulesetRecalcUnknownVal	OBJECT-TYPE
	SYNTAX	 Counter64
	MAX-ACCESS read-only
	STATUS current
	DESCRIPTION "Flow ruleset recalcs from state"

	::={rulesetRecalcUnknown 1}

rulesetRecalcUnknownMom	OBJECT-TYPE
	SYNTAX	 CounterBasedGauge64
	MAX-ACCESS read-only
	STATUS current
	DESCRIPTION "Flow ruleset recalcs from state"

	::={rulesetRecalcUnknown 2}

rulesetRecalcUnknownMax	OBJECT-TYPE
	SYNTAX	 CounterBasedGauge64
	MAX-ACCESS read-only
	STATUS current
	DESCRIPTION "Flow ruleset recalcs from state"

	::={rulesetRecalcUnknown 3}

rulesetOutdatedService	OBJECT IDENTIFIER ::={ruleset 36}

rulesetOutdatedServiceVal	OBJECT-TYPE
	SYNTAX	 Counter64
	MAX-ACCESS read-only
	STATUS current
	DESCRIPTION "Ruleset recalcs with outdated service ruleset"

	::={rulesetOutdatedService 1}

rulesetOutdatedServiceMom	OBJECT-TYPE
	SYNTAX	 CounterBasedGauge64
	MAX-ACCESS read-only
	STATUS current
	DESCRIPTION "Ruleset recalcs with outdated service ruleset"

	::={rulesetOutdatedService 2}

rulesetOutdatedServiceMax	OBJECT-TYPE
	SYNTAX	 CounterBasedGauge64
	MAX-ACCESS read-only
	STATUS current
	DESCRIPTION "Ruleset recalcs with outdated service ruleset"

	::={rulesetOutdatedService 3}

rulesetSubscribers	OBJECT IDENTIFIER ::={ruleset 37}

rulesetSubscribersVal	OBJECT-TYPE
	SYNTAX	 CounterBasedGauge64
	MAX-ACCESS read-only
	STATUS current
	DESCRIPTION "Number of added subscribers"

	::={rulesetSubscribers 1}

rulesetSubscribersMax	OBJECT-TYPE
	SYNTAX	 CounterBasedGauge64
	MAX-ACCESS read-only
	STATUS current
	DESCRIPTION "Number of added subscribers"

	::={rulesetSubscribers 3}

rulesetBadAspath	OBJECT IDENTIFIER ::={ruleset 38}

rulesetBadAspathVal	OBJECT-TYPE
	SYNTAX	 Counter64
	MAX-ACCESS read-only
	STATUS current
	DESCRIPTION "Old or corrupted AS-path entry"

	::={rulesetBadAspath 1}

rulesetBadAspathMom	OBJECT-TYPE
	SYNTAX	 CounterBasedGauge64
	MAX-ACCESS read-only
	STATUS current
	DESCRIPTION "Old or corrupted AS-path entry"

	::={rulesetBadAspath 2}

rulesetBadAspathMax	OBJECT-TYPE
	SYNTAX	 CounterBasedGauge64
	MAX-ACCESS read-only
	STATUS current
	DESCRIPTION "Old or corrupted AS-path entry"

	::={rulesetBadAspath 3}

rulesetConnStatechangeLinklevel	OBJECT IDENTIFIER ::={ruleset 39}

rulesetConnStatechangeLinklevelVal	OBJECT-TYPE
	SYNTAX	 Counter64
	MAX-ACCESS read-only
	STATUS current
	DESCRIPTION "Flow ruleset statechanges (linklevel)"

	::={rulesetConnStatechangeLinklevel 1}

rulesetConnStatechangeLinklevelMom	OBJECT-TYPE
	SYNTAX	 CounterBasedGauge64
	MAX-ACCESS read-only
	STATUS current
	DESCRIPTION "Flow ruleset statechanges (linklevel)"

	::={rulesetConnStatechangeLinklevel 2}

rulesetConnStatechangeLinklevelMax	OBJECT-TYPE
	SYNTAX	 CounterBasedGauge64
	MAX-ACCESS read-only
	STATUS current
	DESCRIPTION "Flow ruleset statechanges (linklevel)"

	::={rulesetConnStatechangeLinklevel 3}

rulesetSubscriberAllocFail	OBJECT IDENTIFIER ::={ruleset 40}

rulesetSubscriberAllocFailVal	OBJECT-TYPE
	SYNTAX	 Counter64
	MAX-ACCESS read-only
	STATUS current
	DESCRIPTION "Subscriber allocation failures"

	::={rulesetSubscriberAllocFail 1}

rulesetSubscriberAllocFailMom	OBJECT-TYPE
	SYNTAX	 CounterBasedGauge64
	MAX-ACCESS read-only
	STATUS current
	DESCRIPTION "Subscriber allocation failures"

	::={rulesetSubscriberAllocFail 2}

rulesetSubscriberAllocFailMax	OBJECT-TYPE
	SYNTAX	 CounterBasedGauge64
	MAX-ACCESS read-only
	STATUS current
	DESCRIPTION "Subscriber allocation failures"

	::={rulesetSubscriberAllocFail 3}

rulesetDynipAllocFail	OBJECT IDENTIFIER ::={ruleset 41}

rulesetDynipAllocFailVal	OBJECT-TYPE
	SYNTAX	 Counter64
	MAX-ACCESS read-only
	STATUS current
	DESCRIPTION "Dynamic ip loading failures (allocation failure)"

	::={rulesetDynipAllocFail 1}

rulesetDynipAllocFailMom	OBJECT-TYPE
	SYNTAX	 CounterBasedGauge64
	MAX-ACCESS read-only
	STATUS current
	DESCRIPTION "Dynamic ip loading failures (allocation failure)"

	::={rulesetDynipAllocFail 2}

rulesetDynipAllocFailMax	OBJECT-TYPE
	SYNTAX	 CounterBasedGauge64
	MAX-ACCESS read-only
	STATUS current
	DESCRIPTION "Dynamic ip loading failures (allocation failure)"

	::={rulesetDynipAllocFail 3}

rulesetDynipOversized	OBJECT IDENTIFIER ::={ruleset 42}

rulesetDynipOversizedVal	OBJECT-TYPE
	SYNTAX	 Counter64
	MAX-ACCESS read-only
	STATUS current
	DESCRIPTION "Dynamic ip loading failures (oversized)"

	::={rulesetDynipOversized 1}

rulesetDynipOversizedMom	OBJECT-TYPE
	SYNTAX	 CounterBasedGauge64
	MAX-ACCESS read-only
	STATUS current
	DESCRIPTION "Dynamic ip loading failures (oversized)"

	::={rulesetDynipOversized 2}

rulesetDynipOversizedMax	OBJECT-TYPE
	SYNTAX	 CounterBasedGauge64
	MAX-ACCESS read-only
	STATUS current
	DESCRIPTION "Dynamic ip loading failures (oversized)"

	::={rulesetDynipOversized 3}

rulesetNonexistentSubscriber	OBJECT IDENTIFIER ::={ruleset 43}

rulesetNonexistentSubscriberVal	OBJECT-TYPE
	SYNTAX	 Counter64
	MAX-ACCESS read-only
	STATUS current
	DESCRIPTION "Split on unknown subscriber"

	::={rulesetNonexistentSubscriber 1}

rulesetNonexistentSubscriberMom	OBJECT-TYPE
	SYNTAX	 CounterBasedGauge64
	MAX-ACCESS read-only
	STATUS current
	DESCRIPTION "Split on unknown subscriber"

	::={rulesetNonexistentSubscriber 2}

rulesetNonexistentSubscriberMax	OBJECT-TYPE
	SYNTAX	 CounterBasedGauge64
	MAX-ACCESS read-only
	STATUS current
	DESCRIPTION "Split on unknown subscriber"

	::={rulesetNonexistentSubscriber 3}

rulesetConnStatechangeTtl	OBJECT IDENTIFIER ::={ruleset 44}

rulesetConnStatechangeTtlVal	OBJECT-TYPE
	SYNTAX	 Counter64
	MAX-ACCESS read-only
	STATUS current
	DESCRIPTION "Flow ruleset statechanges (ttl)"

	::={rulesetConnStatechangeTtl 1}

rulesetConnStatechangeTtlMom	OBJECT-TYPE
	SYNTAX	 CounterBasedGauge64
	MAX-ACCESS read-only
	STATUS current
	DESCRIPTION "Flow ruleset statechanges (ttl)"

	::={rulesetConnStatechangeTtl 2}

rulesetConnStatechangeTtlMax	OBJECT-TYPE
	SYNTAX	 CounterBasedGauge64
	MAX-ACCESS read-only
	STATUS current
	DESCRIPTION "Flow ruleset statechanges (ttl)"

	::={rulesetConnStatechangeTtl 3}

firewall	OBJECT IDENTIFIER ::={sysdiag 80}

fwAccepts	OBJECT IDENTIFIER ::={firewall 1}

fwAcceptsVal	OBJECT-TYPE
	SYNTAX	 Counter64
	MAX-ACCESS read-only
	STATUS current
	DESCRIPTION "Ruleset evaluations giving ACCEPT"

	::={fwAccepts 1}

fwAcceptsMom	OBJECT-TYPE
	SYNTAX	 CounterBasedGauge64
	MAX-ACCESS read-only
	STATUS current
	DESCRIPTION "Ruleset evaluations giving ACCEPT"

	::={fwAccepts 2}

fwAcceptsMax	OBJECT-TYPE
	SYNTAX	 CounterBasedGauge64
	MAX-ACCESS read-only
	STATUS current
	DESCRIPTION "Ruleset evaluations giving ACCEPT"

	::={fwAccepts 3}

fwRejects	OBJECT IDENTIFIER ::={firewall 2}

fwRejectsVal	OBJECT-TYPE
	SYNTAX	 Counter64
	MAX-ACCESS read-only
	STATUS current
	DESCRIPTION "Ruleset evaluations giving REJECT"

	::={fwRejects 1}

fwRejectsMom	OBJECT-TYPE
	SYNTAX	 CounterBasedGauge64
	MAX-ACCESS read-only
	STATUS current
	DESCRIPTION "Ruleset evaluations giving REJECT"

	::={fwRejects 2}

fwRejectsMax	OBJECT-TYPE
	SYNTAX	 CounterBasedGauge64
	MAX-ACCESS read-only
	STATUS current
	DESCRIPTION "Ruleset evaluations giving REJECT"

	::={fwRejects 3}

fwDrops	OBJECT IDENTIFIER ::={firewall 3}

fwDropsVal	OBJECT-TYPE
	SYNTAX	 Counter64
	MAX-ACCESS read-only
	STATUS current
	DESCRIPTION "Ruleset evaluations giving DROP"

	::={fwDrops 1}

fwDropsMom	OBJECT-TYPE
	SYNTAX	 CounterBasedGauge64
	MAX-ACCESS read-only
	STATUS current
	DESCRIPTION "Ruleset evaluations giving DROP"

	::={fwDrops 2}

fwDropsMax	OBJECT-TYPE
	SYNTAX	 CounterBasedGauge64
	MAX-ACCESS read-only
	STATUS current
	DESCRIPTION "Ruleset evaluations giving DROP"

	::={fwDrops 3}

fwRewites	OBJECT IDENTIFIER ::={firewall 4}

fwRewitesVal	OBJECT-TYPE
	SYNTAX	 Counter64
	MAX-ACCESS read-only
	STATUS current
	DESCRIPTION "Ruleset evaluations giving REWRITE"

	::={fwRewites 1}

fwRewitesMom	OBJECT-TYPE
	SYNTAX	 CounterBasedGauge64
	MAX-ACCESS read-only
	STATUS current
	DESCRIPTION "Ruleset evaluations giving REWRITE"

	::={fwRewites 2}

fwRewitesMax	OBJECT-TYPE
	SYNTAX	 CounterBasedGauge64
	MAX-ACCESS read-only
	STATUS current
	DESCRIPTION "Ruleset evaluations giving REWRITE"

	::={fwRewites 3}

fwDiverts	OBJECT IDENTIFIER ::={firewall 5}

fwDivertsVal	OBJECT-TYPE
	SYNTAX	 Counter64
	MAX-ACCESS read-only
	STATUS current
	DESCRIPTION "Ruleset evaluations giving DIVERT"

	::={fwDiverts 1}

fwDivertsMom	OBJECT-TYPE
	SYNTAX	 CounterBasedGauge64
	MAX-ACCESS read-only
	STATUS current
	DESCRIPTION "Ruleset evaluations giving DIVERT"

	::={fwDiverts 2}

fwDivertsMax	OBJECT-TYPE
	SYNTAX	 CounterBasedGauge64
	MAX-ACCESS read-only
	STATUS current
	DESCRIPTION "Ruleset evaluations giving DIVERT"

	::={fwDiverts 3}

fwRuleSets	OBJECT IDENTIFIER ::={firewall 6}

fwRuleSetsVal	OBJECT-TYPE
	SYNTAX	 Counter64
	MAX-ACCESS read-only
	STATUS current
	DESCRIPTION "Ruleset evaluations"

	::={fwRuleSets 1}

fwRuleSetsMom	OBJECT-TYPE
	SYNTAX	 CounterBasedGauge64
	MAX-ACCESS read-only
	STATUS current
	DESCRIPTION "Ruleset evaluations"

	::={fwRuleSets 2}

fwRuleSetsMax	OBJECT-TYPE
	SYNTAX	 CounterBasedGauge64
	MAX-ACCESS read-only
	STATUS current
	DESCRIPTION "Ruleset evaluations"

	::={fwRuleSets 3}

fwLogs	OBJECT IDENTIFIER ::={firewall 7}

fwLogsVal	OBJECT-TYPE
	SYNTAX	 Counter64
	MAX-ACCESS read-only
	STATUS current
	DESCRIPTION "Log entries"

	::={fwLogs 1}

fwLogsMom	OBJECT-TYPE
	SYNTAX	 CounterBasedGauge64
	MAX-ACCESS read-only
	STATUS current
	DESCRIPTION "Log entries"

	::={fwLogs 2}

fwLogsMax	OBJECT-TYPE
	SYNTAX	 CounterBasedGauge64
	MAX-ACCESS read-only
	STATUS current
	DESCRIPTION "Log entries"

	::={fwLogs 3}

fwMonitor	OBJECT IDENTIFIER ::={firewall 8}

fwMonitorVal	OBJECT-TYPE
	SYNTAX	 Counter64
	MAX-ACCESS read-only
	STATUS current
	DESCRIPTION "Monitored packets"

	::={fwMonitor 1}

fwMonitorMom	OBJECT-TYPE
	SYNTAX	 CounterBasedGauge64
	MAX-ACCESS read-only
	STATUS current
	DESCRIPTION "Monitored packets"

	::={fwMonitor 2}

fwMonitorMax	OBJECT-TYPE
	SYNTAX	 CounterBasedGauge64
	MAX-ACCESS read-only
	STATUS current
	DESCRIPTION "Monitored packets"

	::={fwMonitor 3}

fwMonitorFailures	OBJECT IDENTIFIER ::={firewall 9}

fwMonitorFailuresVal	OBJECT-TYPE
	SYNTAX	 Counter64
	MAX-ACCESS read-only
	STATUS current
	DESCRIPTION "Failed monitored packets"

	::={fwMonitorFailures 1}

fwMonitorFailuresMom	OBJECT-TYPE
	SYNTAX	 CounterBasedGauge64
	MAX-ACCESS read-only
	STATUS current
	DESCRIPTION "Failed monitored packets"

	::={fwMonitorFailures 2}

fwMonitorFailuresMax	OBJECT-TYPE
	SYNTAX	 CounterBasedGauge64
	MAX-ACCESS read-only
	STATUS current
	DESCRIPTION "Failed monitored packets"

	::={fwMonitorFailures 3}

fwInjects	OBJECT IDENTIFIER ::={firewall 10}

fwInjectsVal	OBJECT-TYPE
	SYNTAX	 Counter64
	MAX-ACCESS read-only
	STATUS current
	DESCRIPTION "Ruleset evaluations giving INJECT"

	::={fwInjects 1}

fwInjectsMom	OBJECT-TYPE
	SYNTAX	 CounterBasedGauge64
	MAX-ACCESS read-only
	STATUS current
	DESCRIPTION "Ruleset evaluations giving INJECT"

	::={fwInjects 2}

fwInjectsMax	OBJECT-TYPE
	SYNTAX	 CounterBasedGauge64
	MAX-ACCESS read-only
	STATUS current
	DESCRIPTION "Ruleset evaluations giving INJECT"

	::={fwInjects 3}

fwInjectsFailures	OBJECT IDENTIFIER ::={firewall 11}

fwInjectsFailuresVal	OBJECT-TYPE
	SYNTAX	 Counter64
	MAX-ACCESS read-only
	STATUS current
	DESCRIPTION "Inject data preparation failures"

	::={fwInjectsFailures 1}

fwInjectsFailuresMom	OBJECT-TYPE
	SYNTAX	 CounterBasedGauge64
	MAX-ACCESS read-only
	STATUS current
	DESCRIPTION "Inject data preparation failures"

	::={fwInjectsFailures 2}

fwInjectsFailuresMax	OBJECT-TYPE
	SYNTAX	 CounterBasedGauge64
	MAX-ACCESS read-only
	STATUS current
	DESCRIPTION "Inject data preparation failures"

	::={fwInjectsFailures 3}

fwInjectsFailuresProp	OBJECT IDENTIFIER ::={firewall 12}

fwInjectsFailuresPropVal	OBJECT-TYPE
	SYNTAX	 Counter64
	MAX-ACCESS read-only
	STATUS current
	DESCRIPTION "Inject properties exceeding max length (255)"

	::={fwInjectsFailuresProp 1}

fwInjectsFailuresPropMom	OBJECT-TYPE
	SYNTAX	 CounterBasedGauge64
	MAX-ACCESS read-only
	STATUS current
	DESCRIPTION "Inject properties exceeding max length (255)"

	::={fwInjectsFailuresProp 2}

fwInjectsFailuresPropMax	OBJECT-TYPE
	SYNTAX	 CounterBasedGauge64
	MAX-ACCESS read-only
	STATUS current
	DESCRIPTION "Inject properties exceeding max length (255)"

	::={fwInjectsFailuresProp 3}

fwMidconnRewrite	OBJECT IDENTIFIER ::={firewall 13}

fwMidconnRewriteVal	OBJECT-TYPE
	SYNTAX	 Counter64
	MAX-ACCESS read-only
	STATUS current
	DESCRIPTION "Rewrites changed in active connection"

	::={fwMidconnRewrite 1}

fwMidconnRewriteMom	OBJECT-TYPE
	SYNTAX	 CounterBasedGauge64
	MAX-ACCESS read-only
	STATUS current
	DESCRIPTION "Rewrites changed in active connection"

	::={fwMidconnRewrite 2}

fwMidconnRewriteMax	OBJECT-TYPE
	SYNTAX	 CounterBasedGauge64
	MAX-ACCESS read-only
	STATUS current
	DESCRIPTION "Rewrites changed in active connection"

	::={fwMidconnRewrite 3}

shaping	OBJECT IDENTIFIER ::={sysdiag 88}

shapingEnqueued	OBJECT IDENTIFIER ::={shaping 1}

shapingEnqueuedVal	OBJECT-TYPE
	SYNTAX	 Counter64
	MAX-ACCESS read-only
	STATUS current
	DESCRIPTION "Enqueued packets"

	::={shapingEnqueued 1}

shapingEnqueuedMom	OBJECT-TYPE
	SYNTAX	 CounterBasedGauge64
	MAX-ACCESS read-only
	STATUS current
	DESCRIPTION "Enqueued packets"

	::={shapingEnqueued 2}

shapingEnqueuedMax	OBJECT-TYPE
	SYNTAX	 CounterBasedGauge64
	MAX-ACCESS read-only
	STATUS current
	DESCRIPTION "Enqueued packets"

	::={shapingEnqueued 3}

shapingDequeued	OBJECT IDENTIFIER ::={shaping 2}

shapingDequeuedVal	OBJECT-TYPE
	SYNTAX	 Counter64
	MAX-ACCESS read-only
	STATUS current
	DESCRIPTION "Dequeued packets"

	::={shapingDequeued 1}

shapingDequeuedMom	OBJECT-TYPE
	SYNTAX	 CounterBasedGauge64
	MAX-ACCESS read-only
	STATUS current
	DESCRIPTION "Dequeued packets"

	::={shapingDequeued 2}

shapingDequeuedMax	OBJECT-TYPE
	SYNTAX	 CounterBasedGauge64
	MAX-ACCESS read-only
	STATUS current
	DESCRIPTION "Dequeued packets"

	::={shapingDequeued 3}

shapingBrownConnDrops	OBJECT IDENTIFIER ::={shaping 8}

shapingBrownConnDropsVal	OBJECT-TYPE
	SYNTAX	 Counter64
	MAX-ACCESS read-only
	STATUS current
	DESCRIPTION "BROWN per connection drops"

	::={shapingBrownConnDrops 1}

shapingBrownConnDropsMom	OBJECT-TYPE
	SYNTAX	 CounterBasedGauge64
	MAX-ACCESS read-only
	STATUS current
	DESCRIPTION "BROWN per connection drops"

	::={shapingBrownConnDrops 2}

shapingBrownConnDropsMax	OBJECT-TYPE
	SYNTAX	 CounterBasedGauge64
	MAX-ACCESS read-only
	STATUS current
	DESCRIPTION "BROWN per connection drops"

	::={shapingBrownConnDrops 3}

shapingQueueSize	OBJECT IDENTIFIER ::={shaping 9}

shapingQueueSizeVal	OBJECT-TYPE
	SYNTAX	 CounterBasedGauge64
	MAX-ACCESS read-only
	STATUS current
	DESCRIPTION "Queue size"

	::={shapingQueueSize 1}

shapingQueueSizeMax	OBJECT-TYPE
	SYNTAX	 CounterBasedGauge64
	MAX-ACCESS read-only
	STATUS current
	DESCRIPTION "Queue size"

	::={shapingQueueSize 3}

shapingRulesSetCount	OBJECT IDENTIFIER ::={shaping 10}

shapingRulesSetCountVal	OBJECT-TYPE
	SYNTAX	 Counter64
	MAX-ACCESS read-only
	STATUS current
	DESCRIPTION "Rule sets"

	::={shapingRulesSetCount 1}

shapingRulesSetCountMom	OBJECT-TYPE
	SYNTAX	 CounterBasedGauge64
	MAX-ACCESS read-only
	STATUS current
	DESCRIPTION "Rule sets"

	::={shapingRulesSetCount 2}

shapingRulesSetCountMax	OBJECT-TYPE
	SYNTAX	 CounterBasedGauge64
	MAX-ACCESS read-only
	STATUS current
	DESCRIPTION "Rule sets"

	::={shapingRulesSetCount 3}

shapingEnqueuedBytes	OBJECT IDENTIFIER ::={shaping 11}

shapingEnqueuedBytesVal	OBJECT-TYPE
	SYNTAX	 Counter64
	MAX-ACCESS read-only
	STATUS current
	DESCRIPTION "Enqueued bytes"

	::={shapingEnqueuedBytes 1}

shapingEnqueuedBytesMom	OBJECT-TYPE
	SYNTAX	 CounterBasedGauge64
	MAX-ACCESS read-only
	STATUS current
	DESCRIPTION "Enqueued bytes"

	::={shapingEnqueuedBytes 2}

shapingEnqueuedBytesMax	OBJECT-TYPE
	SYNTAX	 CounterBasedGauge64
	MAX-ACCESS read-only
	STATUS current
	DESCRIPTION "Enqueued bytes"

	::={shapingEnqueuedBytes 3}

shapingDequeuedBytes	OBJECT IDENTIFIER ::={shaping 12}

shapingDequeuedBytesVal	OBJECT-TYPE
	SYNTAX	 Counter64
	MAX-ACCESS read-only
	STATUS current
	DESCRIPTION "Dequeued bytes"

	::={shapingDequeuedBytes 1}

shapingDequeuedBytesMom	OBJECT-TYPE
	SYNTAX	 CounterBasedGauge64
	MAX-ACCESS read-only
	STATUS current
	DESCRIPTION "Dequeued bytes"

	::={shapingDequeuedBytes 2}

shapingDequeuedBytesMax	OBJECT-TYPE
	SYNTAX	 CounterBasedGauge64
	MAX-ACCESS read-only
	STATUS current
	DESCRIPTION "Dequeued bytes"

	::={shapingDequeuedBytes 3}

shapingObjectCopies	OBJECT IDENTIFIER ::={shaping 13}

shapingObjectCopiesVal	OBJECT-TYPE
	SYNTAX	 CounterBasedGauge64
	MAX-ACCESS read-only
	STATUS current
	DESCRIPTION "Object copies"

	::={shapingObjectCopies 1}

shapingObjectCopiesMax	OBJECT-TYPE
	SYNTAX	 CounterBasedGauge64
	MAX-ACCESS read-only
	STATUS current
	DESCRIPTION "Object copies"

	::={shapingObjectCopies 3}

shapingOutofpacketsDrops	OBJECT IDENTIFIER ::={shaping 15}

shapingOutofpacketsDropsVal	OBJECT-TYPE
	SYNTAX	 Counter64
	MAX-ACCESS read-only
	STATUS current
	DESCRIPTION "Out of packets drops"

	::={shapingOutofpacketsDrops 1}

shapingOutofpacketsDropsMom	OBJECT-TYPE
	SYNTAX	 CounterBasedGauge64
	MAX-ACCESS read-only
	STATUS current
	DESCRIPTION "Out of packets drops"

	::={shapingOutofpacketsDrops 2}

shapingOutofpacketsDropsMax	OBJECT-TYPE
	SYNTAX	 CounterBasedGauge64
	MAX-ACCESS read-only
	STATUS current
	DESCRIPTION "Out of packets drops"

	::={shapingOutofpacketsDrops 3}

shapingReceived	OBJECT IDENTIFIER ::={shaping 16}

shapingReceivedVal	OBJECT-TYPE
	SYNTAX	 Counter64
	MAX-ACCESS read-only
	STATUS current
	DESCRIPTION "Packets received"

	::={shapingReceived 1}

shapingReceivedMom	OBJECT-TYPE
	SYNTAX	 CounterBasedGauge64
	MAX-ACCESS read-only
	STATUS current
	DESCRIPTION "Packets received"

	::={shapingReceived 2}

shapingReceivedMax	OBJECT-TYPE
	SYNTAX	 CounterBasedGauge64
	MAX-ACCESS read-only
	STATUS current
	DESCRIPTION "Packets received"

	::={shapingReceived 3}

shapingObjectChecks	OBJECT IDENTIFIER ::={shaping 17}

shapingObjectChecksVal	OBJECT-TYPE
	SYNTAX	 Counter64
	MAX-ACCESS read-only
	STATUS current
	DESCRIPTION "Object checks"

	::={shapingObjectChecks 1}

shapingObjectChecksMom	OBJECT-TYPE
	SYNTAX	 CounterBasedGauge64
	MAX-ACCESS read-only
	STATUS current
	DESCRIPTION "Object checks"

	::={shapingObjectChecks 2}

shapingObjectChecksMax	OBJECT-TYPE
	SYNTAX	 CounterBasedGauge64
	MAX-ACCESS read-only
	STATUS current
	DESCRIPTION "Object checks"

	::={shapingObjectChecks 3}

shapingObjectPoolExhausted	OBJECT IDENTIFIER ::={shaping 25}

shapingObjectPoolExhaustedVal	OBJECT-TYPE
	SYNTAX	 Counter64
	MAX-ACCESS read-only
	STATUS current
	DESCRIPTION "Too many dynamic objects"

	::={shapingObjectPoolExhausted 1}

shapingObjectPoolExhaustedMom	OBJECT-TYPE
	SYNTAX	 CounterBasedGauge64
	MAX-ACCESS read-only
	STATUS current
	DESCRIPTION "Too many dynamic objects"

	::={shapingObjectPoolExhausted 2}

shapingObjectPoolExhaustedMax	OBJECT-TYPE
	SYNTAX	 CounterBasedGauge64
	MAX-ACCESS read-only
	STATUS current
	DESCRIPTION "Too many dynamic objects"

	::={shapingObjectPoolExhausted 3}

shapingOutOfCreditsDrops	OBJECT IDENTIFIER ::={shaping 26}

shapingOutOfCreditsDropsVal	OBJECT-TYPE
	SYNTAX	 Counter64
	MAX-ACCESS read-only
	STATUS current
	DESCRIPTION "Out of credits (vbs) drops"

	::={shapingOutOfCreditsDrops 1}

shapingOutOfCreditsDropsMom	OBJECT-TYPE
	SYNTAX	 CounterBasedGauge64
	MAX-ACCESS read-only
	STATUS current
	DESCRIPTION "Out of credits (vbs) drops"

	::={shapingOutOfCreditsDrops 2}

shapingOutOfCreditsDropsMax	OBJECT-TYPE
	SYNTAX	 CounterBasedGauge64
	MAX-ACCESS read-only
	STATUS current
	DESCRIPTION "Out of credits (vbs) drops"

	::={shapingOutOfCreditsDrops 3}

shapingObjectOverflow	OBJECT IDENTIFIER ::={shaping 31}

shapingObjectOverflowVal	OBJECT-TYPE
	SYNTAX	 Counter64
	MAX-ACCESS read-only
	STATUS current
	DESCRIPTION "Too many shaping objects matching a connection"

	::={shapingObjectOverflow 1}

shapingObjectOverflowMom	OBJECT-TYPE
	SYNTAX	 CounterBasedGauge64
	MAX-ACCESS read-only
	STATUS current
	DESCRIPTION "Too many shaping objects matching a connection"

	::={shapingObjectOverflow 2}

shapingObjectOverflowMax	OBJECT-TYPE
	SYNTAX	 CounterBasedGauge64
	MAX-ACCESS read-only
	STATUS current
	DESCRIPTION "Too many shaping objects matching a connection"

	::={shapingObjectOverflow 3}

shapingRuleOverflow	OBJECT IDENTIFIER ::={shaping 32}

shapingRuleOverflowVal	OBJECT-TYPE
	SYNTAX	 Counter64
	MAX-ACCESS read-only
	STATUS current
	DESCRIPTION "Too many matching rules"

	::={shapingRuleOverflow 1}

shapingRuleOverflowMom	OBJECT-TYPE
	SYNTAX	 CounterBasedGauge64
	MAX-ACCESS read-only
	STATUS current
	DESCRIPTION "Too many matching rules"

	::={shapingRuleOverflow 2}

shapingRuleOverflowMax	OBJECT-TYPE
	SYNTAX	 CounterBasedGauge64
	MAX-ACCESS read-only
	STATUS current
	DESCRIPTION "Too many matching rules"

	::={shapingRuleOverflow 3}

shapingDrops	OBJECT IDENTIFIER ::={shaping 37}

shapingDropsVal	OBJECT-TYPE
	SYNTAX	 Counter64
	MAX-ACCESS read-only
	STATUS current
	DESCRIPTION "Queuing drops (all types)"

	::={shapingDrops 1}

shapingDropsMom	OBJECT-TYPE
	SYNTAX	 CounterBasedGauge64
	MAX-ACCESS read-only
	STATUS current
	DESCRIPTION "Queuing drops (all types)"

	::={shapingDrops 2}

shapingDropsMax	OBJECT-TYPE
	SYNTAX	 CounterBasedGauge64
	MAX-ACCESS read-only
	STATUS current
	DESCRIPTION "Queuing drops (all types)"

	::={shapingDrops 3}

shapingObjectFull	OBJECT IDENTIFIER ::={shaping 38}

shapingObjectFullVal	OBJECT-TYPE
	SYNTAX	 Counter64
	MAX-ACCESS read-only
	STATUS current
	DESCRIPTION "Shaping object queue full"

	::={shapingObjectFull 1}

shapingObjectFullMom	OBJECT-TYPE
	SYNTAX	 CounterBasedGauge64
	MAX-ACCESS read-only
	STATUS current
	DESCRIPTION "Shaping object queue full"

	::={shapingObjectFull 2}

shapingObjectFullMax	OBJECT-TYPE
	SYNTAX	 CounterBasedGauge64
	MAX-ACCESS read-only
	STATUS current
	DESCRIPTION "Shaping object queue full"

	::={shapingObjectFull 3}

shapingUnshaped	OBJECT IDENTIFIER ::={shaping 39}

shapingUnshapedVal	OBJECT-TYPE
	SYNTAX	 Counter64
	MAX-ACCESS read-only
	STATUS current
	DESCRIPTION "Unshaped packets"

	::={shapingUnshaped 1}

shapingUnshapedMom	OBJECT-TYPE
	SYNTAX	 CounterBasedGauge64
	MAX-ACCESS read-only
	STATUS current
	DESCRIPTION "Unshaped packets"

	::={shapingUnshaped 2}

shapingUnshapedMax	OBJECT-TYPE
	SYNTAX	 CounterBasedGauge64
	MAX-ACCESS read-only
	STATUS current
	DESCRIPTION "Unshaped packets"

	::={shapingUnshaped 3}

shapingUnshapedBytes	OBJECT IDENTIFIER ::={shaping 40}

shapingUnshapedBytesVal	OBJECT-TYPE
	SYNTAX	 Counter64
	MAX-ACCESS read-only
	STATUS current
	DESCRIPTION "Unshaped bytes"

	::={shapingUnshapedBytes 1}

shapingUnshapedBytesMom	OBJECT-TYPE
	SYNTAX	 CounterBasedGauge64
	MAX-ACCESS read-only
	STATUS current
	DESCRIPTION "Unshaped bytes"

	::={shapingUnshapedBytes 2}

shapingUnshapedBytesMax	OBJECT-TYPE
	SYNTAX	 CounterBasedGauge64
	MAX-ACCESS read-only
	STATUS current
	DESCRIPTION "Unshaped bytes"

	::={shapingUnshapedBytes 3}

shapingDequeueCalls	OBJECT IDENTIFIER ::={shaping 41}

shapingDequeueCallsVal	OBJECT-TYPE
	SYNTAX	 Counter64
	MAX-ACCESS read-only
	STATUS current
	DESCRIPTION "Dequeue calls"

	::={shapingDequeueCalls 1}

shapingDequeueCallsMom	OBJECT-TYPE
	SYNTAX	 CounterBasedGauge64
	MAX-ACCESS read-only
	STATUS current
	DESCRIPTION "Dequeue calls"

	::={shapingDequeueCalls 2}

shapingDequeueCallsMax	OBJECT-TYPE
	SYNTAX	 CounterBasedGauge64
	MAX-ACCESS read-only
	STATUS current
	DESCRIPTION "Dequeue calls"

	::={shapingDequeueCalls 3}

shapingRecycleObjects	OBJECT IDENTIFIER ::={shaping 42}

shapingRecycleObjectsVal	OBJECT-TYPE
	SYNTAX	 CounterBasedGauge64
	MAX-ACCESS read-only
	STATUS current
	DESCRIPTION "Objects in recycle queue"

	::={shapingRecycleObjects 1}

shapingRecycleObjectsMax	OBJECT-TYPE
	SYNTAX	 CounterBasedGauge64
	MAX-ACCESS read-only
	STATUS current
	DESCRIPTION "Objects in recycle queue"

	::={shapingRecycleObjects 3}

shapingDirect	OBJECT IDENTIFIER ::={shaping 44}

shapingDirectVal	OBJECT-TYPE
	SYNTAX	 Counter64
	MAX-ACCESS read-only
	STATUS current
	DESCRIPTION "Directly sent packets"

	::={shapingDirect 1}

shapingDirectMom	OBJECT-TYPE
	SYNTAX	 CounterBasedGauge64
	MAX-ACCESS read-only
	STATUS current
	DESCRIPTION "Directly sent packets"

	::={shapingDirect 2}

shapingDirectMax	OBJECT-TYPE
	SYNTAX	 CounterBasedGauge64
	MAX-ACCESS read-only
	STATUS current
	DESCRIPTION "Directly sent packets"

	::={shapingDirect 3}

shapingDirectBytes	OBJECT IDENTIFIER ::={shaping 45}

shapingDirectBytesVal	OBJECT-TYPE
	SYNTAX	 Counter64
	MAX-ACCESS read-only
	STATUS current
	DESCRIPTION "Directly sent bytes"

	::={shapingDirectBytes 1}

shapingDirectBytesMom	OBJECT-TYPE
	SYNTAX	 CounterBasedGauge64
	MAX-ACCESS read-only
	STATUS current
	DESCRIPTION "Directly sent bytes"

	::={shapingDirectBytes 2}

shapingDirectBytesMax	OBJECT-TYPE
	SYNTAX	 CounterBasedGauge64
	MAX-ACCESS read-only
	STATUS current
	DESCRIPTION "Directly sent bytes"

	::={shapingDirectBytes 3}

shapingBorrowDequeues	OBJECT IDENTIFIER ::={shaping 46}

shapingBorrowDequeuesVal	OBJECT-TYPE
	SYNTAX	 Counter64
	MAX-ACCESS read-only
	STATUS current
	DESCRIPTION "Borrowing dequeues"

	::={shapingBorrowDequeues 1}

shapingBorrowDequeuesMom	OBJECT-TYPE
	SYNTAX	 CounterBasedGauge64
	MAX-ACCESS read-only
	STATUS current
	DESCRIPTION "Borrowing dequeues"

	::={shapingBorrowDequeues 2}

shapingBorrowDequeuesMax	OBJECT-TYPE
	SYNTAX	 CounterBasedGauge64
	MAX-ACCESS read-only
	STATUS current
	DESCRIPTION "Borrowing dequeues"

	::={shapingBorrowDequeues 3}

shapingVbsSplitError	OBJECT IDENTIFIER ::={shaping 47}

shapingVbsSplitErrorVal	OBJECT-TYPE
	SYNTAX	 Counter64
	MAX-ACCESS read-only
	STATUS obsolete
	DESCRIPTION "VBS split allocation failures"

	::={shapingVbsSplitError 1}

shapingVbsSplitErrorMom	OBJECT-TYPE
	SYNTAX	 CounterBasedGauge64
	MAX-ACCESS read-only
	STATUS obsolete
	DESCRIPTION "VBS split allocation failures"

	::={shapingVbsSplitError 2}

shapingVbsSplitErrorMax	OBJECT-TYPE
	SYNTAX	 CounterBasedGauge64
	MAX-ACCESS read-only
	STATUS obsolete
	DESCRIPTION "VBS split allocation failures"

	::={shapingVbsSplitError 3}

shapingBrownHostDrops	OBJECT IDENTIFIER ::={shaping 48}

shapingBrownHostDropsVal	OBJECT-TYPE
	SYNTAX	 Counter64
	MAX-ACCESS read-only
	STATUS current
	DESCRIPTION "BROWN per host drops"

	::={shapingBrownHostDrops 1}

shapingBrownHostDropsMom	OBJECT-TYPE
	SYNTAX	 CounterBasedGauge64
	MAX-ACCESS read-only
	STATUS current
	DESCRIPTION "BROWN per host drops"

	::={shapingBrownHostDrops 2}

shapingBrownHostDropsMax	OBJECT-TYPE
	SYNTAX	 CounterBasedGauge64
	MAX-ACCESS read-only
	STATUS current
	DESCRIPTION "BROWN per host drops"

	::={shapingBrownHostDrops 3}

shapingMaxConnDrops	OBJECT IDENTIFIER ::={shaping 49}

shapingMaxConnDropsVal	OBJECT-TYPE
	SYNTAX	 Counter64
	MAX-ACCESS read-only
	STATUS current
	DESCRIPTION "Object max connections reached"

	::={shapingMaxConnDrops 1}

shapingMaxConnDropsMom	OBJECT-TYPE
	SYNTAX	 CounterBasedGauge64
	MAX-ACCESS read-only
	STATUS current
	DESCRIPTION "Object max connections reached"

	::={shapingMaxConnDrops 2}

shapingMaxConnDropsMax	OBJECT-TYPE
	SYNTAX	 CounterBasedGauge64
	MAX-ACCESS read-only
	STATUS current
	DESCRIPTION "Object max connections reached"

	::={shapingMaxConnDrops 3}

shapingScheduledOdirs	OBJECT IDENTIFIER ::={shaping 50}

shapingScheduledOdirsVal	OBJECT-TYPE
	SYNTAX	 CounterBasedGauge64
	MAX-ACCESS read-only
	STATUS current
	DESCRIPTION "Scheduled odirs"

	::={shapingScheduledOdirs 1}

shapingScheduledOdirsMax	OBJECT-TYPE
	SYNTAX	 CounterBasedGauge64
	MAX-ACCESS read-only
	STATUS current
	DESCRIPTION "Scheduled odirs"

	::={shapingScheduledOdirs 3}

shapingQueuePoolExhausted	OBJECT IDENTIFIER ::={shaping 51}

shapingQueuePoolExhaustedVal	OBJECT-TYPE
	SYNTAX	 Counter64
	MAX-ACCESS read-only
	STATUS current
	DESCRIPTION "Queue pool exhausted"

	::={shapingQueuePoolExhausted 1}

shapingQueuePoolExhaustedMom	OBJECT-TYPE
	SYNTAX	 CounterBasedGauge64
	MAX-ACCESS read-only
	STATUS current
	DESCRIPTION "Queue pool exhausted"

	::={shapingQueuePoolExhausted 2}

shapingQueuePoolExhaustedMax	OBJECT-TYPE
	SYNTAX	 CounterBasedGauge64
	MAX-ACCESS read-only
	STATUS current
	DESCRIPTION "Queue pool exhausted"

	::={shapingQueuePoolExhausted 3}

shapingActiveQueues	OBJECT IDENTIFIER ::={shaping 52}

shapingActiveQueuesVal	OBJECT-TYPE
	SYNTAX	 CounterBasedGauge64
	MAX-ACCESS read-only
	STATUS current
	DESCRIPTION "Active queues"

	::={shapingActiveQueues 1}

shapingActiveQueuesMax	OBJECT-TYPE
	SYNTAX	 CounterBasedGauge64
	MAX-ACCESS read-only
	STATUS current
	DESCRIPTION "Active queues"

	::={shapingActiveQueues 3}

shapingQueueAllocations	OBJECT IDENTIFIER ::={shaping 53}

shapingQueueAllocationsVal	OBJECT-TYPE
	SYNTAX	 Counter64
	MAX-ACCESS read-only
	STATUS current
	DESCRIPTION "Queue allocations"

	::={shapingQueueAllocations 1}

shapingQueueAllocationsMom	OBJECT-TYPE
	SYNTAX	 CounterBasedGauge64
	MAX-ACCESS read-only
	STATUS current
	DESCRIPTION "Queue allocations"

	::={shapingQueueAllocations 2}

shapingQueueAllocationsMax	OBJECT-TYPE
	SYNTAX	 CounterBasedGauge64
	MAX-ACCESS read-only
	STATUS current
	DESCRIPTION "Queue allocations"

	::={shapingQueueAllocations 3}

shapingDropsPrio1	OBJECT IDENTIFIER ::={shaping 54}

shapingDropsPrio1Val	OBJECT-TYPE
	SYNTAX	 Counter64
	MAX-ACCESS read-only
	STATUS current
	DESCRIPTION "Queuing drops (prio 1)"

	::={shapingDropsPrio1 1}

shapingDropsPrio1Mom	OBJECT-TYPE
	SYNTAX	 CounterBasedGauge64
	MAX-ACCESS read-only
	STATUS current
	DESCRIPTION "Queuing drops (prio 1)"

	::={shapingDropsPrio1 2}

shapingDropsPrio1Max	OBJECT-TYPE
	SYNTAX	 CounterBasedGauge64
	MAX-ACCESS read-only
	STATUS current
	DESCRIPTION "Queuing drops (prio 1)"

	::={shapingDropsPrio1 3}

shapingDropsPrio2	OBJECT IDENTIFIER ::={shaping 55}

shapingDropsPrio2Val	OBJECT-TYPE
	SYNTAX	 Counter64
	MAX-ACCESS read-only
	STATUS current
	DESCRIPTION "Queuing drops (prio 2)"

	::={shapingDropsPrio2 1}

shapingDropsPrio2Mom	OBJECT-TYPE
	SYNTAX	 CounterBasedGauge64
	MAX-ACCESS read-only
	STATUS current
	DESCRIPTION "Queuing drops (prio 2)"

	::={shapingDropsPrio2 2}

shapingDropsPrio2Max	OBJECT-TYPE
	SYNTAX	 CounterBasedGauge64
	MAX-ACCESS read-only
	STATUS current
	DESCRIPTION "Queuing drops (prio 2)"

	::={shapingDropsPrio2 3}

shapingDropsPrio3	OBJECT IDENTIFIER ::={shaping 56}

shapingDropsPrio3Val	OBJECT-TYPE
	SYNTAX	 Counter64
	MAX-ACCESS read-only
	STATUS current
	DESCRIPTION "Queuing drops (prio 3)"

	::={shapingDropsPrio3 1}

shapingDropsPrio3Mom	OBJECT-TYPE
	SYNTAX	 CounterBasedGauge64
	MAX-ACCESS read-only
	STATUS current
	DESCRIPTION "Queuing drops (prio 3)"

	::={shapingDropsPrio3 2}

shapingDropsPrio3Max	OBJECT-TYPE
	SYNTAX	 CounterBasedGauge64
	MAX-ACCESS read-only
	STATUS current
	DESCRIPTION "Queuing drops (prio 3)"

	::={shapingDropsPrio3 3}

shapingDropsPrio4	OBJECT IDENTIFIER ::={shaping 57}

shapingDropsPrio4Val	OBJECT-TYPE
	SYNTAX	 Counter64
	MAX-ACCESS read-only
	STATUS current
	DESCRIPTION "Queuing drops (prio 4)"

	::={shapingDropsPrio4 1}

shapingDropsPrio4Mom	OBJECT-TYPE
	SYNTAX	 CounterBasedGauge64
	MAX-ACCESS read-only
	STATUS current
	DESCRIPTION "Queuing drops (prio 4)"

	::={shapingDropsPrio4 2}

shapingDropsPrio4Max	OBJECT-TYPE
	SYNTAX	 CounterBasedGauge64
	MAX-ACCESS read-only
	STATUS current
	DESCRIPTION "Queuing drops (prio 4)"

	::={shapingDropsPrio4 3}

shapingDropsPrio5	OBJECT IDENTIFIER ::={shaping 58}

shapingDropsPrio5Val	OBJECT-TYPE
	SYNTAX	 Counter64
	MAX-ACCESS read-only
	STATUS current
	DESCRIPTION "Queuing drops (prio 5)"

	::={shapingDropsPrio5 1}

shapingDropsPrio5Mom	OBJECT-TYPE
	SYNTAX	 CounterBasedGauge64
	MAX-ACCESS read-only
	STATUS current
	DESCRIPTION "Queuing drops (prio 5)"

	::={shapingDropsPrio5 2}

shapingDropsPrio5Max	OBJECT-TYPE
	SYNTAX	 CounterBasedGauge64
	MAX-ACCESS read-only
	STATUS current
	DESCRIPTION "Queuing drops (prio 5)"

	::={shapingDropsPrio5 3}

shapingDropsPrio6	OBJECT IDENTIFIER ::={shaping 59}

shapingDropsPrio6Val	OBJECT-TYPE
	SYNTAX	 Counter64
	MAX-ACCESS read-only
	STATUS current
	DESCRIPTION "Queuing drops (prio 6)"

	::={shapingDropsPrio6 1}

shapingDropsPrio6Mom	OBJECT-TYPE
	SYNTAX	 CounterBasedGauge64
	MAX-ACCESS read-only
	STATUS current
	DESCRIPTION "Queuing drops (prio 6)"

	::={shapingDropsPrio6 2}

shapingDropsPrio6Max	OBJECT-TYPE
	SYNTAX	 CounterBasedGauge64
	MAX-ACCESS read-only
	STATUS current
	DESCRIPTION "Queuing drops (prio 6)"

	::={shapingDropsPrio6 3}

shapingDropsPrio7	OBJECT IDENTIFIER ::={shaping 60}

shapingDropsPrio7Val	OBJECT-TYPE
	SYNTAX	 Counter64
	MAX-ACCESS read-only
	STATUS current
	DESCRIPTION "Queuing drops (prio 7)"

	::={shapingDropsPrio7 1}

shapingDropsPrio7Mom	OBJECT-TYPE
	SYNTAX	 CounterBasedGauge64
	MAX-ACCESS read-only
	STATUS current
	DESCRIPTION "Queuing drops (prio 7)"

	::={shapingDropsPrio7 2}

shapingDropsPrio7Max	OBJECT-TYPE
	SYNTAX	 CounterBasedGauge64
	MAX-ACCESS read-only
	STATUS current
	DESCRIPTION "Queuing drops (prio 7)"

	::={shapingDropsPrio7 3}

shapingDropsPrio8	OBJECT IDENTIFIER ::={shaping 61}

shapingDropsPrio8Val	OBJECT-TYPE
	SYNTAX	 Counter64
	MAX-ACCESS read-only
	STATUS current
	DESCRIPTION "Queuing drops (prio 8)"

	::={shapingDropsPrio8 1}

shapingDropsPrio8Mom	OBJECT-TYPE
	SYNTAX	 CounterBasedGauge64
	MAX-ACCESS read-only
	STATUS current
	DESCRIPTION "Queuing drops (prio 8)"

	::={shapingDropsPrio8 2}

shapingDropsPrio8Max	OBJECT-TYPE
	SYNTAX	 CounterBasedGauge64
	MAX-ACCESS read-only
	STATUS current
	DESCRIPTION "Queuing drops (prio 8)"

	::={shapingDropsPrio8 3}

shapingDropsPrio9	OBJECT IDENTIFIER ::={shaping 62}

shapingDropsPrio9Val	OBJECT-TYPE
	SYNTAX	 Counter64
	MAX-ACCESS read-only
	STATUS current
	DESCRIPTION "Queuing drops (prio 9)"

	::={shapingDropsPrio9 1}

shapingDropsPrio9Mom	OBJECT-TYPE
	SYNTAX	 CounterBasedGauge64
	MAX-ACCESS read-only
	STATUS current
	DESCRIPTION "Queuing drops (prio 9)"

	::={shapingDropsPrio9 2}

shapingDropsPrio9Max	OBJECT-TYPE
	SYNTAX	 CounterBasedGauge64
	MAX-ACCESS read-only
	STATUS current
	DESCRIPTION "Queuing drops (prio 9)"

	::={shapingDropsPrio9 3}

shapingDropsPrioOther	OBJECT IDENTIFIER ::={shaping 63}

shapingDropsPrioOtherVal	OBJECT-TYPE
	SYNTAX	 Counter64
	MAX-ACCESS read-only
	STATUS current
	DESCRIPTION "Queuing drops (other prio)"

	::={shapingDropsPrioOther 1}

shapingDropsPrioOtherMom	OBJECT-TYPE
	SYNTAX	 CounterBasedGauge64
	MAX-ACCESS read-only
	STATUS current
	DESCRIPTION "Queuing drops (other prio)"

	::={shapingDropsPrioOther 2}

shapingDropsPrioOtherMax	OBJECT-TYPE
	SYNTAX	 CounterBasedGauge64
	MAX-ACCESS read-only
	STATUS current
	DESCRIPTION "Queuing drops (other prio)"

	::={shapingDropsPrioOther 3}

shapingDropsCps	OBJECT IDENTIFIER ::={shaping 64}

shapingDropsCpsVal	OBJECT-TYPE
	SYNTAX	 Counter64
	MAX-ACCESS read-only
	STATUS current
	DESCRIPTION "CPS limit drops"

	::={shapingDropsCps 1}

shapingDropsCpsMom	OBJECT-TYPE
	SYNTAX	 CounterBasedGauge64
	MAX-ACCESS read-only
	STATUS current
	DESCRIPTION "CPS limit drops"

	::={shapingDropsCps 2}

shapingDropsCpsMax	OBJECT-TYPE
	SYNTAX	 CounterBasedGauge64
	MAX-ACCESS read-only
	STATUS current
	DESCRIPTION "CPS limit drops"

	::={shapingDropsCps 3}

shapingFailedFairnessObjects	OBJECT IDENTIFIER ::={shaping 65}

shapingFailedFairnessObjectsVal	OBJECT-TYPE
	SYNTAX	 Counter64
	MAX-ACCESS read-only
	STATUS current
	DESCRIPTION "Host fairness data allocation failures"

	::={shapingFailedFairnessObjects 1}

shapingFailedFairnessObjectsMom	OBJECT-TYPE
	SYNTAX	 CounterBasedGauge64
	MAX-ACCESS read-only
	STATUS current
	DESCRIPTION "Host fairness data allocation failures"

	::={shapingFailedFairnessObjects 2}

shapingFailedFairnessObjectsMax	OBJECT-TYPE
	SYNTAX	 CounterBasedGauge64
	MAX-ACCESS read-only
	STATUS current
	DESCRIPTION "Host fairness data allocation failures"

	::={shapingFailedFairnessObjects 3}

shapingUsedFairnessObjects	OBJECT IDENTIFIER ::={shaping 66}

shapingUsedFairnessObjectsVal	OBJECT-TYPE
	SYNTAX	 CounterBasedGauge64
	MAX-ACCESS read-only
	STATUS current
	DESCRIPTION "Host fairness data used"

	::={shapingUsedFairnessObjects 1}

shapingUsedFairnessObjectsMax	OBJECT-TYPE
	SYNTAX	 CounterBasedGauge64
	MAX-ACCESS read-only
	STATUS current
	DESCRIPTION "Host fairness data used"

	::={shapingUsedFairnessObjects 3}

shapingReloadDrops	OBJECT IDENTIFIER ::={shaping 67}

shapingReloadDropsVal	OBJECT-TYPE
	SYNTAX	 Counter64
	MAX-ACCESS read-only
	STATUS current
	DESCRIPTION "Drops caused by ruleset reload"

	::={shapingReloadDrops 1}

shapingReloadDropsMom	OBJECT-TYPE
	SYNTAX	 CounterBasedGauge64
	MAX-ACCESS read-only
	STATUS current
	DESCRIPTION "Drops caused by ruleset reload"

	::={shapingReloadDrops 2}

shapingReloadDropsMax	OBJECT-TYPE
	SYNTAX	 CounterBasedGauge64
	MAX-ACCESS read-only
	STATUS current
	DESCRIPTION "Drops caused by ruleset reload"

	::={shapingReloadDrops 3}

shapingRequeueQueueUsed	OBJECT IDENTIFIER ::={shaping 68}

shapingRequeueQueueUsedVal	OBJECT-TYPE
	SYNTAX	 CounterBasedGauge64
	MAX-ACCESS read-only
	STATUS current
	DESCRIPTION "Packets in requeue queue"

	::={shapingRequeueQueueUsed 1}

shapingRequeueQueueUsedMax	OBJECT-TYPE
	SYNTAX	 CounterBasedGauge64
	MAX-ACCESS read-only
	STATUS current
	DESCRIPTION "Packets in requeue queue"

	::={shapingRequeueQueueUsed 3}

shapingDirectBytesPrio0	OBJECT IDENTIFIER ::={shaping 69}

shapingDirectBytesPrio0Val	OBJECT-TYPE
	SYNTAX	 Counter64
	MAX-ACCESS read-only
	STATUS current
	DESCRIPTION "Directly sent bytes (prio 0)"

	::={shapingDirectBytesPrio0 1}

shapingDirectBytesPrio0Mom	OBJECT-TYPE
	SYNTAX	 CounterBasedGauge64
	MAX-ACCESS read-only
	STATUS current
	DESCRIPTION "Directly sent bytes (prio 0)"

	::={shapingDirectBytesPrio0 2}

shapingDirectBytesPrio0Max	OBJECT-TYPE
	SYNTAX	 CounterBasedGauge64
	MAX-ACCESS read-only
	STATUS current
	DESCRIPTION "Directly sent bytes (prio 0)"

	::={shapingDirectBytesPrio0 3}

shapingDequeuedOdirs	OBJECT IDENTIFIER ::={shaping 70}

shapingDequeuedOdirsVal	OBJECT-TYPE
	SYNTAX	 Counter64
	MAX-ACCESS read-only
	STATUS current
	DESCRIPTION "Dequeued Odirs"

	::={shapingDequeuedOdirs 1}

shapingDequeuedOdirsMom	OBJECT-TYPE
	SYNTAX	 CounterBasedGauge64
	MAX-ACCESS read-only
	STATUS current
	DESCRIPTION "Dequeued Odirs"

	::={shapingDequeuedOdirs 2}

shapingDequeuedOdirsMax	OBJECT-TYPE
	SYNTAX	 CounterBasedGauge64
	MAX-ACCESS read-only
	STATUS current
	DESCRIPTION "Dequeued Odirs"

	::={shapingDequeuedOdirs 3}

shapingSkippedQsyncUpdates	OBJECT IDENTIFIER ::={shaping 71}

shapingSkippedQsyncUpdatesVal	OBJECT-TYPE
	SYNTAX	 Counter64
	MAX-ACCESS read-only
	STATUS current
	DESCRIPTION "Skipped qsync updates (no xfer)"

	::={shapingSkippedQsyncUpdates 1}

shapingSkippedQsyncUpdatesMom	OBJECT-TYPE
	SYNTAX	 CounterBasedGauge64
	MAX-ACCESS read-only
	STATUS current
	DESCRIPTION "Skipped qsync updates (no xfer)"

	::={shapingSkippedQsyncUpdates 2}

shapingSkippedQsyncUpdatesMax	OBJECT-TYPE
	SYNTAX	 CounterBasedGauge64
	MAX-ACCESS read-only
	STATUS current
	DESCRIPTION "Skipped qsync updates (no xfer)"

	::={shapingSkippedQsyncUpdates 3}

shapingObjectCopiesCreated	OBJECT IDENTIFIER ::={shaping 72}

shapingObjectCopiesCreatedVal	OBJECT-TYPE
	SYNTAX	 Counter64
	MAX-ACCESS read-only
	STATUS current
	DESCRIPTION "Object copies created"

	::={shapingObjectCopiesCreated 1}

shapingObjectCopiesCreatedMom	OBJECT-TYPE
	SYNTAX	 CounterBasedGauge64
	MAX-ACCESS read-only
	STATUS current
	DESCRIPTION "Object copies created"

	::={shapingObjectCopiesCreated 2}

shapingObjectCopiesCreatedMax	OBJECT-TYPE
	SYNTAX	 CounterBasedGauge64
	MAX-ACCESS read-only
	STATUS current
	DESCRIPTION "Object copies created"

	::={shapingObjectCopiesCreated 3}

shapingEcnMarks	OBJECT IDENTIFIER ::={shaping 73}

shapingEcnMarksVal	OBJECT-TYPE
	SYNTAX	 Counter64
	MAX-ACCESS read-only
	STATUS current
	DESCRIPTION "ECN Marked Packets"

	::={shapingEcnMarks 1}

shapingEcnMarksMom	OBJECT-TYPE
	SYNTAX	 CounterBasedGauge64
	MAX-ACCESS read-only
	STATUS current
	DESCRIPTION "ECN Marked Packets"

	::={shapingEcnMarks 2}

shapingEcnMarksMax	OBJECT-TYPE
	SYNTAX	 CounterBasedGauge64
	MAX-ACCESS read-only
	STATUS current
	DESCRIPTION "ECN Marked Packets"

	::={shapingEcnMarks 3}

pppoe	OBJECT IDENTIFIER ::={sysdiag 96}

pppoeShortPackets	OBJECT IDENTIFIER ::={pppoe 1}

pppoeShortPacketsVal	OBJECT-TYPE
	SYNTAX	 Counter64
	MAX-ACCESS read-only
	STATUS current
	DESCRIPTION "Short Packets dropped"

	::={pppoeShortPackets 1}

pppoeShortPacketsMom	OBJECT-TYPE
	SYNTAX	 CounterBasedGauge64
	MAX-ACCESS read-only
	STATUS current
	DESCRIPTION "Short Packets dropped"

	::={pppoeShortPackets 2}

pppoeShortPacketsMax	OBJECT-TYPE
	SYNTAX	 CounterBasedGauge64
	MAX-ACCESS read-only
	STATUS current
	DESCRIPTION "Short Packets dropped"

	::={pppoeShortPackets 3}

pppoeBadversionPackets	OBJECT IDENTIFIER ::={pppoe 2}

pppoeBadversionPacketsVal	OBJECT-TYPE
	SYNTAX	 Counter64
	MAX-ACCESS read-only
	STATUS current
	DESCRIPTION "Packets with unknown version"

	::={pppoeBadversionPackets 1}

pppoeBadversionPacketsMom	OBJECT-TYPE
	SYNTAX	 CounterBasedGauge64
	MAX-ACCESS read-only
	STATUS current
	DESCRIPTION "Packets with unknown version"

	::={pppoeBadversionPackets 2}

pppoeBadversionPacketsMax	OBJECT-TYPE
	SYNTAX	 CounterBasedGauge64
	MAX-ACCESS read-only
	STATUS current
	DESCRIPTION "Packets with unknown version"

	::={pppoeBadversionPackets 3}

pppoeControlPackets	OBJECT IDENTIFIER ::={pppoe 3}

pppoeControlPacketsVal	OBJECT-TYPE
	SYNTAX	 Counter64
	MAX-ACCESS read-only
	STATUS current
	DESCRIPTION "Control packets"

	::={pppoeControlPackets 1}

pppoeControlPacketsMom	OBJECT-TYPE
	SYNTAX	 CounterBasedGauge64
	MAX-ACCESS read-only
	STATUS current
	DESCRIPTION "Control packets"

	::={pppoeControlPackets 2}

pppoeControlPacketsMax	OBJECT-TYPE
	SYNTAX	 CounterBasedGauge64
	MAX-ACCESS read-only
	STATUS current
	DESCRIPTION "Control packets"

	::={pppoeControlPackets 3}

pppoeTruncatedPackets	OBJECT IDENTIFIER ::={pppoe 4}

pppoeTruncatedPacketsVal	OBJECT-TYPE
	SYNTAX	 Counter64
	MAX-ACCESS read-only
	STATUS current
	DESCRIPTION "Truncated packets dropped"

	::={pppoeTruncatedPackets 1}

pppoeTruncatedPacketsMom	OBJECT-TYPE
	SYNTAX	 CounterBasedGauge64
	MAX-ACCESS read-only
	STATUS current
	DESCRIPTION "Truncated packets dropped"

	::={pppoeTruncatedPackets 2}

pppoeTruncatedPacketsMax	OBJECT-TYPE
	SYNTAX	 CounterBasedGauge64
	MAX-ACCESS read-only
	STATUS current
	DESCRIPTION "Truncated packets dropped"

	::={pppoeTruncatedPackets 3}

pppoePaddedPackets	OBJECT IDENTIFIER ::={pppoe 5}

pppoePaddedPacketsVal	OBJECT-TYPE
	SYNTAX	 Counter64
	MAX-ACCESS read-only
	STATUS current
	DESCRIPTION "Padded packets"

	::={pppoePaddedPackets 1}

pppoePaddedPacketsMom	OBJECT-TYPE
	SYNTAX	 CounterBasedGauge64
	MAX-ACCESS read-only
	STATUS current
	DESCRIPTION "Padded packets"

	::={pppoePaddedPackets 2}

pppoePaddedPacketsMax	OBJECT-TYPE
	SYNTAX	 CounterBasedGauge64
	MAX-ACCESS read-only
	STATUS current
	DESCRIPTION "Padded packets"

	::={pppoePaddedPackets 3}

pppoeIpv4Packets	OBJECT IDENTIFIER ::={pppoe 6}

pppoeIpv4PacketsVal	OBJECT-TYPE
	SYNTAX	 Counter64
	MAX-ACCESS read-only
	STATUS current
	DESCRIPTION "IPv4 packets"

	::={pppoeIpv4Packets 1}

pppoeIpv4PacketsMom	OBJECT-TYPE
	SYNTAX	 CounterBasedGauge64
	MAX-ACCESS read-only
	STATUS current
	DESCRIPTION "IPv4 packets"

	::={pppoeIpv4Packets 2}

pppoeIpv4PacketsMax	OBJECT-TYPE
	SYNTAX	 CounterBasedGauge64
	MAX-ACCESS read-only
	STATUS current
	DESCRIPTION "IPv4 packets"

	::={pppoeIpv4Packets 3}

pppoeNonIpPackets	OBJECT IDENTIFIER ::={pppoe 7}

pppoeNonIpPacketsVal	OBJECT-TYPE
	SYNTAX	 Counter64
	MAX-ACCESS read-only
	STATUS current
	DESCRIPTION "Non IP packets"

	::={pppoeNonIpPackets 1}

pppoeNonIpPacketsMom	OBJECT-TYPE
	SYNTAX	 CounterBasedGauge64
	MAX-ACCESS read-only
	STATUS current
	DESCRIPTION "Non IP packets"

	::={pppoeNonIpPackets 2}

pppoeNonIpPacketsMax	OBJECT-TYPE
	SYNTAX	 CounterBasedGauge64
	MAX-ACCESS read-only
	STATUS current
	DESCRIPTION "Non IP packets"

	::={pppoeNonIpPackets 3}

pppoeIpv6Packets	OBJECT IDENTIFIER ::={pppoe 8}

pppoeIpv6PacketsVal	OBJECT-TYPE
	SYNTAX	 Counter64
	MAX-ACCESS read-only
	STATUS current
	DESCRIPTION "IPv6 packets"

	::={pppoeIpv6Packets 1}

pppoeIpv6PacketsMom	OBJECT-TYPE
	SYNTAX	 CounterBasedGauge64
	MAX-ACCESS read-only
	STATUS current
	DESCRIPTION "IPv6 packets"

	::={pppoeIpv6Packets 2}

pppoeIpv6PacketsMax	OBJECT-TYPE
	SYNTAX	 CounterBasedGauge64
	MAX-ACCESS read-only
	STATUS current
	DESCRIPTION "IPv6 packets"

	::={pppoeIpv6Packets 3}

interface	OBJECT IDENTIFIER ::={sysdiag 120}

interfaceBytesToEngine	OBJECT IDENTIFIER ::={interface 8}

interfaceBytesToEngineVal	OBJECT-TYPE
	SYNTAX	 Counter64
	MAX-ACCESS read-only
	STATUS current
	DESCRIPTION "Sent to engine"

	::={interfaceBytesToEngine 1}

interfaceBytesToEngineMom	OBJECT-TYPE
	SYNTAX	 CounterBasedGauge64
	MAX-ACCESS read-only
	STATUS current
	DESCRIPTION "Sent to engine"

	::={interfaceBytesToEngine 2}

interfaceBytesToEngineMax	OBJECT-TYPE
	SYNTAX	 CounterBasedGauge64
	MAX-ACCESS read-only
	STATUS current
	DESCRIPTION "Sent to engine"

	::={interfaceBytesToEngine 3}

interfaceBytesFromEngine	OBJECT IDENTIFIER ::={interface 9}

interfaceBytesFromEngineVal	OBJECT-TYPE
	SYNTAX	 Counter64
	MAX-ACCESS read-only
	STATUS current
	DESCRIPTION "Received from engine"

	::={interfaceBytesFromEngine 1}

interfaceBytesFromEngineMom	OBJECT-TYPE
	SYNTAX	 CounterBasedGauge64
	MAX-ACCESS read-only
	STATUS current
	DESCRIPTION "Received from engine"

	::={interfaceBytesFromEngine 2}

interfaceBytesFromEngineMax	OBJECT-TYPE
	SYNTAX	 CounterBasedGauge64
	MAX-ACCESS read-only
	STATUS current
	DESCRIPTION "Received from engine"

	::={interfaceBytesFromEngine 3}

interfaceFlowNewMissed	OBJECT IDENTIFIER ::={interface 10}

interfaceFlowNewMissedVal	OBJECT-TYPE
	SYNTAX	 Counter64
	MAX-ACCESS read-only
	STATUS current
	DESCRIPTION "New flows missed"

	::={interfaceFlowNewMissed 1}

interfaceFlowNewMissedMom	OBJECT-TYPE
	SYNTAX	 CounterBasedGauge64
	MAX-ACCESS read-only
	STATUS current
	DESCRIPTION "New flows missed"

	::={interfaceFlowNewMissed 2}

interfaceFlowNewMissedMax	OBJECT-TYPE
	SYNTAX	 CounterBasedGauge64
	MAX-ACCESS read-only
	STATUS current
	DESCRIPTION "New flows missed"

	::={interfaceFlowNewMissed 3}

interfaceFlowUpdMissed	OBJECT IDENTIFIER ::={interface 11}

interfaceFlowUpdMissedVal	OBJECT-TYPE
	SYNTAX	 Counter64
	MAX-ACCESS read-only
	STATUS current
	DESCRIPTION "Flow updates missed"

	::={interfaceFlowUpdMissed 1}

interfaceFlowUpdMissedMom	OBJECT-TYPE
	SYNTAX	 CounterBasedGauge64
	MAX-ACCESS read-only
	STATUS current
	DESCRIPTION "Flow updates missed"

	::={interfaceFlowUpdMissed 2}

interfaceFlowUpdMissedMax	OBJECT-TYPE
	SYNTAX	 CounterBasedGauge64
	MAX-ACCESS read-only
	STATUS current
	DESCRIPTION "Flow updates missed"

	::={interfaceFlowUpdMissed 3}

interfaceFlowNew	OBJECT IDENTIFIER ::={interface 12}

interfaceFlowNewVal	OBJECT-TYPE
	SYNTAX	 Counter64
	MAX-ACCESS read-only
	STATUS current
	DESCRIPTION "New flows"

	::={interfaceFlowNew 1}

interfaceFlowNewMom	OBJECT-TYPE
	SYNTAX	 CounterBasedGauge64
	MAX-ACCESS read-only
	STATUS current
	DESCRIPTION "New flows"

	::={interfaceFlowNew 2}

interfaceFlowNewMax	OBJECT-TYPE
	SYNTAX	 CounterBasedGauge64
	MAX-ACCESS read-only
	STATUS current
	DESCRIPTION "New flows"

	::={interfaceFlowNew 3}

interfaceFlowHostnameAllocFail	OBJECT IDENTIFIER ::={interface 13}

interfaceFlowHostnameAllocFailVal	OBJECT-TYPE
	SYNTAX	 Counter64
	MAX-ACCESS read-only
	STATUS current
	DESCRIPTION "Hostname allocation failures"

	::={interfaceFlowHostnameAllocFail 1}

interfaceFlowHostnameAllocFailMom	OBJECT-TYPE
	SYNTAX	 CounterBasedGauge64
	MAX-ACCESS read-only
	STATUS current
	DESCRIPTION "Hostname allocation failures"

	::={interfaceFlowHostnameAllocFail 2}

interfaceFlowHostnameAllocFailMax	OBJECT-TYPE
	SYNTAX	 CounterBasedGauge64
	MAX-ACCESS read-only
	STATUS current
	DESCRIPTION "Hostname allocation failures"

	::={interfaceFlowHostnameAllocFail 3}

interfaceFlowUpdReordered	OBJECT IDENTIFIER ::={interface 14}

interfaceFlowUpdReorderedVal	OBJECT-TYPE
	SYNTAX	 Counter64
	MAX-ACCESS read-only
	STATUS current
	DESCRIPTION "Reordered flow updates"

	::={interfaceFlowUpdReordered 1}

interfaceFlowUpdReorderedMom	OBJECT-TYPE
	SYNTAX	 CounterBasedGauge64
	MAX-ACCESS read-only
	STATUS current
	DESCRIPTION "Reordered flow updates"

	::={interfaceFlowUpdReordered 2}

interfaceFlowUpdReorderedMax	OBJECT-TYPE
	SYNTAX	 CounterBasedGauge64
	MAX-ACCESS read-only
	STATUS current
	DESCRIPTION "Reordered flow updates"

	::={interfaceFlowUpdReordered 3}


dynnetobjs	OBJECT IDENTIFIER ::={sysdiag 121}

dynamicnetobjectFailedInserts	OBJECT IDENTIFIER ::={dynnetobjs 1}

dynamicnetobjectFailedInsertsVal	OBJECT-TYPE
	SYNTAX	 Counter64
	MAX-ACCESS read-only
	STATUS current
	DESCRIPTION "Failed inserts (too many dynamic items)"

	::={dynamicnetobjectFailedInserts 1}

dynamicnetobjectFailedInsertsMom	OBJECT-TYPE
	SYNTAX	 CounterBasedGauge64
	MAX-ACCESS read-only
	STATUS current
	DESCRIPTION "Failed inserts (too many dynamic items)"

	::={dynamicnetobjectFailedInserts 2}

dynamicnetobjectFailedInsertsMax	OBJECT-TYPE
	SYNTAX	 CounterBasedGauge64
	MAX-ACCESS read-only
	STATUS current
	DESCRIPTION "Failed inserts (too many dynamic items)"

	::={dynamicnetobjectFailedInserts 3}

dynamicnetobjectListItems	OBJECT IDENTIFIER ::={dynnetobjs 2}

dynamicnetobjectListItemsVal	OBJECT-TYPE
	SYNTAX	 CounterBasedGauge64
	MAX-ACCESS read-only
	STATUS current
	DESCRIPTION "Items returned from last PLDB query"

	::={dynamicnetobjectListItems 1}

dynamicnetobjectListItemsMax	OBJECT-TYPE
	SYNTAX	 CounterBasedGauge64
	MAX-ACCESS read-only
	STATUS current
	DESCRIPTION "Items returned from last PLDB query"

	::={dynamicnetobjectListItems 3}

dynamicnetobjectRemoveSucceeded	OBJECT IDENTIFIER ::={dynnetobjs 3}

dynamicnetobjectRemoveSucceededVal	OBJECT-TYPE
	SYNTAX	 Counter64
	MAX-ACCESS read-only
	STATUS current
	DESCRIPTION "Remove calls succeeded"

	::={dynamicnetobjectRemoveSucceeded 1}

dynamicnetobjectRemoveSucceededMom	OBJECT-TYPE
	SYNTAX	 CounterBasedGauge64
	MAX-ACCESS read-only
	STATUS current
	DESCRIPTION "Remove calls succeeded"

	::={dynamicnetobjectRemoveSucceeded 2}

dynamicnetobjectRemoveSucceededMax	OBJECT-TYPE
	SYNTAX	 CounterBasedGauge64
	MAX-ACCESS read-only
	STATUS current
	DESCRIPTION "Remove calls succeeded"

	::={dynamicnetobjectRemoveSucceeded 3}

dynamicnetobjectRemoveFailed	OBJECT IDENTIFIER ::={dynnetobjs 4}

dynamicnetobjectRemoveFailedVal	OBJECT-TYPE
	SYNTAX	 Counter64
	MAX-ACCESS read-only
	STATUS current
	DESCRIPTION "Remove calls failed"

	::={dynamicnetobjectRemoveFailed 1}

dynamicnetobjectRemoveFailedMom	OBJECT-TYPE
	SYNTAX	 CounterBasedGauge64
	MAX-ACCESS read-only
	STATUS current
	DESCRIPTION "Remove calls failed"

	::={dynamicnetobjectRemoveFailed 2}

dynamicnetobjectRemoveFailedMax	OBJECT-TYPE
	SYNTAX	 CounterBasedGauge64
	MAX-ACCESS read-only
	STATUS current
	DESCRIPTION "Remove calls failed"

	::={dynamicnetobjectRemoveFailed 3}

dynamicnetobjectCurrentIpCount	OBJECT IDENTIFIER ::={dynnetobjs 5}

dynamicnetobjectCurrentIpCountVal	OBJECT-TYPE
	SYNTAX	 CounterBasedGauge64
	MAX-ACCESS read-only
	STATUS current
	DESCRIPTION "IPs in table"

	::={dynamicnetobjectCurrentIpCount 1}

dynamicnetobjectCurrentIpCountMax	OBJECT-TYPE
	SYNTAX	 CounterBasedGauge64
	MAX-ACCESS read-only
	STATUS current
	DESCRIPTION "IPs in table"

	::={dynamicnetobjectCurrentIpCount 3}

dynamicnetobjectCurrentCount	OBJECT IDENTIFIER ::={dynnetobjs 6}

dynamicnetobjectCurrentCountVal	OBJECT-TYPE
	SYNTAX	 CounterBasedGauge64
	MAX-ACCESS read-only
	STATUS current
	DESCRIPTION "Items in table"

	::={dynamicnetobjectCurrentCount 1}

dynamicnetobjectCurrentCountMax	OBJECT-TYPE
	SYNTAX	 CounterBasedGauge64
	MAX-ACCESS read-only
	STATUS current
	DESCRIPTION "Items in table"

	::={dynamicnetobjectCurrentCount 3}

dynamicnetobjectAddSucceeded	OBJECT IDENTIFIER ::={dynnetobjs 8}

dynamicnetobjectAddSucceededVal	OBJECT-TYPE
	SYNTAX	 Counter64
	MAX-ACCESS read-only
	STATUS current
	DESCRIPTION "Add calls succeeded"

	::={dynamicnetobjectAddSucceeded 1}

dynamicnetobjectAddSucceededMom	OBJECT-TYPE
	SYNTAX	 CounterBasedGauge64
	MAX-ACCESS read-only
	STATUS current
	DESCRIPTION "Add calls succeeded"

	::={dynamicnetobjectAddSucceeded 2}

dynamicnetobjectAddSucceededMax	OBJECT-TYPE
	SYNTAX	 CounterBasedGauge64
	MAX-ACCESS read-only
	STATUS current
	DESCRIPTION "Add calls succeeded"

	::={dynamicnetobjectAddSucceeded 3}

dynamicnetobjectAddFailed	OBJECT IDENTIFIER ::={dynnetobjs 9}

dynamicnetobjectAddFailedVal	OBJECT-TYPE
	SYNTAX	 Counter64
	MAX-ACCESS read-only
	STATUS current
	DESCRIPTION "Add calls failed"

	::={dynamicnetobjectAddFailed 1}

dynamicnetobjectAddFailedMom	OBJECT-TYPE
	SYNTAX	 CounterBasedGauge64
	MAX-ACCESS read-only
	STATUS current
	DESCRIPTION "Add calls failed"

	::={dynamicnetobjectAddFailed 2}

dynamicnetobjectAddFailedMax	OBJECT-TYPE
	SYNTAX	 CounterBasedGauge64
	MAX-ACCESS read-only
	STATUS current
	DESCRIPTION "Add calls failed"

	::={dynamicnetobjectAddFailed 3}

dynamicnetobjectInsertPldbFailed	OBJECT IDENTIFIER ::={dynnetobjs 10}

dynamicnetobjectInsertPldbFailedVal	OBJECT-TYPE
	SYNTAX	 Counter64
	MAX-ACCESS read-only
	STATUS current
	DESCRIPTION "Add calls failed in PLDB"

	::={dynamicnetobjectInsertPldbFailed 1}

dynamicnetobjectInsertPldbFailedMom	OBJECT-TYPE
	SYNTAX	 CounterBasedGauge64
	MAX-ACCESS read-only
	STATUS current
	DESCRIPTION "Add calls failed in PLDB"

	::={dynamicnetobjectInsertPldbFailed 2}

dynamicnetobjectInsertPldbFailedMax	OBJECT-TYPE
	SYNTAX	 CounterBasedGauge64
	MAX-ACCESS read-only
	STATUS current
	DESCRIPTION "Add calls failed in PLDB"

	::={dynamicnetobjectInsertPldbFailed 3}

dynamicnetobjectAddCalls	OBJECT IDENTIFIER ::={dynnetobjs 11}

dynamicnetobjectAddCallsVal	OBJECT-TYPE
	SYNTAX	 Counter64
	MAX-ACCESS read-only
	STATUS current
	DESCRIPTION "Add calls attempted"

	::={dynamicnetobjectAddCalls 1}

dynamicnetobjectAddCallsMom	OBJECT-TYPE
	SYNTAX	 CounterBasedGauge64
	MAX-ACCESS read-only
	STATUS current
	DESCRIPTION "Add calls attempted"

	::={dynamicnetobjectAddCalls 2}

dynamicnetobjectAddCallsMax	OBJECT-TYPE
	SYNTAX	 CounterBasedGauge64
	MAX-ACCESS read-only
	STATUS current
	DESCRIPTION "Add calls attempted"

	::={dynamicnetobjectAddCalls 3}

dynamicnetobjectRemoveCalls	OBJECT IDENTIFIER ::={dynnetobjs 12}

dynamicnetobjectRemoveCallsVal	OBJECT-TYPE
	SYNTAX	 Counter64
	MAX-ACCESS read-only
	STATUS current
	DESCRIPTION "Remove calls attempted"

	::={dynamicnetobjectRemoveCalls 1}

dynamicnetobjectRemoveCallsMom	OBJECT-TYPE
	SYNTAX	 CounterBasedGauge64
	MAX-ACCESS read-only
	STATUS current
	DESCRIPTION "Remove calls attempted"

	::={dynamicnetobjectRemoveCalls 2}

dynamicnetobjectRemoveCallsMax	OBJECT-TYPE
	SYNTAX	 CounterBasedGauge64
	MAX-ACCESS read-only
	STATUS current
	DESCRIPTION "Remove calls attempted"

	::={dynamicnetobjectRemoveCalls 3}

dynamicnetobjectListCalls	OBJECT IDENTIFIER ::={dynnetobjs 15}

dynamicnetobjectListCallsVal	OBJECT-TYPE
	SYNTAX	 Counter64
	MAX-ACCESS read-only
	STATUS current
	DESCRIPTION "List calls attempted"

	::={dynamicnetobjectListCalls 1}

dynamicnetobjectListCallsMom	OBJECT-TYPE
	SYNTAX	 CounterBasedGauge64
	MAX-ACCESS read-only
	STATUS current
	DESCRIPTION "List calls attempted"

	::={dynamicnetobjectListCalls 2}

dynamicnetobjectListCallsMax	OBJECT-TYPE
	SYNTAX	 CounterBasedGauge64
	MAX-ACCESS read-only
	STATUS current
	DESCRIPTION "List calls attempted"

	::={dynamicnetobjectListCalls 3}

dynamicnetobjectListItemsReturned	OBJECT IDENTIFIER ::={dynnetobjs 16}

dynamicnetobjectListItemsReturnedVal	OBJECT-TYPE
	SYNTAX	 Counter64
	MAX-ACCESS read-only
	STATUS current
	DESCRIPTION "Items returned from list calls"

	::={dynamicnetobjectListItemsReturned 1}

dynamicnetobjectListItemsReturnedMom	OBJECT-TYPE
	SYNTAX	 CounterBasedGauge64
	MAX-ACCESS read-only
	STATUS current
	DESCRIPTION "Items returned from list calls"

	::={dynamicnetobjectListItemsReturned 2}

dynamicnetobjectListItemsReturnedMax	OBJECT-TYPE
	SYNTAX	 CounterBasedGauge64
	MAX-ACCESS read-only
	STATUS current
	DESCRIPTION "Items returned from list calls"

	::={dynamicnetobjectListItemsReturned 3}

dynamicnetobjectSubscriberConflicts	OBJECT IDENTIFIER ::={dynnetobjs 17}

dynamicnetobjectSubscriberConflictsVal	OBJECT-TYPE
	SYNTAX	 Counter64
	MAX-ACCESS read-only
	STATUS current
	DESCRIPTION "Conflicting subscriber names"

	::={dynamicnetobjectSubscriberConflicts 1}

dynamicnetobjectSubscriberConflictsMom	OBJECT-TYPE
	SYNTAX	 CounterBasedGauge64
	MAX-ACCESS read-only
	STATUS current
	DESCRIPTION "Conflicting subscriber names"

	::={dynamicnetobjectSubscriberConflicts 2}

dynamicnetobjectSubscriberConflictsMax	OBJECT-TYPE
	SYNTAX	 CounterBasedGauge64
	MAX-ACCESS read-only
	STATUS current
	DESCRIPTION "Conflicting subscriber names"

	::={dynamicnetobjectSubscriberConflicts 3}

dynamicnetobjectSubscriberCount	OBJECT IDENTIFIER ::={dynnetobjs 18}

dynamicnetobjectSubscriberCountVal	OBJECT-TYPE
	SYNTAX	 CounterBasedGauge64
	MAX-ACCESS read-only
	STATUS current
	DESCRIPTION "Number of unique subscriber names"

	::={dynamicnetobjectSubscriberCount 1}

dynamicnetobjectSubscriberCountMax	OBJECT-TYPE
	SYNTAX	 CounterBasedGauge64
	MAX-ACCESS read-only
	STATUS current
	DESCRIPTION "Number of unique subscriber names"

	::={dynamicnetobjectSubscriberCount 3}

dynamicnetobjectSubscriberTooMany	OBJECT IDENTIFIER ::={dynnetobjs 19}

dynamicnetobjectSubscriberTooManyVal	OBJECT-TYPE
	SYNTAX	 Counter64
	MAX-ACCESS read-only
	STATUS current
	DESCRIPTION "Too many unique subscriber names failures"

	::={dynamicnetobjectSubscriberTooMany 1}

dynamicnetobjectSubscriberTooManyMom	OBJECT-TYPE
	SYNTAX	 CounterBasedGauge64
	MAX-ACCESS read-only
	STATUS current
	DESCRIPTION "Too many unique subscriber names failures"

	::={dynamicnetobjectSubscriberTooMany 2}

dynamicnetobjectSubscriberTooManyMax	OBJECT-TYPE
	SYNTAX	 CounterBasedGauge64
	MAX-ACCESS read-only
	STATUS current
	DESCRIPTION "Too many unique subscriber names failures"

	::={dynamicnetobjectSubscriberTooMany 3}

dynamicnetobjectSqliteMemoryUsed	OBJECT IDENTIFIER ::={dynnetobjs 20}

dynamicnetobjectSqliteMemoryUsedVal	OBJECT-TYPE
	SYNTAX	 CounterBasedGauge64
	MAX-ACCESS read-only
	STATUS obsolete
	DESCRIPTION "Add requests in queue"

	::={dynamicnetobjectSqliteMemoryUsed 1}

dynamicnetobjectSqliteMemoryUsedMax	OBJECT-TYPE
	SYNTAX	 CounterBasedGauge64
	MAX-ACCESS read-only
	STATUS obsolete
	DESCRIPTION "Add requests in queue"

	::={dynamicnetobjectSqliteMemoryUsed 3}

dynamicnetobjectPendingAdds	OBJECT IDENTIFIER ::={dynnetobjs 21}

dynamicnetobjectPendingAddsVal	OBJECT-TYPE
	SYNTAX	 CounterBasedGauge64
	MAX-ACCESS read-only
	STATUS obsolete
	DESCRIPTION "Memory used by the dynitems sqlite thread"

	::={dynamicnetobjectPendingAdds 1}

dynamicnetobjectPendingAddsMax	OBJECT-TYPE
	SYNTAX	 CounterBasedGauge64
	MAX-ACCESS read-only
	STATUS obsolete
	DESCRIPTION "Memory used by the dynitems sqlite thread"

	::={dynamicnetobjectPendingAdds 3}

bgp	OBJECT IDENTIFIER ::={sysdiag 122}

bgpUpdates	OBJECT IDENTIFIER ::={bgp 1}

bgpUpdatesVal	OBJECT-TYPE
	SYNTAX	 CounterBasedGauge64
	MAX-ACCESS read-only
	STATUS current
	DESCRIPTION "Updates received"

	::={bgpUpdates 1}

bgpUpdatesMax	OBJECT-TYPE
	SYNTAX	 CounterBasedGauge64
	MAX-ACCESS read-only
	STATUS current
	DESCRIPTION "Updates received"

	::={bgpUpdates 3}

bgpPrefixes	OBJECT IDENTIFIER ::={bgp 2}

bgpPrefixesVal	OBJECT-TYPE
	SYNTAX	 CounterBasedGauge64
	MAX-ACCESS read-only
	STATUS current
	DESCRIPTION "Number of prefixes"

	::={bgpPrefixes 1}

bgpPrefixesMax	OBJECT-TYPE
	SYNTAX	 CounterBasedGauge64
	MAX-ACCESS read-only
	STATUS current
	DESCRIPTION "Number of prefixes"

	::={bgpPrefixes 3}

bgpPaths	OBJECT IDENTIFIER ::={bgp 3}

bgpPathsVal	OBJECT-TYPE
	SYNTAX	 CounterBasedGauge64
	MAX-ACCESS read-only
	STATUS current
	DESCRIPTION "Number of unique paths"

	::={bgpPaths 1}

bgpPathsMax	OBJECT-TYPE
	SYNTAX	 CounterBasedGauge64
	MAX-ACCESS read-only
	STATUS current
	DESCRIPTION "Number of unique paths"

	::={bgpPaths 3}

bgpUptime	OBJECT IDENTIFIER ::={bgp 4}

bgpUptimeVal	OBJECT-TYPE
	SYNTAX	 TimeTicks
	MAX-ACCESS read-only
	STATUS current
	DESCRIPTION "Connection uptime"

	::={bgpUptime 1}

bgpConvresionTime	OBJECT IDENTIFIER ::={bgp 5}

bgpConvresionTimeVal	OBJECT-TYPE
	SYNTAX	 CounterBasedGauge64
	MAX-ACCESS read-only
	STATUS current
	DESCRIPTION "Time to convert lookup tree"

	::={bgpConvresionTime 1}

bgpConvresionTimeMax	OBJECT-TYPE
	SYNTAX	 CounterBasedGauge64
	MAX-ACCESS read-only
	STATUS current
	DESCRIPTION "Time to convert lookup tree"

	::={bgpConvresionTime 3}

bgpSendTime	OBJECT IDENTIFIER ::={bgp 6}

bgpSendTimeVal	OBJECT-TYPE
	SYNTAX	 CounterBasedGauge64
	MAX-ACCESS read-only
	STATUS current
	DESCRIPTION "Time to update lookup tree"

	::={bgpSendTime 1}

bgpSendTimeMax	OBJECT-TYPE
	SYNTAX	 CounterBasedGauge64
	MAX-ACCESS read-only
	STATUS current
	DESCRIPTION "Time to update lookup tree"

	::={bgpSendTime 3}

bgpReplaces	OBJECT IDENTIFIER ::={bgp 7}

bgpReplacesVal	OBJECT-TYPE
	SYNTAX	 CounterBasedGauge64
	MAX-ACCESS read-only
	STATUS current
	DESCRIPTION "Total count of announces without withdraw"

	::={bgpReplaces 1}

bgpReplacesMax	OBJECT-TYPE
	SYNTAX	 CounterBasedGauge64
	MAX-ACCESS read-only
	STATUS current
	DESCRIPTION "Total count of announces without withdraw"

	::={bgpReplaces 3}

bgpWithdraws	OBJECT IDENTIFIER ::={bgp 8}

bgpWithdrawsVal	OBJECT-TYPE
	SYNTAX	 CounterBasedGauge64
	MAX-ACCESS read-only
	STATUS current
	DESCRIPTION "Total count of withdrawn routes"

	::={bgpWithdraws 1}

bgpWithdrawsMax	OBJECT-TYPE
	SYNTAX	 CounterBasedGauge64
	MAX-ACCESS read-only
	STATUS current
	DESCRIPTION "Total count of withdrawn routes"

	::={bgpWithdraws 3}

bgpAnnounces	OBJECT IDENTIFIER ::={bgp 9}

bgpAnnouncesVal	OBJECT-TYPE
	SYNTAX	 CounterBasedGauge64
	MAX-ACCESS read-only
	STATUS current
	DESCRIPTION "Total count of announced routes"

	::={bgpAnnounces 1}

bgpAnnouncesMax	OBJECT-TYPE
	SYNTAX	 CounterBasedGauge64
	MAX-ACCESS read-only
	STATUS current
	DESCRIPTION "Total count of announced routes"

	::={bgpAnnounces 3}

bgpReconnects	OBJECT IDENTIFIER ::={bgp 10}

bgpReconnectsVal	OBJECT-TYPE
	SYNTAX	 CounterBasedGauge64
	MAX-ACCESS read-only
	STATUS current
	DESCRIPTION "Total number of reconnects"

	::={bgpReconnects 1}

bgpReconnectsMax	OBJECT-TYPE
	SYNTAX	 CounterBasedGauge64
	MAX-ACCESS read-only
	STATUS current
	DESCRIPTION "Total number of reconnects"

	::={bgpReconnects 3}

bgpRecyclePaths	OBJECT IDENTIFIER ::={bgp 12}

bgpRecyclePathsVal	OBJECT-TYPE
	SYNTAX	 CounterBasedGauge64
	MAX-ACCESS read-only
	STATUS current
	DESCRIPTION "Number of paths waiting for garbage collection"

	::={bgpRecyclePaths 1}

bgpRecyclePathsMax	OBJECT-TYPE
	SYNTAX	 CounterBasedGauge64
	MAX-ACCESS read-only
	STATUS current
	DESCRIPTION "Number of paths waiting for garbage collection"

	::={bgpRecyclePaths 3}

bgpFreelistPaths	OBJECT IDENTIFIER ::={bgp 13}

bgpFreelistPathsVal	OBJECT-TYPE
	SYNTAX	 CounterBasedGauge64
	MAX-ACCESS read-only
	STATUS current
	DESCRIPTION "Number of paths in freelist"

	::={bgpFreelistPaths 1}

bgpFreelistPathsMax	OBJECT-TYPE
	SYNTAX	 CounterBasedGauge64
	MAX-ACCESS read-only
	STATUS current
	DESCRIPTION "Number of paths in freelist"

	::={bgpFreelistPaths 3}

bgpBalanceTime	OBJECT IDENTIFIER ::={bgp 14}

bgpBalanceTimeVal	OBJECT-TYPE
	SYNTAX	 CounterBasedGauge64
	MAX-ACCESS read-only
	STATUS current
	DESCRIPTION "Time to rebalance tree"

	::={bgpBalanceTime 1}

bgpBalanceTimeMax	OBJECT-TYPE
	SYNTAX	 CounterBasedGauge64
	MAX-ACCESS read-only
	STATUS current
	DESCRIPTION "Time to rebalance tree"

	::={bgpBalanceTime 3}

bgpCommunityTooSmall	OBJECT IDENTIFIER ::={bgp 24}

bgpCommunityTooSmallVal	OBJECT-TYPE
	SYNTAX	 CounterBasedGauge64
	MAX-ACCESS read-only
	STATUS current
	DESCRIPTION "Number of community updates received that exceed PL_CONFIG_BGP_MAX_COMMUNITIES"

	::={bgpCommunityTooSmall 1}

bgpCommunityTooSmallMax	OBJECT-TYPE
	SYNTAX	 CounterBasedGauge64
	MAX-ACCESS read-only
	STATUS current
	DESCRIPTION "Number of community updates received that exceed PL_CONFIG_BGP_MAX_COMMUNITIES"

	::={bgpCommunityTooSmall 3}

bgpCommunityMaxSeen	OBJECT IDENTIFIER ::={bgp 25}

bgpCommunityMaxSeenVal	OBJECT-TYPE
	SYNTAX	 CounterBasedGauge64
	MAX-ACCESS read-only
	STATUS current
	DESCRIPTION "Maximum number of communities we have seen in a BGP update"

	::={bgpCommunityMaxSeen 1}

bgpCommunityMaxSeenMax	OBJECT-TYPE
	SYNTAX	 CounterBasedGauge64
	MAX-ACCESS read-only
	STATUS current
	DESCRIPTION "Maximum number of communities we have seen in a BGP update"

	::={bgpCommunityMaxSeen 3}

qsync	OBJECT IDENTIFIER ::={sysdiag 123}

qsyncIUpdates	OBJECT IDENTIFIER ::={qsync 1}

qsyncIUpdatesVal	OBJECT-TYPE
	SYNTAX	 Counter64
	MAX-ACCESS read-only
	STATUS current
	DESCRIPTION "Updates received from reapers"

	::={qsyncIUpdates 1}

qsyncIUpdatesMom	OBJECT-TYPE
	SYNTAX	 CounterBasedGauge64
	MAX-ACCESS read-only
	STATUS current
	DESCRIPTION "Updates received from reapers"

	::={qsyncIUpdates 2}

qsyncIUpdatesMax	OBJECT-TYPE
	SYNTAX	 CounterBasedGauge64
	MAX-ACCESS read-only
	STATUS current
	DESCRIPTION "Updates received from reapers"

	::={qsyncIUpdates 3}

qsyncIUpdatesOldRuleset	OBJECT IDENTIFIER ::={qsync 2}

qsyncIUpdatesOldRulesetVal	OBJECT-TYPE
	SYNTAX	 Counter64
	MAX-ACCESS read-only
	STATUS current
	DESCRIPTION "Updates received from reapers with old ruleset"

	::={qsyncIUpdatesOldRuleset 1}

qsyncIUpdatesOldRulesetMom	OBJECT-TYPE
	SYNTAX	 CounterBasedGauge64
	MAX-ACCESS read-only
	STATUS current
	DESCRIPTION "Updates received from reapers with old ruleset"

	::={qsyncIUpdatesOldRuleset 2}

qsyncIUpdatesOldRulesetMax	OBJECT-TYPE
	SYNTAX	 CounterBasedGauge64
	MAX-ACCESS read-only
	STATUS current
	DESCRIPTION "Updates received from reapers with old ruleset"

	::={qsyncIUpdatesOldRuleset 3}

qsyncIUpdatesUnknownObject	OBJECT IDENTIFIER ::={qsync 3}

qsyncIUpdatesUnknownObjectVal	OBJECT-TYPE
	SYNTAX	 Counter64
	MAX-ACCESS read-only
	STATUS current
	DESCRIPTION "Updates received for unknown object"

	::={qsyncIUpdatesUnknownObject 1}

qsyncIUpdatesUnknownObjectMom	OBJECT-TYPE
	SYNTAX	 CounterBasedGauge64
	MAX-ACCESS read-only
	STATUS current
	DESCRIPTION "Updates received for unknown object"

	::={qsyncIUpdatesUnknownObject 2}

qsyncIUpdatesUnknownObjectMax	OBJECT-TYPE
	SYNTAX	 CounterBasedGauge64
	MAX-ACCESS read-only
	STATUS current
	DESCRIPTION "Updates received for unknown object"

	::={qsyncIUpdatesUnknownObject 3}

qsyncIReaperSplitsCreated	OBJECT IDENTIFIER ::={qsync 4}

qsyncIReaperSplitsCreatedVal	OBJECT-TYPE
	SYNTAX	 Counter64
	MAX-ACCESS read-only
	STATUS current
	DESCRIPTION "Split entries created (reaper)"

	::={qsyncIReaperSplitsCreated 1}

qsyncIReaperSplitsCreatedMom	OBJECT-TYPE
	SYNTAX	 CounterBasedGauge64
	MAX-ACCESS read-only
	STATUS current
	DESCRIPTION "Split entries created (reaper)"

	::={qsyncIReaperSplitsCreated 2}

qsyncIReaperSplitsCreatedMax	OBJECT-TYPE
	SYNTAX	 CounterBasedGauge64
	MAX-ACCESS read-only
	STATUS current
	DESCRIPTION "Split entries created (reaper)"

	::={qsyncIReaperSplitsCreated 3}

qsyncIReaperSplitsActive	OBJECT IDENTIFIER ::={qsync 5}

qsyncIReaperSplitsActiveVal	OBJECT-TYPE
	SYNTAX	 CounterBasedGauge64
	MAX-ACCESS read-only
	STATUS current
	DESCRIPTION "Split entries active (reaper)"

	::={qsyncIReaperSplitsActive 1}

qsyncIReaperSplitsActiveMax	OBJECT-TYPE
	SYNTAX	 CounterBasedGauge64
	MAX-ACCESS read-only
	STATUS current
	DESCRIPTION "Split entries active (reaper)"

	::={qsyncIReaperSplitsActive 3}

qsyncISumFreelistSize	OBJECT IDENTIFIER ::={qsync 6}

qsyncISumFreelistSizeVal	OBJECT-TYPE
	SYNTAX	 CounterBasedGauge64
	MAX-ACCESS read-only
	STATUS current
	DESCRIPTION "Split entries on free list (sum)"

	::={qsyncISumFreelistSize 1}

qsyncISumFreelistSizeMax	OBJECT-TYPE
	SYNTAX	 CounterBasedGauge64
	MAX-ACCESS read-only
	STATUS current
	DESCRIPTION "Split entries on free list (sum)"

	::={qsyncISumFreelistSize 3}

qsyncISumSplitsActive	OBJECT IDENTIFIER ::={qsync 7}

qsyncISumSplitsActiveVal	OBJECT-TYPE
	SYNTAX	 CounterBasedGauge64
	MAX-ACCESS read-only
	STATUS current
	DESCRIPTION "Split entries active (sum)"

	::={qsyncISumSplitsActive 1}

qsyncISumSplitsActiveMax	OBJECT-TYPE
	SYNTAX	 CounterBasedGauge64
	MAX-ACCESS read-only
	STATUS current
	DESCRIPTION "Split entries active (sum)"

	::={qsyncISumSplitsActive 3}

qsyncIAdjustmentsSent	OBJECT IDENTIFIER ::={qsync 8}

qsyncIAdjustmentsSentVal	OBJECT-TYPE
	SYNTAX	 Counter64
	MAX-ACCESS read-only
	STATUS current
	DESCRIPTION "Object adjustments sent"

	::={qsyncIAdjustmentsSent 1}

qsyncIAdjustmentsSentMom	OBJECT-TYPE
	SYNTAX	 CounterBasedGauge64
	MAX-ACCESS read-only
	STATUS current
	DESCRIPTION "Object adjustments sent"

	::={qsyncIAdjustmentsSent 2}

qsyncIAdjustmentsSentMax	OBJECT-TYPE
	SYNTAX	 CounterBasedGauge64
	MAX-ACCESS read-only
	STATUS current
	DESCRIPTION "Object adjustments sent"

	::={qsyncIAdjustmentsSent 3}

qsyncENumPeers	OBJECT IDENTIFIER ::={qsync 9}

qsyncENumPeersVal	OBJECT-TYPE
	SYNTAX	 CounterBasedGauge64
	MAX-ACCESS read-only
	STATUS current
	DESCRIPTION "(ext) Number of peers"

	::={qsyncENumPeers 1}

qsyncENumPeersMax	OBJECT-TYPE
	SYNTAX	 CounterBasedGauge64
	MAX-ACCESS read-only
	STATUS current
	DESCRIPTION "(ext) Number of peers"

	::={qsyncENumPeers 3}

qsyncEUpdatesMismatch	OBJECT IDENTIFIER ::={qsync 10}

qsyncEUpdatesMismatchVal	OBJECT-TYPE
	SYNTAX	 Counter64
	MAX-ACCESS read-only
	STATUS current
	DESCRIPTION "(ext) Updates with mismatching ruleset"

	::={qsyncEUpdatesMismatch 1}

qsyncEUpdatesMismatchMom	OBJECT-TYPE
	SYNTAX	 CounterBasedGauge64
	MAX-ACCESS read-only
	STATUS current
	DESCRIPTION "(ext) Updates with mismatching ruleset"

	::={qsyncEUpdatesMismatch 2}

qsyncEUpdatesMismatchMax	OBJECT-TYPE
	SYNTAX	 CounterBasedGauge64
	MAX-ACCESS read-only
	STATUS current
	DESCRIPTION "(ext) Updates with mismatching ruleset"

	::={qsyncEUpdatesMismatch 3}

qsyncEUpdatePackets	OBJECT IDENTIFIER ::={qsync 11}

qsyncEUpdatePacketsVal	OBJECT-TYPE
	SYNTAX	 Counter64
	MAX-ACCESS read-only
	STATUS current
	DESCRIPTION "(ext) Update packets"

	::={qsyncEUpdatePackets 1}

qsyncEUpdatePacketsMom	OBJECT-TYPE
	SYNTAX	 CounterBasedGauge64
	MAX-ACCESS read-only
	STATUS current
	DESCRIPTION "(ext) Update packets"

	::={qsyncEUpdatePackets 2}

qsyncEUpdatePacketsMax	OBJECT-TYPE
	SYNTAX	 CounterBasedGauge64
	MAX-ACCESS read-only
	STATUS current
	DESCRIPTION "(ext) Update packets"

	::={qsyncEUpdatePackets 3}

qsyncESplitTimeout	OBJECT IDENTIFIER ::={qsync 12}

qsyncESplitTimeoutVal	OBJECT-TYPE
	SYNTAX	 Counter64
	MAX-ACCESS read-only
	STATUS current
	DESCRIPTION "(ext) Split object age timeout"

	::={qsyncESplitTimeout 1}

qsyncESplitTimeoutMom	OBJECT-TYPE
	SYNTAX	 CounterBasedGauge64
	MAX-ACCESS read-only
	STATUS current
	DESCRIPTION "(ext) Split object age timeout"

	::={qsyncESplitTimeout 2}

qsyncESplitTimeoutMax	OBJECT-TYPE
	SYNTAX	 CounterBasedGauge64
	MAX-ACCESS read-only
	STATUS current
	DESCRIPTION "(ext) Split object age timeout"

	::={qsyncESplitTimeout 3}

qsyncERecvUpdateEntries	OBJECT IDENTIFIER ::={qsync 13}

qsyncERecvUpdateEntriesVal	OBJECT-TYPE
	SYNTAX	 Counter64
	MAX-ACCESS read-only
	STATUS current
	DESCRIPTION "(ext) Received update entries"

	::={qsyncERecvUpdateEntries 1}

qsyncERecvUpdateEntriesMom	OBJECT-TYPE
	SYNTAX	 CounterBasedGauge64
	MAX-ACCESS read-only
	STATUS current
	DESCRIPTION "(ext) Received update entries"

	::={qsyncERecvUpdateEntries 2}

qsyncERecvUpdateEntriesMax	OBJECT-TYPE
	SYNTAX	 CounterBasedGauge64
	MAX-ACCESS read-only
	STATUS current
	DESCRIPTION "(ext) Received update entries"

	::={qsyncERecvUpdateEntries 3}

qsyncESendUpdateEntries	OBJECT IDENTIFIER ::={qsync 14}

qsyncESendUpdateEntriesVal	OBJECT-TYPE
	SYNTAX	 Counter64
	MAX-ACCESS read-only
	STATUS current
	DESCRIPTION "(ext) Sent update entries"

	::={qsyncESendUpdateEntries 1}

qsyncESendUpdateEntriesMom	OBJECT-TYPE
	SYNTAX	 CounterBasedGauge64
	MAX-ACCESS read-only
	STATUS current
	DESCRIPTION "(ext) Sent update entries"

	::={qsyncESendUpdateEntries 2}

qsyncESendUpdateEntriesMax	OBJECT-TYPE
	SYNTAX	 CounterBasedGauge64
	MAX-ACCESS read-only
	STATUS current
	DESCRIPTION "(ext) Sent update entries"

	::={qsyncESendUpdateEntries 3}

qsyncESendUpdatePackets	OBJECT IDENTIFIER ::={qsync 15}

qsyncESendUpdatePacketsVal	OBJECT-TYPE
	SYNTAX	 Counter64
	MAX-ACCESS read-only
	STATUS current
	DESCRIPTION "(ext) Sent update packets"

	::={qsyncESendUpdatePackets 1}

qsyncESendUpdatePacketsMom	OBJECT-TYPE
	SYNTAX	 CounterBasedGauge64
	MAX-ACCESS read-only
	STATUS current
	DESCRIPTION "(ext) Sent update packets"

	::={qsyncESendUpdatePackets 2}

qsyncESendUpdatePacketsMax	OBJECT-TYPE
	SYNTAX	 CounterBasedGauge64
	MAX-ACCESS read-only
	STATUS current
	DESCRIPTION "(ext) Sent update packets"

	::={qsyncESendUpdatePackets 3}

qsyncIUnsync	OBJECT IDENTIFIER ::={qsync 16}

qsyncIUnsyncVal	OBJECT-TYPE
	SYNTAX	 Counter64
	MAX-ACCESS read-only
	STATUS current
	DESCRIPTION "Qsync not run because unsynced objects"

	::={qsyncIUnsync 1}

qsyncIUnsyncMom	OBJECT-TYPE
	SYNTAX	 CounterBasedGauge64
	MAX-ACCESS read-only
	STATUS current
	DESCRIPTION "Qsync not run because unsynced objects"

	::={qsyncIUnsync 2}

qsyncIUnsyncMax	OBJECT-TYPE
	SYNTAX	 CounterBasedGauge64
	MAX-ACCESS read-only
	STATUS current
	DESCRIPTION "Qsync not run because unsynced objects"

	::={qsyncIUnsync 3}

qsyncESendbufFull	OBJECT IDENTIFIER ::={qsync 17}

qsyncESendbufFullVal	OBJECT-TYPE
	SYNTAX	 Counter64
	MAX-ACCESS read-only
	STATUS current
	DESCRIPTION "(ext) Entries dropped due to full sendbuffer"

	::={qsyncESendbufFull 1}

qsyncESendbufFullMom	OBJECT-TYPE
	SYNTAX	 CounterBasedGauge64
	MAX-ACCESS read-only
	STATUS current
	DESCRIPTION "(ext) Entries dropped due to full sendbuffer"

	::={qsyncESendbufFull 2}

qsyncESendbufFullMax	OBJECT-TYPE
	SYNTAX	 CounterBasedGauge64
	MAX-ACCESS read-only
	STATUS current
	DESCRIPTION "(ext) Entries dropped due to full sendbuffer"

	::={qsyncESendbufFull 3}

qsyncESendbufUsage	OBJECT IDENTIFIER ::={qsync 18}

qsyncESendbufUsageVal	OBJECT-TYPE
	SYNTAX	 CounterBasedGauge64
	MAX-ACCESS read-only
	STATUS current
	DESCRIPTION "(ext) Sendbuffer usage"

	::={qsyncESendbufUsage 1}

qsyncESendbufUsageMax	OBJECT-TYPE
	SYNTAX	 CounterBasedGauge64
	MAX-ACCESS read-only
	STATUS current
	DESCRIPTION "(ext) Sendbuffer usage"

	::={qsyncESendbufUsage 3}

qsyncIIgnoredOOO	OBJECT IDENTIFIER ::={qsync 19}

qsyncIIgnoredOOOVal	OBJECT-TYPE
	SYNTAX	 Counter64
	MAX-ACCESS read-only
	STATUS current
	DESCRIPTION "Ignored out of order updates"

	::={qsyncIIgnoredOOO 1}

qsyncIIgnoredOOOMom	OBJECT-TYPE
	SYNTAX	 CounterBasedGauge64
	MAX-ACCESS read-only
	STATUS current
	DESCRIPTION "Ignored out of order updates"

	::={qsyncIIgnoredOOO 2}

qsyncIIgnoredOOOMax	OBJECT-TYPE
	SYNTAX	 CounterBasedGauge64
	MAX-ACCESS read-only
	STATUS current
	DESCRIPTION "Ignored out of order updates"

	::={qsyncIIgnoredOOO 3}

qsyncIIgnoredGenWrap	OBJECT IDENTIFIER ::={qsync 20}

qsyncIIgnoredGenWrapVal	OBJECT-TYPE
	SYNTAX	 Counter64
	MAX-ACCESS read-only
	STATUS current
	DESCRIPTION "Ignored updates (generation wrap)"

	::={qsyncIIgnoredGenWrap 1}

qsyncIIgnoredGenWrapMom	OBJECT-TYPE
	SYNTAX	 CounterBasedGauge64
	MAX-ACCESS read-only
	STATUS current
	DESCRIPTION "Ignored updates (generation wrap)"

	::={qsyncIIgnoredGenWrap 2}

qsyncIIgnoredGenWrapMax	OBJECT-TYPE
	SYNTAX	 CounterBasedGauge64
	MAX-ACCESS read-only
	STATUS current
	DESCRIPTION "Ignored updates (generation wrap)"

	::={qsyncIIgnoredGenWrap 3}

shapingcounter	OBJECT IDENTIFIER ::={sysdiag 124}

shapingcounterUpdates	OBJECT IDENTIFIER ::={shapingcounter 1}

shapingcounterUpdatesVal	OBJECT-TYPE
	SYNTAX	 Counter64
	MAX-ACCESS read-only
	STATUS current
	DESCRIPTION "Updates received"

	::={shapingcounterUpdates 1}

shapingcounterUpdatesMom	OBJECT-TYPE
	SYNTAX	 CounterBasedGauge64
	MAX-ACCESS read-only
	STATUS current
	DESCRIPTION "Updates received"

	::={shapingcounterUpdates 2}

shapingcounterUpdatesMax	OBJECT-TYPE
	SYNTAX	 CounterBasedGauge64
	MAX-ACCESS read-only
	STATUS current
	DESCRIPTION "Updates received"

	::={shapingcounterUpdates 3}

shapingcounterActive	OBJECT IDENTIFIER ::={shapingcounter 2}

shapingcounterActiveVal	OBJECT-TYPE
	SYNTAX	 CounterBasedGauge64
	MAX-ACCESS read-only
	STATUS current
	DESCRIPTION "Active counters"

	::={shapingcounterActive 1}

shapingcounterActiveMax	OBJECT-TYPE
	SYNTAX	 CounterBasedGauge64
	MAX-ACCESS read-only
	STATUS current
	DESCRIPTION "Active counters"

	::={shapingcounterActive 3}

shapingcounterClients	OBJECT IDENTIFIER ::={shapingcounter 3}

shapingcounterClientsVal	OBJECT-TYPE
	SYNTAX	 CounterBasedGauge64
	MAX-ACCESS read-only
	STATUS current
	DESCRIPTION "Active clients"

	::={shapingcounterClients 1}

shapingcounterClientsMax	OBJECT-TYPE
	SYNTAX	 CounterBasedGauge64
	MAX-ACCESS read-only
	STATUS current
	DESCRIPTION "Active clients"

	::={shapingcounterClients 3}

shapingcounterRecycle	OBJECT IDENTIFIER ::={shapingcounter 4}

shapingcounterRecycleVal	OBJECT-TYPE
	SYNTAX	 Counter64
	MAX-ACCESS read-only
	STATUS current
	DESCRIPTION "Recycles"

	::={shapingcounterRecycle 1}

shapingcounterRecycleMom	OBJECT-TYPE
	SYNTAX	 CounterBasedGauge64
	MAX-ACCESS read-only
	STATUS current
	DESCRIPTION "Recycles"

	::={shapingcounterRecycle 2}

shapingcounterRecycleMax	OBJECT-TYPE
	SYNTAX	 CounterBasedGauge64
	MAX-ACCESS read-only
	STATUS current
	DESCRIPTION "Recycles"

	::={shapingcounterRecycle 3}

shapingcounterUpdatesInteresting	OBJECT IDENTIFIER ::={shapingcounter 5}

shapingcounterUpdatesInterestingVal	OBJECT-TYPE
	SYNTAX	 Counter64
	MAX-ACCESS read-only
	STATUS current
	DESCRIPTION "Updates crossing granularity boundary received"

	::={shapingcounterUpdatesInteresting 1}

shapingcounterUpdatesInterestingMom	OBJECT-TYPE
	SYNTAX	 CounterBasedGauge64
	MAX-ACCESS read-only
	STATUS current
	DESCRIPTION "Updates crossing granularity boundary received"

	::={shapingcounterUpdatesInteresting 2}

shapingcounterUpdatesInterestingMax	OBJECT-TYPE
	SYNTAX	 CounterBasedGauge64
	MAX-ACCESS read-only
	STATUS current
	DESCRIPTION "Updates crossing granularity boundary received"

	::={shapingcounterUpdatesInteresting 3}

divert	OBJECT IDENTIFIER ::={sysdiag 125}

divertOutOfHosts	OBJECT IDENTIFIER ::={divert 2}

divertOutOfHostsVal	OBJECT-TYPE
	SYNTAX	 Counter64
	MAX-ACCESS read-only
	STATUS current
	DESCRIPTION "Out of hosts"

	::={divertOutOfHosts 1}

divertOutOfHostsMom	OBJECT-TYPE
	SYNTAX	 CounterBasedGauge64
	MAX-ACCESS read-only
	STATUS current
	DESCRIPTION "Out of hosts"

	::={divertOutOfHosts 2}

divertOutOfHostsMax	OBJECT-TYPE
	SYNTAX	 CounterBasedGauge64
	MAX-ACCESS read-only
	STATUS current
	DESCRIPTION "Out of hosts"

	::={divertOutOfHosts 3}

divertOversizeL2	OBJECT IDENTIFIER ::={divert 3}

divertOversizeL2Val	OBJECT-TYPE
	SYNTAX	 Counter64
	MAX-ACCESS read-only
	STATUS current
	DESCRIPTION "Too large L2-headers"

	::={divertOversizeL2 1}

divertOversizeL2Mom	OBJECT-TYPE
	SYNTAX	 CounterBasedGauge64
	MAX-ACCESS read-only
	STATUS current
	DESCRIPTION "Too large L2-headers"

	::={divertOversizeL2 2}

divertOversizeL2Max	OBJECT-TYPE
	SYNTAX	 CounterBasedGauge64
	MAX-ACCESS read-only
	STATUS current
	DESCRIPTION "Too large L2-headers"

	::={divertOversizeL2 3}

divertEgressPackets	OBJECT IDENTIFIER ::={divert 4}

divertEgressPacketsVal	OBJECT-TYPE
	SYNTAX	 Counter64
	MAX-ACCESS read-only
	STATUS current
	DESCRIPTION "Egress packets"

	::={divertEgressPackets 1}

divertEgressPacketsMom	OBJECT-TYPE
	SYNTAX	 CounterBasedGauge64
	MAX-ACCESS read-only
	STATUS current
	DESCRIPTION "Egress packets"

	::={divertEgressPackets 2}

divertEgressPacketsMax	OBJECT-TYPE
	SYNTAX	 CounterBasedGauge64
	MAX-ACCESS read-only
	STATUS current
	DESCRIPTION "Egress packets"

	::={divertEgressPackets 3}

divertEgressBytes	OBJECT IDENTIFIER ::={divert 5}

divertEgressBytesVal	OBJECT-TYPE
	SYNTAX	 Counter64
	MAX-ACCESS read-only
	STATUS current
	DESCRIPTION "Egress bytes"

	::={divertEgressBytes 1}

divertEgressBytesMom	OBJECT-TYPE
	SYNTAX	 CounterBasedGauge64
	MAX-ACCESS read-only
	STATUS current
	DESCRIPTION "Egress bytes"

	::={divertEgressBytes 2}

divertEgressBytesMax	OBJECT-TYPE
	SYNTAX	 CounterBasedGauge64
	MAX-ACCESS read-only
	STATUS current
	DESCRIPTION "Egress bytes"

	::={divertEgressBytes 3}

divertIngressPackets	OBJECT IDENTIFIER ::={divert 6}

divertIngressPacketsVal	OBJECT-TYPE
	SYNTAX	 Counter64
	MAX-ACCESS read-only
	STATUS current
	DESCRIPTION "Ingress packets"

	::={divertIngressPackets 1}

divertIngressPacketsMom	OBJECT-TYPE
	SYNTAX	 CounterBasedGauge64
	MAX-ACCESS read-only
	STATUS current
	DESCRIPTION "Ingress packets"

	::={divertIngressPackets 2}

divertIngressPacketsMax	OBJECT-TYPE
	SYNTAX	 CounterBasedGauge64
	MAX-ACCESS read-only
	STATUS current
	DESCRIPTION "Ingress packets"

	::={divertIngressPackets 3}

divertIngressBytes	OBJECT IDENTIFIER ::={divert 7}

divertIngressBytesVal	OBJECT-TYPE
	SYNTAX	 Counter64
	MAX-ACCESS read-only
	STATUS current
	DESCRIPTION "Ingress bytes"

	::={divertIngressBytes 1}

divertIngressBytesMom	OBJECT-TYPE
	SYNTAX	 CounterBasedGauge64
	MAX-ACCESS read-only
	STATUS current
	DESCRIPTION "Ingress bytes"

	::={divertIngressBytes 2}

divertIngressBytesMax	OBJECT-TYPE
	SYNTAX	 CounterBasedGauge64
	MAX-ACCESS read-only
	STATUS current
	DESCRIPTION "Ingress bytes"

	::={divertIngressBytes 3}

divertIngressPacketsNohost	OBJECT IDENTIFIER ::={divert 8}

divertIngressPacketsNohostVal	OBJECT-TYPE
	SYNTAX	 Counter64
	MAX-ACCESS read-only
	STATUS current
	DESCRIPTION "Ingress packets with missing host"

	::={divertIngressPacketsNohost 1}

divertIngressPacketsNohostMom	OBJECT-TYPE
	SYNTAX	 CounterBasedGauge64
	MAX-ACCESS read-only
	STATUS current
	DESCRIPTION "Ingress packets with missing host"

	::={divertIngressPacketsNohost 2}

divertIngressPacketsNohostMax	OBJECT-TYPE
	SYNTAX	 CounterBasedGauge64
	MAX-ACCESS read-only
	STATUS current
	DESCRIPTION "Ingress packets with missing host"

	::={divertIngressPacketsNohost 3}

divertIngressPacketsNol2	OBJECT IDENTIFIER ::={divert 9}

divertIngressPacketsNol2Val	OBJECT-TYPE
	SYNTAX	 Counter64
	MAX-ACCESS read-only
	STATUS current
	DESCRIPTION "Ingress packets with host missing L2-header"

	::={divertIngressPacketsNol2 1}

divertIngressPacketsNol2Mom	OBJECT-TYPE
	SYNTAX	 CounterBasedGauge64
	MAX-ACCESS read-only
	STATUS current
	DESCRIPTION "Ingress packets with host missing L2-header"

	::={divertIngressPacketsNol2 2}

divertIngressPacketsNol2Max	OBJECT-TYPE
	SYNTAX	 CounterBasedGauge64
	MAX-ACCESS read-only
	STATUS current
	DESCRIPTION "Ingress packets with host missing L2-header"

	::={divertIngressPacketsNol2 3}

divertHostsUse	OBJECT IDENTIFIER ::={divert 10}

divertHostsUseVal	OBJECT-TYPE
	SYNTAX	 CounterBasedGauge64
	MAX-ACCESS read-only
	STATUS current
	DESCRIPTION "Hosts"

	::={divertHostsUse 1}

divertHostsUseMax	OBJECT-TYPE
	SYNTAX	 CounterBasedGauge64
	MAX-ACCESS read-only
	STATUS current
	DESCRIPTION "Hosts"

	::={divertHostsUse 3}

divertConnections	OBJECT IDENTIFIER ::={divert 11}

divertConnectionsVal	OBJECT-TYPE
	SYNTAX	 CounterBasedGauge64
	MAX-ACCESS read-only
	STATUS current
	DESCRIPTION "Connections"

	::={divertConnections 1}

divertConnectionsMax	OBJECT-TYPE
	SYNTAX	 CounterBasedGauge64
	MAX-ACCESS read-only
	STATUS current
	DESCRIPTION "Connections"

	::={divertConnections 3}

divertHbReqSent	OBJECT IDENTIFIER ::={divert 12}

divertHbReqSentVal	OBJECT-TYPE
	SYNTAX	 Counter64
	MAX-ACCESS read-only
	STATUS current
	DESCRIPTION "Heartbeat requests sent"

	::={divertHbReqSent 1}

divertHbReqSentMom	OBJECT-TYPE
	SYNTAX	 CounterBasedGauge64
	MAX-ACCESS read-only
	STATUS current
	DESCRIPTION "Heartbeat requests sent"

	::={divertHbReqSent 2}

divertHbReqSentMax	OBJECT-TYPE
	SYNTAX	 CounterBasedGauge64
	MAX-ACCESS read-only
	STATUS current
	DESCRIPTION "Heartbeat requests sent"

	::={divertHbReqSent 3}

divertHbReqRecv	OBJECT IDENTIFIER ::={divert 13}

divertHbReqRecvVal	OBJECT-TYPE
	SYNTAX	 Counter64
	MAX-ACCESS read-only
	STATUS current
	DESCRIPTION "Heartbeat requests received"

	::={divertHbReqRecv 1}

divertHbReqRecvMom	OBJECT-TYPE
	SYNTAX	 CounterBasedGauge64
	MAX-ACCESS read-only
	STATUS current
	DESCRIPTION "Heartbeat requests received"

	::={divertHbReqRecv 2}

divertHbReqRecvMax	OBJECT-TYPE
	SYNTAX	 CounterBasedGauge64
	MAX-ACCESS read-only
	STATUS current
	DESCRIPTION "Heartbeat requests received"

	::={divertHbReqRecv 3}

divertHbRepSent	OBJECT IDENTIFIER ::={divert 14}

divertHbRepSentVal	OBJECT-TYPE
	SYNTAX	 Counter64
	MAX-ACCESS read-only
	STATUS current
	DESCRIPTION "Heartbeat replies sent"

	::={divertHbRepSent 1}

divertHbRepSentMom	OBJECT-TYPE
	SYNTAX	 CounterBasedGauge64
	MAX-ACCESS read-only
	STATUS current
	DESCRIPTION "Heartbeat replies sent"

	::={divertHbRepSent 2}

divertHbRepSentMax	OBJECT-TYPE
	SYNTAX	 CounterBasedGauge64
	MAX-ACCESS read-only
	STATUS current
	DESCRIPTION "Heartbeat replies sent"

	::={divertHbRepSent 3}

divertHbRepRecv	OBJECT IDENTIFIER ::={divert 15}

divertHbRepRecvVal	OBJECT-TYPE
	SYNTAX	 Counter64
	MAX-ACCESS read-only
	STATUS current
	DESCRIPTION "Heartbeat replies received"

	::={divertHbRepRecv 1}

divertHbRepRecvMom	OBJECT-TYPE
	SYNTAX	 CounterBasedGauge64
	MAX-ACCESS read-only
	STATUS current
	DESCRIPTION "Heartbeat replies received"

	::={divertHbRepRecv 2}

divertHbRepRecvMax	OBJECT-TYPE
	SYNTAX	 CounterBasedGauge64
	MAX-ACCESS read-only
	STATUS current
	DESCRIPTION "Heartbeat replies received"

	::={divertHbRepRecv 3}

divertHbLost	OBJECT IDENTIFIER ::={divert 16}

divertHbLostVal	OBJECT-TYPE
	SYNTAX	 Counter64
	MAX-ACCESS read-only
	STATUS current
	DESCRIPTION "Heartbeats lost"

	::={divertHbLost 1}

divertHbLostMom	OBJECT-TYPE
	SYNTAX	 CounterBasedGauge64
	MAX-ACCESS read-only
	STATUS current
	DESCRIPTION "Heartbeats lost"

	::={divertHbLost 2}

divertHbLostMax	OBJECT-TYPE
	SYNTAX	 CounterBasedGauge64
	MAX-ACCESS read-only
	STATUS current
	DESCRIPTION "Heartbeats lost"

	::={divertHbLost 3}

divertBypassPackets	OBJECT IDENTIFIER ::={divert 17}

divertBypassPacketsVal	OBJECT-TYPE
	SYNTAX	 Counter64
	MAX-ACCESS read-only
	STATUS current
	DESCRIPTION "Bypassed packets"

	::={divertBypassPackets 1}

divertBypassPacketsMom	OBJECT-TYPE
	SYNTAX	 CounterBasedGauge64
	MAX-ACCESS read-only
	STATUS current
	DESCRIPTION "Bypassed packets"

	::={divertBypassPackets 2}

divertBypassPacketsMax	OBJECT-TYPE
	SYNTAX	 CounterBasedGauge64
	MAX-ACCESS read-only
	STATUS current
	DESCRIPTION "Bypassed packets"

	::={divertBypassPackets 3}

divertDroppedPackets	OBJECT IDENTIFIER ::={divert 18}

divertDroppedPacketsVal	OBJECT-TYPE
	SYNTAX	 Counter64
	MAX-ACCESS read-only
	STATUS current
	DESCRIPTION "Dropped packets"

	::={divertDroppedPackets 1}

divertDroppedPacketsMom	OBJECT-TYPE
	SYNTAX	 CounterBasedGauge64
	MAX-ACCESS read-only
	STATUS current
	DESCRIPTION "Dropped packets"

	::={divertDroppedPackets 2}

divertDroppedPacketsMax	OBJECT-TYPE
	SYNTAX	 CounterBasedGauge64
	MAX-ACCESS read-only
	STATUS current
	DESCRIPTION "Dropped packets"

	::={divertDroppedPackets 3}

teredo	OBJECT IDENTIFIER ::={sysdiag 128}

teredoPackets	OBJECT IDENTIFIER ::={teredo 2}

teredoPacketsVal	OBJECT-TYPE
	SYNTAX	 Counter64
	MAX-ACCESS read-only
	STATUS current
	DESCRIPTION "RX packets"

	::={teredoPackets 1}

teredoPacketsMom	OBJECT-TYPE
	SYNTAX	 CounterBasedGauge64
	MAX-ACCESS read-only
	STATUS current
	DESCRIPTION "RX packets"

	::={teredoPackets 2}

teredoPacketsMax	OBJECT-TYPE
	SYNTAX	 CounterBasedGauge64
	MAX-ACCESS read-only
	STATUS current
	DESCRIPTION "RX packets"

	::={teredoPackets 3}

teredoBytes	OBJECT IDENTIFIER ::={teredo 3}

teredoBytesVal	OBJECT-TYPE
	SYNTAX	 Counter64
	MAX-ACCESS read-only
	STATUS current
	DESCRIPTION "RX data"

	::={teredoBytes 1}

teredoBytesMom	OBJECT-TYPE
	SYNTAX	 CounterBasedGauge64
	MAX-ACCESS read-only
	STATUS current
	DESCRIPTION "RX data"

	::={teredoBytes 2}

teredoBytesMax	OBJECT-TYPE
	SYNTAX	 CounterBasedGauge64
	MAX-ACCESS read-only
	STATUS current
	DESCRIPTION "RX data"

	::={teredoBytes 3}

teredoOrgHeaders	OBJECT IDENTIFIER ::={teredo 4}

teredoOrgHeadersVal	OBJECT-TYPE
	SYNTAX	 Counter64
	MAX-ACCESS read-only
	STATUS current
	DESCRIPTION "Origin indication headers"

	::={teredoOrgHeaders 1}

teredoOrgHeadersMom	OBJECT-TYPE
	SYNTAX	 CounterBasedGauge64
	MAX-ACCESS read-only
	STATUS current
	DESCRIPTION "Origin indication headers"

	::={teredoOrgHeaders 2}

teredoOrgHeadersMax	OBJECT-TYPE
	SYNTAX	 CounterBasedGauge64
	MAX-ACCESS read-only
	STATUS current
	DESCRIPTION "Origin indication headers"

	::={teredoOrgHeaders 3}

teredoAuthHeaders	OBJECT IDENTIFIER ::={teredo 5}

teredoAuthHeadersVal	OBJECT-TYPE
	SYNTAX	 Counter64
	MAX-ACCESS read-only
	STATUS current
	DESCRIPTION "Authentication headers"

	::={teredoAuthHeaders 1}

teredoAuthHeadersMom	OBJECT-TYPE
	SYNTAX	 CounterBasedGauge64
	MAX-ACCESS read-only
	STATUS current
	DESCRIPTION "Authentication headers"

	::={teredoAuthHeaders 2}

teredoAuthHeadersMax	OBJECT-TYPE
	SYNTAX	 CounterBasedGauge64
	MAX-ACCESS read-only
	STATUS current
	DESCRIPTION "Authentication headers"

	::={teredoAuthHeaders 3}

teredoFrags	OBJECT IDENTIFIER ::={teredo 6}

teredoFragsVal	OBJECT-TYPE
	SYNTAX	 Counter64
	MAX-ACCESS read-only
	STATUS current
	DESCRIPTION "Teredo packets inside fragments"

	::={teredoFrags 1}

teredoFragsMom	OBJECT-TYPE
	SYNTAX	 CounterBasedGauge64
	MAX-ACCESS read-only
	STATUS current
	DESCRIPTION "Teredo packets inside fragments"

	::={teredoFrags 2}

teredoFragsMax	OBJECT-TYPE
	SYNTAX	 CounterBasedGauge64
	MAX-ACCESS read-only
	STATUS current
	DESCRIPTION "Teredo packets inside fragments"

	::={teredoFrags 3}

gtp	OBJECT IDENTIFIER ::={sysdiag 129}

gtpPackets	OBJECT IDENTIFIER ::={gtp 2}

gtpPacketsVal	OBJECT-TYPE
	SYNTAX	 Counter64
	MAX-ACCESS read-only
	STATUS current
	DESCRIPTION "RX packets"

	::={gtpPackets 1}

gtpPacketsMom	OBJECT-TYPE
	SYNTAX	 CounterBasedGauge64
	MAX-ACCESS read-only
	STATUS current
	DESCRIPTION "RX packets"

	::={gtpPackets 2}

gtpPacketsMax	OBJECT-TYPE
	SYNTAX	 CounterBasedGauge64
	MAX-ACCESS read-only
	STATUS current
	DESCRIPTION "RX packets"

	::={gtpPackets 3}

gtpBytes	OBJECT IDENTIFIER ::={gtp 3}

gtpBytesVal	OBJECT-TYPE
	SYNTAX	 Counter64
	MAX-ACCESS read-only
	STATUS current
	DESCRIPTION "RX data"

	::={gtpBytes 1}

gtpBytesMom	OBJECT-TYPE
	SYNTAX	 CounterBasedGauge64
	MAX-ACCESS read-only
	STATUS current
	DESCRIPTION "RX data"

	::={gtpBytes 2}

gtpBytesMax	OBJECT-TYPE
	SYNTAX	 CounterBasedGauge64
	MAX-ACCESS read-only
	STATUS current
	DESCRIPTION "RX data"

	::={gtpBytes 3}

gtpGpdus	OBJECT IDENTIFIER ::={gtp 4}

gtpGpdusVal	OBJECT-TYPE
	SYNTAX	 Counter64
	MAX-ACCESS read-only
	STATUS current
	DESCRIPTION "G-PDU Packets"

	::={gtpGpdus 1}

gtpGpdusMom	OBJECT-TYPE
	SYNTAX	 CounterBasedGauge64
	MAX-ACCESS read-only
	STATUS current
	DESCRIPTION "G-PDU Packets"

	::={gtpGpdus 2}

gtpGpdusMax	OBJECT-TYPE
	SYNTAX	 CounterBasedGauge64
	MAX-ACCESS read-only
	STATUS current
	DESCRIPTION "G-PDU Packets"

	::={gtpGpdus 3}

gtpCreatePdpReq	OBJECT IDENTIFIER ::={gtp 5}

gtpCreatePdpReqVal	OBJECT-TYPE
	SYNTAX	 Counter64
	MAX-ACCESS read-only
	STATUS current
	DESCRIPTION "Create PDP Context Request Packets"

	::={gtpCreatePdpReq 1}

gtpCreatePdpReqMom	OBJECT-TYPE
	SYNTAX	 CounterBasedGauge64
	MAX-ACCESS read-only
	STATUS current
	DESCRIPTION "Create PDP Context Request Packets"

	::={gtpCreatePdpReq 2}

gtpCreatePdpReqMax	OBJECT-TYPE
	SYNTAX	 CounterBasedGauge64
	MAX-ACCESS read-only
	STATUS current
	DESCRIPTION "Create PDP Context Request Packets"

	::={gtpCreatePdpReq 3}

gtpCreatePdpRsp	OBJECT IDENTIFIER ::={gtp 6}

gtpCreatePdpRspVal	OBJECT-TYPE
	SYNTAX	 Counter64
	MAX-ACCESS read-only
	STATUS current
	DESCRIPTION "Create PDP Context Response Packets"

	::={gtpCreatePdpRsp 1}

gtpCreatePdpRspMom	OBJECT-TYPE
	SYNTAX	 CounterBasedGauge64
	MAX-ACCESS read-only
	STATUS current
	DESCRIPTION "Create PDP Context Response Packets"

	::={gtpCreatePdpRsp 2}

gtpCreatePdpRspMax	OBJECT-TYPE
	SYNTAX	 CounterBasedGauge64
	MAX-ACCESS read-only
	STATUS current
	DESCRIPTION "Create PDP Context Response Packets"

	::={gtpCreatePdpRsp 3}

gtpDeletePdpReq	OBJECT IDENTIFIER ::={gtp 7}

gtpDeletePdpReqVal	OBJECT-TYPE
	SYNTAX	 Counter64
	MAX-ACCESS read-only
	STATUS current
	DESCRIPTION "Delete PDP Context Request Packets"

	::={gtpDeletePdpReq 1}

gtpDeletePdpReqMom	OBJECT-TYPE
	SYNTAX	 CounterBasedGauge64
	MAX-ACCESS read-only
	STATUS current
	DESCRIPTION "Delete PDP Context Request Packets"

	::={gtpDeletePdpReq 2}

gtpDeletePdpReqMax	OBJECT-TYPE
	SYNTAX	 CounterBasedGauge64
	MAX-ACCESS read-only
	STATUS current
	DESCRIPTION "Delete PDP Context Request Packets"

	::={gtpDeletePdpReq 3}

gtpDeletePdpRsp	OBJECT IDENTIFIER ::={gtp 8}

gtpDeletePdpRspVal	OBJECT-TYPE
	SYNTAX	 Counter64
	MAX-ACCESS read-only
	STATUS current
	DESCRIPTION "Delete PDP Context Response Packets"

	::={gtpDeletePdpRsp 1}

gtpDeletePdpRspMom	OBJECT-TYPE
	SYNTAX	 CounterBasedGauge64
	MAX-ACCESS read-only
	STATUS current
	DESCRIPTION "Delete PDP Context Response Packets"

	::={gtpDeletePdpRsp 2}

gtpDeletePdpRspMax	OBJECT-TYPE
	SYNTAX	 CounterBasedGauge64
	MAX-ACCESS read-only
	STATUS current
	DESCRIPTION "Delete PDP Context Response Packets"

	::={gtpDeletePdpRsp 3}

gtpErrorInd	OBJECT IDENTIFIER ::={gtp 9}

gtpErrorIndVal	OBJECT-TYPE
	SYNTAX	 Counter64
	MAX-ACCESS read-only
	STATUS current
	DESCRIPTION "Error Indication"

	::={gtpErrorInd 1}

gtpErrorIndMom	OBJECT-TYPE
	SYNTAX	 CounterBasedGauge64
	MAX-ACCESS read-only
	STATUS current
	DESCRIPTION "Error Indication"

	::={gtpErrorInd 2}

gtpErrorIndMax	OBJECT-TYPE
	SYNTAX	 CounterBasedGauge64
	MAX-ACCESS read-only
	STATUS current
	DESCRIPTION "Error Indication"

	::={gtpErrorInd 3}

gtpUnknown	OBJECT IDENTIFIER ::={gtp 10}

gtpUnknownVal	OBJECT-TYPE
	SYNTAX	 Counter64
	MAX-ACCESS read-only
	STATUS current
	DESCRIPTION "Unkown GTP Type"

	::={gtpUnknown 1}

gtpUnknownMom	OBJECT-TYPE
	SYNTAX	 CounterBasedGauge64
	MAX-ACCESS read-only
	STATUS current
	DESCRIPTION "Unkown GTP Type"

	::={gtpUnknown 2}

gtpUnknownMax	OBJECT-TYPE
	SYNTAX	 CounterBasedGauge64
	MAX-ACCESS read-only
	STATUS current
	DESCRIPTION "Unkown GTP Type"

	::={gtpUnknown 3}

gtpUpdatePdpReq	OBJECT IDENTIFIER ::={gtp 11}

gtpUpdatePdpReqVal	OBJECT-TYPE
	SYNTAX	 Counter64
	MAX-ACCESS read-only
	STATUS current
	DESCRIPTION "Update PDP Context Request Packets"

	::={gtpUpdatePdpReq 1}

gtpUpdatePdpReqMom	OBJECT-TYPE
	SYNTAX	 CounterBasedGauge64
	MAX-ACCESS read-only
	STATUS current
	DESCRIPTION "Update PDP Context Request Packets"

	::={gtpUpdatePdpReq 2}

gtpUpdatePdpReqMax	OBJECT-TYPE
	SYNTAX	 CounterBasedGauge64
	MAX-ACCESS read-only
	STATUS current
	DESCRIPTION "Update PDP Context Request Packets"

	::={gtpUpdatePdpReq 3}

gtpUpdatePdpRsp	OBJECT IDENTIFIER ::={gtp 12}

gtpUpdatePdpRspVal	OBJECT-TYPE
	SYNTAX	 Counter64
	MAX-ACCESS read-only
	STATUS current
	DESCRIPTION "Update PDP Context Response Packets"

	::={gtpUpdatePdpRsp 1}

gtpUpdatePdpRspMom	OBJECT-TYPE
	SYNTAX	 CounterBasedGauge64
	MAX-ACCESS read-only
	STATUS current
	DESCRIPTION "Update PDP Context Response Packets"

	::={gtpUpdatePdpRsp 2}

gtpUpdatePdpRspMax	OBJECT-TYPE
	SYNTAX	 CounterBasedGauge64
	MAX-ACCESS read-only
	STATUS current
	DESCRIPTION "Update PDP Context Response Packets"

	::={gtpUpdatePdpRsp 3}

gtpEchoPdpReq	OBJECT IDENTIFIER ::={gtp 13}

gtpEchoPdpReqVal	OBJECT-TYPE
	SYNTAX	 Counter64
	MAX-ACCESS read-only
	STATUS current
	DESCRIPTION "Echo Request Packets"

	::={gtpEchoPdpReq 1}

gtpEchoPdpReqMom	OBJECT-TYPE
	SYNTAX	 CounterBasedGauge64
	MAX-ACCESS read-only
	STATUS current
	DESCRIPTION "Echo Request Packets"

	::={gtpEchoPdpReq 2}

gtpEchoPdpReqMax	OBJECT-TYPE
	SYNTAX	 CounterBasedGauge64
	MAX-ACCESS read-only
	STATUS current
	DESCRIPTION "Echo Request Packets"

	::={gtpEchoPdpReq 3}

gtpEchoPdpRsp	OBJECT IDENTIFIER ::={gtp 14}

gtpEchoPdpRspVal	OBJECT-TYPE
	SYNTAX	 Counter64
	MAX-ACCESS read-only
	STATUS current
	DESCRIPTION "Echo Response Packets"

	::={gtpEchoPdpRsp 1}

gtpEchoPdpRspMom	OBJECT-TYPE
	SYNTAX	 CounterBasedGauge64
	MAX-ACCESS read-only
	STATUS current
	DESCRIPTION "Echo Response Packets"

	::={gtpEchoPdpRsp 2}

gtpEchoPdpRspMax	OBJECT-TYPE
	SYNTAX	 CounterBasedGauge64
	MAX-ACCESS read-only
	STATUS current
	DESCRIPTION "Echo Response Packets"

	::={gtpEchoPdpRsp 3}

gtpSgsnReq	OBJECT IDENTIFIER ::={gtp 15}

gtpSgsnReqVal	OBJECT-TYPE
	SYNTAX	 Counter64
	MAX-ACCESS read-only
	STATUS current
	DESCRIPTION "SGSN Context Request"

	::={gtpSgsnReq 1}

gtpSgsnReqMom	OBJECT-TYPE
	SYNTAX	 CounterBasedGauge64
	MAX-ACCESS read-only
	STATUS current
	DESCRIPTION "SGSN Context Request"

	::={gtpSgsnReq 2}

gtpSgsnReqMax	OBJECT-TYPE
	SYNTAX	 CounterBasedGauge64
	MAX-ACCESS read-only
	STATUS current
	DESCRIPTION "SGSN Context Request"

	::={gtpSgsnReq 3}

gtpSgsnRsp	OBJECT IDENTIFIER ::={gtp 16}

gtpSgsnRspVal	OBJECT-TYPE
	SYNTAX	 Counter64
	MAX-ACCESS read-only
	STATUS current
	DESCRIPTION "SGSN Context Response"

	::={gtpSgsnRsp 1}

gtpSgsnRspMom	OBJECT-TYPE
	SYNTAX	 CounterBasedGauge64
	MAX-ACCESS read-only
	STATUS current
	DESCRIPTION "SGSN Context Response"

	::={gtpSgsnRsp 2}

gtpSgsnRspMax	OBJECT-TYPE
	SYNTAX	 CounterBasedGauge64
	MAX-ACCESS read-only
	STATUS current
	DESCRIPTION "SGSN Context Response"

	::={gtpSgsnRsp 3}

tunnel	OBJECT IDENTIFIER ::={sysdiag 130}

tunnelGtp	OBJECT IDENTIFIER ::={tunnel 2}

tunnelGtpVal	OBJECT-TYPE
	SYNTAX	 CounterBasedGauge64
	MAX-ACCESS read-only
	STATUS current
	DESCRIPTION "GTP Tunnel Contexts"

	::={tunnelGtp 1}

tunnelGtpMax	OBJECT-TYPE
	SYNTAX	 CounterBasedGauge64
	MAX-ACCESS read-only
	STATUS current
	DESCRIPTION "GTP Tunnel Contexts"

	::={tunnelGtp 3}

tunnelEsp	OBJECT IDENTIFIER ::={tunnel 3}

tunnelEspVal	OBJECT-TYPE
	SYNTAX	 CounterBasedGauge64
	MAX-ACCESS read-only
	STATUS current
	DESCRIPTION "ESP Tunnel Contexts"

	::={tunnelEsp 1}

tunnelEspMax	OBJECT-TYPE
	SYNTAX	 CounterBasedGauge64
	MAX-ACCESS read-only
	STATUS current
	DESCRIPTION "ESP Tunnel Contexts"

	::={tunnelEsp 3}

tunnelTeredo	OBJECT IDENTIFIER ::={tunnel 4}

tunnelTeredoVal	OBJECT-TYPE
	SYNTAX	 CounterBasedGauge64
	MAX-ACCESS read-only
	STATUS current
	DESCRIPTION "Teredo Tunnel Contexts"

	::={tunnelTeredo 1}

tunnelTeredoMax	OBJECT-TYPE
	SYNTAX	 CounterBasedGauge64
	MAX-ACCESS read-only
	STATUS current
	DESCRIPTION "Teredo Tunnel Contexts"

	::={tunnelTeredo 3}

tunnelGre	OBJECT IDENTIFIER ::={tunnel 5}

tunnelGreVal	OBJECT-TYPE
	SYNTAX	 CounterBasedGauge64
	MAX-ACCESS read-only
	STATUS current
	DESCRIPTION "GRE Tunnel Contexts"

	::={tunnelGre 1}

tunnelGreMax	OBJECT-TYPE
	SYNTAX	 CounterBasedGauge64
	MAX-ACCESS read-only
	STATUS current
	DESCRIPTION "GRE Tunnel Contexts"

	::={tunnelGre 3}

tunnelUnknownPkts	OBJECT IDENTIFIER ::={tunnel 6}

tunnelUnknownPktsVal	OBJECT-TYPE
	SYNTAX	 Counter64
	MAX-ACCESS read-only
	STATUS current
	DESCRIPTION "Packets For Unknown Tunnels"

	::={tunnelUnknownPkts 1}

tunnelUnknownPktsMom	OBJECT-TYPE
	SYNTAX	 CounterBasedGauge64
	MAX-ACCESS read-only
	STATUS current
	DESCRIPTION "Packets For Unknown Tunnels"

	::={tunnelUnknownPkts 2}

tunnelUnknownPktsMax	OBJECT-TYPE
	SYNTAX	 CounterBasedGauge64
	MAX-ACCESS read-only
	STATUS current
	DESCRIPTION "Packets For Unknown Tunnels"

	::={tunnelUnknownPkts 3}

tunnelDuplicates	OBJECT IDENTIFIER ::={tunnel 7}

tunnelDuplicatesVal	OBJECT-TYPE
	SYNTAX	 Counter64
	MAX-ACCESS read-only
	STATUS current
	DESCRIPTION "Tunnels With Duplicate Keys"

	::={tunnelDuplicates 1}

tunnelDuplicatesMom	OBJECT-TYPE
	SYNTAX	 CounterBasedGauge64
	MAX-ACCESS read-only
	STATUS current
	DESCRIPTION "Tunnels With Duplicate Keys"

	::={tunnelDuplicates 2}

tunnelDuplicatesMax	OBJECT-TYPE
	SYNTAX	 CounterBasedGauge64
	MAX-ACCESS read-only
	STATUS current
	DESCRIPTION "Tunnels With Duplicate Keys"

	::={tunnelDuplicates 3}

tunnelGeneric	OBJECT IDENTIFIER ::={tunnel 8}

tunnelGenericVal	OBJECT-TYPE
	SYNTAX	 CounterBasedGauge64
	MAX-ACCESS read-only
	STATUS current
	DESCRIPTION "Generic Tunnel Contexts"

	::={tunnelGeneric 1}

tunnelGenericMax	OBJECT-TYPE
	SYNTAX	 CounterBasedGauge64
	MAX-ACCESS read-only
	STATUS current
	DESCRIPTION "Generic Tunnel Contexts"

	::={tunnelGeneric 3}

tunnelKnownPkts	OBJECT IDENTIFIER ::={tunnel 9}

tunnelKnownPktsVal	OBJECT-TYPE
	SYNTAX	 Counter64
	MAX-ACCESS read-only
	STATUS current
	DESCRIPTION "Packets For Known Tunnels"

	::={tunnelKnownPkts 1}

tunnelKnownPktsMom	OBJECT-TYPE
	SYNTAX	 CounterBasedGauge64
	MAX-ACCESS read-only
	STATUS current
	DESCRIPTION "Packets For Known Tunnels"

	::={tunnelKnownPkts 2}

tunnelKnownPktsMax	OBJECT-TYPE
	SYNTAX	 CounterBasedGauge64
	MAX-ACCESS read-only
	STATUS current
	DESCRIPTION "Packets For Known Tunnels"

	::={tunnelKnownPkts 3}

tunnelL2tp	OBJECT IDENTIFIER ::={tunnel 10}

tunnelL2tpVal	OBJECT-TYPE
	SYNTAX	 CounterBasedGauge64
	MAX-ACCESS read-only
	STATUS current
	DESCRIPTION "L2TP Tunnel Contexts"

	::={tunnelL2tp 1}

tunnelL2tpMax	OBJECT-TYPE
	SYNTAX	 CounterBasedGauge64
	MAX-ACCESS read-only
	STATUS current
	DESCRIPTION "L2TP Tunnel Contexts"

	::={tunnelL2tp 3}

gre	OBJECT IDENTIFIER ::={sysdiag 131}

grePackets	OBJECT IDENTIFIER ::={gre 2}

grePacketsVal	OBJECT-TYPE
	SYNTAX	 Counter64
	MAX-ACCESS read-only
	STATUS current
	DESCRIPTION "RX packets"

	::={grePackets 1}

grePacketsMom	OBJECT-TYPE
	SYNTAX	 CounterBasedGauge64
	MAX-ACCESS read-only
	STATUS current
	DESCRIPTION "RX packets"

	::={grePackets 2}

grePacketsMax	OBJECT-TYPE
	SYNTAX	 CounterBasedGauge64
	MAX-ACCESS read-only
	STATUS current
	DESCRIPTION "RX packets"

	::={grePackets 3}

greBytes	OBJECT IDENTIFIER ::={gre 3}

greBytesVal	OBJECT-TYPE
	SYNTAX	 Counter64
	MAX-ACCESS read-only
	STATUS current
	DESCRIPTION "RX data"

	::={greBytes 1}

greBytesMom	OBJECT-TYPE
	SYNTAX	 CounterBasedGauge64
	MAX-ACCESS read-only
	STATUS current
	DESCRIPTION "RX data"

	::={greBytes 2}

greBytesMax	OBJECT-TYPE
	SYNTAX	 CounterBasedGauge64
	MAX-ACCESS read-only
	STATUS current
	DESCRIPTION "RX data"

	::={greBytes 3}

greUnknownVersion	OBJECT IDENTIFIER ::={gre 4}

greUnknownVersionVal	OBJECT-TYPE
	SYNTAX	 Counter64
	MAX-ACCESS read-only
	STATUS current
	DESCRIPTION "GRE Packets with unknown version"

	::={greUnknownVersion 1}

greUnknownVersionMom	OBJECT-TYPE
	SYNTAX	 CounterBasedGauge64
	MAX-ACCESS read-only
	STATUS current
	DESCRIPTION "GRE Packets with unknown version"

	::={greUnknownVersion 2}

greUnknownVersionMax	OBJECT-TYPE
	SYNTAX	 CounterBasedGauge64
	MAX-ACCESS read-only
	STATUS current
	DESCRIPTION "GRE Packets with unknown version"

	::={greUnknownVersion 3}

greShortPackets	OBJECT IDENTIFIER ::={gre 5}

greShortPacketsVal	OBJECT-TYPE
	SYNTAX	 Counter64
	MAX-ACCESS read-only
	STATUS current
	DESCRIPTION "Too Short GRE Packets"

	::={greShortPackets 1}

greShortPacketsMom	OBJECT-TYPE
	SYNTAX	 CounterBasedGauge64
	MAX-ACCESS read-only
	STATUS current
	DESCRIPTION "Too Short GRE Packets"

	::={greShortPackets 2}

greShortPacketsMax	OBJECT-TYPE
	SYNTAX	 CounterBasedGauge64
	MAX-ACCESS read-only
	STATUS current
	DESCRIPTION "Too Short GRE Packets"

	::={greShortPackets 3}

greUnknownType	OBJECT IDENTIFIER ::={gre 6}

greUnknownTypeVal	OBJECT-TYPE
	SYNTAX	 Counter64
	MAX-ACCESS read-only
	STATUS current
	DESCRIPTION "GRE packets with unkown type"

	::={greUnknownType 1}

greUnknownTypeMom	OBJECT-TYPE
	SYNTAX	 CounterBasedGauge64
	MAX-ACCESS read-only
	STATUS current
	DESCRIPTION "GRE packets with unkown type"

	::={greUnknownType 2}

greUnknownTypeMax	OBJECT-TYPE
	SYNTAX	 CounterBasedGauge64
	MAX-ACCESS read-only
	STATUS current
	DESCRIPTION "GRE packets with unkown type"

	::={greUnknownType 3}

greRouteFlag	OBJECT IDENTIFIER ::={gre 7}

greRouteFlagVal	OBJECT-TYPE
	SYNTAX	 Counter64
	MAX-ACCESS read-only
	STATUS current
	DESCRIPTION "GRE packets with depricated route flag"

	::={greRouteFlag 1}

greRouteFlagMom	OBJECT-TYPE
	SYNTAX	 CounterBasedGauge64
	MAX-ACCESS read-only
	STATUS current
	DESCRIPTION "GRE packets with depricated route flag"

	::={greRouteFlag 2}

greRouteFlagMax	OBJECT-TYPE
	SYNTAX	 CounterBasedGauge64
	MAX-ACCESS read-only
	STATUS current
	DESCRIPTION "GRE packets with depricated route flag"

	::={greRouteFlag 3}

greIpv4Packets	OBJECT IDENTIFIER ::={gre 8}

greIpv4PacketsVal	OBJECT-TYPE
	SYNTAX	 Counter64
	MAX-ACCESS read-only
	STATUS current
	DESCRIPTION "IPv4 Type packets"

	::={greIpv4Packets 1}

greIpv4PacketsMom	OBJECT-TYPE
	SYNTAX	 CounterBasedGauge64
	MAX-ACCESS read-only
	STATUS current
	DESCRIPTION "IPv4 Type packets"

	::={greIpv4Packets 2}

greIpv4PacketsMax	OBJECT-TYPE
	SYNTAX	 CounterBasedGauge64
	MAX-ACCESS read-only
	STATUS current
	DESCRIPTION "IPv4 Type packets"

	::={greIpv4Packets 3}

greIpv6Packets	OBJECT IDENTIFIER ::={gre 9}

greIpv6PacketsVal	OBJECT-TYPE
	SYNTAX	 Counter64
	MAX-ACCESS read-only
	STATUS current
	DESCRIPTION "IPv6 Type packets"

	::={greIpv6Packets 1}

greIpv6PacketsMom	OBJECT-TYPE
	SYNTAX	 CounterBasedGauge64
	MAX-ACCESS read-only
	STATUS current
	DESCRIPTION "IPv6 Type packets"

	::={greIpv6Packets 2}

greIpv6PacketsMax	OBJECT-TYPE
	SYNTAX	 CounterBasedGauge64
	MAX-ACCESS read-only
	STATUS current
	DESCRIPTION "IPv6 Type packets"

	::={greIpv6Packets 3}

greFfffPackets	OBJECT IDENTIFIER ::={gre 10}

greFfffPacketsVal	OBJECT-TYPE
	SYNTAX	 Counter64
	MAX-ACCESS read-only
	STATUS current
	DESCRIPTION "0xffff Type packets"

	::={greFfffPackets 1}

greFfffPacketsMom	OBJECT-TYPE
	SYNTAX	 CounterBasedGauge64
	MAX-ACCESS read-only
	STATUS current
	DESCRIPTION "0xffff Type packets"

	::={greFfffPackets 2}

greFfffPacketsMax	OBJECT-TYPE
	SYNTAX	 CounterBasedGauge64
	MAX-ACCESS read-only
	STATUS current
	DESCRIPTION "0xffff Type packets"

	::={greFfffPackets 3}

grePptpPackets	OBJECT IDENTIFIER ::={gre 11}

grePptpPacketsVal	OBJECT-TYPE
	SYNTAX	 Counter64
	MAX-ACCESS read-only
	STATUS current
	DESCRIPTION "PPTP Packets"

	::={grePptpPackets 1}

grePptpPacketsMom	OBJECT-TYPE
	SYNTAX	 CounterBasedGauge64
	MAX-ACCESS read-only
	STATUS current
	DESCRIPTION "PPTP Packets"

	::={grePptpPackets 2}

grePptpPacketsMax	OBJECT-TYPE
	SYNTAX	 CounterBasedGauge64
	MAX-ACCESS read-only
	STATUS current
	DESCRIPTION "PPTP Packets"

	::={grePptpPackets 3}

grePppPackets	OBJECT IDENTIFIER ::={gre 12}

grePppPacketsVal	OBJECT-TYPE
	SYNTAX	 Counter64
	MAX-ACCESS read-only
	STATUS current
	DESCRIPTION "PPP Type Packets"

	::={grePppPackets 1}

grePppPacketsMom	OBJECT-TYPE
	SYNTAX	 CounterBasedGauge64
	MAX-ACCESS read-only
	STATUS current
	DESCRIPTION "PPP Type Packets"

	::={grePppPackets 2}

grePppPacketsMax	OBJECT-TYPE
	SYNTAX	 CounterBasedGauge64
	MAX-ACCESS read-only
	STATUS current
	DESCRIPTION "PPP Type Packets"

	::={grePppPackets 3}

grePppUnknownPackets	OBJECT IDENTIFIER ::={gre 13}

grePppUnknownPacketsVal	OBJECT-TYPE
	SYNTAX	 Counter64
	MAX-ACCESS read-only
	STATUS current
	DESCRIPTION "PPP Type Packets with Unknown Protocol"

	::={grePppUnknownPackets 1}

grePppUnknownPacketsMom	OBJECT-TYPE
	SYNTAX	 CounterBasedGauge64
	MAX-ACCESS read-only
	STATUS current
	DESCRIPTION "PPP Type Packets with Unknown Protocol"

	::={grePppUnknownPackets 2}

grePppUnknownPacketsMax	OBJECT-TYPE
	SYNTAX	 CounterBasedGauge64
	MAX-ACCESS read-only
	STATUS current
	DESCRIPTION "PPP Type Packets with Unknown Protocol"

	::={grePppUnknownPackets 3}

l2tp	OBJECT IDENTIFIER ::={sysdiag 132}

l2tpPackets	OBJECT IDENTIFIER ::={l2tp 2}

l2tpPacketsVal	OBJECT-TYPE
	SYNTAX	 Counter64
	MAX-ACCESS read-only
	STATUS current
	DESCRIPTION "RX packets"

	::={l2tpPackets 1}

l2tpPacketsMom	OBJECT-TYPE
	SYNTAX	 CounterBasedGauge64
	MAX-ACCESS read-only
	STATUS current
	DESCRIPTION "RX packets"

	::={l2tpPackets 2}

l2tpPacketsMax	OBJECT-TYPE
	SYNTAX	 CounterBasedGauge64
	MAX-ACCESS read-only
	STATUS current
	DESCRIPTION "RX packets"

	::={l2tpPackets 3}

l2tpBytes	OBJECT IDENTIFIER ::={l2tp 3}

l2tpBytesVal	OBJECT-TYPE
	SYNTAX	 Counter64
	MAX-ACCESS read-only
	STATUS current
	DESCRIPTION "RX data"

	::={l2tpBytes 1}

l2tpBytesMom	OBJECT-TYPE
	SYNTAX	 CounterBasedGauge64
	MAX-ACCESS read-only
	STATUS current
	DESCRIPTION "RX data"

	::={l2tpBytes 2}

l2tpBytesMax	OBJECT-TYPE
	SYNTAX	 CounterBasedGauge64
	MAX-ACCESS read-only
	STATUS current
	DESCRIPTION "RX data"

	::={l2tpBytes 3}

l2tpIpv4Packets	OBJECT IDENTIFIER ::={l2tp 4}

l2tpIpv4PacketsVal	OBJECT-TYPE
	SYNTAX	 Counter64
	MAX-ACCESS read-only
	STATUS current
	DESCRIPTION "PPP IPv4 RX packets"

	::={l2tpIpv4Packets 1}

l2tpIpv4PacketsMom	OBJECT-TYPE
	SYNTAX	 CounterBasedGauge64
	MAX-ACCESS read-only
	STATUS current
	DESCRIPTION "PPP IPv4 RX packets"

	::={l2tpIpv4Packets 2}

l2tpIpv4PacketsMax	OBJECT-TYPE
	SYNTAX	 CounterBasedGauge64
	MAX-ACCESS read-only
	STATUS current
	DESCRIPTION "PPP IPv4 RX packets"

	::={l2tpIpv4Packets 3}

l2tpIpv6Packets	OBJECT IDENTIFIER ::={l2tp 5}

l2tpIpv6PacketsVal	OBJECT-TYPE
	SYNTAX	 Counter64
	MAX-ACCESS read-only
	STATUS current
	DESCRIPTION "PPP IPv6 RX packets"

	::={l2tpIpv6Packets 1}

l2tpIpv6PacketsMom	OBJECT-TYPE
	SYNTAX	 CounterBasedGauge64
	MAX-ACCESS read-only
	STATUS current
	DESCRIPTION "PPP IPv6 RX packets"

	::={l2tpIpv6Packets 2}

l2tpIpv6PacketsMax	OBJECT-TYPE
	SYNTAX	 CounterBasedGauge64
	MAX-ACCESS read-only
	STATUS current
	DESCRIPTION "PPP IPv6 RX packets"

	::={l2tpIpv6Packets 3}

l2tplcpPackets	OBJECT IDENTIFIER ::={l2tp 6}

l2tplcpPacketsVal	OBJECT-TYPE
	SYNTAX	 Counter64
	MAX-ACCESS read-only
	STATUS current
	DESCRIPTION "PPP LCP RX packets"

	::={l2tplcpPackets 1}

l2tplcpPacketsMom	OBJECT-TYPE
	SYNTAX	 CounterBasedGauge64
	MAX-ACCESS read-only
	STATUS current
	DESCRIPTION "PPP LCP RX packets"

	::={l2tplcpPackets 2}

l2tplcpPacketsMax	OBJECT-TYPE
	SYNTAX	 CounterBasedGauge64
	MAX-ACCESS read-only
	STATUS current
	DESCRIPTION "PPP LCP RX packets"

	::={l2tplcpPackets 3}

l2tpcipv4Packets	OBJECT IDENTIFIER ::={l2tp 7}

l2tpcipv4PacketsVal	OBJECT-TYPE
	SYNTAX	 Counter64
	MAX-ACCESS read-only
	STATUS current
	DESCRIPTION "PPP CIPv4 RX packets"

	::={l2tpcipv4Packets 1}

l2tpcipv4PacketsMom	OBJECT-TYPE
	SYNTAX	 CounterBasedGauge64
	MAX-ACCESS read-only
	STATUS current
	DESCRIPTION "PPP CIPv4 RX packets"

	::={l2tpcipv4Packets 2}

l2tpcipv4PacketsMax	OBJECT-TYPE
	SYNTAX	 CounterBasedGauge64
	MAX-ACCESS read-only
	STATUS current
	DESCRIPTION "PPP CIPv4 RX packets"

	::={l2tpcipv4Packets 3}

l2tpcipv6Packets	OBJECT IDENTIFIER ::={l2tp 8}

l2tpcipv6PacketsVal	OBJECT-TYPE
	SYNTAX	 Counter64
	MAX-ACCESS read-only
	STATUS current
	DESCRIPTION "PPP CIPv6 RX packets"

	::={l2tpcipv6Packets 1}

l2tpcipv6PacketsMom	OBJECT-TYPE
	SYNTAX	 CounterBasedGauge64
	MAX-ACCESS read-only
	STATUS current
	DESCRIPTION "PPP CIPv6 RX packets"

	::={l2tpcipv6Packets 2}

l2tpcipv6PacketsMax	OBJECT-TYPE
	SYNTAX	 CounterBasedGauge64
	MAX-ACCESS read-only
	STATUS current
	DESCRIPTION "PPP CIPv6 RX packets"

	::={l2tpcipv6Packets 3}

l2tpchap6Packets	OBJECT IDENTIFIER ::={l2tp 9}

l2tpchap6PacketsVal	OBJECT-TYPE
	SYNTAX	 Counter64
	MAX-ACCESS read-only
	STATUS current
	DESCRIPTION "PPP CHAP RX packets"

	::={l2tpchap6Packets 1}

l2tpchap6PacketsMom	OBJECT-TYPE
	SYNTAX	 CounterBasedGauge64
	MAX-ACCESS read-only
	STATUS current
	DESCRIPTION "PPP CHAP RX packets"

	::={l2tpchap6Packets 2}

l2tpchap6PacketsMax	OBJECT-TYPE
	SYNTAX	 CounterBasedGauge64
	MAX-ACCESS read-only
	STATUS current
	DESCRIPTION "PPP CHAP RX packets"

	::={l2tpchap6Packets 3}

system	OBJECT IDENTIFIER ::={sysdiag 133}

systemCPULoad	OBJECT IDENTIFIER ::={system 1}

systemCPULoadVal	OBJECT-TYPE
	SYNTAX	 Unsigned32
	MAX-ACCESS read-only
	STATUS current
	DESCRIPTION "CPU load"

	::={systemCPULoad 1}

systemCPULoadMax	OBJECT-TYPE
	SYNTAX	 Unsigned32
	MAX-ACCESS read-only
	STATUS current
	DESCRIPTION "CPU load"

	::={systemCPULoad 3}

systemMemTotal	OBJECT IDENTIFIER ::={system 2}

systemMemTotalVal	OBJECT-TYPE
	SYNTAX	 CounterBasedGauge64
	MAX-ACCESS read-only
	STATUS current
	DESCRIPTION "Total RAM"

	::={systemMemTotal 1}

systemMemTotalMax	OBJECT-TYPE
	SYNTAX	 CounterBasedGauge64
	MAX-ACCESS read-only
	STATUS current
	DESCRIPTION "Total RAM"

	::={systemMemTotal 3}

systemMemFree	OBJECT IDENTIFIER ::={system 3}

systemMemFreeVal	OBJECT-TYPE
	SYNTAX	 CounterBasedGauge64
	MAX-ACCESS read-only
	STATUS current
	DESCRIPTION "Free RAM"

	::={systemMemFree 1}

systemMemFreeMax	OBJECT-TYPE
	SYNTAX	 CounterBasedGauge64
	MAX-ACCESS read-only
	STATUS current
	DESCRIPTION "Free RAM"

	::={systemMemFree 3}

systemSwapTotal	OBJECT IDENTIFIER ::={system 4}

systemSwapTotalVal	OBJECT-TYPE
	SYNTAX	 CounterBasedGauge64
	MAX-ACCESS read-only
	STATUS current
	DESCRIPTION "Total swap"

	::={systemSwapTotal 1}

systemSwapTotalMax	OBJECT-TYPE
	SYNTAX	 CounterBasedGauge64
	MAX-ACCESS read-only
	STATUS current
	DESCRIPTION "Total swap"

	::={systemSwapTotal 3}

systemSwapFree	OBJECT IDENTIFIER ::={system 5}

systemSwapFreeVal	OBJECT-TYPE
	SYNTAX	 CounterBasedGauge64
	MAX-ACCESS read-only
	STATUS current
	DESCRIPTION "Free swap"

	::={systemSwapFree 1}

systemSwapFreeMax	OBJECT-TYPE
	SYNTAX	 CounterBasedGauge64
	MAX-ACCESS read-only
	STATUS current
	DESCRIPTION "Free swap"

	::={systemSwapFree 3}

systemUptime	OBJECT IDENTIFIER ::={system 6}

systemUptimeVal	OBJECT-TYPE
	SYNTAX	 TimeTicks
	MAX-ACCESS read-only
	STATUS current
	DESCRIPTION "Uptime"

	::={systemUptime 1}

systemHdUsage	OBJECT IDENTIFIER ::={system 7}

systemHdUsageVal	OBJECT-TYPE
	SYNTAX	 Unsigned32
	MAX-ACCESS read-only
	STATUS current
	DESCRIPTION "System disk usage"

	::={systemHdUsage 1}

systemHdUsageMax	OBJECT-TYPE
	SYNTAX	 Unsigned32
	MAX-ACCESS read-only
	STATUS current
	DESCRIPTION "System disk usage"

	::={systemHdUsage 3}

systemHdSize	OBJECT IDENTIFIER ::={system 8}

systemHdSizeVal	OBJECT-TYPE
	SYNTAX	 CounterBasedGauge64
	MAX-ACCESS read-only
	STATUS current
	DESCRIPTION "System disk size"

	::={systemHdSize 1}

systemHdSizeMax	OBJECT-TYPE
	SYNTAX	 CounterBasedGauge64
	MAX-ACCESS read-only
	STATUS current
	DESCRIPTION "System disk size"

	::={systemHdSize 3}

liveview	OBJECT IDENTIFIER ::={sysdiag 134}

liveviewUptime	OBJECT IDENTIFIER ::={liveview 1}

liveviewUptimeVal	OBJECT-TYPE
	SYNTAX	 TimeTicks
	MAX-ACCESS read-only
	STATUS current
	DESCRIPTION "Uptime"

	::={liveviewUptime 1}

liveviewClients	OBJECT IDENTIFIER ::={liveview 2}

liveviewClientsVal	OBJECT-TYPE
	SYNTAX	 CounterBasedGauge64
	MAX-ACCESS read-only
	STATUS current
	DESCRIPTION "Connected clients"

	::={liveviewClients 1}

liveviewClientsMax	OBJECT-TYPE
	SYNTAX	 CounterBasedGauge64
	MAX-ACCESS read-only
	STATUS current
	DESCRIPTION "Connected clients"

	::={liveviewClients 3}

liveviewPLSDClients	OBJECT IDENTIFIER ::={liveview 3}

liveviewPLSDClientsVal	OBJECT-TYPE
	SYNTAX	 CounterBasedGauge64
	MAX-ACCESS read-only
	STATUS current
	DESCRIPTION "Connected PLSD clients"

	::={liveviewPLSDClients 1}

liveviewPLSDClientsMax	OBJECT-TYPE
	SYNTAX	 CounterBasedGauge64
	MAX-ACCESS read-only
	STATUS current
	DESCRIPTION "Connected PLSD clients"

	::={liveviewPLSDClients 3}

liveviewHosts	OBJECT IDENTIFIER ::={liveview 4}

liveviewHostsVal	OBJECT-TYPE
	SYNTAX	 CounterBasedGauge64
	MAX-ACCESS read-only
	STATUS current
	DESCRIPTION "Hosts"

	::={liveviewHosts 1}

liveviewHostsMax	OBJECT-TYPE
	SYNTAX	 CounterBasedGauge64
	MAX-ACCESS read-only
	STATUS current
	DESCRIPTION "Hosts"

	::={liveviewHosts 3}

liveviewVNOs	OBJECT IDENTIFIER ::={liveview 5}

liveviewVNOsVal	OBJECT-TYPE
	SYNTAX	 CounterBasedGauge64
	MAX-ACCESS read-only
	STATUS current
	DESCRIPTION "Visible NetObjects"

	::={liveviewVNOs 1}

liveviewVNOsMax	OBJECT-TYPE
	SYNTAX	 CounterBasedGauge64
	MAX-ACCESS read-only
	STATUS current
	DESCRIPTION "Visible NetObjects"

	::={liveviewVNOs 3}

liveviewActiveVNOs	OBJECT IDENTIFIER ::={liveview 6}

liveviewActiveVNOsVal	OBJECT-TYPE
	SYNTAX	 CounterBasedGauge64
	MAX-ACCESS read-only
	STATUS current
	DESCRIPTION "Active visible NetObjects"

	::={liveviewActiveVNOs 1}

liveviewActiveVNOsMax	OBJECT-TYPE
	SYNTAX	 CounterBasedGauge64
	MAX-ACCESS read-only
	STATUS current
	DESCRIPTION "Active visible NetObjects"

	::={liveviewActiveVNOs 3}

liveviewDrdlRevision	OBJECT IDENTIFIER ::={liveview 7}

liveviewDrdlRevisionVal	OBJECT-TYPE
	SYNTAX	 CounterBasedGauge64
	MAX-ACCESS read-only
	STATUS current
	DESCRIPTION "DRDL revision"

	::={liveviewDrdlRevision 1}

liveviewDrdlRevisionMax	OBJECT-TYPE
	SYNTAX	 CounterBasedGauge64
	MAX-ACCESS read-only
	STATUS current
	DESCRIPTION "DRDL revision"

	::={liveviewDrdlRevision 3}

liveviewFailedNetobjects	OBJECT IDENTIFIER ::={liveview 8}

liveviewFailedNetobjectsVal	OBJECT-TYPE
	SYNTAX	 Counter64
	MAX-ACCESS read-only
	STATUS current
	DESCRIPTION "Visible netobject pool exhausted"

	::={liveviewFailedNetobjects 1}

liveviewFailedNetobjectsMom	OBJECT-TYPE
	SYNTAX	 CounterBasedGauge64
	MAX-ACCESS read-only
	STATUS current
	DESCRIPTION "Visible netobject pool exhausted"

	::={liveviewFailedNetobjects 2}

liveviewFailedNetobjectsMax	OBJECT-TYPE
	SYNTAX	 CounterBasedGauge64
	MAX-ACCESS read-only
	STATUS current
	DESCRIPTION "Visible netobject pool exhausted"

	::={liveviewFailedNetobjects 3}

liveviewFailedFullNetobjects	OBJECT IDENTIFIER ::={liveview 9}

liveviewFailedFullNetobjectsVal	OBJECT-TYPE
	SYNTAX	 Counter64
	MAX-ACCESS read-only
	STATUS current
	DESCRIPTION "Active visible netobject pool exhausted"

	::={liveviewFailedFullNetobjects 1}

liveviewFailedFullNetobjectsMom	OBJECT-TYPE
	SYNTAX	 CounterBasedGauge64
	MAX-ACCESS read-only
	STATUS current
	DESCRIPTION "Active visible netobject pool exhausted"

	::={liveviewFailedFullNetobjects 2}

liveviewFailedFullNetobjectsMax	OBJECT-TYPE
	SYNTAX	 CounterBasedGauge64
	MAX-ACCESS read-only
	STATUS current
	DESCRIPTION "Active visible netobject pool exhausted"

	::={liveviewFailedFullNetobjects 3}

liveviewStringCacheUsage	OBJECT IDENTIFIER ::={liveview 10}

liveviewStringCacheUsageVal	OBJECT-TYPE
	SYNTAX	 CounterBasedGauge64
	MAX-ACCESS read-only
	STATUS current
	DESCRIPTION "String cache usage"

	::={liveviewStringCacheUsage 1}

liveviewStringCacheUsageMax	OBJECT-TYPE
	SYNTAX	 CounterBasedGauge64
	MAX-ACCESS read-only
	STATUS current
	DESCRIPTION "String cache usage"

	::={liveviewStringCacheUsage 3}

liveviewUnaccountedPlsdIn	OBJECT IDENTIFIER ::={liveview 11}

liveviewUnaccountedPlsdInVal	OBJECT-TYPE
	SYNTAX	 Counter64
	MAX-ACCESS read-only
	STATUS current
	DESCRIPTION "Bytes in not accounted in plsd"

	::={liveviewUnaccountedPlsdIn 1}

liveviewUnaccountedPlsdInMom	OBJECT-TYPE
	SYNTAX	 CounterBasedGauge64
	MAX-ACCESS read-only
	STATUS current
	DESCRIPTION "Bytes in not accounted in plsd"

	::={liveviewUnaccountedPlsdIn 2}

liveviewUnaccountedPlsdInMax	OBJECT-TYPE
	SYNTAX	 CounterBasedGauge64
	MAX-ACCESS read-only
	STATUS current
	DESCRIPTION "Bytes in not accounted in plsd"

	::={liveviewUnaccountedPlsdIn 3}

liveviewUnaccountedPlsdOut	OBJECT IDENTIFIER ::={liveview 12}

liveviewUnaccountedPlsdOutVal	OBJECT-TYPE
	SYNTAX	 Counter64
	MAX-ACCESS read-only
	STATUS current
	DESCRIPTION "Bytes out not accounted in plsd"

	::={liveviewUnaccountedPlsdOut 1}

liveviewUnaccountedPlsdOutMom	OBJECT-TYPE
	SYNTAX	 CounterBasedGauge64
	MAX-ACCESS read-only
	STATUS current
	DESCRIPTION "Bytes out not accounted in plsd"

	::={liveviewUnaccountedPlsdOut 2}

liveviewUnaccountedPlsdOutMax	OBJECT-TYPE
	SYNTAX	 CounterBasedGauge64
	MAX-ACCESS read-only
	STATUS current
	DESCRIPTION "Bytes out not accounted in plsd"

	::={liveviewUnaccountedPlsdOut 3}

liveviewUnaccountedPlsdFlows	OBJECT IDENTIFIER ::={liveview 13}

liveviewUnaccountedPlsdFlowsVal	OBJECT-TYPE
	SYNTAX	 Counter64
	MAX-ACCESS read-only
	STATUS current
	DESCRIPTION "Flow updates not sent to plsd"

	::={liveviewUnaccountedPlsdFlows 1}

liveviewUnaccountedPlsdFlowsMom	OBJECT-TYPE
	SYNTAX	 CounterBasedGauge64
	MAX-ACCESS read-only
	STATUS current
	DESCRIPTION "Flow updates not sent to plsd"

	::={liveviewUnaccountedPlsdFlows 2}

liveviewUnaccountedPlsdFlowsMax	OBJECT-TYPE
	SYNTAX	 CounterBasedGauge64
	MAX-ACCESS read-only
	STATUS current
	DESCRIPTION "Flow updates not sent to plsd"

	::={liveviewUnaccountedPlsdFlows 3}

liveviewHostCacheExhausted	OBJECT IDENTIFIER ::={liveview 14}

liveviewHostCacheExhaustedVal	OBJECT-TYPE
	SYNTAX	 Counter64
	MAX-ACCESS read-only
	STATUS current
	DESCRIPTION "Hosts not created due to exhausted cache"

	::={liveviewHostCacheExhausted 1}

liveviewHostCacheExhaustedMom	OBJECT-TYPE
	SYNTAX	 CounterBasedGauge64
	MAX-ACCESS read-only
	STATUS current
	DESCRIPTION "Hosts not created due to exhausted cache"

	::={liveviewHostCacheExhausted 2}

liveviewHostCacheExhaustedMax	OBJECT-TYPE
	SYNTAX	 CounterBasedGauge64
	MAX-ACCESS read-only
	STATUS current
	DESCRIPTION "Hosts not created due to exhausted cache"

	::={liveviewHostCacheExhausted 3}

liveviewPropEntryUsage	OBJECT IDENTIFIER ::={liveview 15}

liveviewPropEntryUsageVal	OBJECT-TYPE
	SYNTAX	 CounterBasedGauge64
	MAX-ACCESS read-only
	STATUS current
	DESCRIPTION "Property entries used"

	::={liveviewPropEntryUsage 1}

liveviewPropEntryUsageMax	OBJECT-TYPE
	SYNTAX	 CounterBasedGauge64
	MAX-ACCESS read-only
	STATUS current
	DESCRIPTION "Property entries used"

	::={liveviewPropEntryUsage 3}

liveviewPropArrayUsage	OBJECT IDENTIFIER ::={liveview 16}

liveviewPropArrayUsageVal	OBJECT-TYPE
	SYNTAX	 CounterBasedGauge64
	MAX-ACCESS read-only
	STATUS current
	DESCRIPTION "Property arrays used"

	::={liveviewPropArrayUsage 1}

liveviewPropArrayUsageMax	OBJECT-TYPE
	SYNTAX	 CounterBasedGauge64
	MAX-ACCESS read-only
	STATUS current
	DESCRIPTION "Property arrays used"

	::={liveviewPropArrayUsage 3}

liveviewPropUsage	OBJECT IDENTIFIER ::={liveview 17}

liveviewPropUsageVal	OBJECT-TYPE
	SYNTAX	 CounterBasedGauge64
	MAX-ACCESS read-only
	STATUS current
	DESCRIPTION "Properties stored"

	::={liveviewPropUsage 1}

liveviewPropUsageMax	OBJECT-TYPE
	SYNTAX	 CounterBasedGauge64
	MAX-ACCESS read-only
	STATUS current
	DESCRIPTION "Properties stored"

	::={liveviewPropUsage 3}

liveviewTooManyNetobjectsOnHost	OBJECT IDENTIFIER ::={liveview 18}

liveviewTooManyNetobjectsOnHostVal	OBJECT-TYPE
	SYNTAX	 CounterBasedGauge64
	MAX-ACCESS read-only
	STATUS current
	DESCRIPTION "Too many netobjects on a single host"

	::={liveviewTooManyNetobjectsOnHost 1}

liveviewTooManyNetobjectsOnHostMax	OBJECT-TYPE
	SYNTAX	 CounterBasedGauge64
	MAX-ACCESS read-only
	STATUS current
	DESCRIPTION "Too many netobjects on a single host"

	::={liveviewTooManyNetobjectsOnHost 3}

liveviewHostnameAllocs	OBJECT IDENTIFIER ::={liveview 19}

liveviewHostnameAllocsVal	OBJECT-TYPE
	SYNTAX	 CounterBasedGauge64
	MAX-ACCESS read-only
	STATUS current
	DESCRIPTION "Hostname allocations"

	::={liveviewHostnameAllocs 1}

liveviewHostnameAllocsMax	OBJECT-TYPE
	SYNTAX	 CounterBasedGauge64
	MAX-ACCESS read-only
	STATUS current
	DESCRIPTION "Hostname allocations"

	::={liveviewHostnameAllocs 3}

liveviewHostnameAllocFail	OBJECT IDENTIFIER ::={liveview 20}

liveviewHostnameAllocFailVal	OBJECT-TYPE
	SYNTAX	 CounterBasedGauge64
	MAX-ACCESS read-only
	STATUS current
	DESCRIPTION "Hostname allocation failures"

	::={liveviewHostnameAllocFail 1}

liveviewHostnameAllocFailMax	OBJECT-TYPE
	SYNTAX	 CounterBasedGauge64
	MAX-ACCESS read-only
	STATUS current
	DESCRIPTION "Hostname allocation failures"

	::={liveviewHostnameAllocFail 3}

liveviewReaperRecvBuf	OBJECT IDENTIFIER ::={liveview 21}

liveviewReaperRecvBufVal	OBJECT-TYPE
	SYNTAX	 CounterBasedGauge64
	MAX-ACCESS read-only
	STATUS current
	DESCRIPTION "Reaper receive buffer usage"

	::={liveviewReaperRecvBuf 1}

liveviewReaperRecvBufMax	OBJECT-TYPE
	SYNTAX	 CounterBasedGauge64
	MAX-ACCESS read-only
	STATUS current
	DESCRIPTION "Reaper receive buffer usage"

	::={liveviewReaperRecvBuf 3}

liveviewReaperSendBuf	OBJECT IDENTIFIER ::={liveview 22}

liveviewReaperSendBufVal	OBJECT-TYPE
	SYNTAX	 CounterBasedGauge64
	MAX-ACCESS read-only
	STATUS current
	DESCRIPTION "Reaper send buffer usage"

	::={liveviewReaperSendBuf 1}

liveviewReaperSendBufMax	OBJECT-TYPE
	SYNTAX	 CounterBasedGauge64
	MAX-ACCESS read-only
	STATUS current
	DESCRIPTION "Reaper send buffer usage"

	::={liveviewReaperSendBuf 3}

liveviewPLSDBuf	OBJECT IDENTIFIER ::={liveview 23}

liveviewPLSDBufVal	OBJECT-TYPE
	SYNTAX	 CounterBasedGauge64
	MAX-ACCESS read-only
	STATUS current
	DESCRIPTION "PLSD buffer usage"

	::={liveviewPLSDBuf 1}

liveviewPLSDBufMax	OBJECT-TYPE
	SYNTAX	 CounterBasedGauge64
	MAX-ACCESS read-only
	STATUS current
	DESCRIPTION "PLSD buffer usage"

	::={liveviewPLSDBuf 3}

lb	OBJECT IDENTIFIER ::={sysdiag 135}

lbNumFp	OBJECT IDENTIFIER ::={lb 1}

lbNumFpVal	OBJECT-TYPE
	SYNTAX	 CounterBasedGauge64
	MAX-ACCESS read-only
	STATUS current
	DESCRIPTION "Number of flow processors"

	::={lbNumFp 1}

lbNumFpMax	OBJECT-TYPE
	SYNTAX	 CounterBasedGauge64
	MAX-ACCESS read-only
	STATUS current
	DESCRIPTION "Number of flow processors"

	::={lbNumFp 3}

lbActiveFp	OBJECT IDENTIFIER ::={lb 2}

lbActiveFpVal	OBJECT-TYPE
	SYNTAX	 CounterBasedGauge64
	MAX-ACCESS read-only
	STATUS current
	DESCRIPTION "Logical flow processors"

	::={lbActiveFp 1}

lbActiveFpMax	OBJECT-TYPE
	SYNTAX	 CounterBasedGauge64
	MAX-ACCESS read-only
	STATUS current
	DESCRIPTION "Logical flow processors"

	::={lbActiveFp 3}

lbRunningFp	OBJECT IDENTIFIER ::={lb 3}

lbRunningFpVal	OBJECT-TYPE
	SYNTAX	 Unsigned32
	MAX-ACCESS read-only
	STATUS current
	DESCRIPTION "Online flow processors"

	::={lbRunningFp 1}

lbRunningFpMax	OBJECT-TYPE
	SYNTAX	 Unsigned32
	MAX-ACCESS read-only
	STATUS current
	DESCRIPTION "Online flow processors"

	::={lbRunningFp 3}

lbRxPktsInt	OBJECT IDENTIFIER ::={lb 4}

lbRxPktsIntVal	OBJECT-TYPE
	SYNTAX	 Counter64
	MAX-ACCESS read-only
	STATUS current
	DESCRIPTION "RX packets internal"

	::={lbRxPktsInt 1}

lbRxPktsIntMom	OBJECT-TYPE
	SYNTAX	 CounterBasedGauge64
	MAX-ACCESS read-only
	STATUS current
	DESCRIPTION "RX packets internal"

	::={lbRxPktsInt 2}

lbRxPktsIntMax	OBJECT-TYPE
	SYNTAX	 CounterBasedGauge64
	MAX-ACCESS read-only
	STATUS current
	DESCRIPTION "RX packets internal"

	::={lbRxPktsInt 3}

lbRxPktsExt	OBJECT IDENTIFIER ::={lb 5}

lbRxPktsExtVal	OBJECT-TYPE
	SYNTAX	 Counter64
	MAX-ACCESS read-only
	STATUS current
	DESCRIPTION "RX packets external"

	::={lbRxPktsExt 1}

lbRxPktsExtMom	OBJECT-TYPE
	SYNTAX	 CounterBasedGauge64
	MAX-ACCESS read-only
	STATUS current
	DESCRIPTION "RX packets external"

	::={lbRxPktsExt 2}

lbRxPktsExtMax	OBJECT-TYPE
	SYNTAX	 CounterBasedGauge64
	MAX-ACCESS read-only
	STATUS current
	DESCRIPTION "RX packets external"

	::={lbRxPktsExt 3}

lbRxBytesInt	OBJECT IDENTIFIER ::={lb 6}

lbRxBytesIntVal	OBJECT-TYPE
	SYNTAX	 Counter64
	MAX-ACCESS read-only
	STATUS current
	DESCRIPTION "RX bytes internal"

	::={lbRxBytesInt 1}

lbRxBytesIntMom	OBJECT-TYPE
	SYNTAX	 CounterBasedGauge64
	MAX-ACCESS read-only
	STATUS current
	DESCRIPTION "RX bytes internal"

	::={lbRxBytesInt 2}

lbRxBytesIntMax	OBJECT-TYPE
	SYNTAX	 CounterBasedGauge64
	MAX-ACCESS read-only
	STATUS current
	DESCRIPTION "RX bytes internal"

	::={lbRxBytesInt 3}

lbRxBytesExt	OBJECT IDENTIFIER ::={lb 7}

lbRxBytesExtVal	OBJECT-TYPE
	SYNTAX	 Counter64
	MAX-ACCESS read-only
	STATUS current
	DESCRIPTION "RX bytes external"

	::={lbRxBytesExt 1}

lbRxBytesExtMom	OBJECT-TYPE
	SYNTAX	 CounterBasedGauge64
	MAX-ACCESS read-only
	STATUS current
	DESCRIPTION "RX bytes external"

	::={lbRxBytesExt 2}

lbRxBytesExtMax	OBJECT-TYPE
	SYNTAX	 CounterBasedGauge64
	MAX-ACCESS read-only
	STATUS current
	DESCRIPTION "RX bytes external"

	::={lbRxBytesExt 3}

lbRxErrorsInt	OBJECT IDENTIFIER ::={lb 8}

lbRxErrorsIntVal	OBJECT-TYPE
	SYNTAX	 Counter64
	MAX-ACCESS read-only
	STATUS current
	DESCRIPTION "RX errors internal"

	::={lbRxErrorsInt 1}

lbRxErrorsIntMom	OBJECT-TYPE
	SYNTAX	 CounterBasedGauge64
	MAX-ACCESS read-only
	STATUS current
	DESCRIPTION "RX errors internal"

	::={lbRxErrorsInt 2}

lbRxErrorsIntMax	OBJECT-TYPE
	SYNTAX	 CounterBasedGauge64
	MAX-ACCESS read-only
	STATUS current
	DESCRIPTION "RX errors internal"

	::={lbRxErrorsInt 3}

lbRxErrorsExt	OBJECT IDENTIFIER ::={lb 9}

lbRxErrorsExtVal	OBJECT-TYPE
	SYNTAX	 Counter64
	MAX-ACCESS read-only
	STATUS current
	DESCRIPTION "RX errors external"

	::={lbRxErrorsExt 1}

lbRxErrorsExtMom	OBJECT-TYPE
	SYNTAX	 CounterBasedGauge64
	MAX-ACCESS read-only
	STATUS current
	DESCRIPTION "RX errors external"

	::={lbRxErrorsExt 2}

lbRxErrorsExtMax	OBJECT-TYPE
	SYNTAX	 CounterBasedGauge64
	MAX-ACCESS read-only
	STATUS current
	DESCRIPTION "RX errors external"

	::={lbRxErrorsExt 3}

lbTxDirectInt	OBJECT IDENTIFIER ::={lb 10}

lbTxDirectIntVal	OBJECT-TYPE
	SYNTAX	 Counter64
	MAX-ACCESS read-only
	STATUS current
	DESCRIPTION "TX direct internal"

	::={lbTxDirectInt 1}

lbTxDirectIntMom	OBJECT-TYPE
	SYNTAX	 CounterBasedGauge64
	MAX-ACCESS read-only
	STATUS current
	DESCRIPTION "TX direct internal"

	::={lbTxDirectInt 2}

lbTxDirectIntMax	OBJECT-TYPE
	SYNTAX	 CounterBasedGauge64
	MAX-ACCESS read-only
	STATUS current
	DESCRIPTION "TX direct internal"

	::={lbTxDirectInt 3}

lbTxDirectExt	OBJECT IDENTIFIER ::={lb 11}

lbTxDirectExtVal	OBJECT-TYPE
	SYNTAX	 Counter64
	MAX-ACCESS read-only
	STATUS current
	DESCRIPTION "TX direct external"

	::={lbTxDirectExt 1}

lbTxDirectExtMom	OBJECT-TYPE
	SYNTAX	 CounterBasedGauge64
	MAX-ACCESS read-only
	STATUS current
	DESCRIPTION "TX direct external"

	::={lbTxDirectExt 2}

lbTxDirectExtMax	OBJECT-TYPE
	SYNTAX	 CounterBasedGauge64
	MAX-ACCESS read-only
	STATUS current
	DESCRIPTION "TX direct external"

	::={lbTxDirectExt 3}

lbTxDropsInt	OBJECT IDENTIFIER ::={lb 12}

lbTxDropsIntVal	OBJECT-TYPE
	SYNTAX	 Counter64
	MAX-ACCESS read-only
	STATUS current
	DESCRIPTION "TX drops internal"

	::={lbTxDropsInt 1}

lbTxDropsIntMom	OBJECT-TYPE
	SYNTAX	 CounterBasedGauge64
	MAX-ACCESS read-only
	STATUS current
	DESCRIPTION "TX drops internal"

	::={lbTxDropsInt 2}

lbTxDropsIntMax	OBJECT-TYPE
	SYNTAX	 CounterBasedGauge64
	MAX-ACCESS read-only
	STATUS current
	DESCRIPTION "TX drops internal"

	::={lbTxDropsInt 3}

lbTxDropsExt	OBJECT IDENTIFIER ::={lb 13}

lbTxDropsExtVal	OBJECT-TYPE
	SYNTAX	 Counter64
	MAX-ACCESS read-only
	STATUS current
	DESCRIPTION "TX drops external"

	::={lbTxDropsExt 1}

lbTxDropsExtMom	OBJECT-TYPE
	SYNTAX	 CounterBasedGauge64
	MAX-ACCESS read-only
	STATUS current
	DESCRIPTION "TX drops external"

	::={lbTxDropsExt 2}

lbTxDropsExtMax	OBJECT-TYPE
	SYNTAX	 CounterBasedGauge64
	MAX-ACCESS read-only
	STATUS current
	DESCRIPTION "TX drops external"

	::={lbTxDropsExt 3}

lbRxFsInvalidVer	OBJECT IDENTIFIER ::={lb 14}

lbRxFsInvalidVerVal	OBJECT-TYPE
	SYNTAX	 Counter64
	MAX-ACCESS read-only
	STATUS current
	DESCRIPTION "Incompatible flowsync packets"

	::={lbRxFsInvalidVer 1}

lbRxFsInvalidVerMom	OBJECT-TYPE
	SYNTAX	 CounterBasedGauge64
	MAX-ACCESS read-only
	STATUS current
	DESCRIPTION "Incompatible flowsync packets"

	::={lbRxFsInvalidVer 2}

lbRxFsInvalidVerMax	OBJECT-TYPE
	SYNTAX	 CounterBasedGauge64
	MAX-ACCESS read-only
	STATUS current
	DESCRIPTION "Incompatible flowsync packets"

	::={lbRxFsInvalidVer 3}

lbShuntPktIpv4AddrInt	OBJECT IDENTIFIER ::={lb 15}

lbShuntPktIpv4AddrIntVal	OBJECT-TYPE
	SYNTAX	 Counter64
	MAX-ACCESS read-only
	STATUS current
	DESCRIPTION "Shunt packets internal (IPv4 address)"

	::={lbShuntPktIpv4AddrInt 1}

lbShuntPktIpv4AddrIntMom	OBJECT-TYPE
	SYNTAX	 CounterBasedGauge64
	MAX-ACCESS read-only
	STATUS current
	DESCRIPTION "Shunt packets internal (IPv4 address)"

	::={lbShuntPktIpv4AddrInt 2}

lbShuntPktIpv4AddrIntMax	OBJECT-TYPE
	SYNTAX	 CounterBasedGauge64
	MAX-ACCESS read-only
	STATUS current
	DESCRIPTION "Shunt packets internal (IPv4 address)"

	::={lbShuntPktIpv4AddrInt 3}

lbShuntPktIpv4AddrExt	OBJECT IDENTIFIER ::={lb 16}

lbShuntPktIpv4AddrExtVal	OBJECT-TYPE
	SYNTAX	 Counter64
	MAX-ACCESS read-only
	STATUS current
	DESCRIPTION "Shunt packets external (IPv4 address)"

	::={lbShuntPktIpv4AddrExt 1}

lbShuntPktIpv4AddrExtMom	OBJECT-TYPE
	SYNTAX	 CounterBasedGauge64
	MAX-ACCESS read-only
	STATUS current
	DESCRIPTION "Shunt packets external (IPv4 address)"

	::={lbShuntPktIpv4AddrExt 2}

lbShuntPktIpv4AddrExtMax	OBJECT-TYPE
	SYNTAX	 CounterBasedGauge64
	MAX-ACCESS read-only
	STATUS current
	DESCRIPTION "Shunt packets external (IPv4 address)"

	::={lbShuntPktIpv4AddrExt 3}

lbShuntByteIpv4AddrInt	OBJECT IDENTIFIER ::={lb 17}

lbShuntByteIpv4AddrIntVal	OBJECT-TYPE
	SYNTAX	 Counter64
	MAX-ACCESS read-only
	STATUS current
	DESCRIPTION "Shunt bytes internal (IPv4 address)"

	::={lbShuntByteIpv4AddrInt 1}

lbShuntByteIpv4AddrIntMom	OBJECT-TYPE
	SYNTAX	 CounterBasedGauge64
	MAX-ACCESS read-only
	STATUS current
	DESCRIPTION "Shunt bytes internal (IPv4 address)"

	::={lbShuntByteIpv4AddrInt 2}

lbShuntByteIpv4AddrIntMax	OBJECT-TYPE
	SYNTAX	 CounterBasedGauge64
	MAX-ACCESS read-only
	STATUS current
	DESCRIPTION "Shunt bytes internal (IPv4 address)"

	::={lbShuntByteIpv4AddrInt 3}

lbShuntByteIpv4AddrExt	OBJECT IDENTIFIER ::={lb 18}

lbShuntByteIpv4AddrExtVal	OBJECT-TYPE
	SYNTAX	 Counter64
	MAX-ACCESS read-only
	STATUS current
	DESCRIPTION "Shunt bytes external (IPv4 address)"

	::={lbShuntByteIpv4AddrExt 1}

lbShuntByteIpv4AddrExtMom	OBJECT-TYPE
	SYNTAX	 CounterBasedGauge64
	MAX-ACCESS read-only
	STATUS current
	DESCRIPTION "Shunt bytes external (IPv4 address)"

	::={lbShuntByteIpv4AddrExt 2}

lbShuntByteIpv4AddrExtMax	OBJECT-TYPE
	SYNTAX	 CounterBasedGauge64
	MAX-ACCESS read-only
	STATUS current
	DESCRIPTION "Shunt bytes external (IPv4 address)"

	::={lbShuntByteIpv4AddrExt 3}

lbShuntPktIpv4ProtoInt	OBJECT IDENTIFIER ::={lb 19}

lbShuntPktIpv4ProtoIntVal	OBJECT-TYPE
	SYNTAX	 Counter64
	MAX-ACCESS read-only
	STATUS current
	DESCRIPTION "Shunt packets internal (IPv4 protocol)"

	::={lbShuntPktIpv4ProtoInt 1}

lbShuntPktIpv4ProtoIntMom	OBJECT-TYPE
	SYNTAX	 CounterBasedGauge64
	MAX-ACCESS read-only
	STATUS current
	DESCRIPTION "Shunt packets internal (IPv4 protocol)"

	::={lbShuntPktIpv4ProtoInt 2}

lbShuntPktIpv4ProtoIntMax	OBJECT-TYPE
	SYNTAX	 CounterBasedGauge64
	MAX-ACCESS read-only
	STATUS current
	DESCRIPTION "Shunt packets internal (IPv4 protocol)"

	::={lbShuntPktIpv4ProtoInt 3}

lbShuntPktIpv4ProtoExt	OBJECT IDENTIFIER ::={lb 20}

lbShuntPktIpv4ProtoExtVal	OBJECT-TYPE
	SYNTAX	 Counter64
	MAX-ACCESS read-only
	STATUS current
	DESCRIPTION "Shunt packets external (IPv4 protocol)"

	::={lbShuntPktIpv4ProtoExt 1}

lbShuntPktIpv4ProtoExtMom	OBJECT-TYPE
	SYNTAX	 CounterBasedGauge64
	MAX-ACCESS read-only
	STATUS current
	DESCRIPTION "Shunt packets external (IPv4 protocol)"

	::={lbShuntPktIpv4ProtoExt 2}

lbShuntPktIpv4ProtoExtMax	OBJECT-TYPE
	SYNTAX	 CounterBasedGauge64
	MAX-ACCESS read-only
	STATUS current
	DESCRIPTION "Shunt packets external (IPv4 protocol)"

	::={lbShuntPktIpv4ProtoExt 3}

lbShuntByteIpv4ProtoInt	OBJECT IDENTIFIER ::={lb 21}

lbShuntByteIpv4ProtoIntVal	OBJECT-TYPE
	SYNTAX	 Counter64
	MAX-ACCESS read-only
	STATUS current
	DESCRIPTION "Shunt bytes internal (IPv4 protocol)"

	::={lbShuntByteIpv4ProtoInt 1}

lbShuntByteIpv4ProtoIntMom	OBJECT-TYPE
	SYNTAX	 CounterBasedGauge64
	MAX-ACCESS read-only
	STATUS current
	DESCRIPTION "Shunt bytes internal (IPv4 protocol)"

	::={lbShuntByteIpv4ProtoInt 2}

lbShuntByteIpv4ProtoIntMax	OBJECT-TYPE
	SYNTAX	 CounterBasedGauge64
	MAX-ACCESS read-only
	STATUS current
	DESCRIPTION "Shunt bytes internal (IPv4 protocol)"

	::={lbShuntByteIpv4ProtoInt 3}

lbShuntByteIpv4ProtoExt	OBJECT IDENTIFIER ::={lb 22}

lbShuntByteIpv4ProtoExtVal	OBJECT-TYPE
	SYNTAX	 Counter64
	MAX-ACCESS read-only
	STATUS current
	DESCRIPTION "Shunt bytes external (IPv4 protocol)"

	::={lbShuntByteIpv4ProtoExt 1}

lbShuntByteIpv4ProtoExtMom	OBJECT-TYPE
	SYNTAX	 CounterBasedGauge64
	MAX-ACCESS read-only
	STATUS current
	DESCRIPTION "Shunt bytes external (IPv4 protocol)"

	::={lbShuntByteIpv4ProtoExt 2}

lbShuntByteIpv4ProtoExtMax	OBJECT-TYPE
	SYNTAX	 CounterBasedGauge64
	MAX-ACCESS read-only
	STATUS current
	DESCRIPTION "Shunt bytes external (IPv4 protocol)"

	::={lbShuntByteIpv4ProtoExt 3}

lbShuntPktEthertypeInt	OBJECT IDENTIFIER ::={lb 23}

lbShuntPktEthertypeIntVal	OBJECT-TYPE
	SYNTAX	 Counter64
	MAX-ACCESS read-only
	STATUS current
	DESCRIPTION "Shunt packets internal (ethertype)"

	::={lbShuntPktEthertypeInt 1}

lbShuntPktEthertypeIntMom	OBJECT-TYPE
	SYNTAX	 CounterBasedGauge64
	MAX-ACCESS read-only
	STATUS current
	DESCRIPTION "Shunt packets internal (ethertype)"

	::={lbShuntPktEthertypeInt 2}

lbShuntPktEthertypeIntMax	OBJECT-TYPE
	SYNTAX	 CounterBasedGauge64
	MAX-ACCESS read-only
	STATUS current
	DESCRIPTION "Shunt packets internal (ethertype)"

	::={lbShuntPktEthertypeInt 3}

lbShuntPktEthertypeExt	OBJECT IDENTIFIER ::={lb 24}

lbShuntPktEthertypeExtVal	OBJECT-TYPE
	SYNTAX	 Counter64
	MAX-ACCESS read-only
	STATUS current
	DESCRIPTION "Shunt packets external (ethertype)"

	::={lbShuntPktEthertypeExt 1}

lbShuntPktEthertypeExtMom	OBJECT-TYPE
	SYNTAX	 CounterBasedGauge64
	MAX-ACCESS read-only
	STATUS current
	DESCRIPTION "Shunt packets external (ethertype)"

	::={lbShuntPktEthertypeExt 2}

lbShuntPktEthertypeExtMax	OBJECT-TYPE
	SYNTAX	 CounterBasedGauge64
	MAX-ACCESS read-only
	STATUS current
	DESCRIPTION "Shunt packets external (ethertype)"

	::={lbShuntPktEthertypeExt 3}

lbShuntByteEthertypeInt	OBJECT IDENTIFIER ::={lb 25}

lbShuntByteEthertypeIntVal	OBJECT-TYPE
	SYNTAX	 Counter64
	MAX-ACCESS read-only
	STATUS current
	DESCRIPTION "Shunt bytes internal (ethertype)"

	::={lbShuntByteEthertypeInt 1}

lbShuntByteEthertypeIntMom	OBJECT-TYPE
	SYNTAX	 CounterBasedGauge64
	MAX-ACCESS read-only
	STATUS current
	DESCRIPTION "Shunt bytes internal (ethertype)"

	::={lbShuntByteEthertypeInt 2}

lbShuntByteEthertypeIntMax	OBJECT-TYPE
	SYNTAX	 CounterBasedGauge64
	MAX-ACCESS read-only
	STATUS current
	DESCRIPTION "Shunt bytes internal (ethertype)"

	::={lbShuntByteEthertypeInt 3}

lbShuntByteEthertypeExt	OBJECT IDENTIFIER ::={lb 26}

lbShuntByteEthertypeExtVal	OBJECT-TYPE
	SYNTAX	 Counter64
	MAX-ACCESS read-only
	STATUS current
	DESCRIPTION "Shunt bytes external (ethertype)"

	::={lbShuntByteEthertypeExt 1}

lbShuntByteEthertypeExtMom	OBJECT-TYPE
	SYNTAX	 CounterBasedGauge64
	MAX-ACCESS read-only
	STATUS current
	DESCRIPTION "Shunt bytes external (ethertype)"

	::={lbShuntByteEthertypeExt 2}

lbShuntByteEthertypeExtMax	OBJECT-TYPE
	SYNTAX	 CounterBasedGauge64
	MAX-ACCESS read-only
	STATUS current
	DESCRIPTION "Shunt bytes external (ethertype)"

	::={lbShuntByteEthertypeExt 3}

lbShuntPktDot1qInt	OBJECT IDENTIFIER ::={lb 27}

lbShuntPktDot1qIntVal	OBJECT-TYPE
	SYNTAX	 Counter64
	MAX-ACCESS read-only
	STATUS current
	DESCRIPTION "Shunt packets internal (dot1q)"

	::={lbShuntPktDot1qInt 1}

lbShuntPktDot1qIntMom	OBJECT-TYPE
	SYNTAX	 CounterBasedGauge64
	MAX-ACCESS read-only
	STATUS current
	DESCRIPTION "Shunt packets internal (dot1q)"

	::={lbShuntPktDot1qInt 2}

lbShuntPktDot1qIntMax	OBJECT-TYPE
	SYNTAX	 CounterBasedGauge64
	MAX-ACCESS read-only
	STATUS current
	DESCRIPTION "Shunt packets internal (dot1q)"

	::={lbShuntPktDot1qInt 3}

lbShuntPktDot1qExt	OBJECT IDENTIFIER ::={lb 28}

lbShuntPktDot1qExtVal	OBJECT-TYPE
	SYNTAX	 Counter64
	MAX-ACCESS read-only
	STATUS current
	DESCRIPTION "Shunt packets external (dot1q)"

	::={lbShuntPktDot1qExt 1}

lbShuntPktDot1qExtMom	OBJECT-TYPE
	SYNTAX	 CounterBasedGauge64
	MAX-ACCESS read-only
	STATUS current
	DESCRIPTION "Shunt packets external (dot1q)"

	::={lbShuntPktDot1qExt 2}

lbShuntPktDot1qExtMax	OBJECT-TYPE
	SYNTAX	 CounterBasedGauge64
	MAX-ACCESS read-only
	STATUS current
	DESCRIPTION "Shunt packets external (dot1q)"

	::={lbShuntPktDot1qExt 3}

lbShuntByteDot1qInt	OBJECT IDENTIFIER ::={lb 29}

lbShuntByteDot1qIntVal	OBJECT-TYPE
	SYNTAX	 Counter64
	MAX-ACCESS read-only
	STATUS current
	DESCRIPTION "Shunt bytes internal (dot1q)"

	::={lbShuntByteDot1qInt 1}

lbShuntByteDot1qIntMom	OBJECT-TYPE
	SYNTAX	 CounterBasedGauge64
	MAX-ACCESS read-only
	STATUS current
	DESCRIPTION "Shunt bytes internal (dot1q)"

	::={lbShuntByteDot1qInt 2}

lbShuntByteDot1qIntMax	OBJECT-TYPE
	SYNTAX	 CounterBasedGauge64
	MAX-ACCESS read-only
	STATUS current
	DESCRIPTION "Shunt bytes internal (dot1q)"

	::={lbShuntByteDot1qInt 3}

lbShuntByteDot1qExt	OBJECT IDENTIFIER ::={lb 30}

lbShuntByteDot1qExtVal	OBJECT-TYPE
	SYNTAX	 Counter64
	MAX-ACCESS read-only
	STATUS current
	DESCRIPTION "Shunt bytes external (dot1q)"

	::={lbShuntByteDot1qExt 1}

lbShuntByteDot1qExtMom	OBJECT-TYPE
	SYNTAX	 CounterBasedGauge64
	MAX-ACCESS read-only
	STATUS current
	DESCRIPTION "Shunt bytes external (dot1q)"

	::={lbShuntByteDot1qExt 2}

lbShuntByteDot1qExtMax	OBJECT-TYPE
	SYNTAX	 CounterBasedGauge64
	MAX-ACCESS read-only
	STATUS current
	DESCRIPTION "Shunt bytes external (dot1q)"

	::={lbShuntByteDot1qExt 3}

lbShuntPktMplsInt	OBJECT IDENTIFIER ::={lb 31}

lbShuntPktMplsIntVal	OBJECT-TYPE
	SYNTAX	 Counter64
	MAX-ACCESS read-only
	STATUS current
	DESCRIPTION "Shunt packets internal (MPLS)"

	::={lbShuntPktMplsInt 1}

lbShuntPktMplsIntMom	OBJECT-TYPE
	SYNTAX	 CounterBasedGauge64
	MAX-ACCESS read-only
	STATUS current
	DESCRIPTION "Shunt packets internal (MPLS)"

	::={lbShuntPktMplsInt 2}

lbShuntPktMplsIntMax	OBJECT-TYPE
	SYNTAX	 CounterBasedGauge64
	MAX-ACCESS read-only
	STATUS current
	DESCRIPTION "Shunt packets internal (MPLS)"

	::={lbShuntPktMplsInt 3}

lbShuntPktMplsExt	OBJECT IDENTIFIER ::={lb 32}

lbShuntPktMplsExtVal	OBJECT-TYPE
	SYNTAX	 Counter64
	MAX-ACCESS read-only
	STATUS current
	DESCRIPTION "Shunt packets external (MPLS)"

	::={lbShuntPktMplsExt 1}

lbShuntPktMplsExtMom	OBJECT-TYPE
	SYNTAX	 CounterBasedGauge64
	MAX-ACCESS read-only
	STATUS current
	DESCRIPTION "Shunt packets external (MPLS)"

	::={lbShuntPktMplsExt 2}

lbShuntPktMplsExtMax	OBJECT-TYPE
	SYNTAX	 CounterBasedGauge64
	MAX-ACCESS read-only
	STATUS current
	DESCRIPTION "Shunt packets external (MPLS)"

	::={lbShuntPktMplsExt 3}

lbShuntByteMplsInt	OBJECT IDENTIFIER ::={lb 33}

lbShuntByteMplsIntVal	OBJECT-TYPE
	SYNTAX	 Counter64
	MAX-ACCESS read-only
	STATUS current
	DESCRIPTION "Shunt bytes internal (MPLS)"

	::={lbShuntByteMplsInt 1}

lbShuntByteMplsIntMom	OBJECT-TYPE
	SYNTAX	 CounterBasedGauge64
	MAX-ACCESS read-only
	STATUS current
	DESCRIPTION "Shunt bytes internal (MPLS)"

	::={lbShuntByteMplsInt 2}

lbShuntByteMplsIntMax	OBJECT-TYPE
	SYNTAX	 CounterBasedGauge64
	MAX-ACCESS read-only
	STATUS current
	DESCRIPTION "Shunt bytes internal (MPLS)"

	::={lbShuntByteMplsInt 3}

lbShuntByteMplsExt	OBJECT IDENTIFIER ::={lb 34}

lbShuntByteMplsExtVal	OBJECT-TYPE
	SYNTAX	 Counter64
	MAX-ACCESS read-only
	STATUS current
	DESCRIPTION "Shunt bytes external (MPLS)"

	::={lbShuntByteMplsExt 1}

lbShuntByteMplsExtMom	OBJECT-TYPE
	SYNTAX	 CounterBasedGauge64
	MAX-ACCESS read-only
	STATUS current
	DESCRIPTION "Shunt bytes external (MPLS)"

	::={lbShuntByteMplsExt 2}

lbShuntByteMplsExtMax	OBJECT-TYPE
	SYNTAX	 CounterBasedGauge64
	MAX-ACCESS read-only
	STATUS current
	DESCRIPTION "Shunt bytes external (MPLS)"

	::={lbShuntByteMplsExt 3}

lbShuntPktEomplsInt	OBJECT IDENTIFIER ::={lb 35}

lbShuntPktEomplsIntVal	OBJECT-TYPE
	SYNTAX	 Counter64
	MAX-ACCESS read-only
	STATUS current
	DESCRIPTION "Shunt packets internal (EoMPLS)"

	::={lbShuntPktEomplsInt 1}

lbShuntPktEomplsIntMom	OBJECT-TYPE
	SYNTAX	 CounterBasedGauge64
	MAX-ACCESS read-only
	STATUS current
	DESCRIPTION "Shunt packets internal (EoMPLS)"

	::={lbShuntPktEomplsInt 2}

lbShuntPktEomplsIntMax	OBJECT-TYPE
	SYNTAX	 CounterBasedGauge64
	MAX-ACCESS read-only
	STATUS current
	DESCRIPTION "Shunt packets internal (EoMPLS)"

	::={lbShuntPktEomplsInt 3}

lbShuntPktEomplsExt	OBJECT IDENTIFIER ::={lb 36}

lbShuntPktEomplsExtVal	OBJECT-TYPE
	SYNTAX	 Counter64
	MAX-ACCESS read-only
	STATUS current
	DESCRIPTION "Shunt packets external (EoMPLS)"

	::={lbShuntPktEomplsExt 1}

lbShuntPktEomplsExtMom	OBJECT-TYPE
	SYNTAX	 CounterBasedGauge64
	MAX-ACCESS read-only
	STATUS current
	DESCRIPTION "Shunt packets external (EoMPLS)"

	::={lbShuntPktEomplsExt 2}

lbShuntPktEomplsExtMax	OBJECT-TYPE
	SYNTAX	 CounterBasedGauge64
	MAX-ACCESS read-only
	STATUS current
	DESCRIPTION "Shunt packets external (EoMPLS)"

	::={lbShuntPktEomplsExt 3}

lbShuntByteEomplsInt	OBJECT IDENTIFIER ::={lb 37}

lbShuntByteEomplsIntVal	OBJECT-TYPE
	SYNTAX	 Counter64
	MAX-ACCESS read-only
	STATUS current
	DESCRIPTION "Shunt bytes internal (EoMPLS)"

	::={lbShuntByteEomplsInt 1}

lbShuntByteEomplsIntMom	OBJECT-TYPE
	SYNTAX	 CounterBasedGauge64
	MAX-ACCESS read-only
	STATUS current
	DESCRIPTION "Shunt bytes internal (EoMPLS)"

	::={lbShuntByteEomplsInt 2}

lbShuntByteEomplsIntMax	OBJECT-TYPE
	SYNTAX	 CounterBasedGauge64
	MAX-ACCESS read-only
	STATUS current
	DESCRIPTION "Shunt bytes internal (EoMPLS)"

	::={lbShuntByteEomplsInt 3}

lbShuntByteEomplsExt	OBJECT IDENTIFIER ::={lb 38}

lbShuntByteEomplsExtVal	OBJECT-TYPE
	SYNTAX	 Counter64
	MAX-ACCESS read-only
	STATUS current
	DESCRIPTION "Shunt bytes external (EoMPLS)"

	::={lbShuntByteEomplsExt 1}

lbShuntByteEomplsExtMom	OBJECT-TYPE
	SYNTAX	 CounterBasedGauge64
	MAX-ACCESS read-only
	STATUS current
	DESCRIPTION "Shunt bytes external (EoMPLS)"

	::={lbShuntByteEomplsExt 2}

lbShuntByteEomplsExtMax	OBJECT-TYPE
	SYNTAX	 CounterBasedGauge64
	MAX-ACCESS read-only
	STATUS current
	DESCRIPTION "Shunt bytes external (EoMPLS)"

	::={lbShuntByteEomplsExt 3}

lbLbUptime	OBJECT IDENTIFIER ::={lb 39}

lbLbUptimeVal	OBJECT-TYPE
	SYNTAX	 TimeTicks
	MAX-ACCESS read-only
	STATUS current
	DESCRIPTION "CPU uptime"

	::={lbLbUptime 1}

lbCpuLoad	OBJECT IDENTIFIER ::={lb 40}

lbCpuLoadVal	OBJECT-TYPE
	SYNTAX	 Unsigned32
	MAX-ACCESS read-only
	STATUS current
	DESCRIPTION "CPU load"

	::={lbCpuLoad 1}

lbCpuLoadMax	OBJECT-TYPE
	SYNTAX	 Unsigned32
	MAX-ACCESS read-only
	STATUS current
	DESCRIPTION "CPU load"

	::={lbCpuLoad 3}

lbShuntPktIpv6AddrInt	OBJECT IDENTIFIER ::={lb 41}

lbShuntPktIpv6AddrIntVal	OBJECT-TYPE
	SYNTAX	 Counter64
	MAX-ACCESS read-only
	STATUS current
	DESCRIPTION "Shunt packets internal (IPv6 address)"

	::={lbShuntPktIpv6AddrInt 1}

lbShuntPktIpv6AddrIntMom	OBJECT-TYPE
	SYNTAX	 CounterBasedGauge64
	MAX-ACCESS read-only
	STATUS current
	DESCRIPTION "Shunt packets internal (IPv6 address)"

	::={lbShuntPktIpv6AddrInt 2}

lbShuntPktIpv6AddrIntMax	OBJECT-TYPE
	SYNTAX	 CounterBasedGauge64
	MAX-ACCESS read-only
	STATUS current
	DESCRIPTION "Shunt packets internal (IPv6 address)"

	::={lbShuntPktIpv6AddrInt 3}

lbShuntPktIpv6AddrExt	OBJECT IDENTIFIER ::={lb 42}

lbShuntPktIpv6AddrExtVal	OBJECT-TYPE
	SYNTAX	 Counter64
	MAX-ACCESS read-only
	STATUS current
	DESCRIPTION "Shunt packets external (IPv6 address)"

	::={lbShuntPktIpv6AddrExt 1}

lbShuntPktIpv6AddrExtMom	OBJECT-TYPE
	SYNTAX	 CounterBasedGauge64
	MAX-ACCESS read-only
	STATUS current
	DESCRIPTION "Shunt packets external (IPv6 address)"

	::={lbShuntPktIpv6AddrExt 2}

lbShuntPktIpv6AddrExtMax	OBJECT-TYPE
	SYNTAX	 CounterBasedGauge64
	MAX-ACCESS read-only
	STATUS current
	DESCRIPTION "Shunt packets external (IPv6 address)"

	::={lbShuntPktIpv6AddrExt 3}

lbShuntByteIpv6AddrInt	OBJECT IDENTIFIER ::={lb 43}

lbShuntByteIpv6AddrIntVal	OBJECT-TYPE
	SYNTAX	 Counter64
	MAX-ACCESS read-only
	STATUS current
	DESCRIPTION "Shunt bytes internal (IPv6 address)"

	::={lbShuntByteIpv6AddrInt 1}

lbShuntByteIpv6AddrIntMom	OBJECT-TYPE
	SYNTAX	 CounterBasedGauge64
	MAX-ACCESS read-only
	STATUS current
	DESCRIPTION "Shunt bytes internal (IPv6 address)"

	::={lbShuntByteIpv6AddrInt 2}

lbShuntByteIpv6AddrIntMax	OBJECT-TYPE
	SYNTAX	 CounterBasedGauge64
	MAX-ACCESS read-only
	STATUS current
	DESCRIPTION "Shunt bytes internal (IPv6 address)"

	::={lbShuntByteIpv6AddrInt 3}

lbShuntByteIpv6AddrExt	OBJECT IDENTIFIER ::={lb 44}

lbShuntByteIpv6AddrExtVal	OBJECT-TYPE
	SYNTAX	 Counter64
	MAX-ACCESS read-only
	STATUS current
	DESCRIPTION "Shunt bytes external (IPv6 address)"

	::={lbShuntByteIpv6AddrExt 1}

lbShuntByteIpv6AddrExtMom	OBJECT-TYPE
	SYNTAX	 CounterBasedGauge64
	MAX-ACCESS read-only
	STATUS current
	DESCRIPTION "Shunt bytes external (IPv6 address)"

	::={lbShuntByteIpv6AddrExt 2}

lbShuntByteIpv6AddrExtMax	OBJECT-TYPE
	SYNTAX	 CounterBasedGauge64
	MAX-ACCESS read-only
	STATUS current
	DESCRIPTION "Shunt bytes external (IPv6 address)"

	::={lbShuntByteIpv6AddrExt 3}

lbLogicalFp	OBJECT IDENTIFIER ::={lb 45}

lbLogicalFpVal	OBJECT-TYPE
	SYNTAX	 Unsigned32
	MAX-ACCESS read-only
	STATUS current
	DESCRIPTION "Logical ID"

	::={lbLogicalFp 1}

lbLogicalFpMax	OBJECT-TYPE
	SYNTAX	 Unsigned32
	MAX-ACCESS read-only
	STATUS current
	DESCRIPTION "Logical ID"

	::={lbLogicalFp 3}

lbTxFs	OBJECT IDENTIFIER ::={lb 46}

lbTxFsVal	OBJECT-TYPE
	SYNTAX	 Counter64
	MAX-ACCESS read-only
	STATUS current
	DESCRIPTION "TX flowsync packets"

	::={lbTxFs 1}

lbTxFsMom	OBJECT-TYPE
	SYNTAX	 CounterBasedGauge64
	MAX-ACCESS read-only
	STATUS current
	DESCRIPTION "TX flowsync packets"

	::={lbTxFs 2}

lbTxFsMax	OBJECT-TYPE
	SYNTAX	 CounterBasedGauge64
	MAX-ACCESS read-only
	STATUS current
	DESCRIPTION "TX flowsync packets"

	::={lbTxFs 3}

lbTxFpInt	OBJECT IDENTIFIER ::={lb 47}

lbTxFpIntVal	OBJECT-TYPE
	SYNTAX	 Counter64
	MAX-ACCESS read-only
	STATUS current
	DESCRIPTION "TX packets internal"

	::={lbTxFpInt 1}

lbTxFpIntMom	OBJECT-TYPE
	SYNTAX	 CounterBasedGauge64
	MAX-ACCESS read-only
	STATUS current
	DESCRIPTION "TX packets internal"

	::={lbTxFpInt 2}

lbTxFpIntMax	OBJECT-TYPE
	SYNTAX	 CounterBasedGauge64
	MAX-ACCESS read-only
	STATUS current
	DESCRIPTION "TX packets internal"

	::={lbTxFpInt 3}

lbTxFpExt	OBJECT IDENTIFIER ::={lb 48}

lbTxFpExtVal	OBJECT-TYPE
	SYNTAX	 Counter64
	MAX-ACCESS read-only
	STATUS current
	DESCRIPTION "TX packets external"

	::={lbTxFpExt 1}

lbTxFpExtMom	OBJECT-TYPE
	SYNTAX	 CounterBasedGauge64
	MAX-ACCESS read-only
	STATUS current
	DESCRIPTION "TX packets external"

	::={lbTxFpExt 2}

lbTxFpExtMax	OBJECT-TYPE
	SYNTAX	 CounterBasedGauge64
	MAX-ACCESS read-only
	STATUS current
	DESCRIPTION "TX packets external"

	::={lbTxFpExt 3}

lbHbLost	OBJECT IDENTIFIER ::={lb 49}

lbHbLostVal	OBJECT-TYPE
	SYNTAX	 Counter64
	MAX-ACCESS read-only
	STATUS current
	DESCRIPTION "Heartbeat packets lost"

	::={lbHbLost 1}

lbHbLostMom	OBJECT-TYPE
	SYNTAX	 CounterBasedGauge64
	MAX-ACCESS read-only
	STATUS current
	DESCRIPTION "Heartbeat packets lost"

	::={lbHbLost 2}

lbHbLostMax	OBJECT-TYPE
	SYNTAX	 CounterBasedGauge64
	MAX-ACCESS read-only
	STATUS current
	DESCRIPTION "Heartbeat packets lost"

	::={lbHbLost 3}

lbBucketMoves	OBJECT IDENTIFIER ::={lb 50}

lbBucketMovesVal	OBJECT-TYPE
	SYNTAX	 Counter64
	MAX-ACCESS read-only
	STATUS current
	DESCRIPTION "Moved buckets"

	::={lbBucketMoves 1}

lbBucketMovesMom	OBJECT-TYPE
	SYNTAX	 CounterBasedGauge64
	MAX-ACCESS read-only
	STATUS current
	DESCRIPTION "Moved buckets"

	::={lbBucketMoves 2}

lbBucketMovesMax	OBJECT-TYPE
	SYNTAX	 CounterBasedGauge64
	MAX-ACCESS read-only
	STATUS current
	DESCRIPTION "Moved buckets"

	::={lbBucketMoves 3}

lbBlacklistedBuckets	OBJECT IDENTIFIER ::={lb 51}

lbBlacklistedBucketsVal	OBJECT-TYPE
	SYNTAX	 CounterBasedGauge64
	MAX-ACCESS read-only
	STATUS current
	DESCRIPTION "Blacklisted buckets"

	::={lbBlacklistedBuckets 1}

lbBlacklistedBucketsMax	OBJECT-TYPE
	SYNTAX	 CounterBasedGauge64
	MAX-ACCESS read-only
	STATUS current
	DESCRIPTION "Blacklisted buckets"

	::={lbBlacklistedBuckets 3}

lbBlacklistedPackets	OBJECT IDENTIFIER ::={lb 52}

lbBlacklistedPacketsVal	OBJECT-TYPE
	SYNTAX	 Counter64
	MAX-ACCESS read-only
	STATUS current
	DESCRIPTION "Blacklisted packets"

	::={lbBlacklistedPackets 1}

lbBlacklistedPacketsMom	OBJECT-TYPE
	SYNTAX	 CounterBasedGauge64
	MAX-ACCESS read-only
	STATUS current
	DESCRIPTION "Blacklisted packets"

	::={lbBlacklistedPackets 2}

lbBlacklistedPacketsMax	OBJECT-TYPE
	SYNTAX	 CounterBasedGauge64
	MAX-ACCESS read-only
	STATUS current
	DESCRIPTION "Blacklisted packets"

	::={lbBlacklistedPackets 3}

plsd	OBJECT IDENTIFIER ::={sysdiag 136}

plsdDumptime	OBJECT IDENTIFIER ::={plsd 1}

plsdDumptimeVal	OBJECT-TYPE
	SYNTAX	 TimeTicks
	MAX-ACCESS read-only
	STATUS current
	DESCRIPTION "Dump time"

	::={plsdDumptime 1}

plsdValuesDataset	OBJECT IDENTIFIER ::={plsd 2}

plsdValuesDatasetVal	OBJECT-TYPE
	SYNTAX	 CounterBasedGauge64
	MAX-ACCESS read-only
	STATUS current
	DESCRIPTION "Values in dataset"

	::={plsdValuesDataset 1}

plsdValuesDatasetMax	OBJECT-TYPE
	SYNTAX	 CounterBasedGauge64
	MAX-ACCESS read-only
	STATUS current
	DESCRIPTION "Values in dataset"

	::={plsdValuesDataset 3}

plsdValuesDelayedExpand	OBJECT IDENTIFIER ::={plsd 3}

plsdValuesDelayedExpandVal	OBJECT-TYPE
	SYNTAX	 CounterBasedGauge64
	MAX-ACCESS read-only
	STATUS current
	DESCRIPTION "Values in dataset (delayed expand)"

	::={plsdValuesDelayedExpand 1}

plsdValuesDelayedExpandMax	OBJECT-TYPE
	SYNTAX	 CounterBasedGauge64
	MAX-ACCESS read-only
	STATUS current
	DESCRIPTION "Values in dataset (delayed expand)"

	::={plsdValuesDelayedExpand 3}

plsdLinksDataset	OBJECT IDENTIFIER ::={plsd 4}

plsdLinksDatasetVal	OBJECT-TYPE
	SYNTAX	 CounterBasedGauge64
	MAX-ACCESS read-only
	STATUS current
	DESCRIPTION "Links in dataset"

	::={plsdLinksDataset 1}

plsdLinksDatasetMax	OBJECT-TYPE
	SYNTAX	 CounterBasedGauge64
	MAX-ACCESS read-only
	STATUS current
	DESCRIPTION "Links in dataset"

	::={plsdLinksDataset 3}

plsdValuesAggrDataset	OBJECT IDENTIFIER ::={plsd 5}

plsdValuesAggrDatasetVal	OBJECT-TYPE
	SYNTAX	 CounterBasedGauge64
	MAX-ACCESS read-only
	STATUS current
	DESCRIPTION "Values in dataset(Aggregation)"

	::={plsdValuesAggrDataset 1}

plsdValuesAggrDatasetMax	OBJECT-TYPE
	SYNTAX	 CounterBasedGauge64
	MAX-ACCESS read-only
	STATUS current
	DESCRIPTION "Values in dataset(Aggregation)"

	::={plsdValuesAggrDataset 3}

plsdValueReject	OBJECT IDENTIFIER ::={plsd 6}

plsdValueRejectVal	OBJECT-TYPE
	SYNTAX	 Counter64
	MAX-ACCESS read-only
	STATUS current
	DESCRIPTION "Values not created, Cache exhausted"

	::={plsdValueReject 1}

plsdValueRejectMom	OBJECT-TYPE
	SYNTAX	 CounterBasedGauge64
	MAX-ACCESS read-only
	STATUS current
	DESCRIPTION "Values not created, Cache exhausted"

	::={plsdValueReject 2}

plsdValueRejectMax	OBJECT-TYPE
	SYNTAX	 CounterBasedGauge64
	MAX-ACCESS read-only
	STATUS current
	DESCRIPTION "Values not created, Cache exhausted"

	::={plsdValueReject 3}

plsdValueRejectPrior	OBJECT IDENTIFIER ::={plsd 7}

plsdValueRejectPriorVal	OBJECT-TYPE
	SYNTAX	 Counter64
	MAX-ACCESS read-only
	STATUS current
	DESCRIPTION "Values not created, Priority Threshold"

	::={plsdValueRejectPrior 1}

plsdValueRejectPriorMom	OBJECT-TYPE
	SYNTAX	 CounterBasedGauge64
	MAX-ACCESS read-only
	STATUS current
	DESCRIPTION "Values not created, Priority Threshold"

	::={plsdValueRejectPrior 2}

plsdValueRejectPriorMax	OBJECT-TYPE
	SYNTAX	 CounterBasedGauge64
	MAX-ACCESS read-only
	STATUS current
	DESCRIPTION "Values not created, Priority Threshold"

	::={plsdValueRejectPrior 3}

plsdValuesFiltered	OBJECT IDENTIFIER ::={plsd 8}

plsdValuesFilteredVal	OBJECT-TYPE
	SYNTAX	 CounterBasedGauge64
	MAX-ACCESS read-only
	STATUS current
	DESCRIPTION "Values filtered"

	::={plsdValuesFiltered 1}

plsdValuesFilteredMax	OBJECT-TYPE
	SYNTAX	 CounterBasedGauge64
	MAX-ACCESS read-only
	STATUS current
	DESCRIPTION "Values filtered"

	::={plsdValuesFiltered 3}

plsdValuesSent	OBJECT IDENTIFIER ::={plsd 9}

plsdValuesSentVal	OBJECT-TYPE
	SYNTAX	 CounterBasedGauge64
	MAX-ACCESS read-only
	STATUS current
	DESCRIPTION "Values sent to Statwriter"

	::={plsdValuesSent 1}

plsdValuesSentMax	OBJECT-TYPE
	SYNTAX	 CounterBasedGauge64
	MAX-ACCESS read-only
	STATUS current
	DESCRIPTION "Values sent to Statwriter"

	::={plsdValuesSent 3}

plsdValueLookups	OBJECT IDENTIFIER ::={plsd 10}

plsdValueLookupsVal	OBJECT-TYPE
	SYNTAX	 Counter64
	MAX-ACCESS read-only
	STATUS current
	DESCRIPTION "Value lookups"

	::={plsdValueLookups 1}

plsdValueLookupsMom	OBJECT-TYPE
	SYNTAX	 CounterBasedGauge64
	MAX-ACCESS read-only
	STATUS current
	DESCRIPTION "Value lookups"

	::={plsdValueLookups 2}

plsdValueLookupsMax	OBJECT-TYPE
	SYNTAX	 CounterBasedGauge64
	MAX-ACCESS read-only
	STATUS current
	DESCRIPTION "Value lookups"

	::={plsdValueLookups 3}

plsdValueUpdatesBytes	OBJECT IDENTIFIER ::={plsd 11}

plsdValueUpdatesBytesVal	OBJECT-TYPE
	SYNTAX	 Counter64
	MAX-ACCESS read-only
	STATUS current
	DESCRIPTION "Value updates(Bytes)"

	::={plsdValueUpdatesBytes 1}

plsdValueUpdatesBytesMom	OBJECT-TYPE
	SYNTAX	 CounterBasedGauge64
	MAX-ACCESS read-only
	STATUS current
	DESCRIPTION "Value updates(Bytes)"

	::={plsdValueUpdatesBytes 2}

plsdValueUpdatesBytesMax	OBJECT-TYPE
	SYNTAX	 CounterBasedGauge64
	MAX-ACCESS read-only
	STATUS current
	DESCRIPTION "Value updates(Bytes)"

	::={plsdValueUpdatesBytes 3}

plsdValueUpdatesBytesHp	OBJECT IDENTIFIER ::={plsd 12}

plsdValueUpdatesBytesHpVal	OBJECT-TYPE
	SYNTAX	 Counter64
	MAX-ACCESS read-only
	STATUS current
	DESCRIPTION "Value updates, High Priority (Bytes)"

	::={plsdValueUpdatesBytesHp 1}

plsdValueUpdatesBytesHpMom	OBJECT-TYPE
	SYNTAX	 CounterBasedGauge64
	MAX-ACCESS read-only
	STATUS current
	DESCRIPTION "Value updates, High Priority (Bytes)"

	::={plsdValueUpdatesBytesHp 2}

plsdValueUpdatesBytesHpMax	OBJECT-TYPE
	SYNTAX	 CounterBasedGauge64
	MAX-ACCESS read-only
	STATUS current
	DESCRIPTION "Value updates, High Priority (Bytes)"

	::={plsdValueUpdatesBytesHp 3}

plsdValueUpdatesConns	OBJECT IDENTIFIER ::={plsd 13}

plsdValueUpdatesConnsVal	OBJECT-TYPE
	SYNTAX	 Counter64
	MAX-ACCESS read-only
	STATUS current
	DESCRIPTION "Value updates(Conns)"

	::={plsdValueUpdatesConns 1}

plsdValueUpdatesConnsMom	OBJECT-TYPE
	SYNTAX	 CounterBasedGauge64
	MAX-ACCESS read-only
	STATUS current
	DESCRIPTION "Value updates(Conns)"

	::={plsdValueUpdatesConns 2}

plsdValueUpdatesConnsMax	OBJECT-TYPE
	SYNTAX	 CounterBasedGauge64
	MAX-ACCESS read-only
	STATUS current
	DESCRIPTION "Value updates(Conns)"

	::={plsdValueUpdatesConns 3}

plsdValueUpdatesConnsHp	OBJECT IDENTIFIER ::={plsd 14}

plsdValueUpdatesConnsHpVal	OBJECT-TYPE
	SYNTAX	 Counter64
	MAX-ACCESS read-only
	STATUS current
	DESCRIPTION "Value updates, High Priority (Conns)"

	::={plsdValueUpdatesConnsHp 1}

plsdValueUpdatesConnsHpMom	OBJECT-TYPE
	SYNTAX	 CounterBasedGauge64
	MAX-ACCESS read-only
	STATUS current
	DESCRIPTION "Value updates, High Priority (Conns)"

	::={plsdValueUpdatesConnsHp 2}

plsdValueUpdatesConnsHpMax	OBJECT-TYPE
	SYNTAX	 CounterBasedGauge64
	MAX-ACCESS read-only
	STATUS current
	DESCRIPTION "Value updates, High Priority (Conns)"

	::={plsdValueUpdatesConnsHp 3}

plsdConnections	OBJECT IDENTIFIER ::={plsd 15}

plsdConnectionsVal	OBJECT-TYPE
	SYNTAX	 CounterBasedGauge64
	MAX-ACCESS read-only
	STATUS current
	DESCRIPTION "Connection table size"

	::={plsdConnections 1}

plsdConnectionsMax	OBJECT-TYPE
	SYNTAX	 CounterBasedGauge64
	MAX-ACCESS read-only
	STATUS current
	DESCRIPTION "Connection table size"

	::={plsdConnections 3}

plsdHosts	OBJECT IDENTIFIER ::={plsd 16}

plsdHostsVal	OBJECT-TYPE
	SYNTAX	 CounterBasedGauge64
	MAX-ACCESS read-only
	STATUS current
	DESCRIPTION "Hosts"

	::={plsdHosts 1}

plsdHostsMax	OBJECT-TYPE
	SYNTAX	 CounterBasedGauge64
	MAX-ACCESS read-only
	STATUS current
	DESCRIPTION "Hosts"

	::={plsdHosts 3}

plsdConnUpdates	OBJECT IDENTIFIER ::={plsd 17}

plsdConnUpdatesVal	OBJECT-TYPE
	SYNTAX	 Counter64
	MAX-ACCESS read-only
	STATUS current
	DESCRIPTION "Connection updates"

	::={plsdConnUpdates 1}

plsdConnUpdatesMom	OBJECT-TYPE
	SYNTAX	 CounterBasedGauge64
	MAX-ACCESS read-only
	STATUS current
	DESCRIPTION "Connection updates"

	::={plsdConnUpdates 2}

plsdConnUpdatesMax	OBJECT-TYPE
	SYNTAX	 CounterBasedGauge64
	MAX-ACCESS read-only
	STATUS current
	DESCRIPTION "Connection updates"

	::={plsdConnUpdates 3}

plsdConnUpdatesFull	OBJECT IDENTIFIER ::={plsd 18}

plsdConnUpdatesFullVal	OBJECT-TYPE
	SYNTAX	 Counter64
	MAX-ACCESS read-only
	STATUS current
	DESCRIPTION "Connection updates (Full)"

	::={plsdConnUpdatesFull 1}

plsdConnUpdatesFullMom	OBJECT-TYPE
	SYNTAX	 CounterBasedGauge64
	MAX-ACCESS read-only
	STATUS current
	DESCRIPTION "Connection updates (Full)"

	::={plsdConnUpdatesFull 2}

plsdConnUpdatesFullMax	OBJECT-TYPE
	SYNTAX	 CounterBasedGauge64
	MAX-ACCESS read-only
	STATUS current
	DESCRIPTION "Connection updates (Full)"

	::={plsdConnUpdatesFull 3}

plsdConnUpdatesNew	OBJECT IDENTIFIER ::={plsd 19}

plsdConnUpdatesNewVal	OBJECT-TYPE
	SYNTAX	 Counter64
	MAX-ACCESS read-only
	STATUS current
	DESCRIPTION "Connection updates (New)"

	::={plsdConnUpdatesNew 1}

plsdConnUpdatesNewMom	OBJECT-TYPE
	SYNTAX	 CounterBasedGauge64
	MAX-ACCESS read-only
	STATUS current
	DESCRIPTION "Connection updates (New)"

	::={plsdConnUpdatesNew 2}

plsdConnUpdatesNewMax	OBJECT-TYPE
	SYNTAX	 CounterBasedGauge64
	MAX-ACCESS read-only
	STATUS current
	DESCRIPTION "Connection updates (New)"

	::={plsdConnUpdatesNew 3}

plsdConnUpdatesFiltered	OBJECT IDENTIFIER ::={plsd 20}

plsdConnUpdatesFilteredVal	OBJECT-TYPE
	SYNTAX	 Counter64
	MAX-ACCESS read-only
	STATUS current
	DESCRIPTION "Connection updates (Threshold Filtered)"

	::={plsdConnUpdatesFiltered 1}

plsdConnUpdatesFilteredMom	OBJECT-TYPE
	SYNTAX	 CounterBasedGauge64
	MAX-ACCESS read-only
	STATUS current
	DESCRIPTION "Connection updates (Threshold Filtered)"

	::={plsdConnUpdatesFiltered 2}

plsdConnUpdatesFilteredMax	OBJECT-TYPE
	SYNTAX	 CounterBasedGauge64
	MAX-ACCESS read-only
	STATUS current
	DESCRIPTION "Connection updates (Threshold Filtered)"

	::={plsdConnUpdatesFiltered 3}

plsdConnsDropped	OBJECT IDENTIFIER ::={plsd 21}

plsdConnsDroppedVal	OBJECT-TYPE
	SYNTAX	 Counter64
	MAX-ACCESS read-only
	STATUS current
	DESCRIPTION "Connections dropped (Cache Exhausted)"

	::={plsdConnsDropped 1}

plsdConnsDroppedMom	OBJECT-TYPE
	SYNTAX	 CounterBasedGauge64
	MAX-ACCESS read-only
	STATUS current
	DESCRIPTION "Connections dropped (Cache Exhausted)"

	::={plsdConnsDropped 2}

plsdConnsDroppedMax	OBJECT-TYPE
	SYNTAX	 CounterBasedGauge64
	MAX-ACCESS read-only
	STATUS current
	DESCRIPTION "Connections dropped (Cache Exhausted)"

	::={plsdConnsDropped 3}

plsdConnlogConns	OBJECT IDENTIFIER ::={plsd 22}

plsdConnlogConnsVal	OBJECT-TYPE
	SYNTAX	 CounterBasedGauge64
	MAX-ACCESS read-only
	STATUS current
	DESCRIPTION "Connlog connections stored"

	::={plsdConnlogConns 1}

plsdConnlogConnsMax	OBJECT-TYPE
	SYNTAX	 CounterBasedGauge64
	MAX-ACCESS read-only
	STATUS current
	DESCRIPTION "Connlog connections stored"

	::={plsdConnlogConns 3}

plsdConnlogConnsAdded	OBJECT IDENTIFIER ::={plsd 23}

plsdConnlogConnsAddedVal	OBJECT-TYPE
	SYNTAX	 Counter64
	MAX-ACCESS read-only
	STATUS current
	DESCRIPTION "Connlog connections added"

	::={plsdConnlogConnsAdded 1}

plsdConnlogConnsAddedMom	OBJECT-TYPE
	SYNTAX	 CounterBasedGauge64
	MAX-ACCESS read-only
	STATUS current
	DESCRIPTION "Connlog connections added"

	::={plsdConnlogConnsAdded 2}

plsdConnlogConnsAddedMax	OBJECT-TYPE
	SYNTAX	 CounterBasedGauge64
	MAX-ACCESS read-only
	STATUS current
	DESCRIPTION "Connlog connections added"

	::={plsdConnlogConnsAdded 3}

plsdConnlogDumptimeRemaining	OBJECT IDENTIFIER ::={plsd 24}

plsdConnlogDumptimeRemainingVal	OBJECT-TYPE
	SYNTAX	 TimeTicks
	MAX-ACCESS read-only
	STATUS current
	DESCRIPTION "Connlog time remaining"

	::={plsdConnlogDumptimeRemaining 1}

plsdConnlogConnsDumped	OBJECT IDENTIFIER ::={plsd 25}

plsdConnlogConnsDumpedVal	OBJECT-TYPE
	SYNTAX	 CounterBasedGauge64
	MAX-ACCESS read-only
	STATUS current
	DESCRIPTION "Connlog connections dumped"

	::={plsdConnlogConnsDumped 1}

plsdConnlogConnsDumpedMax	OBJECT-TYPE
	SYNTAX	 CounterBasedGauge64
	MAX-ACCESS read-only
	STATUS current
	DESCRIPTION "Connlog connections dumped"

	::={plsdConnlogConnsDumped 3}

plsdConnlogDumptime	OBJECT IDENTIFIER ::={plsd 26}

plsdConnlogDumptimeVal	OBJECT-TYPE
	SYNTAX	 TimeTicks
	MAX-ACCESS read-only
	STATUS current
	DESCRIPTION "Connlog dumptime"

	::={plsdConnlogDumptime 1}

plsdLastdump	OBJECT IDENTIFIER ::={plsd 27}

plsdLastdumpVal	OBJECT-TYPE
	SYNTAX	 DateAndTime
	MAX-ACCESS read-only
	STATUS current
	DESCRIPTION "Time of last dump"

	::={plsdLastdump 1}

plsdRingbufUsage	OBJECT IDENTIFIER ::={plsd 28}

plsdRingbufUsageVal	OBJECT-TYPE
	SYNTAX	 CounterBasedGauge64
	MAX-ACCESS read-only
	STATUS current
	DESCRIPTION "Recv Ringbuf usage (Collector)"

	::={plsdRingbufUsage 1}

plsdRingbufUsageMax	OBJECT-TYPE
	SYNTAX	 CounterBasedGauge64
	MAX-ACCESS read-only
	STATUS current
	DESCRIPTION "Recv Ringbuf usage (Collector)"

	::={plsdRingbufUsage 3}

plsdConnlogDrops	OBJECT IDENTIFIER ::={plsd 30}

plsdConnlogDropsVal	OBJECT-TYPE
	SYNTAX	 CounterBasedGauge64
	MAX-ACCESS read-only
	STATUS current
	DESCRIPTION "Connlog entries dropped"

	::={plsdConnlogDrops 1}

plsdConnlogDropsMax	OBJECT-TYPE
	SYNTAX	 CounterBasedGauge64
	MAX-ACCESS read-only
	STATUS current
	DESCRIPTION "Connlog entries dropped"

	::={plsdConnlogDrops 3}

plsdBwUsed	OBJECT IDENTIFIER ::={plsd 31}

plsdBwUsedVal	OBJECT-TYPE
	SYNTAX	 Counter64
	MAX-ACCESS read-only
	STATUS current
	DESCRIPTION "Bandwidth used"

	::={plsdBwUsed 1}

plsdBwUsedMom	OBJECT-TYPE
	SYNTAX	 CounterBasedGauge64
	MAX-ACCESS read-only
	STATUS current
	DESCRIPTION "Bandwidth used"

	::={plsdBwUsed 2}

plsdBwUsedMax	OBJECT-TYPE
	SYNTAX	 CounterBasedGauge64
	MAX-ACCESS read-only
	STATUS current
	DESCRIPTION "Bandwidth used"

	::={plsdBwUsed 3}

plsdTimeConnected	OBJECT IDENTIFIER ::={plsd 32}

plsdTimeConnectedVal	OBJECT-TYPE
	SYNTAX	 TimeTicks
	MAX-ACCESS read-only
	STATUS current
	DESCRIPTION "Time connected"

	::={plsdTimeConnected 1}

plsdConnects	OBJECT IDENTIFIER ::={plsd 33}

plsdConnectsVal	OBJECT-TYPE
	SYNTAX	 CounterBasedGauge64
	MAX-ACCESS read-only
	STATUS current
	DESCRIPTION "Connects"

	::={plsdConnects 1}

plsdConnectsMax	OBJECT-TYPE
	SYNTAX	 CounterBasedGauge64
	MAX-ACCESS read-only
	STATUS current
	DESCRIPTION "Connects"

	::={plsdConnects 3}

plsdVmsize	OBJECT IDENTIFIER ::={plsd 34}

plsdVmsizeVal	OBJECT-TYPE
	SYNTAX	 CounterBasedGauge64
	MAX-ACCESS read-only
	STATUS current
	DESCRIPTION "Memory usage (Virtual)"

	::={plsdVmsize 1}

plsdVmsizeMax	OBJECT-TYPE
	SYNTAX	 CounterBasedGauge64
	MAX-ACCESS read-only
	STATUS current
	DESCRIPTION "Memory usage (Virtual)"

	::={plsdVmsize 3}

plsdVmrss	OBJECT IDENTIFIER ::={plsd 35}

plsdVmrssVal	OBJECT-TYPE
	SYNTAX	 CounterBasedGauge64
	MAX-ACCESS read-only
	STATUS current
	DESCRIPTION "Memory usage (RAM)"

	::={plsdVmrss 1}

plsdVmrssMax	OBJECT-TYPE
	SYNTAX	 CounterBasedGauge64
	MAX-ACCESS read-only
	STATUS current
	DESCRIPTION "Memory usage (RAM)"

	::={plsdVmrss 3}

plsdConnlogIncomplete	OBJECT IDENTIFIER ::={plsd 36}

plsdConnlogIncompleteVal	OBJECT-TYPE
	SYNTAX	 CounterBasedGauge64
	MAX-ACCESS read-only
	STATUS current
	DESCRIPTION "Connlog entries incomplete"

	::={plsdConnlogIncomplete 1}

plsdConnlogIncompleteMax	OBJECT-TYPE
	SYNTAX	 CounterBasedGauge64
	MAX-ACCESS read-only
	STATUS current
	DESCRIPTION "Connlog entries incomplete"

	::={plsdConnlogIncomplete 3}

plsdConnProp	OBJECT IDENTIFIER ::={plsd 37}

plsdConnPropVal	OBJECT-TYPE
	SYNTAX	 CounterBasedGauge64
	MAX-ACCESS read-only
	STATUS current
	DESCRIPTION "Connection Properties count"

	::={plsdConnProp 1}

plsdConnPropMax	OBJECT-TYPE
	SYNTAX	 CounterBasedGauge64
	MAX-ACCESS read-only
	STATUS current
	DESCRIPTION "Connection Properties count"

	::={plsdConnProp 3}

plsdConnPropHash	OBJECT IDENTIFIER ::={plsd 38}

plsdConnPropHashVal	OBJECT-TYPE
	SYNTAX	 CounterBasedGauge64
	MAX-ACCESS read-only
	STATUS current
	DESCRIPTION "Connection Properties Hashtables"

	::={plsdConnPropHash 1}

plsdConnPropHashMax	OBJECT-TYPE
	SYNTAX	 CounterBasedGauge64
	MAX-ACCESS read-only
	STATUS current
	DESCRIPTION "Connection Properties Hashtables"

	::={plsdConnPropHash 3}

plsw	OBJECT IDENTIFIER ::={sysdiag 137}

plswDatasetStart	OBJECT IDENTIFIER ::={plsw 1}

plswDatasetStartVal	OBJECT-TYPE
	SYNTAX	 DateAndTime
	MAX-ACCESS read-only
	STATUS current
	DESCRIPTION "Dataset, Begin"

	::={plswDatasetStart 1}

plswDatasetEnd	OBJECT IDENTIFIER ::={plsw 2}

plswDatasetEndVal	OBJECT-TYPE
	SYNTAX	 DateAndTime
	MAX-ACCESS read-only
	STATUS current
	DESCRIPTION "Dataset, End"

	::={plswDatasetEnd 1}

plswSessions	OBJECT IDENTIFIER ::={plsw 3}

plswSessionsVal	OBJECT-TYPE
	SYNTAX	 CounterBasedGauge64
	MAX-ACCESS read-only
	STATUS current
	DESCRIPTION "Dataset, Sessions"

	::={plswSessions 1}

plswSessionsMax	OBJECT-TYPE
	SYNTAX	 CounterBasedGauge64
	MAX-ACCESS read-only
	STATUS current
	DESCRIPTION "Dataset, Sessions"

	::={plswSessions 3}

plswValues	OBJECT IDENTIFIER ::={plsw 4}

plswValuesVal	OBJECT-TYPE
	SYNTAX	 CounterBasedGauge64
	MAX-ACCESS read-only
	STATUS current
	DESCRIPTION "Dataset Values"

	::={plswValues 1}

plswValuesMax	OBJECT-TYPE
	SYNTAX	 CounterBasedGauge64
	MAX-ACCESS read-only
	STATUS current
	DESCRIPTION "Dataset Values"

	::={plswValues 3}

plswValuesDropped1	OBJECT IDENTIFIER ::={plsw 5}

plswValuesDropped1Val	OBJECT-TYPE
	SYNTAX	 CounterBasedGauge64
	MAX-ACCESS read-only
	STATUS current
	DESCRIPTION "Dataset Values Dropped (cache exhausted)"

	::={plswValuesDropped1 1}

plswValuesDropped1Max	OBJECT-TYPE
	SYNTAX	 CounterBasedGauge64
	MAX-ACCESS read-only
	STATUS current
	DESCRIPTION "Dataset Values Dropped (cache exhausted)"

	::={plswValuesDropped1 3}

plswValuesDropped2	OBJECT IDENTIFIER ::={plsw 6}

plswValuesDropped2Val	OBJECT-TYPE
	SYNTAX	 CounterBasedGauge64
	MAX-ACCESS read-only
	STATUS current
	DESCRIPTION "Dataset Values Dropped (malformed name)"

	::={plswValuesDropped2 1}

plswValuesDropped2Max	OBJECT-TYPE
	SYNTAX	 CounterBasedGauge64
	MAX-ACCESS read-only
	STATUS current
	DESCRIPTION "Dataset Values Dropped (malformed name)"

	::={plswValuesDropped2 3}

plswValuesDropped3	OBJECT IDENTIFIER ::={plsw 7}

plswValuesDropped3Val	OBJECT-TYPE
	SYNTAX	 CounterBasedGauge64
	MAX-ACCESS read-only
	STATUS current
	DESCRIPTION "Dataset Values Dropped (Global Index exhausted)"

	::={plswValuesDropped3 1}

plswValuesDropped3Max	OBJECT-TYPE
	SYNTAX	 CounterBasedGauge64
	MAX-ACCESS read-only
	STATUS current
	DESCRIPTION "Dataset Values Dropped (Global Index exhausted)"

	::={plswValuesDropped3 3}

plswValuesDropped4	OBJECT IDENTIFIER ::={plsw 8}

plswValuesDropped4Val	OBJECT-TYPE
	SYNTAX	 CounterBasedGauge64
	MAX-ACCESS read-only
	STATUS current
	DESCRIPTION "Dataset Values Dropped (Symlink target not found)"

	::={plswValuesDropped4 1}

plswValuesDropped4Max	OBJECT-TYPE
	SYNTAX	 CounterBasedGauge64
	MAX-ACCESS read-only
	STATUS current
	DESCRIPTION "Dataset Values Dropped (Symlink target not found)"

	::={plswValuesDropped4 3}

plswNewglobal	OBJECT IDENTIFIER ::={plsw 9}

plswNewglobalVal	OBJECT-TYPE
	SYNTAX	 CounterBasedGauge64
	MAX-ACCESS read-only
	STATUS current
	DESCRIPTION "Dataset values, New Global Indexes"

	::={plswNewglobal 1}

plswNewglobalMax	OBJECT-TYPE
	SYNTAX	 CounterBasedGauge64
	MAX-ACCESS read-only
	STATUS current
	DESCRIPTION "Dataset values, New Global Indexes"

	::={plswNewglobal 3}

plswNewcoll	OBJECT IDENTIFIER ::={plsw 10}

plswNewcollVal	OBJECT-TYPE
	SYNTAX	 CounterBasedGauge64
	MAX-ACCESS read-only
	STATUS current
	DESCRIPTION "Dataset values, New Global collisions"

	::={plswNewcoll 1}

plswNewcollMax	OBJECT-TYPE
	SYNTAX	 CounterBasedGauge64
	MAX-ACCESS read-only
	STATUS current
	DESCRIPTION "Dataset values, New Global collisions"

	::={plswNewcoll 3}

plswNewdaily	OBJECT IDENTIFIER ::={plsw 11}

plswNewdailyVal	OBJECT-TYPE
	SYNTAX	 CounterBasedGauge64
	MAX-ACCESS read-only
	STATUS current
	DESCRIPTION "Dataset values, New Daily Indexes"

	::={plswNewdaily 1}

plswNewdailyMax	OBJECT-TYPE
	SYNTAX	 CounterBasedGauge64
	MAX-ACCESS read-only
	STATUS current
	DESCRIPTION "Dataset values, New Daily Indexes"

	::={plswNewdaily 3}

plswTupdate	OBJECT IDENTIFIER ::={plsw 12}

plswTupdateVal	OBJECT-TYPE
	SYNTAX	 CounterBasedGauge64
	MAX-ACCESS read-only
	STATUS current
	DESCRIPTION "Dataset values, Updates (Totals)"

	::={plswTupdate 1}

plswTupdateMax	OBJECT-TYPE
	SYNTAX	 CounterBasedGauge64
	MAX-ACCESS read-only
	STATUS current
	DESCRIPTION "Dataset values, Updates (Totals)"

	::={plswTupdate 3}

plswGupdate	OBJECT IDENTIFIER ::={plsw 13}

plswGupdateVal	OBJECT-TYPE
	SYNTAX	 CounterBasedGauge64
	MAX-ACCESS read-only
	STATUS current
	DESCRIPTION "Dataset values, Updates (Graphs)"

	::={plswGupdate 1}

plswGupdateMax	OBJECT-TYPE
	SYNTAX	 CounterBasedGauge64
	MAX-ACCESS read-only
	STATUS current
	DESCRIPTION "Dataset values, Updates (Graphs)"

	::={plswGupdate 3}

plswTimeDataset	OBJECT IDENTIFIER ::={plsw 14}

plswTimeDatasetVal	OBJECT-TYPE
	SYNTAX	 TimeTicks
	MAX-ACCESS read-only
	STATUS current
	DESCRIPTION "Dataset, Total Write time"

	::={plswTimeDataset 1}

plswTimeGlobal	OBJECT IDENTIFIER ::={plsw 15}

plswTimeGlobalVal	OBJECT-TYPE
	SYNTAX	 TimeTicks
	MAX-ACCESS read-only
	STATUS current
	DESCRIPTION "Dataset, Time for Globals file I/O"

	::={plswTimeGlobal 1}

plswTimeDaily	OBJECT IDENTIFIER ::={plsw 16}

plswTimeDailyVal	OBJECT-TYPE
	SYNTAX	 TimeTicks
	MAX-ACCESS read-only
	STATUS current
	DESCRIPTION "Dataset, Time for Daily Index file I/O"

	::={plswTimeDaily 1}

plswTimeTotal	OBJECT IDENTIFIER ::={plsw 17}

plswTimeTotalVal	OBJECT-TYPE
	SYNTAX	 TimeTicks
	MAX-ACCESS read-only
	STATUS current
	DESCRIPTION "Dataset, Time for Totals file I/O"

	::={plswTimeTotal 1}

plswTimeGraph	OBJECT IDENTIFIER ::={plsw 18}

plswTimeGraphVal	OBJECT-TYPE
	SYNTAX	 TimeTicks
	MAX-ACCESS read-only
	STATUS current
	DESCRIPTION "Dataset, Time for Graph file I/O"

	::={plswTimeGraph 1}

plswGlobals	OBJECT IDENTIFIER ::={plsw 19}

plswGlobalsVal	OBJECT-TYPE
	SYNTAX	 CounterBasedGauge64
	MAX-ACCESS read-only
	STATUS current
	DESCRIPTION "Statisticsfs, Values (Global Indexes)"

	::={plswGlobals 1}

plswGlobalsMax	OBJECT-TYPE
	SYNTAX	 CounterBasedGauge64
	MAX-ACCESS read-only
	STATUS current
	DESCRIPTION "Statisticsfs, Values (Global Indexes)"

	::={plswGlobals 3}

plswColls	OBJECT IDENTIFIER ::={plsw 20}

plswCollsVal	OBJECT-TYPE
	SYNTAX	 CounterBasedGauge64
	MAX-ACCESS read-only
	STATUS current
	DESCRIPTION "Statisticsfs, Values (Global Collisions)"

	::={plswColls 1}

plswCollsMax	OBJECT-TYPE
	SYNTAX	 CounterBasedGauge64
	MAX-ACCESS read-only
	STATUS current
	DESCRIPTION "Statisticsfs, Values (Global Collisions)"

	::={plswColls 3}

plswDailys	OBJECT IDENTIFIER ::={plsw 21}

plswDailysVal	OBJECT-TYPE
	SYNTAX	 CounterBasedGauge64
	MAX-ACCESS read-only
	STATUS current
	DESCRIPTION "Statisticsfs, Values (Daily Indexes)"

	::={plswDailys 1}

plswDailysMax	OBJECT-TYPE
	SYNTAX	 CounterBasedGauge64
	MAX-ACCESS read-only
	STATUS current
	DESCRIPTION "Statisticsfs, Values (Daily Indexes)"

	::={plswDailys 3}

plswBlocks	OBJECT IDENTIFIER ::={plsw 22}

plswBlocksVal	OBJECT-TYPE
	SYNTAX	 CounterBasedGauge64
	MAX-ACCESS read-only
	STATUS current
	DESCRIPTION "Statisticsfs, Daily Totals file blocks"

	::={plswBlocks 1}

plswBlocksMax	OBJECT-TYPE
	SYNTAX	 CounterBasedGauge64
	MAX-ACCESS read-only
	STATUS current
	DESCRIPTION "Statisticsfs, Daily Totals file blocks"

	::={plswBlocks 3}

plswGraphs	OBJECT IDENTIFIER ::={plsw 23}

plswGraphsVal	OBJECT-TYPE
	SYNTAX	 CounterBasedGauge64
	MAX-ACCESS read-only
	STATUS current
	DESCRIPTION "Statisticsfs, Daily Graph data usage (Bytes)"

	::={plswGraphs 1}

plswGraphsMax	OBJECT-TYPE
	SYNTAX	 CounterBasedGauge64
	MAX-ACCESS read-only
	STATUS current
	DESCRIPTION "Statisticsfs, Daily Graph data usage (Bytes)"

	::={plswGraphs 3}

plswSysdiagHdUsage	OBJECT IDENTIFIER ::={plsw 24}

plswSysdiagHdUsageVal	OBJECT-TYPE
	SYNTAX	 Unsigned32
	MAX-ACCESS read-only
	STATUS current
	DESCRIPTION "Statisticsfs, Disk Usage"

	::={plswSysdiagHdUsage 1}

plswSysdiagHdUsageMax	OBJECT-TYPE
	SYNTAX	 Unsigned32
	MAX-ACCESS read-only
	STATUS current
	DESCRIPTION "Statisticsfs, Disk Usage"

	::={plswSysdiagHdUsage 3}

plswSysdiagHdSize	OBJECT IDENTIFIER ::={plsw 25}

plswSysdiagHdSizeVal	OBJECT-TYPE
	SYNTAX	 CounterBasedGauge64
	MAX-ACCESS read-only
	STATUS current
	DESCRIPTION "Statisticsfs, Disk Size"

	::={plswSysdiagHdSize 1}

plswSysdiagHdSizeMax	OBJECT-TYPE
	SYNTAX	 CounterBasedGauge64
	MAX-ACCESS read-only
	STATUS current
	DESCRIPTION "Statisticsfs, Disk Size"

	::={plswSysdiagHdSize 3}

plswSystemHdUsage	OBJECT IDENTIFIER ::={plsw 26}

plswSystemHdUsageVal	OBJECT-TYPE
	SYNTAX	 Unsigned32
	MAX-ACCESS read-only
	STATUS current
	DESCRIPTION "System, Disk Usage"

	::={plswSystemHdUsage 1}

plswSystemHdUsageMax	OBJECT-TYPE
	SYNTAX	 Unsigned32
	MAX-ACCESS read-only
	STATUS current
	DESCRIPTION "System, Disk Usage"

	::={plswSystemHdUsage 3}

plswSystemHdSize	OBJECT IDENTIFIER ::={plsw 27}

plswSystemHdSizeVal	OBJECT-TYPE
	SYNTAX	 CounterBasedGauge64
	MAX-ACCESS read-only
	STATUS current
	DESCRIPTION "System, Disk Size"

	::={plswSystemHdSize 1}

plswSystemHdSizeMax	OBJECT-TYPE
	SYNTAX	 CounterBasedGauge64
	MAX-ACCESS read-only
	STATUS current
	DESCRIPTION "System, Disk Size"

	::={plswSystemHdSize 3}

plswSysdiagDaySize	OBJECT IDENTIFIER ::={plsw 28}

plswSysdiagDaySizeVal	OBJECT-TYPE
	SYNTAX	 CounterBasedGauge64
	MAX-ACCESS read-only
	STATUS current
	DESCRIPTION "Statisticsfs, Disk Usage Per Day"

	::={plswSysdiagDaySize 1}

plswSysdiagDaySizeMax	OBJECT-TYPE
	SYNTAX	 CounterBasedGauge64
	MAX-ACCESS read-only
	STATUS current
	DESCRIPTION "Statisticsfs, Disk Usage Per Day"

	::={plswSysdiagDaySize 3}

plswMemused	OBJECT IDENTIFIER ::={plsw 29}

plswMemusedVal	OBJECT-TYPE
	SYNTAX	 CounterBasedGauge64
	MAX-ACCESS read-only
	STATUS current
	DESCRIPTION "Statwriter, Peak memory usage"

	::={plswMemused 1}

plswMemusedMax	OBJECT-TYPE
	SYNTAX	 CounterBasedGauge64
	MAX-ACCESS read-only
	STATUS current
	DESCRIPTION "Statwriter, Peak memory usage"

	::={plswMemused 3}

rulesetCompiler	OBJECT IDENTIFIER ::={sysdiag 138}

rulesetCompilerReaperRecvBuf	OBJECT IDENTIFIER ::={rulesetCompiler 1}

rulesetCompilerReaperRecvBufVal	OBJECT-TYPE
	SYNTAX	 CounterBasedGauge64
	MAX-ACCESS read-only
	STATUS current
	DESCRIPTION "Reaper receive buffer usage"

	::={rulesetCompilerReaperRecvBuf 1}

rulesetCompilerReaperRecvBufMax	OBJECT-TYPE
	SYNTAX	 CounterBasedGauge64
	MAX-ACCESS read-only
	STATUS current
	DESCRIPTION "Reaper receive buffer usage"

	::={rulesetCompilerReaperRecvBuf 3}

rulesetCompilerReaperSendBuf	OBJECT IDENTIFIER ::={rulesetCompiler 2}

rulesetCompilerReaperSendBufVal	OBJECT-TYPE
	SYNTAX	 CounterBasedGauge64
	MAX-ACCESS read-only
	STATUS current
	DESCRIPTION "Reaper send buffer usage"

	::={rulesetCompilerReaperSendBuf 1}

rulesetCompilerReaperSendBufMax	OBJECT-TYPE
	SYNTAX	 CounterBasedGauge64
	MAX-ACCESS read-only
	STATUS current
	DESCRIPTION "Reaper send buffer usage"

	::={rulesetCompilerReaperSendBuf 3}

ipfix	OBJECT IDENTIFIER ::={sysdiag 139}

ipfixConnections	OBJECT IDENTIFIER ::={ipfix 1}

ipfixConnectionsVal	OBJECT-TYPE
	SYNTAX	 CounterBasedGauge64
	MAX-ACCESS read-only
	STATUS current
	DESCRIPTION "Connection table size"

	::={ipfixConnections 1}

ipfixConnectionsMax	OBJECT-TYPE
	SYNTAX	 CounterBasedGauge64
	MAX-ACCESS read-only
	STATUS current
	DESCRIPTION "Connection table size"

	::={ipfixConnections 3}

ipfixConnUpdates	OBJECT IDENTIFIER ::={ipfix 2}

ipfixConnUpdatesVal	OBJECT-TYPE
	SYNTAX	 Counter64
	MAX-ACCESS read-only
	STATUS current
	DESCRIPTION "Connection updates"

	::={ipfixConnUpdates 1}

ipfixConnUpdatesMom	OBJECT-TYPE
	SYNTAX	 CounterBasedGauge64
	MAX-ACCESS read-only
	STATUS current
	DESCRIPTION "Connection updates"

	::={ipfixConnUpdates 2}

ipfixConnUpdatesMax	OBJECT-TYPE
	SYNTAX	 CounterBasedGauge64
	MAX-ACCESS read-only
	STATUS current
	DESCRIPTION "Connection updates"

	::={ipfixConnUpdates 3}

ipfixExportedIpv4Records	OBJECT IDENTIFIER ::={ipfix 3}

ipfixExportedIpv4RecordsVal	OBJECT-TYPE
	SYNTAX	 Counter64
	MAX-ACCESS read-only
	STATUS current
	DESCRIPTION "Exported Records IPv4"

	::={ipfixExportedIpv4Records 1}

ipfixExportedIpv4RecordsMom	OBJECT-TYPE
	SYNTAX	 CounterBasedGauge64
	MAX-ACCESS read-only
	STATUS current
	DESCRIPTION "Exported Records IPv4"

	::={ipfixExportedIpv4Records 2}

ipfixExportedIpv4RecordsMax	OBJECT-TYPE
	SYNTAX	 CounterBasedGauge64
	MAX-ACCESS read-only
	STATUS current
	DESCRIPTION "Exported Records IPv4"

	::={ipfixExportedIpv4Records 3}

ipfixExportedIpv6Records	OBJECT IDENTIFIER ::={ipfix 4}

ipfixExportedIpv6RecordsVal	OBJECT-TYPE
	SYNTAX	 Counter64
	MAX-ACCESS read-only
	STATUS current
	DESCRIPTION "Exported Records IPv6"

	::={ipfixExportedIpv6Records 1}

ipfixExportedIpv6RecordsMom	OBJECT-TYPE
	SYNTAX	 CounterBasedGauge64
	MAX-ACCESS read-only
	STATUS current
	DESCRIPTION "Exported Records IPv6"

	::={ipfixExportedIpv6Records 2}

ipfixExportedIpv6RecordsMax	OBJECT-TYPE
	SYNTAX	 CounterBasedGauge64
	MAX-ACCESS read-only
	STATUS current
	DESCRIPTION "Exported Records IPv6"

	::={ipfixExportedIpv6Records 3}

ipfixExportedIpv4Sets	OBJECT IDENTIFIER ::={ipfix 5}

ipfixExportedIpv4SetsVal	OBJECT-TYPE
	SYNTAX	 Counter64
	MAX-ACCESS read-only
	STATUS current
	DESCRIPTION "Exported Sets IPv4"

	::={ipfixExportedIpv4Sets 1}

ipfixExportedIpv4SetsMom	OBJECT-TYPE
	SYNTAX	 CounterBasedGauge64
	MAX-ACCESS read-only
	STATUS current
	DESCRIPTION "Exported Sets IPv4"

	::={ipfixExportedIpv4Sets 2}

ipfixExportedIpv4SetsMax	OBJECT-TYPE
	SYNTAX	 CounterBasedGauge64
	MAX-ACCESS read-only
	STATUS current
	DESCRIPTION "Exported Sets IPv4"

	::={ipfixExportedIpv4Sets 3}

ipfixExportedIpv6Sets	OBJECT IDENTIFIER ::={ipfix 6}

ipfixExportedIpv6SetsVal	OBJECT-TYPE
	SYNTAX	 Counter64
	MAX-ACCESS read-only
	STATUS current
	DESCRIPTION "Exported Sets IPv6"

	::={ipfixExportedIpv6Sets 1}

ipfixExportedIpv6SetsMom	OBJECT-TYPE
	SYNTAX	 CounterBasedGauge64
	MAX-ACCESS read-only
	STATUS current
	DESCRIPTION "Exported Sets IPv6"

	::={ipfixExportedIpv6Sets 2}

ipfixExportedIpv6SetsMax	OBJECT-TYPE
	SYNTAX	 CounterBasedGauge64
	MAX-ACCESS read-only
	STATUS current
	DESCRIPTION "Exported Sets IPv6"

	::={ipfixExportedIpv6Sets 3}

ipfixExportedMsgs	OBJECT IDENTIFIER ::={ipfix 7}

ipfixExportedMsgsVal	OBJECT-TYPE
	SYNTAX	 Counter64
	MAX-ACCESS read-only
	STATUS current
	DESCRIPTION "Exported Ipfix Messages"

	::={ipfixExportedMsgs 1}

ipfixExportedMsgsMom	OBJECT-TYPE
	SYNTAX	 CounterBasedGauge64
	MAX-ACCESS read-only
	STATUS current
	DESCRIPTION "Exported Ipfix Messages"

	::={ipfixExportedMsgs 2}

ipfixExportedMsgsMax	OBJECT-TYPE
	SYNTAX	 CounterBasedGauge64
	MAX-ACCESS read-only
	STATUS current
	DESCRIPTION "Exported Ipfix Messages"

	::={ipfixExportedMsgs 3}




END
