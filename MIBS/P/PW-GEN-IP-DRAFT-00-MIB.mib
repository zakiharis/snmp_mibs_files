-- extracted from draft-nadeau-l2tpext-pw-l2tpv3-mib-01.txt
-- at Sat Jun 30 06:08:28 2007

  PW-GEN-IP-DRAFT-00-MIB DEFINITIONS ::= BEGIN

  IMPORTS  
     MODULE-IDENTITY, OBJECT-TYPE, Unsigned32, transmission  
        FROM SNMPv2-SMI                   -- [RFC2578] 

     MODULE-COMPLIANCE, OBJECT-GROUP  
        FROM SNMPv2-CONF                  -- [RFC2580]  

     StorageType, RowStatus  
        FROM SNMPv2-TC                    -- [RFC2579] 

     InterfaceIndexOrZero  
        FROM IF-MIB                       -- [RFC2863] 

     SnmpAdminString
        FROM SNMP-FRAMEWORK-MIB

     InetAddress, InetAddressType
        FROM INET-ADDRESS-MIB              -- [RFC4001]

     pwIndex                               -- [RFCxxxx] 
  -- RFC Editor: Please replace XXXX with RFC number & remove this 
  -- note.  
        FROM PW-STD-MIB  

  ;  

  pwGenIpDraft00MIB MODULE-IDENTITY  
     LAST-UPDATED "200702011200Z"  -- 01 Feb 2007 12:00:00 GMT
     ORGANIZATION    "IETF L2TP Working Group"
     CONTACT-INFO
               "Layer Two Tunneling Protocol Extensions WG
                Working Group Area:        Internet
                Working Group Name:        l2tpext
                General Discussion:        l2tp@l2tp.net"

     DESCRIPTION  
         "This MIB module complements the PW-STD-MIB module for PW   
          operation over IP.  

         Copyright (C) The Internet Society (2006).  This version  
         of this MIB module is part of RFC yyyy;  see the RFC  
         itself for full legal notices.  
         -- RFC Ed.: replace yyyy with actual RFC number & remove  
         -- this note  
         "        
     -- Revision history.  
      REVISION       "200702011200Z"  -- 01 Feb 2007 12:00:00 GMT
      DESCRIPTION  
          " First published as RFCWXYZ. "  
  -- RFC Editor: Please replace WXYZ with correct # and remove this 
  -- note 

    ::= { transmission 1 } 
  -- RFC Editor: To be assigned by IANA. Please replace XXX 
  -- with the assigned value and remove this note. 

  -- Top-level components of this MIB.  

                     

   -- Notifications  
   pwGenIpNotifications OBJECT IDENTIFIER   
                                 ::= { pwGenIpDraft00MIB 0 }  

  -- Tables, Scalars  
  pwGenIpObjects       OBJECT IDENTIFIER  
                                ::= { pwGenIpDraft00MIB 1 }  
  -- Conformance  
  pwGenIpConformance   OBJECT IDENTIFIER   
                                ::= { pwGenIpDraft00MIB 2 }  

   
  -- PW IP table  

  pwGenIpTable   OBJECT-TYPE  
     SYNTAX        SEQUENCE OF PwGenIpEntry  
     MAX-ACCESS    not-accessible  
     STATUS        current  
     DESCRIPTION  
         "This table contains the Pseudo wire objects for 
          Generic IP PSN type."
     ::= { pwGenIpObjects 2 }  

pwGenIpEntry   OBJECT-TYPE  
     SYNTAX        PwGenIpEntry  
     MAX-ACCESS    not-accessible  
     STATUS        current  
     DESCRIPTION  
          "A row in this table represents Generic parameters 
           specific to pseudo wire (PW) over IP PSN . 

           A row MUST be created automatically by the local agent 
           for every entry in the pwTable if the pwPsnType is   
           udpOverIp. Each entry is indexed by pwIndex, which uniquely

           identifies a singular PW.
          "  
     INDEX  { pwIndex }  

        ::= { pwGenIpTable 1 }  

  PwGenIpEntry ::= SEQUENCE {  
        pwGenSourceIpAddressType        InetAddressType,
        pwGenSourceIpAddress            InetAddress,
        pwGenIpTos                      Unsigned32,
        pwGenIpTosDropPrecedence        Unsigned32
     }  


  pwGenSourceIpAddressType OBJECT-TYPE
     SYNTAX InetAddressType
     MAX-ACCESS read-write
     STATUS current
     DESCRIPTION
         "This object indicates the type of IP address stored in
          pwGenSourceIpAddress."
     ::= { pwGenIpEntry 1  }


  pwGenSourceIpAddress OBJECT-TYPE
     SYNTAX InetAddress
     MAX-ACCESS read-write
     STATUS current
     DESCRIPTION
         "This object indicates source IP Address for PW having 
          pwPsnType= udpOverIp (3)"
     ::= { pwGenIpEntry 2  }

  pwGenIpTos OBJECT-TYPE
     SYNTAX Unsigned32 
     MAX-ACCESS read-write
     STATUS current
     DESCRIPTION
         "This object indicates TOS field value for PW having 
          pwPsnType= udpOverIp (3), IP precedence (bits 0-2 in IP 
          TOS byte),DSCP (bits 0-5 in IP TOS byte)."
     ::= { pwGenIpEntry 3  }

   pwGenIpTosDropPrecedence   OBJECT-TYPE
       SYNTAX Unsigned32 
       MAX-ACCESS read-write
       STATUS current
       DESCRIPTION
           "In implementations that support two level of drop
            precedence marking, this object defines the DSCP 
            or TOS field to be used for packets with higher drop 
            precedence compared to packets marked with pwGenIpTos, 
            otherwise this object should return the the value equal 
            to pwGenIpTos ."

      ::= { pwGenIpEntry 4 }

  -- End of PW IP table  



  -- conformance information  

  pwGenIpGroups      OBJECT IDENTIFIER ::= { pwGenIpConformance 1 }  
  pwGenIpCompliances OBJECT IDENTIFIER ::= { pwGenIpConformance 2 }  

  -- Compliance requirement for fully compliant implementations.  

  pwGenIpModuleFullCompliance MODULE-COMPLIANCE  
      STATUS  current  
      DESCRIPTION  
              "The compliance statement for agents that provide full  
               support for PW-IP MIB Module. Such devices can  
               then be monitored and also be configured using  
               this MIB module."  

     MODULE  -- this module  
     MANDATORY-GROUPS { pwGenIpGroup
                       }  

      ::= { pwGenIpCompliances 1 }  

  -- Compliance requirement for Read Only compliant implementations.  

  pwGenIpModuleReadOnlyCompliance MODULE-COMPLIANCE  
      STATUS  current  
      DESCRIPTION  
              "The compliance statement for agents that provide read  
               only support for PW-IP MIB Module. Such devices can  
               then be monitored but cannot be configured using this  
               MIB module."  

                     

     MODULE  -- this module  
     MANDATORY-GROUPS { pwGenIpGroup 
                       }  


      ::= { pwGenIpCompliances 2 }  

  -- Units of conformance.  

  pwGenIpGroup OBJECT-GROUP   
     OBJECTS {  
        pwGenSourceIpAddressType,
        pwGenSourceIpAddress,
        pwGenIpTos,
        pwGenIpTosDropPrecedence
            }  
     STATUS  current  
     DESCRIPTION  
         "Collection of objects needed for PW over IP PSN   
          configuration."  
     ::= { pwGenIpGroups 1 }  

                     
END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE  
--    REPRESENTS OR IS SPONSORED BY (IF ANY), THE INTERNET SOCIETY, THE
--    IETF TRUST AND THE INTERNET ENGINEERING TASK FORCE DISCLAIM ALL
--    WARRANTIES, EXPRESS OR IMPLIED, INCLUDING BUT NOT LIMITED TO ANY
--    WARRANTY THAT THE USE OF THE INFORMATION HEREIN WILL NOT INFRINGE
--    ANY RIGHTS OR ANY IMPLIED WARRANTIES OF MERCHANTABILITY OR FITNESS
--    FOR A PARTICULAR PURPOSE.
-- 
-- 
-- 12 Intellectual Property Notice 
--    
--    The IETF takes no position regarding the validity or scope of any
--    Intellectual Property Rights or other rights that might be claimed to
--    pertain to the implementation or use of the technology described in
--    this document or the extent to which any license under such rights
--    might or might not be available; nor does it represent that it has
--    made any independent effort to identify any such rights. Information
--    on the procedures with respect to rights in RFC documents can be
--    found in BCP 78 and BCP 79.
--    Copies of IPR disclosures made to the IETF Secretariat and any
--    assurances of licenses to be made available, or the result of an
--    attempt made to obtain a general license or permission for the use 
--    of such proprietary rights by implementers or users of this
--    specification can be obtained from the IETF on-line IPR repository
--    at http://www.ietf.org/ipr.
-- 
--    The IETF invites any interested party to bring to its attention any
--    copyrights, patents or patent applications, or other proprietary
--    rights that may cover technology that may be required to implement
--    this standard. Please address the information to the IETF at ietf-
--    ipr@ietf.org.
-- 
-- Disclaimer of Validity
-- 
--    This document and the information contained herein are provided
--    on an "AS IS" basis and THE CONTRIBUTOR, THE ORGANIZATION HE/SHE
--    REPRESENTS OR IS SPONSORED BY (IF ANY), THE INTERNET SOCIETY, THE
--    IETF TRUST AND THE INTERNET ENGINEERING TASK FORCE DISCLAIM ALL
--    WARRANTIES, EXPRESS OR IMPLIED, INCLUDING BUT NOT LIMITED TO ANY
--    WARRANTY THAT THE USE OF THE INFORMATION HEREIN WILL NOT INFRINGE
--    ANY RIGHTS OR ANY IMPLIED WARRANTIES OF MERCHANTABILITY OR FITNESS
--    FOR A PARTICULAR PURPOSE.
