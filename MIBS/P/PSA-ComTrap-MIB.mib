PSA-ComTrap-MIB DEFINITIONS ::= BEGIN

--PRIMEQUEST system management MIB for Partition
--
--
--$Copyright$
--Copyright Fujitsu Limited 2004 - 2009
--All rights reserved
--
--
--MIB Revision: 02000002
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaComTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise        OBJECT IDENTIFIER  ::={ partition 201 }
     psaComTrap                OBJECT IDENTIFIER  ::={ partitionEnterprise 1 }
     psaLinLanComTrap          OBJECT IDENTIFIER  ::={ partitionEnterprise 2 }
     psaLinIntelE100Trap       OBJECT IDENTIFIER  ::={ partitionEnterprise 3 }
     psaLinIntelE1000Trap      OBJECT IDENTIFIER  ::={ partitionEnterprise 4 }
     psaLinBcm5700Trap         OBJECT IDENTIFIER  ::={ partitionEnterprise 5 }
     psaLinEmulexTrap          OBJECT IDENTIFIER  ::={ partitionEnterprise 6 }
     psaLinLsiLogicTrap        OBJECT IDENTIFIER  ::={ partitionEnterprise 7 }
     psaLinScsiComTrap         OBJECT IDENTIFIER  ::={ partitionEnterprise 8 }
     psaLinGrmpdTrap           OBJECT IDENTIFIER  ::={ partitionEnterprise 9 }
     psaLinGdsTrap             OBJECT IDENTIFIER  ::={ partitionEnterprise 10 }
     psaLinGlsTrap             OBJECT IDENTIFIER  ::={ partitionEnterprise 11 }
     psaLinTg3Trap             OBJECT IDENTIFIER  ::={ partitionEnterprise 12 }
     psaLinIbTrap              OBJECT IDENTIFIER  ::={ partitionEnterprise 13 }
     psaLinXframe2Trap         OBJECT IDENTIFIER  ::={ partitionEnterprise 14 }
     psaGschTrap               OBJECT IDENTIFIER  ::={ partitionEnterprise 15 }
     psaLinIntelE1000ETrap     OBJECT IDENTIFIER  ::={ partitionEnterprise 16 }
     psaLinIntelIgbTrap        OBJECT IDENTIFIER  ::={ partitionEnterprise 17 }
     psaLinSvsRaidTrap         OBJECT IDENTIFIER  ::={ partitionEnterprise 18 }
     psaExternalFileUnitTrap   OBJECT IDENTIFIER  ::={ partitionEnterprise 101 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

trapFlagcode OBJECT-TYPE
   SYNTAX   DisplayString
   ACCESS   not-accessible
   STATUS   mandatory
   DESCRIPTION " "
   ::= { trapVarDivInfo 28 }

--***************************************************************************************
--
--FUJITSU PRIMEQUEST system management TRAP definition for Partition
--	Trap enterprise:	psaComTrap (.1.3.6.1.4.1.211.1.31.1.2.201.1)
--
--***************************************************************************************

psaDetectEvent0 TRAP-TYPE
   ENTERPRISE   psaComTrap
   VARIABLES {
      trapPartitionName,
      trapPartitionId,
      trapEventLevel,
      trapEventId,
      trapUnitName,
      trapMmbVip
   }
   DESCRIPTION "MMB error occurred (ipmi command failed)"
   --#TYPE			"Psa Detect Event 0"
   --#SUMMARY		"%s(PID=%d) %s %d %s error occurred (ipmi command failed)"
   --#ARGUMENTS		{ 0, 1, 2, 3, 4 }
   --#SEVERITY		MAJOR
   ::= 9990

psaDetectEvent1 TRAP-TYPE
   ENTERPRISE   psaComTrap
   VARIABLES {
      trapPartitionName,
      trapPartitionId,
      trapEventLevel,
      trapEventId,
      trapUnitName,
      trapMmbVip
   }
   DESCRIPTION "BMC error occurred (ipmi command failed)"
   --#TYPE			"Psa Detect Event 1"
   --#SUMMARY		"%s(PID=%d) %s %d %s error occurred (ipmi command failed)"
   --#ARGUMENTS		{ 0, 1, 2, 3, 4 }
   --#SEVERITY		MAJOR
   ::= 9991

psaDetectEvent2 TRAP-TYPE
   ENTERPRISE   psaComTrap
   VARIABLES {
      trapPartitionName,
      trapPartitionId,
      trapEventLevel,
      trapEventId,
      trapUnitName,
      trapMmbVip
   }
   DESCRIPTION "MMB or BMC error occurred (ipmi command failed)"
   --#TYPE			"Psa Detect Event 2"
   --#SUMMARY		"%s(PID=%d) %s %d %s error occurred (ipmi command failed)"
   --#ARGUMENTS		{ 0, 1, 2, 3, 4 }
   --#SEVERITY		MAJOR
   ::= 9992

psaDetectEvent3 TRAP-TYPE
   ENTERPRISE   psaComTrap
   VARIABLES {
      trapPartitionName,
      trapPartitionId,
      trapEventLevel,
      trapEventId,
      trapUnitName,
      trapMmbVip
   }
   DESCRIPTION "Management LAN disconnected"
   --#TYPE			"Psa Detect Event 3"
   --#SUMMARY		"%s(PID=%d) %s %d %s Management LAN disconnected"
   --#ARGUMENTS		{ 0, 1, 2, 3, 4 }
   --#SEVERITY		MAJOR
   ::= 9993

cpuCorrectableError TRAP-TYPE
   ENTERPRISE   psaComTrap
   VARIABLES {
      trapPartitionName,
      trapPartitionId,
      trapEventLevel,
      trapEventId,
      trapUnitName,
      trapModelName,
      trapStepping,
      trapMmbVip
   }
   DESCRIPTION "The correctable error exceeded the threshold."
   --#TYPE			"Cpu Correctable Error"
   --#SUMMARY		"%s(PID=%d) %s %d %s The correctable error exceeded the threshold model=%s stepping=%s"
   --#ARGUMENTS		{ 0, 1, 2, 3, 4, 5, 6 }
   --#SEVERITY		MINOR
   ::= 10000

dimmCorrectableError TRAP-TYPE
   ENTERPRISE   psaComTrap
   VARIABLES {
      trapPartitionName,
      trapPartitionId,
      trapEventLevel,
      trapEventId,
      trapUnitName,
      trapPartNo,
      trapSerialNo,
      trapMmbVip
   }
   DESCRIPTION "The correctable error (1-bit error) exceeded the threshold."
   --#TYPE			"Dimm Correctable Error"
   --#SUMMARY		"%s(PID=%d) %s %d %s The correctable error (1-bit error) exceeded the threshold part-no=%s serial-no=%s"
   --#ARGUMENTS		{ 0, 1, 2, 3, 4, 5, 6 }
   --#SEVERITY		MINOR
   ::= 10100

dimmUncorrectableError TRAP-TYPE
   ENTERPRISE   psaComTrap
   VARIABLES {
      trapPartitionName,
      trapPartitionId,
      trapEventLevel,
      trapEventId,
      trapUnitName,
      trapPartNo,
      trapSerialNo,
      trapMmbVip
   }
   DESCRIPTION "The uncorrectable error (2-bit error) exceeded the threshold."
   --#TYPE			"Dimm Uncorrectable Error"
   --#SUMMARY		"%s(PID=%d) %s %d %s The uncorrectable error (2-bit error) exceeded the threshold part-no=%s serial-no=%s"
   --#ARGUMENTS		{ 0, 1, 2, 3, 4, 5, 6 }
   --#SEVERITY		MINOR
   ::= 10200

flnCorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fln CorrectableError"
   --#SUMMARY		"%s(PID=%d) %s %d %s The correctable error exceeded the threshold part-no=%s serial-no=%s"
   --#ARGUMENTS		{ 0, 1, 2, 3, 4, 5, 6 }
   --#SEVERITY		MINOR
   ::= 10300

ldx0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx0 Correctable Error"
   --#SUMMARY		"%s(PID=%d) %s %d %s The correctable error exceeded the threshold part-no=%s serial-no=%s"
   --#ARGUMENTS		{ 0, 1, 2, 3, 4, 5, 6 }
   --#SEVERITY		MINOR
   ::= 10310

ldx1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx1 Correctable Error"
   --#SUMMARY		"%s(PID=%d) %s %d %s The correctable error exceeded the threshold part-no=%s serial-no=%s"
   --#ARGUMENTS		{ 0, 1, 2, 3, 4, 5, 6 }
   --#SEVERITY		MINOR
   ::= 10311

ldx2CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx2 Correctable Error"
   --#SUMMARY		"%s(PID=%d) %s %d %s The correctable error exceeded the threshold part-no=%s serial-no=%s"
   --#ARGUMENTS		{ 0, 1, 2, 3, 4, 5, 6 }
   --#SEVERITY		MINOR
   ::= 10312

ldx3CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx3 Correctable Error"
   --#SUMMARY		"%s(PID=%d) %s %d %s The correctable error exceeded the threshold part-no=%s serial-no=%s"
   --#ARGUMENTS		{ 0, 1, 2, 3, 4, 5, 6 }
   --#SEVERITY		MINOR
   ::= 10313

flnGac0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fln Gac0 Correctable Error"
   --#SUMMARY		"%s(PID=%d) %s %d %s The correctable error exceeded the threshold part-no=%s serial-no=%s"
   --#ARGUMENTS		{ 0, 1, 2, 3, 4, 5, 6 }
   --#SEVERITY		MINOR
   ::= 10320

flnGac1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fln Gac1Correctable Error"
   --#SUMMARY		"%s(PID=%d) %s %d %s The correctable error exceeded the threshold part-no=%s serial-no=%s"
   --#ARGUMENTS		{ 0, 1, 2, 3, 4, 5, 6 }
   --#SEVERITY		MINOR
   ::= 10321

ldx0Gdx0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx0 Gdx0 Correctable Error"
   --#SUMMARY		"%s(PID=%d) %s %d %s The correctable error exceeded the threshold part-no=%s serial-no=%s"
   --#ARGUMENTS		{ 0, 1, 2, 3, 4, 5, 6 }
   --#SEVERITY		MINOR
   ::= 10330

ldx1Gdx1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx1 Gdx1 Correctable Error"
   --#SUMMARY		"%s(PID=%d) %s %d %s The correctable error exceeded the threshold part-no=%s serial-no=%s"
   --#ARGUMENTS		{ 0, 1, 2, 3, 4, 5, 6 }
   --#SEVERITY		MINOR
   ::= 10331

ldx2Gdx2CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx2 Gdx2 Correctable Error"
   --#SUMMARY		"%s(PID=%d) %s %d %s The correctable error exceeded the threshold part-no=%s serial-no=%s"
   --#ARGUMENTS		{ 0, 1, 2, 3, 4, 5, 6 }
   --#SEVERITY		MINOR
   ::= 10332

ldx3Gdx3CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx3 Gdx3 Correctable Error"
   --#SUMMARY		"%s(PID=%d) %s %d %s The correctable error exceeded the threshold part-no=%s serial-no=%s"
   --#ARGUMENTS		{ 0, 1, 2, 3, 4, 5, 6 }
   --#SEVERITY		MINOR
   ::= 10333

ldx1Gdx0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx1 Gdx0 Correctable Error"
   --#SUMMARY		"%s(PID=%d) %s %d %s The correctable error exceeded the threshold part-no=%s serial-no=%s"
   --#ARGUMENTS		{ 0, 1, 2, 3, 4, 5, 6 }
   --#SEVERITY		MINOR
   ::= 10334

ldx2Gdx1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx2 Gdx1 Correctable Error"
   --#SUMMARY		"%s(PID=%d) %s %d %s The correctable error exceeded the threshold part-no=%s serial-no=%s"
   --#ARGUMENTS		{ 0, 1, 2, 3, 4, 5, 6 }
   --#SEVERITY		MINOR
   ::= 10335

ldx3Gdx1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Ldx3 Gdx1 Correctable Error"
   --#SUMMARY		"%s(PID=%d) %s %d %s The correctable error exceeded the threshold part-no=%s serial-no=%s"
   --#ARGUMENTS		{ 0, 1, 2, 3, 4, 5, 6 }
   --#SEVERITY		MINOR
   ::= 10336

fliCorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Correctable Error"
   --#SUMMARY		"%s(PID=%d) %s %d %s The correctable error exceeded the threshold part-no=%s serial-no=%s"
   --#ARGUMENTS		{ 0, 1, 2, 3, 4, 5, 6 }
   --#SEVERITY		MINOR
   ::= 10400

flp0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Flp0 Correctable Error"
   --#SUMMARY		"%s(PID=%d) %s %d %s The correctable error exceeded the threshold part-no=%s serial-no=%s"
   --#ARGUMENTS		{ 0, 1, 2, 3, 4, 5, 6 }
   --#SEVERITY		MINOR
   ::= 10410

flp1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Flp1 Correctable Error"
   --#SUMMARY		"%s(PID=%d) %s %d %s The correctable error exceeded the threshold part-no=%s serial-no=%s"
   --#ARGUMENTS		{ 0, 1, 2, 3, 4, 5, 6 }
   --#SEVERITY		MINOR
   ::= 10411

fliGdx0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gdx0 Correctable Error"
   --#SUMMARY		"%s(PID=%d) %s %d %s The correctable error exceeded the threshold part-no=%s serial-no=%s"
   --#ARGUMENTS		{ 0, 1, 2, 3, 4, 5, 6 }
   --#SEVERITY		MINOR
   ::= 10420

fliGdx1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gdx1 Correctable Error"
   --#SUMMARY		"%s(PID=%d) %s %d %s The correctable error exceeded the threshold part-no=%s serial-no=%s"
   --#ARGUMENTS		{ 0, 1, 2, 3, 4, 5, 6 }
   --#SEVERITY		MINOR
   ::= 10421

fliGdx2CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gdx2 Correctable Error"
   --#SUMMARY		"%s(PID=%d) %s %d %s The correctable error exceeded the threshold part-no=%s serial-no=%s"
   --#ARGUMENTS		{ 0, 1, 2, 3, 4, 5, 6 }
   --#SEVERITY		MINOR
   ::= 10422

fliGdx3CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gdx3 Correctable Error"
   --#SUMMARY		"%s(PID=%d) %s %d %s The correctable error exceeded the threshold part-no=%s serial-no=%s"
   --#ARGUMENTS		{ 0, 1, 2, 3, 4, 5, 6 }
   --#SEVERITY		MINOR
   ::= 10423

fliGac0CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gac0 Correctable Error"
   --#SUMMARY		"%s(PID=%d) %s %d %s The correctable error exceeded the threshold part-no=%s serial-no=%s"
   --#ARGUMENTS		{ 0, 1, 2, 3, 4, 5, 6 }
   --#SEVERITY		MINOR
   ::= 10430

fliGac1CorrectableError TRAP-TYPE
   ENTERPRISE   psaComTrap
   VARIABLES {
      trapPartitionName,
      trapPartitionId,
      trapEventLevel,
      trapEventId,
      trapUnitName,
      trapModelNo,
      trapSerialNo,
      trapMmbVip
   }
   DESCRIPTION "The correctable error exceeded the threshold."
   --#TYPE			"Fli Gac1 Correctable Error"
   --#SUMMARY		"%s(PID=%d) %s %d %s The correctable error exceeded the threshold part-no=%s serial-no=%s"
   --#ARGUMENTS		{ 0, 1, 2, 3, 4, 5, 6 }
   --#SEVERITY		MINOR
   ::= 10431

smartEvent0 TRAP-TYPE
   ENTERPRISE   psaComTrap
   VARIABLES {
      trapPartitionName,
      trapPartitionId,
      trapEventLevel,
      trapEventId,
      trapUnitName,
      trapVendorId,
      trapCardName,
      trapSerialNo,
      trapMmbVip
   }
   DESCRIPTION "Failure Prediction Threshold Exceeded."
   --#TYPE			"Smart Event 0"
   --#SUMMARY		"%s(PID=%d) %s %d %s Failure Prediction Threshold Exceeded vendor=%s model=%s serial-no=%s"
   --#ARGUMENTS		{ 0, 1, 2, 3, 4, 5, 6, 7 }
   --#SEVERITY		MINOR
   ::= 10500

smartEvent1 TRAP-TYPE
   ENTERPRISE   psaComTrap
   VARIABLES {
      trapPartitionName,
      trapPartitionId,
      trapEventLevel,
      trapEventId,
      trapUnitName,
      trapVendorId,
      trapCardName,
      trapSerialNo,
      trapMmbVip
   }
   DESCRIPTION "Failure Prediction Threshold Exceeded."
   --#TYPE			"Smart Event 1"
   --#SUMMARY		"%s(PID=%d) %s %d %s Failure Prediction Threshold Exceeded vendor=%s model=%s serial-no=%s"
   --#ARGUMENTS		{ 0, 1, 2, 3, 4, 5, 6, 7 }
   --#SEVERITY		MINOR
   ::= 10501

rasToolEvent0 TRAP-TYPE
   ENTERPRISE   psaComTrap
   VARIABLES {
      trapPartitionName,
      trapPartitionId,
      trapEventLevel,
      trapEventId,
      trapUnitName,
      trapSuspect,
      trapVendorId,
      trapDeviceId,
      trapRevision,
      trapMmbVip
   }
   DESCRIPTION "RASStatusCheck:RAID BBU announcement of the remaining time of the operating life"
   --#TYPE			"Ras Tool Event 0"
   --#SUMMARY		"%s(PID=%d) %s %d %s RASStatusCheck:%s RAID BBU announcement of the remaining time of the operating life vendor-id=%s device-id=%s revision=%s"
   --#ARGUMENTS		{ 0, 1, 2, 3, 4, 5, 6, 7, 8 }
   --#SEVERITY		MINOR
   ::= 10600

rasToolEvent1 TRAP-TYPE
   ENTERPRISE   psaComTrap
   VARIABLES {
      trapPartitionName,
      trapPartitionId,
      trapEventLevel,
      trapEventId,
      trapUnitName,
      trapSuspect,
      trapVendorId,
      trapDeviceId,
      trapRevision,
      trapMmbVip
   }
   DESCRIPTION "RASStatusCheck:RAID BBU exceeded the operating life"
   --#TYPE			"Ras Tool Event 1"
   --#SUMMARY		"%s(PID=%d) %s %d %s RASStatusCheck:%s RAID BBU exceeded the operating life vendor-id=%s device-id=%s revision=%s"
   --#ARGUMENTS		{ 0, 1, 2, 3, 4, 5, 6, 7, 8 }
   --#SEVERITY		MAJOR
   ::= 10601

rasToolEvent2 TRAP-TYPE
   ENTERPRISE   psaComTrap
   VARIABLES {
      trapPartitionName,
      trapPartitionId,
      trapEventLevel,
      trapEventId,
      trapUnitName,
      trapMmbVip
   }
   DESCRIPTION "RASStatusCheck: UPS BBU announcement of the remaining time of the operating life"
   --#TYPE			"Ras Tool Event 2"
   --#SUMMARY		"%s(PID=%d) %s %d %s RASStatusCheck: UPS BBU announcement of the remaining time of the operating life"
   --#ARGUMENTS		{ 0, 1, 2, 3, 4 }
   --#SEVERITY		MINOR
   ::= 10602

rasToolEvent3 TRAP-TYPE
   ENTERPRISE   psaComTrap
   VARIABLES {
      trapPartitionName,
      trapPartitionId,
      trapEventLevel,
      trapEventId,
      trapUnitName,
      trapMmbVip
   }
   DESCRIPTION "RASStatusCheck: UPS BBU exceeded the operating life"
   --#TYPE			"Ras Tool Event 3"
   --#SUMMARY		"%s(PID=%d) %s %d %s RASStatusCheck: UPS BBU exceeded the operating life"
   --#ARGUMENTS		{ 0, 1, 2, 3, 4 }
   --#SEVERITY		MAJOR
   ::= 10603

END
