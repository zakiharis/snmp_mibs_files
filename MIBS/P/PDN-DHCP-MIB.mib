-- ===================================================================
-- == Copyright (C) 2004 Paradyne Corporation.                      ==
-- ===================================================================

PDN-DHCP-MIB DEFINITIONS ::= BEGIN

IMPORTS
   MODULE-IDENTITY, OBJECT-TYPE
      FROM SNMPv2-SMI
   OBJECT-GROUP, MODULE-COMPLIANCE
      FROM SNMPv2-CONF
   SwitchState
       FROM PDN-TC
   dot1qVlanStaticEntry
       FROM Q-BRIDGE-MIB  
   pdn-common
      FROM PDN-HEADER-MIB;
        
pdnDhcpMIB MODULE-IDENTITY
   LAST-UPDATED "200409130000Z"  -- September 13, 2004
   ORGANIZATION "Paradyne Networks
                 MIB Working Group
                 Other information about group editing the MIB"
   CONTACT-INFO "Paradyne Networks, Inc.
                 8545 126th Avenue North
                 Largo, FL 33733
                 www.paradyne.com
        
                 General Comments to: mibwg_team@paradyne.com

                 Editor
                    Clay Sikes"

   DESCRIPTION  "The MIB module provides objects to manage an 
                 interface's Dynamic Host Configuration Protocol 
                 (DHCP)."

   REVISION     "200409140000Z"  -- September 13, 2004
   DESCRIPTION  "Initial release."

::=  { pdn-common 57 }



-- ====================================================================
-- == Define groups for Notifications, MIB Objects, Accessible for   ==
-- == Notifications (AFNs), and Conformance.                         ==
-- == These may just be place holders.                               ==
-- ====================================================================
pdnDhcpNotifications OBJECT IDENTIFIER ::= { pdnDhcpMIB 0 }
pdnDhcpObjects       OBJECT IDENTIFIER ::= { pdnDhcpMIB 1 }
pdnDhcpAFNs          OBJECT IDENTIFIER ::= { pdnDhcpMIB 2 } 
pdnDhcpConformance   OBJECT IDENTIFIER ::= { pdnDhcpMIB 3 }




-- ====================================================================
-- ==                  Textual Conventions                           ==
-- ====================================================================
-- None defined.




-- ====================================================================
-- ==                  MIB Objects                                   ==
-- ====================================================================


-- ===================================================================
-- == pdnDhcpVlanConfigTable                                        ==
-- ===================================================================
pdnDhcpVlanConfigTable  OBJECT-TYPE
   SYNTAX      SEQUENCE OF PdnDhcpVlanConfigEntry
   MAX-ACCESS  not-accessible
   STATUS      current
   DESCRIPTION "The PDN DHCP VLAN Configuration Table.  This table
                manages DHCP configuration options.  The index allows
                the configuration to be applied on a per VLAN basis."
   ::= { pdnDhcpObjects 1 }

pdnDhcpVlanConfigEntry  OBJECT-TYPE
   SYNTAX      PdnDhcpVlanConfigEntry
   MAX-ACCESS  not-accessible
   STATUS      current
   DESCRIPTION "An entry in the PDN DHCP VLAN Configuration Table."
   AUGMENTS    { dot1qVlanStaticEntry }
   ::= { pdnDhcpVlanConfigTable 1 }

PdnDhcpVlanConfigEntry ::=
   SEQUENCE {
      pdnDhcpVlanConfigOption82      SwitchState
   }

pdnDhcpVlanConfigOption82  OBJECT-TYPE
   SYNTAX      SwitchState
   MAX-ACCESS  read-create
   STATUS      current
   DESCRIPTION "The DHCP Relay Agent Information (Option 82) circuit
                identifier suboption.  When enabled, Option82  will be
                supported.  When disabled, Option 82 will not be
                supported."
   DEFVAL      { disabled }
   ::= { pdnDhcpVlanConfigEntry 1 }



-- ====================================================================
-- ==                  Accessible for Notifications (AFNs)           ==
-- ====================================================================
-- None defined



-- ===================================================================
-- ==                  Traps/Notifications                          ==
-- ===================================================================
-- None defined



-- ====================================================================
-- ==                  Conformance Information                       ==
-- ====================================================================

pdnDhcpCompliances  OBJECT IDENTIFIER ::= { pdnDhcpConformance 1 }
pdnDhcpGroups       OBJECT IDENTIFIER ::= { pdnDhcpConformance 2 }


-- ===========================
-- == Compliance Statements ==
-- ===========================


pdnDhcpCompliance  MODULE-COMPLIANCE
   STATUS      current
   DESCRIPTION "The compliance statement for network elements 
                implementing DHCP."
   MODULE      -- this module
   -- No mandatory groups are specified.    

   GROUP       pdnDhcpVlanConfigOpt82Group
   DESCRIPTION "This group is only required for implementations that
                need to configure DHCP Option 82 on a per-VLAN basis."
    ::= { pdnDhcpCompliances 1 }


-- ==========================
-- == Units of Conformance ==
-- ==========================

pdnDhcpObjGroups   OBJECT IDENTIFIER ::= { pdnDhcpGroups 1 }
pdnDhcpAfnGroups   OBJECT IDENTIFIER ::= { pdnDhcpGroups 2 }
pdnDhcpNtfyGroups  OBJECT IDENTIFIER ::= { pdnDhcpGroups 3 }


-- ===================
-- == Object Groups ==
-- ===================


pdnDhcpVlanConfigOpt82Group  OBJECT-GROUP
   OBJECTS {
      pdnDhcpVlanConfigOption82
   }
   STATUS      current
   DESCRIPTION "Configures DHCP Option 82 on a per-VLAN basis."
   ::= { pdnDhcpObjGroups 2 }



-- =========================================
-- == Accessible for Notifications Groups ==
-- =========================================
-- None defined



-- =========================
-- == Notification Groups ==
-- =========================
-- None defined




-- =========
-- == END ==
-- =========
END
