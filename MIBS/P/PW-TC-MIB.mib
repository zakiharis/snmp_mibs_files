-- extracted from draft-ietf-pwe3-pw-tc-mib-02.txt
-- at Thu Oct 23 06:15:14 2003

PW-TC-MIB DEFINITIONS ::= BEGIN

IMPORTS
   MODULE-IDENTITY, Unsigned32, Integer32, experimental
      FROM SNMPv2-SMI

   TEXTUAL-CONVENTION, TruthValue
      FROM SNMPv2-TC;

pwTCMIB MODULE-IDENTITY
   LAST-UPDATED "200307281200Z"  -- 28 July 2003 12:00:00 GMT
   ORGANIZATION "Pseudo Wire Edge to Edge Emulation (PWE3) Working
                 Group"
   CONTACT-INFO
   "         Thomas D. Nadeau
     Postal: Cisco Systems, Inc.
             250 Apollo Drive
             Chelmsford, MA 01824
     Tel:    +1-978-497-3051
     Email:  tnadeau@cisco.com

             Dave Danenberg
     Postal: Litchfield Communications, Inc.
             76 Westbury Park Rd
             Princeton Building East
             Watertown, CT 06795
     Tel:    +1-860-945-1573 x3180
     Email:  dave_danenberg@litchfieldcomm.com
 
             David Zelig
     Postal: Corrigent Systems.
             126, Yigal Alon St.
             Tel Aviv, ISRAEL
             Phone: +972-3-6945273
     E-mail: davidz@corrigent.com

             Andrew G. Malis 
     Postal: Tellabs, Inc. 
             2730 Orchard Parkway 
             San Jose, CA 95134 
     Email:  Andy.Malis@tellabs.com
       
     PWE3 Working Group Mailing List: pwe3@ietf.org"

   DESCRIPTION
       "This MIB Module provides Textual Conventions
        and OBJECT-IDENTITY Objects to be used PW services."

   -- Revision history.

   REVISION "200307281200Z"  -- 28 July 2003 12:00:00 GMT
   DESCRIPTION "Adding objects to cover new control draft. 
      Adapt VC types for current values in WG documents."

   REVISION "200305011200Z"  -- 1 May 2003 12:00:00 GMT
   DESCRIPTION "Adding PwVcAttachmentIdentifierType, 
      Adapt VC types for current values in WG documents."

   REVISION "0205281200Z"  -- 28 May 2002 12:00:00 GMT
   DESCRIPTION "Adding PwVcType, and enhance some descriptions."
   
   REVISION "0201301200Z"  -- 30 January 2002 12:00:00 GMT
   DESCRIPTION "Adding PwVcVlanCfg, PwAddressType and 
                PwOperStatus."

   REVISION "200112201200Z"  -- 20 Dec 2001 12:00:00 GMT
   DESCRIPTION "Remove PwVcInstance"

   REVISION "200107121200Z"  -- 12 July 2001 12:00:00 GMT
   DESCRIPTION "Initial version."

   ::= { pwMIB 1 } -- pwMIB To Be Assigned by IANA

pwMIB OBJECT IDENTIFIER
       ::= { experimental 8888 } -- To be assigned by IANA

-- Textual Conventions defined below are organized alphabetically

PwGroupID ::= TEXTUAL-CONVENTION
   STATUS      current
   DESCRIPTION
        "An administrative identification mechanism for grouping a
         set of service-specific pseudo-wire services. May only
         have local significance."
   SYNTAX  Unsigned32

PwVcIDType ::= TEXTUAL-CONVENTION
   STATUS      current
   DESCRIPTION
        "Virtual Circuit Identifier. Used to identify the VC 
         (together with some other fields) in the signaling 
         session. Zero if the VC is set-up manually."
   SYNTAX  Unsigned32

PwVcIndexType ::= TEXTUAL-CONVENTION
   STATUS      current
   DESCRIPTION
        "Virtual Circuit Index. Locally unique index for indexing
         several MIB tables associated with a particular VC."
   SYNTAX  Unsigned32

PwVcVlanCfg ::= TEXTUAL-CONVENTION
   STATUS      current
   DESCRIPTION
        "VLAN configuration for Ethernet PW. 
         Values between 0 to 4095 indicate the actual VLAN field
         value. 
         A value of 4096 indicates that the object refer to 
         untagged frames, i.e. frames without 802.1Q field.
         A value of 4097 indicates that the object is not 
         relevant."
   SYNTAX  Integer32 (0..4097)

 PwOperStatus ::= TEXTUAL-CONVENTION
   STATUS      current
   DESCRIPTION
      "Indicate the operational status of the PW VC.
      
      - up:             Ready to pass packets. 
      - down:           If PW signaling has not yet finished, or
                        indications available at the service 
                        level indicate that the VC is not 
                        passing packets.
      - testing:        If AdminStatus at the PW level is set to 
                        test.
      - dormant:        The PW is not available because of the
                        required resources are occupied PW with 
                        higher priority PWs .
      - notPresent:     Some component is missing to accomplish 
                        the set up of the PW.
      - lowerLayerDown: The underlying PSN or outer tunnel is not
                        in OperStatus 'up'. 
      "
 SYNTAX   INTEGER {
     up(1),
     down(2),
     testing(3),
     unknown(4),
     dormant(5),
     notPresent(6),
     lowerLayerDown(7)
     }      

 PwVcType ::= TEXTUAL-CONVENTION
   STATUS      current
   DESCRIPTION
      "Indicate the VC type (i.e. the carried service).
       Note: the exact set of VC types is yet to be worked 
       out by the WG.
      "
 SYNTAX   INTEGER {
    other(0),
    frameRelayDlci(1),
    atmAal5SduVcc(2),
    atmTransparent(3),
    ethernetTagged(4),
    ethernet(5),
    hdlc(6),
    ppp(7),
    cem(8),  -- old format
    atmCellNto1Vcc(9),
    atmCellNto1Vpc(10),
	ipLayer2Transport(11),
	atmCell1to1Vcc(12),
    atmCell1to1Vpc(13),
    atmAal5PduVcc(14),
	frameRelayPortMode(15),
	cep(16)
     }      

PwVcAttachmentIdentifierType ::= TEXTUAL-CONVENTION

   STATUS      current
   DESCRIPTION
      "An octet string used in the generalized FEC element for
       identifying attachment forwarder and groups. The NULL 
       identifier is of zero length.
      "
 SYNTAX    OCTET STRING (SIZE (0..255))

PwVcCw ::= TEXTUAL-CONVENTION

   STATUS      current
   DESCRIPTION
      "If true, indicate the existence or configuration 
      of control word. 
      "
 SYNTAX    TruthValue

PwVcRemoteCwStatus ::= TEXTUAL-CONVENTION

   STATUS      current
   DESCRIPTION
      "Indicate the status of the control word as advertized by 
       the remote.  
	   notApplicable is set by the agent for manulaly configured PW.

	   waitingForNextMsg indicate that the node is waiting for
another 
	   label mapping from the remote.
	   sentWrongBitErrorCode indicate that the local node has
notified the
	   peer about mismatch in the C bit.
	   rxWithdrawWithWrongBitErrorCode indicate that a withdraw
message 
	   has been recieved with wrong C-bit error code.
	   illegalRecievedBit indicate a C bit configuration with the
remote
	   which is not compatible with the PW type.
	   sameAsSent indicate consistent C bit setting between the
peers.
	   notYetKnown indicate that a label mapping has not yet
recieved
	   from the peer.
      "
 SYNTAX    INTEGER {
              notApplicable (0),
              waitingForNextMsg (1),
              sentWrongBitErrorCode (2),
              rxWithdrawWithWrongBitErrorCode (3),
			  illegalRecievedBit (4),
              sameAsSent (5),
              notYetKnown(6)
			  }

PwVcCapabilities ::= TEXTUAL-CONVENTION
   STATUS      current
   DESCRIPTION
      "Indicate the optional capabilities of the control protocol.
       A value of zero indicate the basic LDP PW signaling. 
       Values may be added in the future based on 
	   new capabilities introduced in IETF documents.
      "
 SYNTAX   BITS {
    pwStatusIndication (0)
     }      

PwVcStatus ::= TEXTUAL-CONVENTION
   STATUS      current
   DESCRIPTION
      "The status of the PW and the interfaces affecting this PW.
      "
 SYNTAX   BITS {
    pwNotForwarding (0),
    customerFacingPwRxFault	(1),
    customerFacingPwTxFault	(2),
    psnFacingPwRxFault	(3),
    psnFacingPwTxFault	(4)
     }      

PwVcFragSize ::= TEXTUAL-CONVENTION
   STATUS      current
   DESCRIPTION
      "If set to value other than zero, it indicates desired
fragmantation
       to the value set. If set to zero, fragmantation is not desired
for
       PSN bound packets. 
      "
 SYNTAX   Unsigned32 

PwVcFragStatus ::= TEXTUAL-CONVENTION
   STATUS      current
   DESCRIPTION
      "The status of the fragmantation process based on local
configuration 
       and the remote capability.

       noFragmantation bit indicate that local configuration is for no
fragmantation.
       cfgFragGreaterThanPsnMtu bit indicate the local desire to
fragment, but the 
       fragamentation size desired is greater than the MTU available at
the PSN between 
       peers. Fragmantation is not done in this case.
cfgFragButRemoteIncapable bit 
       indicate local configuration indicate the desire for
fragmantation but the remote
       is not capable of fragmantation. remoteFragCapable bit indicate
that the remote 
       has advertized it's fragmantation capability.
       fragmantationEnabled bit indicate that both the local was
configured for 
       fragmantation and the remote has the cabability
       to accept fragmented packets.
      "
 SYNTAX   BITS {
    noFragmantation (0),
    cfgFragGreaterThanPsnMtu (1),
    cfgFragButRemoteIncapable (2),
    remoteFragCapable (3),
	fragmantationEnabled (4)
     }      

END

-- 
--    Copyright (C) The Internet Society (2000).  All Rights Reserved.
--    This document and translations of it may be copied and furnished to
--    others, and derivative works that comment on or otherwise explain
--    it or assist in its implementation may be prepared, copied,
--    published and distributed, in whole or in part, without restriction
--    of any kind, provided that the above copyright notice and this
--    paragraph are included on all such copies and derivative works.
--    However, this document itself may not be modified in any way, such
--    as by removing the copyright notice or references to the Internet
--    Society or other Internet organizations, except as needed for the
--    purpose of developing Internet standards in which case the
--    procedures for copyrights defined in the Internet Standards process
--    must be followed, or as required to translate it into languages
--    other than English.
--    The limited permissions granted above are perpetual and will not be
--    revoked by the Internet Society or its successors or assigns. This
--    document and the information contained herein is provided on an "AS
--    IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
