-- *********************************************************************
-- *********************************************************************
-- ** Filename: PRVT-ELMI-MIB
-- ** Project: Ethernet Local Management Interface
 -- ** Purpose: Private MIB
-- *********************************************************************
-- (c) Copyright,  2001,  BATM Advanced Communications. All rights reserved.
-- WARNING:
--
-- BY UTILIZING THIS FILE,  YOU AGREE TO THE FOLLOWING:
--
-- This file is the property of BATM Advanced Communications.
-- BATM Advanced Communications retains all title and
-- ownership in the Specification,  including any revisions.

-- BATM Advanced Communications grants all interested parties a non-exclusive
-- license to use and distribute an unmodified copy of this
-- Specification in connection with management of BATM Advanced Communications 
-- and Telco Systems products,  and without fee,  provided that the following
-- conditions are met:
-- 1. Redistributions of this specification must retain the above copyright
-- notice,  this list of conditions and the following disclaimer.
-- 2. Redistributions in binary form must reproduce the above copyright
-- notice,  this list of conditions and the following disclaimer in the
-- documentation and/or other materials provided with the distribution.
-- 3. The name of the BATM Advanced Communications MAY NOT be used to endorse
-- or promote products derived from this specification without specific prior written
-- permission.
--
-- EXCEPT AS RESTRICTED BY LAW,  OR AS PROVIDED IN BATM'S LIMITED
-- WARRANTY,  THE SPECIFICATIONS CONTAINED IN THIS FILE ARE
-- PROVIDED "AS IS" WITHOUT WARRANTY OF ANY KIND,  EITHER EXPRESSED
-- OR IMPLIED,  INCLUDING BUT NOT LIMITED TO,  ANY IMPLIED WARRANTIES
-- OF MERCHANTABILITY OR FITNESS FOR A PARTICULAR PURPOSE.
-- IN NO EVENT SHALL BATM BE LIABLE FOR ANY DAMAGES WHATSOEVER
-- INCLUDING,  WITHOUT LIMITATION,  DAMAGES FOR LOSS OF BUSINESS
-- PROFITS,  BUSINESS INTERRUPTION,  LOSS OF BUSINESS INFORMATION OR
-- OTHER CONSEQUENTIAL DAMAGES ARISING OUT OF THE USE,  OR INABILITY
-- TO USE,  THE SPECIFICATION CONTAINED IN THIS FILE.
PRVT-ELMI-MIB DEFINITIONS ::= BEGIN

IMPORTS
MODULE-IDENTITY, 
OBJECT-TYPE, 
Counter32, 
Unsigned32,  
Integer32, 
Gauge32, 
IpAddress
FROM SNMPv2-SMI

MODULE-COMPLIANCE,  NOTIFICATION-GROUP, 
OBJECT-GROUP
FROM SNMPv2-CONF

TEXTUAL-CONVENTION, 
TruthValue, 
RowStatus, 
StorageType, 
TimeStamp
FROM SNMPv2-TC

NOTIFICATION-TYPE,  transmission
          FROM SNMPv2-SMI                    -- [RFC2578]

InterfaceIndex,  ifIndex
FROM IF-MIB

switch FROM PRVT-SWITCH-MIB; 

-- The ELMI MIB
prvtELMIMib MODULE-IDENTITY

LAST-UPDATED "200907130000Z"
ORGANIZATION "BATM Advanced Communication"
CONTACT-INFO
"BATM/Telco Systems Support team
Email: 
For North America: techsupport@telco.com
For North Europe: support@batm.de,  info@batm.de
For the rest of the world: techsupport@telco.com"

DESCRIPTION
"This MIB contains managed object definitions for
encapsulating E-LMI that is terminated by the UNI-C 
on the CE side of the UNI and by the UNI-N on the MEN side of the UNI."

             
REVISION "200907130000Z"
DESCRIPTION
"Initial version." 
 
 
::= { switch 120 }


prvtELMINotifications OBJECT IDENTIFIER ::= { prvtELMIMib 0 } 
prvtELMIObjects OBJECT IDENTIFIER 		::= { prvtELMIMib 1 } 
prvtELMIConformance OBJECT IDENTIFIER 	::= { prvtELMIMib 2 }


--------------------------------------------------------------
--E-LMI objects
--------------------------------------------------------------

prvtELMIEnable OBJECT-TYPE
SYNTAX INTEGER {
enable(1), 
disable(2)
}   
MAX-ACCESS read-write
STATUS current
DESCRIPTION
"E-LMI enable protocol"
DEFVAL { disable }
::=  { prvtELMIObjects 1 }   

prvtELMICfgTable OBJECT-TYPE
SYNTAX SEQUENCE OF PrvtELMICfgEntry
MAX-ACCESS not-accessible
STATUS current
DESCRIPTION
"This table contains object for configuring E-LMI protocol."
::= { prvtELMIObjects 2 }
  
  
prvtELMICfgEntry OBJECT-TYPE
SYNTAX PrvtELMICfgEntry
MAX-ACCESS not-accessible
STATUS current
DESCRIPTION
""
INDEX { ifIndex }
::= { prvtELMICfgTable 1 }

PrvtELMICfgEntry ::=  SEQUENCE{
prvtELMIIfEnable 			INTEGER,    
prvtELMIIfMode 			INTEGER, 
prvtELMIPollingCnt 		INTEGER, 
prvtELMIPollingTimer 	INTEGER, 
prvtELMIVerifPollTimer 	INTEGER, 
prvtELMIStatusCnt		INTEGER, 
prvtELMIClearStatistics INTEGER, 
prvtELMIMapEvcCEVlanType INTEGER  
}


prvtELMIIfEnable   OBJECT-TYPE
SYNTAX INTEGER    
{
enable (1), 
disable (2)
}
MAX-ACCESS read-write
STATUS current
DESCRIPTION
" Enables or disables E-LMI feature per interface." 
::= { prvtELMICfgEntry 1 }            


prvtELMIIfMode   OBJECT-TYPE
SYNTAX INTEGER    
{
uni-n (1), 
uni-c (2)
}
MAX-ACCESS read-write
STATUS current
DESCRIPTION
" E-LMI working mode per interface." 
::= { prvtELMICfgEntry 2 }  


prvtELMIPollingCnt   OBJECT-TYPE
SYNTAX INTEGER  (1 .. 65535)
MAX-ACCESS read-write
STATUS current
DESCRIPTION
" Polling counter -  controls the number of polling cycles between Full Status exchanges.
Aplicable only in UNI-C mode"        
 DEFVAL { 360 }
::= { prvtELMICfgEntry 3 } 

prvtELMIPollingTimer   OBJECT-TYPE
SYNTAX INTEGER  (5..30)
MAX-ACCESS read-write
STATUS current
DESCRIPTION
" Polling timer - controls the interval at which STATUS ENQUIRY messages are transmitted.
Aplicable only in UNI-C mode"        
 DEFVAL { 10 }
::= { prvtELMICfgEntry 4 } 

prvtELMIVerifPollTimer   OBJECT-TYPE
SYNTAX INTEGER (5..30)
MAX-ACCESS read-write
STATUS current
DESCRIPTION
" Polling Verification Timer - controls the interval during which information sent to the UNI-C in a STATUS message is consider valid.
 The Polling Verification Timer MAY be disabled and thus the PVT never expires.
 Polling Verification Timer is valid only for UNI-N mode.
 For disable the counter SET 0 value"   
 DEFVAL { 15 }
::= { prvtELMICfgEntry 5 }
 

prvtELMIStatusCnt OBJECT-TYPE
SYNTAX INTEGER (2..10)
MAX-ACCESS read-write
STATUS current
DESCRIPTION
" Status Counter - controls the number of consecutive errors that must occur before E-LMI at the UNI is declared as not operational.
Aplicable in both UNI-Cand UNI-N mode"   
DEFVAL { 4 }
::= { prvtELMICfgEntry 6 } 
 
prvtELMIClearStatistics  OBJECT-TYPE
SYNTAX INTEGER 
{       
none (0), 
clear(1)
}
MAX-ACCESS read-write
STATUS current
DESCRIPTION
"Clear ELMI statistics per interface."
::= { prvtELMICfgEntry 7 }  

prvtELMIMapEvcCEVlanType OBJECT-TYPE
SYNTAX INTEGER 
{   
allToOneBundling  (1), 
serviceMultiplexingWithNoBund (2),  
budling(3)
}
MAX-ACCESS read-only
STATUS current
DESCRIPTION
"CE-VLAN ID/EVC Map Type ."
::= { prvtELMICfgEntry 8}          

prvtELMIStatisticsTable OBJECT-TYPE
SYNTAX SEQUENCE OF PrvtELMIStatisticsEntry
MAX-ACCESS not-accessible
STATUS current
DESCRIPTION
"This table contains objects for displaing E-LMI statistics."
::= { prvtELMIObjects 3 }
  
  
prvtELMIStatisticsEntry OBJECT-TYPE
SYNTAX PrvtELMIStatisticsEntry
MAX-ACCESS not-accessible
STATUS current
DESCRIPTION
""
INDEX { ifIndex }
::= { prvtELMIStatisticsTable 1 }

PrvtELMIStatisticsEntry ::= SEQUENCE{
prvtELMIStatusChange	 INTEGER, 
prvtELMILastFullReport TimeStamp, 
prvtELMITimeOuts	 INTEGER, 
prvtELMIMsgISN		 INTEGER, 
prvtELMIInavlidProtocolVers INTEGER, 
prvtELMIEVCInvalidRefId	 INTEGER, 
prvtELMIInavlidMsgType INTEGER,    
prvtELMIOOSIE		INTEGER, 
prvtELMIDuplicateIE INTEGER, 
prvtELMIMandatoryIEMissing INTEGER,    
prvtELMIInavlidMandatoryIE INTEGER,       
prvtELMIInvalidNonMandatoryIE INTEGER, 
prvtELMIUnrecognizedIE	INTEGER, 
prvtELMIUnexpectedIE INTEGER, 
prvtELMIShortMessage INTEGER

}
  

prvtELMIStatusChange  OBJECT-TYPE
SYNTAX INTEGER
{
up (1), 
down (2)
}
MAX-ACCESS read-only
STATUS current
DESCRIPTION
"E-LMI operational status"
::= { prvtELMIStatisticsEntry 1 }        

prvtELMILastFullReport  OBJECT-TYPE
SYNTAX TimeStamp
MAX-ACCESS read-only
STATUS current
DESCRIPTION
"E-LMI 	Time of the last full status report."
::= { prvtELMIStatisticsEntry 2 }  

prvtELMITimeOuts  OBJECT-TYPE
SYNTAX INTEGER
MAX-ACCESS read-only
STATUS current
DESCRIPTION
"Number of Status Timeouts."
::= { prvtELMIStatisticsEntry 3 } 


prvtELMIMsgISN  OBJECT-TYPE
SYNTAX INTEGER
MAX-ACCESS read-only
STATUS current
DESCRIPTION
"Number of messages with Invalid Sequence Number."
::= { prvtELMIStatisticsEntry 4 }            

prvtELMIInavlidProtocolVers  OBJECT-TYPE
SYNTAX INTEGER
MAX-ACCESS read-only
STATUS current
DESCRIPTION
"Invalid Protocol Version."
::= { prvtELMIStatisticsEntry 5 }         

prvtELMIEVCInvalidRefId  OBJECT-TYPE
SYNTAX INTEGER
MAX-ACCESS read-only
STATUS current
DESCRIPTION
"Invalid Ethernet Virtual Connection Reference Id."
::= { prvtELMIStatisticsEntry 6 }   

prvtELMIInavlidMsgType  OBJECT-TYPE
SYNTAX INTEGER
MAX-ACCESS read-only
STATUS current
DESCRIPTION
"Invalid Message Type."
::= { prvtELMIStatisticsEntry 7 } 

prvtELMIOOSIE  OBJECT-TYPE
SYNTAX INTEGER
MAX-ACCESS read-only
STATUS current
DESCRIPTION
"Out of Sequence IE."
::= { prvtELMIStatisticsEntry 8 }           

prvtELMIDuplicateIE  OBJECT-TYPE
SYNTAX INTEGER
MAX-ACCESS read-only
STATUS current
DESCRIPTION
"Duplicate IE."
::= { prvtELMIStatisticsEntry 9 }  

prvtELMIMandatoryIEMissing  OBJECT-TYPE
SYNTAX INTEGER
MAX-ACCESS read-only
STATUS current
DESCRIPTION
"Mandatory IE Missing."
::= { prvtELMIStatisticsEntry 10 } 

prvtELMIInavlidMandatoryIE  OBJECT-TYPE
SYNTAX INTEGER
MAX-ACCESS read-only
STATUS current
DESCRIPTION
"Invalid Mandatory IE."
::= { prvtELMIStatisticsEntry 11 } 

prvtELMIInvalidNonMandatoryIE  OBJECT-TYPE
SYNTAX INTEGER
MAX-ACCESS read-only
STATUS current
DESCRIPTION
"Invalid non-Mandatory IE."
::= { prvtELMIStatisticsEntry 12 }          

prvtELMIUnrecognizedIE  OBJECT-TYPE
SYNTAX INTEGER
MAX-ACCESS read-only
STATUS current
DESCRIPTION
"Unrecognized  IE."
::= { prvtELMIStatisticsEntry 13 } 

prvtELMIUnexpectedIE  OBJECT-TYPE
SYNTAX INTEGER
MAX-ACCESS read-only
STATUS current
DESCRIPTION
"Unexpected  IE."
::= { prvtELMIStatisticsEntry 14 }

prvtELMIShortMessage  OBJECT-TYPE
SYNTAX INTEGER
MAX-ACCESS read-only
STATUS current
DESCRIPTION
"Short Message."
::= { prvtELMIStatisticsEntry 15 }


prvtELMIEVCTable OBJECT-TYPE
SYNTAX SEQUENCE OF PrvtELMIEVCEntry
MAX-ACCESS not-accessible
STATUS current
DESCRIPTION
"This table contains objects for displaing EVC informations."
::= { prvtELMIObjects 4 }        

prvtELMIEVCEntry  OBJECT-TYPE
SYNTAX PrvtELMIEVCEntry
MAX-ACCESS not-accessible
STATUS current
DESCRIPTION
"An entry display information about EVC."
INDEX { ifIndex,  prvtELMIEVCId   }
::= { prvtELMIEVCTable 1 } 

PrvtELMIEVCEntry  ::= SEQUENCE{
prvtELMIEVCId INTEGER,       
prvtELMIServicesId Unsigned32, 
prvtELMIEVCStatus INTEGER, 
prvtELMIEVCType INTEGER
}

prvtELMIEVCId  OBJECT-TYPE
SYNTAX INTEGER (1..65535)
MAX-ACCESS accessible-for-notify  
STATUS current
DESCRIPTION
"An integer that uniquely identifies EVC Refernces id."   
::= {prvtELMIEVCEntry 1}         

prvtELMIServicesId  OBJECT-TYPE
SYNTAX Unsigned32 
MAX-ACCESS read-only   
STATUS current
DESCRIPTION
"An integer that uniquely identifies Services id."   
::= {prvtELMIEVCEntry 2} 

prvtELMIEVCStatus  OBJECT-TYPE
SYNTAX INTEGER {
non-active (0), 
new-non-active (1), 
active (2), 
new-active (3), 
partially-active(4), 
new-partially-active(5)
}
MAX-ACCESS read-only  
STATUS current
DESCRIPTION
"EVC State."   
::= {prvtELMIEVCEntry 3}      
                     
                     
prvtELMIEVCType   OBJECT-TYPE
SYNTAX INTEGER {
point-to-point (1), 
multi-point-to-point (2)
}
MAX-ACCESS read-only  
STATUS current
DESCRIPTION
"EVC Type."   
::= {prvtELMIEVCEntry 4}    

  
prvtELMIMapEvcCEVlanTable OBJECT-TYPE
SYNTAX SEQUENCE OF PrvtELMIMapEvcCEVlanEntry
MAX-ACCESS not-accessible
STATUS current
DESCRIPTION
"This table contains objects for displaying the map between EVC and CE-VLAN"
::= { prvtELMIObjects 5 }       

prvtELMIMapEvcCEVlanEntry   OBJECT-TYPE
SYNTAX PrvtELMIMapEvcCEVlanEntry
MAX-ACCESS not-accessible
STATUS current
DESCRIPTION
"An entry links EVC id with CE-VLAN id."
INDEX { ifIndex,  prvtELMIMapEVCId,   prvtELMIMapCeVlanId }
::= { prvtELMIMapEvcCEVlanTable 1 }   


PrvtELMIMapEvcCEVlanEntry ::= SEQUENCE{
prvtELMIMapEVCId INTEGER,      
prvtELMIMapCeVlanId INTEGER
}       
prvtELMIMapEVCId   OBJECT-TYPE
SYNTAX INTEGER  (1..65535)
MAX-ACCESS read-only  
STATUS current
DESCRIPTION
"An integer that uniquely identifies EVC id."   
::= {prvtELMIMapEvcCEVlanEntry 1} 

prvtELMIMapCeVlanId   OBJECT-TYPE
SYNTAX INTEGER (1..65535)
MAX-ACCESS read-only  
STATUS current
DESCRIPTION
"An integer that uniquely identifies CE-VLAN id."   
::= {prvtELMIMapEvcCEVlanEntry 2} 

                                            
                                            
prvtELMIStatus NOTIFICATION-TYPE
OBJECTS { prvtELMIEnable,  prvtELMIStatusChange }
STATUS current
DESCRIPTION
"This notification is sent  when status of ELMI changes."
::= {prvtELMINotifications 1}    

 

prvtELMIChangeEVC NOTIFICATION-TYPE
OBJECTS { prvtELMIEVCId }
STATUS current
DESCRIPTION
"This notification is sent  when status of CE-VLAN ID/EVC Map per interface changes."
::= {prvtELMINotifications 2}    

END
