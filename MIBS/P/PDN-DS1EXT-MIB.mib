PDN-DS1EXT-MIB DEFINITIONS ::= BEGIN

-------------------------------------------------------------------
--	Copyright (C) 2002, Paradyne. All rights reserved.
--
--	This MIB is an extension to the standard DS1 MIB (rfc2495).
-------------------------------------------------------------------

IMPORTS
	MODULE-IDENTITY, OBJECT-TYPE
	    FROM SNMPv2-SMI
	ifIndex
	    FROM IF-MIB
	MODULE-COMPLIANCE, OBJECT-GROUP
	    FROM SNMPv2-CONF
	ent-ds1
	    FROM PDN-HEADER-MIB;
	
pdnDs1Ext  MODULE-IDENTITY
	    LAST-UPDATED "200204050000Z"
	    ORGANIZATION "Paradyne Corp MIB Working Group"
	    CONTACT-INFO "Paradyne Networks, Inc.
			  8545, 126th Ave. N.,
			  Largo, FL 33779
			  www.paradyne.com

			  General Comments to:
			    mibwg_team@paradyne.com

			  Editors: Vic Sperry" 

	    DESCRIPTION 
               "The Paradyne enterprise DS1/G.703 extension MIB.
                This MIB provides additional DS1 and G.703 (E1) configuration
                objects not provided by rfc2495."

	    ::= { ent-ds1 5 }

pdnDs1ExtObjects  OBJECT IDENTIFIER ::= { pdnDs1Ext 1 }

--
-- START OF pdnDs1Ext mib definitions
--

pdnDs1ExtConfTable OBJECT-TYPE
     SYNTAX	 SEQUENCE OF PdnDs1ExtConfEntry
     MAX-ACCESS  not-accessible
     STATUS  	 current
     DESCRIPTION
	"The Paradyne DS1/G.703 extension configuration table.
	 This table is used for configuring extensions to DS1
         and G.703 interfaces."
	::= { pdnDs1ExtObjects 1 }

pdnDs1ExtConfEntry OBJECT-TYPE
     SYNTAX	 PdnDs1ExtConfEntry
     MAX-ACCESS  not-accessible
     STATUS  	 current
     DESCRIPTION
	"An entry in the Paradyne DS1/G.703 extension configuration table.
         Note: The objects used depend on the type of interface.

         For DS1: use pdnDs1ExtConfLineLengthType and one of
                      (pdnDs1ExtConfLineLength or pdnDs1ExtConfLineBuildOut)

         For G.703: use pdnDs1ExtConfLineLengthType and pdnDs1ExtConfConnector
        "
    INDEX   { ifIndex }
    ::= { pdnDs1ExtConfTable 1 }

PdnDs1ExtConfEntry ::=
     SEQUENCE {
     pdnDs1ExtConfLineLengthType   INTEGER,
     pdnDs1ExtConfLineLength       INTEGER,
     pdnDs1ExtConfLineBuildOut     INTEGER,
     pdnDs1ExtConfConnector        INTEGER
     }

pdnDs1ExtConfLineLengthType OBJECT-TYPE
     SYNTAX  	INTEGER {
		  shortHaul(1),
		  longHaul(2)
     }
     MAX-ACCESS read-write
     STATUS	current
     DESCRIPTION
	"This entry specifies the type of loop length for the interface.
         short-haul is intended for intra-building use.
         long-haul is intended for inter-building use."

     DEFVAL { longHaul }
     ::= { pdnDs1ExtConfEntry 1 }

pdnDs1ExtConfLineLength OBJECT-TYPE
     SYNTAX  	INTEGER {
		  feet000To133(1),
		  feet134To266(2),
		  feet267To399(3),
		  feet400To533(4),
		  feet534To655(5)
     }
     MAX-ACCESS read-write
     STATUS	current
     DESCRIPTION
	"This entry specifies the loop length, in feet, for a short-haul
         DS1 line. This object only applies to DS1 interfaces.
	 Note: This object shares a mutually exclusive relationship 
	 with the pdnDs1ExtConfLineBuildOut object i.e. only one of the
         two can be used for configuration at one time, based on the
         pdnDs1ExtConfLineLengthType object."
     DEFVAL { feet000To133 }
     ::= { pdnDs1ExtConfEntry 2 }

pdnDs1ExtConfLineBuildOut OBJECT-TYPE
     SYNTAX  	INTEGER {
		  dB0Pnt0(1),
		  dB7Pnt5(2),
		  dB15Pnt0(3),
		  dB22Pnt5(4)
     }
     MAX-ACCESS read-write
     STATUS	current
     DESCRIPTION
	"This entry specifies the line build out, in decibels, for a
         long-haul DS1 line.
         dB0Pnt0  = 0.0 dB         
         dB7Pnt5  = -7.5 dB         
         dB15Pnt0 = -15.0 dB         
         dB22Pnt5 = -22.5 dB         
         This object only applies to DS1 interfaces.
	 Note: This object shares a mutually exclusive relationship 
	 with the pdnDs1ExtConfLineLength object i.e. only one of the
         two can be used for configuration at one time, based on the
         pdnDs1ExtConfLineLengthType object."
     DEFVAL { dB0Pnt0 }
     ::= { pdnDs1ExtConfEntry 3 }

pdnDs1ExtConfConnector OBJECT-TYPE
     SYNTAX  	INTEGER {
		  bnc(1),
		  rj48(2)
     }
     MAX-ACCESS read-write
     STATUS	current
     DESCRIPTION
	"This entry specifies the type of connector to be used.
         This object only applies to G.703 interfaces.

         bnc: 75-Ohm connector supporting only short-haul.
         rj48: 120-Ohm connector supporting both short-haul and long-haul."

     DEFVAL { rj48 }
     ::= { pdnDs1ExtConfEntry 4 }

------------------------------------------
-- Conformance information
------------------------------------------

pdnDs1ExtConformance OBJECT IDENTIFIER ::= { pdnDs1Ext 2 }
pdnDs1ExtGroups      OBJECT IDENTIFIER ::= { pdnDs1ExtConformance 1 }
pdnDs1ExtCompliances OBJECT IDENTIFIER ::= { pdnDs1ExtConformance 2 }

pdnDs1ExtCompliance MODULE-COMPLIANCE
     STATUS  current
     DESCRIPTION
         "Compliance statement for using this MIB for configuring
          DS1 interfaces."
     MODULE  -- this module

         GROUP       pdnDs1ExtT1ConfigGroup
         DESCRIPTION
             "Implementation of this group is required for systems
              wishing to conform to this MIB for the purposes of
              configuring a DS1 interface."

         OBJECT     pdnDs1ExtConfLineLengthType
         MIN-ACCESS read-only
         DESCRIPTION
             "The ability to set pdnDs1ExtConfLineLengthType is not required."

         OBJECT     pdnDs1ExtConfLineLength
         MIN-ACCESS read-only
         DESCRIPTION
             "The ability to set pdnDs1ExtConfLineLength is not required."

         OBJECT     pdnDs1ExtConfLineBuildOut
         MIN-ACCESS read-only
         DESCRIPTION
             "The ability to set pdnDs1ExtConfLineBuildOut is not required."

 ::= { pdnDs1ExtCompliances 1 }


pdnDs1ExtG703Compliance MODULE-COMPLIANCE
     STATUS  current
     DESCRIPTION
         "Compliance statement for using this MIB for configuring
          G.703 interfaces."
     MODULE  -- this module

         GROUP       pdnDs1ExtE1ConfigGroup
         DESCRIPTION
             "Implementation of this group is required for systems
              wishing to conform to this MIB for the purposes of
              configuring a G.703 interface."

         OBJECT     pdnDs1ExtConfLineLengthType
         MIN-ACCESS read-only
         DESCRIPTION
             "The ability to set pdnDs1ExtConfLineLengthType is not required."

         OBJECT     pdnDs1ExtConfConnector
         MIN-ACCESS read-only
         DESCRIPTION
             "The ability to set pdnDs1ExtConfConnector is not required."

 ::= { pdnDs1ExtCompliances 2 }


--
-- Units of Conformance
--

pdnDs1ExtT1ConfigGroup OBJECT-GROUP
	OBJECTS {
           pdnDs1ExtConfLineLengthType,
           pdnDs1ExtConfLineLength,
           pdnDs1ExtConfLineBuildOut
        }
	STATUS  current -- Set as required for the group
	DESCRIPTION 
	   "A collection of configuration objects required 
	    for configuring a T1 interface."

	::= { pdnDs1ExtGroups 1 }

pdnDs1ExtE1ConfigGroup OBJECT-GROUP
	OBJECTS {
           pdnDs1ExtConfLineLengthType,
           pdnDs1ExtConfConnector
        }
	STATUS  current -- Set as required for the group
	DESCRIPTION 
	   "A collection of configuration objects required 
	    for configuring a G.703 (E1) interface."

	::= { pdnDs1ExtGroups 2 }
END
