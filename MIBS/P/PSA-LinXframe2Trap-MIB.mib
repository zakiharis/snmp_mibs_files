PSA-LinXframe2Trap-MIB DEFINITIONS ::= BEGIN

--PRIMEQUEST system management MIB for Partition
--
--
--$Copyright$
--Copyright Fujitsu Limited 2007
--All rights reserved
--
--
--MIB Revision: 01130000
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaLinXframe2Trap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise		OBJECT IDENTIFIER  ::={ partition 201 }
     psaComTrap				OBJECT IDENTIFIER  ::={ partitionEnterprise 1 }
     psaLinLanComTrap			OBJECT IDENTIFIER  ::={ partitionEnterprise 2 }
     psaLinIntelE100Trap		OBJECT IDENTIFIER  ::={ partitionEnterprise 3 }
     psaLinIntelE1000Trap		OBJECT IDENTIFIER  ::={ partitionEnterprise 4 }
     psaLinBcm5700Trap			OBJECT IDENTIFIER  ::={ partitionEnterprise 5 }
     psaLinEmulexTrap			OBJECT IDENTIFIER  ::={ partitionEnterprise 6 }
     psaLinLsiLogicTrap		OBJECT IDENTIFIER  ::={ partitionEnterprise 7 }
     psaLinScsiComTrap			OBJECT IDENTIFIER  ::={ partitionEnterprise 8 }
     psaLinGrmpdTrap			OBJECT IDENTIFIER  ::={ partitionEnterprise 9 }
     psaLinGdsTrap				OBJECT IDENTIFIER  ::={ partitionEnterprise 10 }
     psaLinGlsTrap				OBJECT IDENTIFIER  ::={ partitionEnterprise 11 }
     psaLinTg3Trap				OBJECT IDENTIFIER  ::={ partitionEnterprise 12 }
     psaLinIbTrap				OBJECT IDENTIFIER  ::={ partitionEnterprise 13 }
     psaLinXframe2Trap			OBJECT IDENTIFIER  ::={ partitionEnterprise 14 }
     psaGschTrap				OBJECT IDENTIFIER  ::={ partitionEnterprise 15 }
     psaExternalFileUnitTrap	OBJECT IDENTIFIER  ::={ partitionEnterprise 101 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

trapFlagcode OBJECT-TYPE
   SYNTAX   DisplayString
   ACCESS   not-accessible
   STATUS   mandatory
   DESCRIPTION " "
   ::= { trapVarDivInfo 28 }

--***************************************************************************************
--
--FUJITSU PRIMEQUEST system management TRAP definition for Partition
--	Trap enterprise:	psaLinXframe2Trap (.1.3.6.1.4.1.211.1.31.1.2.201.14)
--
--***************************************************************************************

xframe2Event0 TRAP-TYPE
   ENTERPRISE   psaLinXframe2Trap
   VARIABLES {
      trapPartitionName,
      trapPartitionId,
      trapEventLevel,
      trapEventId,
      trapUnitName,
      trapMmbVip
   }
   DESCRIPTION "s2io: Adapter error (ERROR: Setting Swapper failed)"
   --#TYPE			"Xframe2 Event 0"
   --#SUMMARY		"%s(PID=%d) %s %d %s s2io: Adapter error (ERROR: Setting Swapper failed)"
   --#ARGUMENTS		{ 0, 1, 2, 3, 4 }
   --#SEVERITY		MINOR
   ::= 11500

xframe2Event1 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (TTI init Failed)"
   --#TYPE			"Xframe2 Event 1"
   --#SUMMARY		"%s(PID=%d) %s %d %s s2io:%s Adapter error (TTI init Failed) vendor-id=%s device-id=%s revision=%s"
   --#ARGUMENTS		{ 0, 1, 2, 3, 4, 5, 6, 7, 8 }
   --#SEVERITY		MINOR
   ::= 11501

xframe2Event2 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (RTI init Failed)"
   --#TYPE			"Xframe2 Event 2"
   --#SUMMARY		"%s(PID=%d) %s %d %s s2io:%s Adapter error (RTI init Failed) vendor-id=%s device-id=%s revision=%s"
   --#ARGUMENTS		{ 0, 1, 2, 3, 4, 5, 6, 7, 8 }
   --#SEVERITY		MINOR
   ::= 11502

xframe2Event3 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (device is not ready)"
   --#TYPE			"Xframe2 Event 3"
   --#SUMMARY		"%s(PID=%d) %s %d %s s2io:%s Adapter error (device is not ready) vendor-id=%s device-id=%s revision=%s"
   --#ARGUMENTS		{ 0, 1, 2, 3, 4, 5, 6, 7, 8 }
   --#SEVERITY		MINOR
   ::= 11503

xframe2Event4 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (The skb is Null in Rx Intr)"
   --#TYPE			"Xframe2 Event 4"
   --#SUMMARY		"%s(PID=%d) %s %d %s s2io:%s Adapter error (The skb is Null in Rx Intr) vendor-id=%s device-id=%s revision=%s"
   --#ARGUMENTS		{ 0, 1, 2, 3, 4, 5, 6, 7, 8 }
   --#SEVERITY		MINOR
   ::= 11504

xframe2Event5 TRAP-TYPE
   ENTERPRISE   psaLinXframe2Trap
   VARIABLES {
      trapPartitionName,
      trapPartitionId,
      trapEventLevel,
      trapEventId,
      trapUnitName,
      trapMmbVip
   }
   DESCRIPTION "s2io: Adapter error (Null skb in Tx Free Intr)"
   --#TYPE			"Xframe2 Event 5"
   --#SUMMARY		"%s(PID=%d) %s %d %s s2io: Adapter error (Null skb in Tx Free Intr)"
   --#ARGUMENTS		{ 0, 1, 2, 3, 4 }
   --#SEVERITY		MINOR
   ::= 11505

xframe2Event6 TRAP-TYPE
   ENTERPRISE   psaLinXframe2Trap
   VARIABLES {
      trapPartitionName,
      trapPartitionId,
      trapEventLevel,
      trapEventId,
      trapUnitName,
      trapMmbVip
   }
   DESCRIPTION "s2io: Adapter error (Excessive temperatures may result in premature transceiver failure)"
   --#TYPE			"Xframe2 Event 6"
   --#SUMMARY		"%s(PID=%d) %s %d %s s2io: Adapter error (Excessive temperatures may result in premature transceiver failure)"
   --#ARGUMENTS		{ 0, 1, 2, 3, 4 }
   --#SEVERITY		MINOR
   ::= 11506

xframe2Event7 TRAP-TYPE
   ENTERPRISE   psaLinXframe2Trap
   VARIABLES {
      trapPartitionName,
      trapPartitionId,
      trapEventLevel,
      trapEventId,
      trapUnitName,
      trapMmbVip
   }
   DESCRIPTION "s2io: Adapter error (Excessive bias currents may indicate imminent laser diode failure)"
   --#TYPE			"Xframe2 Event 7"
   --#SUMMARY		"%s(PID=%d) %s %d %s s2io: Adapter error (Excessive bias currents may indicate imminent laser diode failure)"
   --#ARGUMENTS		{ 0, 1, 2, 3, 4 }
   --#SEVERITY		MINOR
   ::= 11507

xframe2Event8 TRAP-TYPE
   ENTERPRISE   psaLinXframe2Trap
   VARIABLES {
      trapPartitionName,
      trapPartitionId,
      trapEventLevel,
      trapEventId,
      trapUnitName,
      trapMmbVip
   }
   DESCRIPTION "s2io: Adapter error (Excessive laser output power may saturate far-end receiver)"
   --#TYPE			"Xframe2 Event 8"
   --#SUMMARY		"%s(PID=%d) %s %d %s s2io: Adapter error (Excessive laser output power may saturate far-end receiver)"
   --#ARGUMENTS		{ 0, 1, 2, 3, 4 }
   --#SEVERITY		MINOR
   ::= 11508

xframe2Event9 TRAP-TYPE
   ENTERPRISE   psaLinXframe2Trap
   VARIABLES {
      trapPartitionName,
      trapPartitionId,
      trapEventLevel,
      trapEventId,
      trapUnitName,
      trapMmbVip
   }
   DESCRIPTION "s2io: Adapter error (Incorrect XPAK Alarm type)"
   --#TYPE			"Xframe2 Event 9"
   --#SUMMARY		"%s(PID=%d) %s %d %s s2io: Adapter error (Incorrect XPAK Alarm type)"
   --#ARGUMENTS		{ 0, 1, 2, 3, 4 }
   --#SEVERITY		MINOR
   ::= 11509

xframe2Event10 TRAP-TYPE
   ENTERPRISE   psaLinXframe2Trap
   VARIABLES {
      trapPartitionName,
      trapPartitionId,
      trapEventLevel,
      trapEventId,
      trapUnitName,
      trapMmbVip
   }
   DESCRIPTION "s2io: Adapter error (ERR: MDIO slave access failed)"
   --#TYPE			"Xframe2 Event 10"
   --#SUMMARY		"%s(PID=%d) %s %d %s s2io: Adapter error (ERR: MDIO slave access failed)"
   --#ARGUMENTS		{ 0, 1, 2, 3, 4 }
   --#SEVERITY		MINOR
   ::= 11510

xframe2Event11 TRAP-TYPE
   ENTERPRISE   psaLinXframe2Trap
   VARIABLES {
      trapPartitionName,
      trapPartitionId,
      trapEventLevel,
      trapEventId,
      trapUnitName,
      trapMmbVip
   }
   DESCRIPTION "s2io: Adapter error (Incorrect value at PMA address 0x0000)"
   --#TYPE			"Xframe2 Event 11"
   --#SUMMARY		"%s(PID=%d) %s %d %s s2io: Adapter error (Incorrect value at PMA address 0x0000)"
   --#ARGUMENTS		{ 0, 1, 2, 3, 4 }
   --#SEVERITY		MINOR
   ::= 11511

xframe2Event12 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Device indicates double ECC error)"
   --#TYPE			"Xframe2 Event 12"
   --#SUMMARY		"%s(PID=%d) %s %d %s s2io:%s Adapter error (Device indicates double ECC error) vendor-id=%s device-id=%s revision=%s"
   --#ARGUMENTS		{ 0, 1, 2, 3, 4, 5, 6, 7, 8 }
   --#SEVERITY		MINOR
   ::= 11512

xframe2Event13 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Device indicates serious error)"
   --#TYPE			"Xframe2 Event 13"
   --#SUMMARY		"%s(PID=%d) %s %d %s s2io:%s Adapter error (Device indicates serious error) vendor-id=%s device-id=%s revision=%s"
   --#ARGUMENTS		{ 0, 1, 2, 3, 4, 5, 6, 7, 8 }
   --#SEVERITY		MINOR
   ::= 11513

xframe2Event14 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Endian settings are wrong)"
   --#TYPE			"Xframe2 Event 14"
   --#SUMMARY		"%s(PID=%d) %s %d %s s2io:%s Adapter error (Endian settings are wrong) vendor-id=%s device-id=%s revision=%s"
   --#ARGUMENTS		{ 0, 1, 2, 3, 4, 5, 6, 7, 8 }
   --#SEVERITY		MINOR
   ::= 11514

xframe2Event15 TRAP-TYPE
   ENTERPRISE   psaLinXframe2Trap
   VARIABLES {
      trapPartitionName,
      trapPartitionId,
      trapEventLevel,
      trapEventId,
      trapUnitName,
      trapMmbVip
   }
   DESCRIPTION "s2io: Adapter error (XMSI register error)"
   --#TYPE			"Xframe2 Event 15"
   --#SUMMARY		"%s(PID=%d) %s %d %s s2io: Adapter error (XMSI register error)"
   --#ARGUMENTS		{ 0, 1, 2, 3, 4 }
   --#SEVERITY		MINOR
   ::= 11515

xframe2Event16 TRAP-TYPE
   ENTERPRISE   psaLinXframe2Trap
   VARIABLES {
      trapPartitionName,
      trapPartitionId,
      trapEventLevel,
      trapEventId,
      trapUnitName,
      trapMmbVip
   }
   DESCRIPTION "s2io: Adapter error (XMSI access_register access error)"
   --#TYPE			"Xframe2 Event 16"
   --#SUMMARY		"%s(PID=%d) %s %d %s s2io: Adapter error (XMSI access_register access error)"
   --#ARGUMENTS		{ 0, 1, 2, 3, 4 }
   --#SEVERITY		MINOR
   ::= 11516

xframe2Event17 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (enabling MSI failed)"
   --#TYPE			"Xframe2 Event 17"
   --#SUMMARY		"%s(PID=%d) %s %d %s s2io:%s Adapter error (enabling MSI failed) vendor-id=%s device-id=%s revision=%s"
   --#ARGUMENTS		{ 0, 1, 2, 3, 4, 5, 6, 7, 8 }
   --#SEVERITY		MINOR
   ::= 11517

xframe2Event18 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Enabling MSIX failed)"
   --#TYPE			"Xframe2 Event 18"
   --#SUMMARY		"%s(PID=%d) %s %d %s s2io:%s Adapter error (Enabling MSIX failed) vendor-id=%s device-id=%s revision=%s"
   --#ARGUMENTS		{ 0, 1, 2, 3, 4, 5, 6, 7, 8 }
   --#SEVERITY		MINOR
   ::= 11518

xframe2Event19 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Adding Multicasts failed)"
   --#TYPE			"Xframe2 Event 19"
   --#SUMMARY		"%s(PID=%d) %s %d %s s2io:%s Adapter error (Adding Multicasts failed) vendor-id=%s device-id=%s revision=%s"
   --#ARGUMENTS		{ 0, 1, 2, 3, 4, 5, 6, 7, 8 }
   --#SEVERITY		MINOR
   ::= 11519

xframe2Event20 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (set_mac_addr failed)"
   --#TYPE			"Xframe2 Event 20"
   --#SUMMARY		"%s(PID=%d) %s %d %s s2io:%s Adapter error (set_mac_addr failed) vendor-id=%s device-id=%s revision=%s"
   --#ARGUMENTS		{ 0, 1, 2, 3, 4, 5, 6, 7, 8 }
   --#SEVERITY		MINOR
   ::= 11520

xframe2Event21 TRAP-TYPE
   ENTERPRISE   psaLinXframe2Trap
   VARIABLES {
      trapPartitionName,
      trapPartitionId,
      trapEventLevel,
      trapEventId,
      trapUnitName,
      trapMmbVip
   }
   DESCRIPTION "s2io: Adapter error (Read of VPD data failed)"
   --#TYPE			"Xframe2 Event 21"
   --#SUMMARY		"%s(PID=%d) %s %d %s s2io: Adapter error (Read of VPD data failed)"
   --#ARGUMENTS		{ 0, 1, 2, 3, 4 }
   --#SEVERITY		MINOR
   ::= 11521

xframe2Event22 TRAP-TYPE
   ENTERPRISE   psaLinXframe2Trap
   VARIABLES {
      trapPartitionName,
      trapPartitionId,
      trapEventLevel,
      trapEventId,
      trapUnitName,
      trapMmbVip
   }
   DESCRIPTION "s2io: Adapter error (Read of EEPROM failed)"
   --#TYPE			"Xframe2 Event 22"
   --#SUMMARY		"%s(PID=%d) %s %d %s s2io: Adapter error (Read of EEPROM failed)"
   --#ARGUMENTS		{ 0, 1, 2, 3, 4 }
   --#SEVERITY		MINOR
   ::= 11522

xframe2Event23 TRAP-TYPE
   ENTERPRISE   psaLinXframe2Trap
   VARIABLES {
      trapPartitionName,
      trapPartitionId,
      trapEventLevel,
      trapEventId,
      trapUnitName,
      trapMmbVip
   }
   DESCRIPTION "s2io: Adapter error (ETHTOOL_WRITE_EEPROM Err: Magic value is wrong)"
   --#TYPE			"Xframe2 Event 23"
   --#SUMMARY		"%s(PID=%d) %s %d %s s2io: Adapter error (ETHTOOL_WRITE_EEPROM Err: Magic value is wrong)"
   --#ARGUMENTS		{ 0, 1, 2, 3, 4 }
   --#SEVERITY		MINOR
   ::= 11523

xframe2Event24 TRAP-TYPE
   ENTERPRISE   psaLinXframe2Trap
   VARIABLES {
      trapPartitionName,
      trapPartitionId,
      trapEventLevel,
      trapEventId,
      trapUnitName,
      trapMmbVip
   }
   DESCRIPTION "s2io: Adapter error (Read Test fails)"
   --#TYPE			"Xframe2 Event 24"
   --#SUMMARY		"%s(PID=%d) %s %d %s s2io: Adapter error (Read Test fails)"
   --#ARGUMENTS		{ 0, 1, 2, 3, 4 }
   --#SEVERITY		MINOR
   ::= 11524

xframe2Event25 TRAP-TYPE
   ENTERPRISE   psaLinXframe2Trap
   VARIABLES {
      trapPartitionName,
      trapPartitionId,
      trapEventLevel,
      trapEventId,
      trapUnitName,
      trapMmbVip
   }
   DESCRIPTION "s2io: Adapter error (Write Test fails)"
   --#TYPE			"Xframe2 Event 25"
   --#SUMMARY		"%s(PID=%d) %s %d %s s2io: Adapter error (Write Test fails)"
   --#ARGUMENTS		{ 0, 1, 2, 3, 4 }
   --#SEVERITY		MINOR
   ::= 11525

xframe2Event26 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (eeprom test error)"
   --#TYPE			"Xframe2 Event 26"
   --#SUMMARY		"%s(PID=%d) %s %d %s s2io:%s Adapter error (eeprom test error) vendor-id=%s device-id=%s revision=%s"
   --#ARGUMENTS		{ 0, 1, 2, 3, 4, 5, 6, 7, 8 }
   --#SEVERITY		MINOR
   ::= 11526

xframe2Event27 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (Error: device is not Quiescent)"
   --#TYPE			"Xframe2 Event 27"
   --#SUMMARY		"%s(PID=%d) %s %d %s s2io:%s Adapter error (Error: device is not Quiescent) vendor-id=%s device-id=%s revision=%s"
   --#ARGUMENTS		{ 0, 1, 2, 3, 4, 5, 6, 7, 8 }
   --#SEVERITY		MINOR
   ::= 11527

xframe2Event28 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (MSI registration failed)"
   --#TYPE			"Xframe2 Event 28"
   --#SUMMARY		"%s(PID=%d) %s %d %s s2io:%s Adapter error (MSI registration failed) vendor-id=%s device-id=%s revision=%s"
   --#ARGUMENTS		{ 0, 1, 2, 3, 4, 5, 6, 7, 8 }
   --#SEVERITY		MINOR
   ::= 11528

xframe2Event29 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (MSIX mode handler registration failed)"
   --#TYPE			"Xframe2 Event 29"
   --#SUMMARY		"%s(PID=%d) %s %d %s s2io:%s Adapter error (MSIX mode handler registration failed) vendor-id=%s device-id=%s revision=%s"
   --#ARGUMENTS		{ 0, 1, 2, 3, 4, 5, 6, 7, 8 }
   --#SEVERITY		MINOR
   ::= 11529

xframe2Event30 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (MSIX registration failed)"
   --#TYPE			"Xframe2 Event 30"
   --#SUMMARY		"%s(PID=%d) %s %d %s s2io:%s Adapter error (MSIX registration failed) vendor-id=%s device-id=%s revision=%s"
   --#ARGUMENTS		{ 0, 1, 2, 3, 4, 5, 6, 7, 8 }
   --#SEVERITY		MINOR
   ::= 11530

xframe2Event31 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (INTA registration failed)"
   --#TYPE			"Xframe2 Event 31"
   --#SUMMARY		"%s(PID=%d) %s %d %s s2io:%s Adapter error (INTA registration failed) vendor-id=%s device-id=%s revision=%s"
   --#ARGUMENTS		{ 0, 1, 2, 3, 4, 5, 6, 7, 8 }
   --#SEVERITY		MINOR
   ::= 11531

xframe2Event32 TRAP-TYPE
   ENTERPRISE   psaLinXframe2Trap
   VARIABLES {
      trapPartitionName,
      trapPartitionId,
      trapEventLevel,
      trapEventId,
      trapUnitName,
      trapMmbVip
   }
   DESCRIPTION "s2io: Adapter error (s2io_close:Device not Quiescent)"
   --#TYPE			"Xframe2 Event 32"
   --#SUMMARY		"%s(PID=%d) %s %d %s s2io: Adapter error (s2io_close:Device not Quiescent)"
   --#ARGUMENTS		{ 0, 1, 2, 3, 4 }
   --#SEVERITY		MINOR
   ::= 11532

xframe2Event33 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (reset by Tx watchdog timer)"
   --#TYPE			"Xframe2 Event 33"
   --#SUMMARY		"%s(PID=%d) %s %d %s s2io:%s Adapter error (reset by Tx watchdog timer) vendor-id=%s device-id=%s revision=%s"
   --#ARGUMENTS		{ 0, 1, 2, 3, 4, 5, 6, 7, 8 }
   --#SEVERITY		MINOR
   ::= 11533

xframe2Event34 TRAP-TYPE
   ENTERPRISE   psaLinXframe2Trap
   VARIABLES {
      trapPartitionName,
      trapPartitionId,
      trapEventLevel,
      trapEventId,
      trapUnitName,
      trapMmbVip
   }
   DESCRIPTION "s2io: Adapter or Software error (s2io_init_nic: pci_enable_device failed)"
   --#TYPE			"Xframe2 Event 34"
   --#SUMMARY		"%s(PID=%d) %s %d %s s2io: Adapter or Software error (s2io_init_nic: pci_enable_device failed)"
   --#ARGUMENTS		{ 0, 1, 2, 3, 4 }
   --#SEVERITY		MINOR
   ::= 11534

xframe2Event35 TRAP-TYPE
   ENTERPRISE   psaLinXframe2Trap
   VARIABLES {
      trapPartitionName,
      trapPartitionId,
      trapEventLevel,
      trapEventId,
      trapUnitName,
      trapMmbVip
   }
   DESCRIPTION "s2io: Adapter or Software error (Unable to obtain 64bit DMA for consistent allocations)"
   --#TYPE			"Xframe2 Event 35"
   --#SUMMARY		"%s(PID=%d) %s %d %s s2io: Adapter or Software error (Unable to obtain 64bit DMA for consistent allocations)"
   --#ARGUMENTS		{ 0, 1, 2, 3, 4 }
   --#SEVERITY		MINOR
   ::= 11535

xframe2Event36 TRAP-TYPE
   ENTERPRISE   psaLinXframe2Trap
   VARIABLES {
      trapPartitionName,
      trapPartitionId,
      trapEventLevel,
      trapEventId,
      trapUnitName,
      trapMmbVip
   }
   DESCRIPTION "s2io: Adapter or Software error (Request Regions failed)"
   --#TYPE			"Xframe2 Event 36"
   --#SUMMARY		"%s(PID=%d) %s %d %s s2io: Adapter or Software error (Request Regions failed)"
   --#ARGUMENTS		{ 0, 1, 2, 3, 4 }
   --#SEVERITY		MINOR
   ::= 11536

xframe2Event37 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (swapper settings are wrong)"
   --#TYPE			"Xframe2 Event 37"
   --#SUMMARY		"%s(PID=%d) %s %d %s s2io:%s Adapter error (swapper settings are wrong) vendor-id=%s device-id=%s revision=%s"
   --#ARGUMENTS		{ 0, 1, 2, 3, 4, 5, 6, 7, 8 }
   --#SEVERITY		MINOR
   ::= 11537

xframe2Event38 TRAP-TYPE
   ENTERPRISE   psaLinXframe2Trap
   VARIABLES {
      trapPartitionName,
      trapPartitionId,
      trapEventLevel,
      trapEventId,
      trapUnitName,
      trapMmbVip
   }
   DESCRIPTION "s2io: Adapter error (Unsupported PCI bus mode)"
   --#TYPE			"Xframe2 Event 38"
   --#SUMMARY		"%s(PID=%d) %s %d %s s2io: Adapter error (Unsupported PCI bus mode)"
   --#ARGUMENTS		{ 0, 1, 2, 3, 4 }
   --#SEVERITY		MINOR
   ::= 11538

xframe2Event39 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (readl/q: PCI parity error detected; retrying.)"
   --#TYPE			"Xframe2 Event 39"
   --#SUMMARY		"%s(PID=%d) %s %d %s s2io:%s Adapter error (readl/q: PCI parity error detected; retrying.) vendor-id=%s device-id=%s revision=%s"
   --#ARGUMENTS		{ 0, 1, 2, 3, 4, 5, 6, 7, 8 }
   --#SEVERITY		MINOR
   ::= 11539

xframe2Event40 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (readl/q: Cannot recover from a PCI parity error)"
   --#TYPE			"Xframe2 Event 40"
   --#SUMMARY		"%s(PID=%d) %s %d %s s2io:%s Adapter error (readl/q: Cannot recover from a PCI parity error) vendor-id=%s device-id=%s revision=%s"
   --#ARGUMENTS		{ 0, 1, 2, 3, 4, 5, 6, 7, 8 }
   --#SEVERITY		MINOR
   ::= 11540

xframe2Event41 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (writeq: PCI parity error detected; retrying.)"
   --#TYPE			"Xframe2 Event 41"
   --#SUMMARY		"%s(PID=%d) %s %d %s s2io:%s Adapter error (writeq: PCI parity error detected; retrying.) vendor-id=%s device-id=%s revision=%s"
   --#ARGUMENTS		{ 0, 1, 2, 3, 4, 5, 6, 7, 8 }
   --#SEVERITY		MINOR
   ::= 11541

xframe2Event42 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (writel: Cannot recover from a PCI parity error)"
   --#TYPE			"Xframe2 Event 42"
   --#SUMMARY		"%s(PID=%d) %s %d %s s2io:%s Adapter error (writel: Cannot recover from a PCI parity error) vendor-id=%s device-id=%s revision=%s"
   --#ARGUMENTS		{ 0, 1, 2, 3, 4, 5, 6, 7, 8 }
   --#SEVERITY		MINOR
   ::= 11542

xframe2Event43 TRAP-TYPE
   ENTERPRISE   psaLinXframe2Trap
   VARIABLES {
      trapPartitionName,
      trapPartitionId,
      trapEventLevel,
      trapEventId,
      trapUnitName,
      trapSuspect,
      trapVendorId,
      trapDeviceId,
      trapRevision,
      trapMmbVip
   }
   DESCRIPTION "s2io: Adapter error (failed rts ds steeringset on codepoint)"
   --#TYPE			"Xframe2 Event 43"
   --#SUMMARY		"%s(PID=%d) %s %d %s s2io: %s Adapter error (failed rts ds steeringset on codepoint) vendor-id=%s device-id=%s revision=%s"
   --#ARGUMENTS		{ 0, 1, 2, 3, 4, 5, 6, 7, 8 }
   --#SEVERITY		MINOR
   ::= 11543

xframe2Event44 TRAP-TYPE
   ENTERPRISE   psaLinXframe2Trap
   VARIABLES {
      trapPartitionName,
      trapPartitionId,
      trapEventLevel,
      trapEventId,
      trapUnitName,
      trapMmbVip
   }
   DESCRIPTION "s2io: Adapter error (TDMA is not ready!)"
   --#TYPE			"Xframe2 Event 44"
   --#SUMMARY		"%s(PID=%d) %s %d %s s2io: Adapter error (TDMA is not ready!)"
   --#ARGUMENTS		{ 0, 1, 2, 3, 4 }
   --#SEVERITY		MINOR
   ::= 11544

xframe2Event45 TRAP-TYPE
   ENTERPRISE   psaLinXframe2Trap
   VARIABLES {
      trapPartitionName,
      trapPartitionId,
      trapEventLevel,
      trapEventId,
      trapUnitName,
      trapMmbVip
   }
   DESCRIPTION "s2io: Adapter error (RDMA is not ready!)"
   --#TYPE			"Xframe2 Event 45"
   --#SUMMARY		"%s(PID=%d) %s %d %s s2io: Adapter error (RDMA is not ready!)"
   --#ARGUMENTS		{ 0, 1, 2, 3, 4 }
   --#SEVERITY		MINOR
   ::= 11545

xframe2Event46 TRAP-TYPE
   ENTERPRISE   psaLinXframe2Trap
   VARIABLES {
      trapPartitionName,
      trapPartitionId,
      trapEventLevel,
      trapEventId,
      trapUnitName,
      trapMmbVip
   }
   DESCRIPTION "s2io: Adapter error (PFC is not ready!)"
   --#TYPE			"Xframe2 Event 46"
   --#SUMMARY		"%s(PID=%d) %s %d %s s2io: Adapter error (PFC is not ready!)"
   --#ARGUMENTS		{ 0, 1, 2, 3, 4 }
   --#SEVERITY		MINOR
   ::= 11546

xframe2Event47 TRAP-TYPE
   ENTERPRISE   psaLinXframe2Trap
   VARIABLES {
      trapPartitionName,
      trapPartitionId,
      trapEventLevel,
      trapEventId,
      trapUnitName,
      trapMmbVip
   }
   DESCRIPTION "s2io: Adapter error (TMAC BUF is not empty!)"
   --#TYPE			"Xframe2 Event 47"
   --#SUMMARY		"%s(PID=%d) %s %d %s s2io: Adapter error (TMAC BUF is not empty!)"
   --#ARGUMENTS		{ 0, 1, 2, 3, 4 }
   --#SEVERITY		MINOR
   ::= 11547

xframe2Event48 TRAP-TYPE
   ENTERPRISE   psaLinXframe2Trap
   VARIABLES {
      trapPartitionName,
      trapPartitionId,
      trapEventLevel,
      trapEventId,
      trapUnitName,
      trapMmbVip
   }
   DESCRIPTION "s2io: Adapter error (PIC is not QUIESCENT!)"
   --#TYPE			"Xframe2 Event 48"
   --#SUMMARY		"%s(PID=%d) %s %d %s s2io: Adapter error (PIC is not QUIESCENT!)"
   --#ARGUMENTS		{ 0, 1, 2, 3, 4 }
   --#SEVERITY		MINOR
   ::= 11548

xframe2Event49 TRAP-TYPE
   ENTERPRISE   psaLinXframe2Trap
   VARIABLES {
      trapPartitionName,
      trapPartitionId,
      trapEventLevel,
      trapEventId,
      trapUnitName,
      trapMmbVip
   }
   DESCRIPTION "s2io: Adapter error (MC_DRAM is not ready!)"
   --#TYPE			"Xframe2 Event 49"
   --#SUMMARY		"%s(PID=%d) %s %d %s s2io: Adapter error (MC_DRAM is not ready!)"
   --#ARGUMENTS		{ 0, 1, 2, 3, 4 }
   --#SEVERITY		MINOR
   ::= 11549

xframe2Event50 TRAP-TYPE
   ENTERPRISE   psaLinXframe2Trap
   VARIABLES {
      trapPartitionName,
      trapPartitionId,
      trapEventLevel,
      trapEventId,
      trapUnitName,
      trapMmbVip
   }
   DESCRIPTION "s2io: Adapter error (MC_QUEUES is not ready!)"
   --#TYPE			"Xframe2 Event 50"
   --#SUMMARY		"%s(PID=%d) %s %d %s s2io: Adapter error (MC_QUEUES is not ready!)"
   --#ARGUMENTS		{ 0, 1, 2, 3, 4 }
   --#SEVERITY		MINOR
   ::= 11550

xframe2Event51 TRAP-TYPE
   ENTERPRISE   psaLinXframe2Trap
   VARIABLES {
      trapPartitionName,
      trapPartitionId,
      trapEventLevel,
      trapEventId,
      trapUnitName,
      trapMmbVip
   }
   DESCRIPTION "s2io: Adapter error (M_PLL is not locked!)"
   --#TYPE			"Xframe2 Event 51"
   --#SUMMARY		"%s(PID=%d) %s %d %s s2io: Adapter error (M_PLL is not locked!)"
   --#ARGUMENTS		{ 0, 1, 2, 3, 4 }
   --#SEVERITY		MINOR
   ::= 11551

xframe2Event52 TRAP-TYPE
   ENTERPRISE   psaLinXframe2Trap
   VARIABLES {
      trapPartitionName,
      trapPartitionId,
      trapEventLevel,
      trapEventId,
      trapUnitName,
      trapMmbVip
   }
   DESCRIPTION "s2io: Adapter error (P_PLL is not locked!)"
   --#TYPE			"Xframe2 Event 52"
   --#SUMMARY		"%s(PID=%d) %s %d %s s2io: Adapter error (P_PLL is not locked!)"
   --#ARGUMENTS		{ 0, 1, 2, 3, 4 }
   --#SEVERITY		MINOR
   ::= 11552

xframe2Event53 TRAP-TYPE
   ENTERPRISE   psaLinXframe2Trap
   VARIABLES {
      trapPartitionName,
      trapPartitionId,
      trapEventLevel,
      trapEventId,
      trapUnitName,
      trapMmbVip
   }
   DESCRIPTION "s2io: Adapter error (RC_PRC is not QUIESCENT!)"
   --#TYPE			"Xframe2 Event 53"
   --#SUMMARY		"%s(PID=%d) %s %d %s s2io: Adapter error (RC_PRC is not QUIESCENT!)"
   --#ARGUMENTS		{ 0, 1, 2, 3, 4 }
   --#SEVERITY		MINOR
   ::= 11553

xframe2Event54 TRAP-TYPE
   ENTERPRISE   psaLinXframe2Trap
   VARIABLES {
      trapPartitionName,
      trapPartitionId,
      trapEventLevel,
      trapEventId,
      trapUnitName,
      trapMmbVip
   }
   DESCRIPTION "s2io: Adapter error (SW_Reset failed!)"
   --#TYPE			"Xframe2 Event 54"
   --#SUMMARY		"%s(PID=%d) %s %d %s s2io: Adapter error (SW_Reset failed!)"
   --#ARGUMENTS		{ 0, 1, 2, 3, 4 }
   --#SEVERITY		MINOR
   ::= 11554

END
