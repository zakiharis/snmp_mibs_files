-- extracted from draft-ietf-pce-tc-mib-02.txt
-- at Wed Sep 26 06:09:21 2007

   PCE-TC-STD-MIB DEFINITIONS ::= BEGIN

   IMPORTS
      MODULE-IDENTITY,
      experimental FROM SNMPv2-SMI
      TEXTUAL-CONVENTION
         FROM SNMPv2-TC;

   pceTCDraftMIB MODULE-IDENTITY
      LAST-UPDATED "200709250000Z" -- September 25, 2007
      ORGANIZATION "Path Computation Element (PCE) Working Group"
      CONTACT-INFO "
         Stephan Emile
         France Telecom
      Email: emile.stephan@orange-ftgroup.com

      Email comments directly to the PCE WG Mailing List at pce@ietf.org
      WG-URL: http://www.ietf.org/html.charters/pce-charter.html"
      DESCRIPTION
         "This memo defines a portion of the Management Information Base
         (MIB) for use with network management protocols in the Internet
         community.  In particular, it defines Textual Conventions to
         represent commonly used Path Computation Element (PCE)
         management information.  The intent is that these TEXTUAL
         CONVENTIONS (TCs) will be imported and used in PCE related MIB
         modules to avoid duplicating conventions."
      ::= { pceStdMIB 1 }

   pceStdMIB OBJECT IDENTIFIER ::= { experimental 9999 }

   -- RFC Editor: Please see the IANA Considerations Section.

   -- 'experimental 9999' is a temporary root for running smilint.

   -- 'pceStdMIB' will be homed in 'mib-2'

   -- Textual Conventions (sorted alphabetically).

   PcePcepIdentifier ::= TEXTUAL-CONVENTION
      DISPLAY-HINT "1d.1d.1d.1d:1d:1d"
      STATUS current
      DESCRIPTION
         "The LDP identifier is a six octet quantity which is used to
         identify a PCE client."
      SYNTAX OCTET STRING (SIZE (0..6))

   PceRoutingDomainID ::= TEXTUAL-CONVENTION
      STATUS current
      DESCRIPTION
         "A PCE-DOMAINS information element or a A PCE-DEST-DOMAINS
         information element carries the identifier of a routing domain
         (area, as) which type depends on both the routing protocol and
         on the version of Internet protocol in use in this routing
         domain.

         This TC defines a common SMI type for the different kinds of
         routing domain identifiers.

         A PceRoutingDomainID value is always interpreted within the
         context of an AddressFamilyNumbers value.  Every usage of the
         PceRoutingDomainID textual convention is required to specify
         the AddressFamilyNumbers object which provides the context.

         The value of an PceRoutingDomainID object must always be
         consistent with the value of the associated
         AddressFamilyNumbers object.

         Following is the mapping between AddressFamilyNumbers type and
         PceRoutingDomainID size:
            ipV4(1):
               PceRoutingDomainID is an InetAddressIPv4 corresponding to
               the name of an OSPF area;
            ipV6(2):
               PceRoutingDomainID is an InetAddressIPv6 corresponding to
               the name of an OSPF area;
            nsap(3):
               PceRoutingDomainID type is OCTET STRING (SIZE (0..20)),
               corresponding to the name of an ISIS area (see RFC 1195);
            asNumber(18)
               PceRoutingDomainID type is OCTET STRING (SIZE (2))
               corresponding to the name of an Autonomous System.
         "
      SYNTAX OCTET STRING (SIZE (0..20))

   END

-- 
--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
-- 
-- 
-- Acknowledgment
-- 
--    Funding for the RFC Editor function is provided by the IETF
--    Administrative Support Activity (IASA).
