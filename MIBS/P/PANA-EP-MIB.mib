-- extracted from draft-ietf-pana-snmp-06.txt
-- at Tue Jun 27 06:06:29 2006

               PANA-EP-MIB DEFINITIONS ::= BEGIN

               IMPORTS

               MODULE-IDENTITY, OBJECT-TYPE, NOTIFICATION-TYPE
               FROM SNMPv2-SMI

               TEXTUAL-CONVENTION, RowStatus, PhysAddress, StorageType,
               TimeStamp, TimeInterval
               FROM SNMPv2-TC

               MODULE-COMPLIANCE, OBJECT-GROUP, NOTIFICATION-GROUP
               FROM SNMPv2-CONF

               InterfaceIndex
               FROM IF-MIB

               spdMIB, spdIPEndpointAddType, spdIPEndpointAddress,
               spdActionExecuted, spdIPSourceType, spdIPSourceAddress,
               spdIPDestinationType,spdIPDestinationAddress
               FROM IPSEC-SPD-MIB;

               --
               -- Module identity
               --

               panaMIB MODULE-IDENTITY
               LAST-UPDATED
               "200605280000Z"            -- 28 may 2006
               ORGANIZATION
               "IETF PANA Working Group"
               CONTACT-INFO
               "Yacine El Mghazli
               Alcatel
               Route de Nozay
               91460 Marcoussis
               France
               Email: yacine.el_mghazli@alcatel.fr

               Yoshihiro Ohba
               Toshiba America Research, Inc.
               1, Telcordia Drive
               Piscataway, NJ  08854
               USA
               Email: yohba@tari.toshiba.com"
               DESCRIPTION
               "The MIB module for defining additional PANA-specific objects to
               the IPsec SPD MIB. Copyright (C) The Internet Society (2003).
               This version of this MIB module is part of RFC XXXX, see the
               RFC itself for full legal notices."

               -- Revision History
               REVISION
               "200605280000Z"            -- 28 may 2006
               DESCRIPTION
               "Removed L2 notif"
               REVISION
               "200512280000Z"            -- 22 december 2005
               DESCRIPTION
               "L2 Filter indexing modified"
               REVISION
               "200506280000Z"            -- 28 Juin 2005
               DESCRIPTION
               "L2 protection generic parameters"
               REVISION
               "200502050000Z"            -- 05 February 2005
               DESCRIPTION
               "L2 generic filters"
               REVISION
               "200410220000Z"            -- 22 October 2004
               DESCRIPTION
               "Version 02, draft-ietf-pana-snmp-02.txt"
               REVISION
               "200402050000Z"            -- 05 February 2004
               DESCRIPTION
               "Version 01, draft-yacine-pana-paa2ep-snmp-01.txt"
               REVISION
               "200310310000Z"            -- 31 October 2003
               DESCRIPTION
               "Initial version, draft-yacine-pana-paa2ep-snmp-00.txt"
               ::= { spdMIB  1 } -- XXX to be assigned by IANA

               --
               -- groups of related objects
               --

               panaConfigObjects         OBJECT IDENTIFIER
               ::= { panaMIB 1 }
               panaNotificationObjects   OBJECT IDENTIFIER
               ::= { panaMIB 2}
               panaConformanceObjects    OBJECT IDENTIFIER



               ::= { panaMIB 3 }



               --
               -- Textual Conventions
               --

               PanaKey ::= TEXTUAL-CONVENTION
               STATUS   current
               DESCRIPTION
               "The PanaKey is used to carry a key.  When the key does
               not exist, the length of the key becomes zero."
               SYNTAX      OCTET STRING (SIZE(0..255))

               PanaKeyName ::= TEXTUAL-CONVENTION
               STATUS   current
               DESCRIPTION
               "The PanaKeyName is used to carry the name of a PanaKey.
               When the key name does not exist, the length of the
               key name becomes zero."
               SYNTAX      OCTET STRING (SIZE(0..255))



               --
               -- PANA Additional Filters Objects
               --


               --
               -- The Link-layer Filter Table
               --


               panaL2FilterTable OBJECT-TYPE
               SYNTAX      SEQUENCE OF PanaL2FilterEntry
               MAX-ACCESS  not-accessible
               STATUS      current
               DESCRIPTION
               "Link-layer filter definitions."
               ::= { panaConfigObjects 1 }
               panaL2FilterEntry OBJECT-TYPE
               SYNTAX      PanaL2FilterEntry
               MAX-ACCESS  not-accessible
               STATUS      current
               DESCRIPTION
               "An entry in the Link-layer filter table."
               INDEX       { panaL2FiltEpIfIndex, panaL2FiltAddr }
               ::= { panaL2FilterTable 1 }

               PanaL2FilterEntry ::= SEQUENCE {
               panaL2FiltEpIfIndex         InterfaceIndex,
               panaL2FiltAddr              PhysAddress,
               panaL2FiltPmk               PanaKey,
               panaL2FiltPmkName           PanaKeyName,
               panaL2FiltPmkLifetime       TimeInterval,
               panaL2FiltLastChanged       TimeStamp,
               panaL2FiltStorageType       StorageType,
               panaL2FiltRowStatus         RowStatus
               }

               panaL2FiltEpIfIndex OBJECT-TYPE
               SYNTAX         InterfaceIndex
               MAX-ACCESS     read-create
               STATUS         current
               DESCRIPTION
               "The index identifying the EP interface where the filter
               policy must be enforced on."
               ::= { panaL2FilterEntry 1 }

               panaL2FiltAddr OBJECT-TYPE
               SYNTAX         PhysAddress
               MAX-ACCESS     read-create
               STATUS         current
               DESCRIPTION
               "The authorized device Link-layer address (DI). For
               example, for a 802.x interface, this object normally
               contains a MAC address. For interfaces which do not have such
               an address (e.g., a serial line), this object should contain
               an octet string of zero length."
               ::= { panaL2FilterEntry 2 }

               panaL2FiltPmk OBJECT-TYPE
               SYNTAX      PanaKey
               MAX-ACCESS  read-create
               STATUS      current
               DESCRIPTION
               "This is PMK (Pairwise Master Key) used for bootstraping
               link-layer ciphers."
               ::= {  panaL2FilterEntry 3 }

               panaL2FiltPmkName OBJECT-TYPE
               SYNTAX      PanaKeyName
               MAX-ACCESS  read-create
               STATUS      current
               DESCRIPTION
               "This is the name of the panaL2Pmk."
               ::= { panaL2FilterEntry 4 }

               panaL2FiltPmkLifetime OBJECT-TYPE
               SYNTAX      TimeInterval
               MAX-ACCESS  read-create
               STATUS      current
               DESCRIPTION
               "This is the lifetime of panaL2Pmk."
               ::= { panaL2FilterEntry 5 }

               panaL2FiltLastChanged OBJECT-TYPE
               SYNTAX      TimeStamp
               MAX-ACCESS  read-only
               STATUS      current
               DESCRIPTION
               "The value of sysUpTime when this row was last modified or
               created either through SNMP SETs or by some other external
               means."
               ::= { panaL2FilterEntry 6 }

               panaL2FiltStorageType OBJECT-TYPE
               SYNTAX      StorageType
               MAX-ACCESS  read-create
               STATUS      current
               DESCRIPTION
               "The storage type for this row. Rows in this table which were
               created through an external process may have a storage type
               of readOnly or permanent."
               DEFVAL { nonVolatile }
               ::= { panaL2FilterEntry 7 }

               panaL2FiltRowStatus OBJECT-TYPE
               SYNTAX      RowStatus
               MAX-ACCESS  read-create
               STATUS      current
               DESCRIPTION
               "This object indicates the conceptual status of this row."
               ::= { panaL2FilterEntry 8 }
               --
               --
               -- Notification objects information



               --
               --

               panaNotificationVariables OBJECT IDENTIFIER ::=
               { panaNotificationObjects 1 }

               panaNotifications OBJECT IDENTIFIER ::=



               { panaNotificationObjects 0 }

               panaEpIfIndex OBJECT-TYPE
               SYNTAX      InterfaceIndex
               MAX-ACCESS  accessible-for-notify
               STATUS      current
               DESCRIPTION
               "Contains the interface index on which the packet triggered
               the notification in question."
               ::= { panaNotificationVariables 1 }

               panaL2SourceAddress OBJECT-TYPE
               SYNTAX      PhysAddress
               MAX-ACCESS  accessible-for-notify
               STATUS      current
               DESCRIPTION
               "Contains the source Link layer address of the packet which
               triggered the notification in question. For
               example, for a 802.x frame, this object normally
               contains a MAC address. For interfaces which do not have such
               an address (e.g., a serial line), this object should contain
               an octet string of zero length."
               ::= { panaNotificationVariables 2 }


               panaNewPacNotification NOTIFICATION-TYPE
               OBJECTS {
               spdActionExecuted,
               spdIPEndpointAddType,
               spdIPEndpointAddress,
               spdIPSourceType,
               spdIPSourceAddress,
               spdIPDestinationType,
               spdIPDestinationAddress,
               panaEpIfIndex,
               panaL2SourceAddress}
               STATUS  current
               DESCRIPTION
               "Notification that EP detected traffic coming from an
               unauthorized source.  When source and destination IP addresses
               of the traffic is unknown, spdIPSourceType and
               spdIPDestinationType must be zero.  When source L2 address of
               the traffic is unknown, panaL2SourceAddress must be zero.Notification
               that EP detected traffic coming from an
               unauthorized source."
               ::= { panaNotifications 1 }

               --
               --
               -- Conformance information
               --
               --

               panaGroups OBJECT IDENTIFIER
               ::= { panaConformanceObjects 1 }
               panaCompliances OBJECT IDENTIFIER
               ::= { panaConformanceObjects 2 }

               --
               -- Compliance Groups Definitions
               --

               panaL2FilterGroup OBJECT-GROUP
               OBJECTS {
               panaL2FiltEpIfIndex,
               panaL2FiltAddr,
               panaL2FiltPmk,
               panaL2FiltPmkName,
               panaL2FiltPmkLifetime,
               panaL2FiltLastChanged,
               panaL2FiltStorageType,
               panaL2FiltRowStatus }
               STATUS current
               DESCRIPTION
               "The Link-layer Filter Group."
               ::= { panaGroups 1 }

               panaNewPacNotificationObjectsGroup OBJECT-GROUP
               OBJECTS {
               panaEpIfIndex,
               panaL2SourceAddress }
               STATUS current
               DESCRIPTION
               "PaC Presence Notification Objects Group."
               ::= { panaGroups 2 }

               panaNewPacNotificationGroup NOTIFICATION-GROUP
               NOTIFICATIONS {
               panaNewPacNotification}
               STATUS current
               DESCRIPTION
               "PaC Presence Notification Group."
               ::= { panaGroups 3 }

               --
               -- Compliance statements
               --




               panaFilterCompliance MODULE-COMPLIANCE
               STATUS      current
               DESCRIPTION
               "The compliance statement for SNMP entities that support
               PANA DI-based filtering."

               MODULE -- This Module

               MANDATORY-GROUPS { panaL2FilterGroup }

               OBJECT      panaL2FiltRowStatus
               SYNTAX      RowStatus { active(1), createAndGo(4), destroy(6) }
               DESCRIPTION
               "Support of the values notInService(2), notReady(3),
               and createAndWait(5) is not required."

               OBJECT      panaL2FiltLastChanged
               MIN-ACCESS  not-accessible
               DESCRIPTION
               "This object not required for compliance."


               MODULE IPSEC-SPD-MIB

               MANDATORY-GROUPS {
               spdEndpointGroup,
               spdGroupContentsGroup,
               spdRuleDefinitionGroup,
               spdStaticFilterGroup,
               spdStaticActionGroup }

               OBJECT      spdEndGroupRowStatus
               SYNTAX      RowStatus { active(1), createAndGo(4), destroy(6) }
               DESCRIPTION
               "Support of the values notInService(2), notReady(3),
               and createAndWait(5) is not required."

               OBJECT      spdEndGroupLastChanged
               MIN-ACCESS  not-accessible
               DESCRIPTION
               "This object not required for compliance."

               OBJECT      spdGroupContComponentType
               SYNTAX      INTEGER { rule(2) }
               DESCRIPTION
               "Support of the value group(1) is only required for
               implementations which support Policy Groups within
               Policy Groups."



               OBJECT      spdGroupContRowStatus
               SYNTAX      RowStatus { active(1), createAndGo(4), destroy(6) }
               DESCRIPTION
               "Support of the values notInService(2), notReady(3),
               and createAndWait(5) is not required."

               OBJECT      spdGroupContLastChanged
               MIN-ACCESS  not-accessible
               DESCRIPTION
               "This object not required for compliance."

               OBJECT      spdRuleDefRowStatus
               SYNTAX      RowStatus { active(1), createAndGo(4), destroy(6) }
               DESCRIPTION
               "Support of the values notInService(2), notReady(3),
               and createAndWait(5) is not required."

               OBJECT      spdRuleDefLastChanged
               MIN-ACCESS  not-accessible
               DESCRIPTION
               "This object not required for compliance."

               ::= { panaCompliances 1 }
               panaNewPacNotificationCompliance MODULE-COMPLIANCE
               STATUS      current
               DESCRIPTION
               "The compliance statement for SNMP entities that support
               new PaC presence Notification."

               MODULE -- This Module

               MANDATORY-GROUPS {
               panaNewPacNotificationObjectsGroup,
               panaNewPacNotificationGroup
               }

               MODULE IPSEC-SPD-MIB

               MANDATORY-GROUPS { spdActionLoggingObjectGroup }

               ::= { panaCompliances 2 }

               END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
