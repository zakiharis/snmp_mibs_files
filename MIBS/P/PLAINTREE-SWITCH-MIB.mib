-- PLAINTREE-SWITCH-MIB { iso org(3) dod(6) internet(1) private(4) enterprises(1) 295 }

-- Title:   Ethernet Switch Enterprise MIB Extension
-- Version: 2.0

PLAINTREE-SWITCH-MIB DEFINITIONS ::= BEGIN

IMPORTS
    enterprises, Counter   		 FROM RFC1155-SMI
    OBJECT-TYPE				 FROM RFC-1212
    DisplayString			 FROM RFC1213-MIB
    MacAddress				 FROM RFC1286-MIB
    TRAP-TYPE                            FROM RFC-1215;

-- *******************************************************************
-- High-level identifiers
-- *******************************************************************

vendor                 OBJECT IDENTIFIER ::= { enterprises 295 }

switch                 OBJECT IDENTIFIER ::= { vendor 3 }

switchHardware         OBJECT IDENTIFIER ::= { switch 1 }
switchChassis          OBJECT IDENTIFIER ::= { switchHardware 1 }
switchPort             OBJECT IDENTIFIER ::= { switchHardware 2 }
switchEthernetPort     OBJECT IDENTIFIER ::= { switchPort 1 }
switchWaveBusPort      OBJECT IDENTIFIER ::= { switchPort 2 }
switchFddiPort         OBJECT IDENTIFIER ::= { switchPort 3 }


switchSoftware         OBJECT IDENTIFIER ::= { switch 2 }
switchInfo             OBJECT IDENTIFIER ::= { switchSoftware 1 }

switchBasicTable OBJECT-TYPE
    SYNTAX SEQUENCE OF SwitchEntry
    ACCESS not-accessible
    STATUS mandatory
    DESCRIPTION
    "Basic information about the switch"
    ::= { switchInfo 1 }

switchBasicEntry OBJECT-TYPE
    SYNTAX SwitchEntry
    ACCESS not-accessible
    STATUS mandatory
    DESCRIPTION
    "Identification information about a particular port on the switch."
    INDEX    { switchBasicIndex }
    ::= { switchBasicTable 1 }

SwitchEntry ::= SEQUENCE {
    switchProductCode
        DisplayString,
    switchSerialNumber
        DisplayString,
    switchPlaceOfManufacture
        INTEGER,
    switchDateOfManufacture
        DisplayString,
    switchMacAddress
        MacAddress,
    switchCodeVersion
        DisplayString,
    switchBpeEnabled
        INTEGER,
    eraseSwitchSnmpConfigInfo
        INTEGER,
    restoreSwitchDot1dDefaults
        INTEGER,
    performSwitchReset
        INTEGER,
    switchIdentPressed
        INTEGER,
    ageFilterDatabase
        INTEGER,
    clearStatistics
        INTEGER,
    switchBasicIndex
        INTEGER
  }

switchProductCode OBJECT-TYPE
    SYNTAX DisplayString
    ACCESS read-only
    STATUS mandatory
    DESCRIPTION
    "An ASCII string giving the product code of the switch."
    ::= { switchBasicEntry 1 }

switchSerialNumber OBJECT-TYPE
    SYNTAX DisplayString
    ACCESS read-only
    STATUS mandatory
    DESCRIPTION
    "An ASCII string giving the switch serial number."
    ::= { switchBasicEntry 2 }

switchPlaceOfManufacture OBJECT-TYPE
    SYNTAX INTEGER { inOttawa (1) }
    ACCESS read-only
    STATUS mandatory
    DESCRIPTION
    "A number identifying where the switch was built."
    ::= { switchBasicEntry 3 }

switchDateOfManufacture OBJECT-TYPE
    SYNTAX DisplayString
    ACCESS read-only
    STATUS mandatory
    DESCRIPTION
    "An ASCII string giving the date of manufacture of the switch."
    ::= { switchBasicEntry 4 }

switchMacAddress OBJECT-TYPE
    SYNTAX MacAddress
    ACCESS read-only
    STATUS mandatory
    DESCRIPTION
    "The IEEE 802 MAC address of the switch."
    ::= { switchBasicEntry 5 }

switchCodeVersion OBJECT-TYPE
    SYNTAX DisplayString
    ACCESS read-only
    STATUS mandatory
    DESCRIPTION
    "An ASCII string giving the version number of the switch software."
    ::= { switchBasicEntry 6 }

switchBpeEnabled OBJECT-TYPE
    SYNTAX INTEGER
    ACCESS read-write
    STATUS mandatory
    DESCRIPTION
    "Setting this variable to TRUE (1) causes the bridge protocol engine
     to perform the Spanning Tree Protocol as defined in IEEE802.1d.
     Setting this variable to FALSE (0) causes the BPE to stop performing
     the Spanning Tree Protocol.  The value of this variable when the
     switch starts operating is 1."
    ::= { switchBasicEntry 7 }

eraseSwitchSnmpConfigInfo OBJECT-TYPE
    SYNTAX INTEGER
    ACCESS read-write
    STATUS mandatory
    DESCRIPTION
    "Setting this variable to TRUE (1) causes the switch to erase its
     SNMP configuration information both from memory and from permanent
     store.  The switch the requests new configuration information using
     the BOOTP protocol.  Setting this variable to any other value has
     no effect.  This variable will always return 0 when read."
    ::= { switchBasicEntry 8 }

restoreSwitchDot1dDefaults OBJECT-TYPE
    SYNTAX INTEGER
    ACCESS read-write
    STATUS mandatory
    DESCRIPTION
    "Setting this variable to TRUE (1) causes the BPE to restore the
     default spanning tree values given in the IEEE 802.1d specification.
     This resets all writeable Bridge MIB variables in the dot1dStp group
     of the Bridge MIB.  Setting the variable to any other value has no
     effect.  This variable will always return 0 when read."
    ::= { switchBasicEntry 9 }

performSwitchReset OBJECT-TYPE
    SYNTAX INTEGER
    ACCESS read-write
    STATUS mandatory
    DESCRIPTION
    "Setting this variable to TRUE (1) causes the switch to perform a
    cold restart.  As a result of this action a coldRestart trap will
    be sent.  Setting this variable to any other value has no effect.
    This variable will always return 0 when read."
    ::= { switchBasicEntry 10 }

switchIdentPressed OBJECT-TYPE
    SYNTAX INTEGER
    ACCESS read-only
    STATUS mandatory
    DESCRIPTION
    "This variable is TRUE (1) if the IDENTIFY button on the switch has
    been pressed since the variable was last read.
    After this variable has been read it will be set to 0."
    ::= { switchBasicEntry 11 }

ageFilterDatabase OBJECT-TYPE
    SYNTAX INTEGER
    ACCESS read-write
    STATUS mandatory
    DESCRIPTION
    "Setting this variable to FALSE (0) causes the switch to stop aging
    out entries from its filter database.  Setting this variable to
    TRUE (1) causes the switch to age out filter database entries as
    defined in IEEE 802.1D.  This variable is set to 0 whenever
    the Switch restarts."
    ::= { switchBasicEntry 12 }

clearStatistics OBJECT-TYPE
    SYNTAX INTEGER
    ACCESS read-write
    STATUS mandatory
    DESCRIPTION
    "Setting this variable to TRUE (1) clears the traffic statistics
    accumulators in the switch.  Setting this variable to any other
    value has no effect.  The variable always returns 0 when read."
    ::= { switchBasicEntry 13 }

switchBasicIndex OBJECT-TYPE
    SYNTAX INTEGER
    ACCESS not-accessible
    STATUS mandatory
    DESCRIPTION
    "This is a dummy variable which provides a meta-index for the
    Basic Information Table."
    ::= { switchBasicEntry 100 }

-- *******************************************************************
-- Switch Port Information
-- *******************************************************************

switchPortTable OBJECT-TYPE
    SYNTAX SEQUENCE OF SwitchPortEntry
    ACCESS not-accessible
    STATUS mandatory
    DESCRIPTION
    "Identification information about the ports on a switch."
    ::= { switchInfo 2 }

switchPortEntry OBJECT-TYPE
    SYNTAX SwitchPortEntry
    ACCESS not-accessible
    STATUS mandatory
    DESCRIPTION
    "Identification information about a particular port on the switch."
    INDEX    { switchPortIndex }
    ::= { switchPortTable 1 }

SwitchPortEntry ::= SEQUENCE {
    switchPortIndex
        INTEGER,
    switchPortProductCode
        DisplayString,
    switchPortSerialNumber
        DisplayString,
    switchPortPlaceOfManufacture
        INTEGER,
    switchPortDateOfManufacture
        DisplayString,
    switchPortState
        DisplayString,
    switchPortHighSensitivity
        INTEGER,
    restoreFddiMibDefaults
        INTEGER,
    translateAllEthertypes
        INTEGER,
    switchPortTxFrames
        Counter,
    switchPortRxFrames
        Counter,
    switchPortFcsErrors
        Counter,
    switchPortFilterDiscards
        Counter,
    switchPortDelayExceededDiscards
        Counter,
    switchPortMtuExceededDiscards
        Counter
  }

switchPortIndex OBJECT-TYPE
    SYNTAX INTEGER
    ACCESS read-only
    STATUS mandatory
    DESCRIPTION
    "The number of the port to which the management information applies."
    ::= { switchPortEntry 1 }

switchPortProductCode OBJECT-TYPE
    SYNTAX DisplayString
    ACCESS read-only
    STATUS mandatory
    DESCRIPTION
    "An ASCII string giving the product code of the card on which this
    port is located."
    ::= { switchPortEntry 2 }

switchPortSerialNumber OBJECT-TYPE
    SYNTAX DisplayString
    ACCESS read-only
    STATUS mandatory
    DESCRIPTION
    "An ASCII string giving the serial number of the card on which this
    port is located."
    ::= { switchPortEntry 3 }

switchPortPlaceOfManufacture OBJECT-TYPE
    SYNTAX INTEGER { inOttawa (1) }
    ACCESS read-only
    STATUS mandatory
    DESCRIPTION
    "A number identifying where the card on which this port is located
    was built."
    ::= { switchPortEntry 4 }

switchPortDateOfManufacture OBJECT-TYPE
    SYNTAX DisplayString
    ACCESS read-only
    STATUS mandatory
    DESCRIPTION
    "An ASCII string giving the date of manufacture of the card on which
    this port is located."
    ::= { switchPortEntry 5 }

switchPortState OBJECT-TYPE
    SYNTAX DisplayString
    ACCESS read-only
    STATUS mandatory
    DESCRIPTION
    "An ASCII string giving the port's operational state."
    ::= { switchPortEntry 6 }

switchPortHighSensitivity OBJECT-TYPE
    SYNTAX INTEGER
    ACCESS read-write
    STATUS mandatory
    DESCRIPTION
    "This variable is only valid if the port is an Ethernet port.
    If this variable is set to TRUE (1), the receiver of the Ethernet
    NIC controlling the port is set to high sensitivity.  If the
    variable is set to 0, the port is set to normal sensitivity.

    If the ports on both ends of the 10BaseT link are set to high
    sensitivity, the maximum permissable length of the link is
    increased from 100 meters to 120 meters.

    Caution: a high sensitivity receiver may be overdriven by
    transmitters closer than 100 meters.

    This variable is 0 when the switch is powered up for the first
    time.  Changes to this variable are preserved across
    system restarts."
    ::= { switchPortEntry 7 }

restoreFddiMibDefaults OBJECT-TYPE
    SYNTAX INTEGER
    ACCESS read-write
    STATUS mandatory
    DESCRIPTION
    "This variable is ony valid if the port is an FDDI station.
     Setting this variable to TRUE (1) causes the agent to restore
     the default MIB values given in the ANSI X3T9.5/84-49 Rev 7.2
     specification.  This resets all writable FDDI MIB variables.
     Setting the variable to any other value has no effect.
     This variable will always return 0 when read."
    ::= { switchPortEntry 8 }


translateAllEthertypes OBJECT-TYPE
    SYNTAX INTEGER
    ACCESS read-write
    STATUS mandatory
    DESCRIPTION
    "This variable is only valid if the port is an FDDI port.
    If this variable is set to TRUE (1), the Bridge Tunnel Encapsulation
    Protocol will be applied to frames containing any Ethertypes,  not
    just the ones in the Selective Translation Table.
    If this variable is set to FALSE (0), the protocol will only be applied
    to Ethertypes in the translation table."
    ::= { switchPortEntry 9 }

switchPortTxFrames OBJECT-TYPE
    SYNTAX Counter
    ACCESS read-only
    STATUS mandatory
    DESCRIPTION
    "This counter is incremented by one for each frame transmitted
    to the network segment attached to the port."
    ::= { switchPortEntry 10 }

switchPortRxFrames OBJECT-TYPE
    SYNTAX Counter
    ACCESS read-only
    STATUS mandatory
    DESCRIPTION
    "This counter is incremented by one for each valid frame received
    from the network segment attached to the port."
    ::= { switchPortEntry 11 }

switchPortFcsErrors OBJECT-TYPE
    SYNTAX Counter
    ACCESS read-only
    STATUS mandatory
    DESCRIPTION
    "This counter is incremented by one for each received frame which failed
    its FCS check."
    ::= { switchPortEntry 12 }

switchPortFilterDiscards OBJECT-TYPE
    SYNTAX Counter
    ACCESS read-only
    STATUS mandatory
    DESCRIPTION
    "The number of frames received on this port which have been discarded
    due to the filtering action of the port's bridge circuit."
    ::= { switchPortEntry 13 }

switchPortDelayExceededDiscards OBJECT-TYPE
    SYNTAX Counter
    ACCESS read-only
    STATUS mandatory
    DESCRIPTION
    "The number of frames discarded by this port due to excessive transit
    delay through the switch.  It reports the same value as the object
    dot1dBasePortDelayExceededDiscards in the Bridge MIB (RFC 1493)."
    ::= { switchPortEntry 14 }

switchPortMtuExceededDiscards OBJECT-TYPE
    SYNTAX Counter
    ACCESS read-only
    STATUS mandatory
    DESCRIPTION
    "The number of frames discarded by this port due to excessive size.
    It is the same value reported in the object
    dot1dBasePortMtuExceededDiscards in the Bridge MIB (RFC 1493)."
    ::= { switchPortEntry 15 }

-- 802.1H Selective Translation Table
-- Maximum 3 entries, valid only if the port is an FDDI port.

switchSelectiveTranslationTable OBJECT-TYPE
    SYNTAX SEQUENCE OF TranslationTableEntry
    ACCESS not-accessible
    STATUS mandatory
    DESCRIPTION
    "The Selective Translation Table as defined in IEEE 802.1h."
    ::= { switchInfo 3 }

translationTableEntry OBJECT-TYPE
    SYNTAX TranslationTableEntry
    ACCESS not-accessible
    STATUS mandatory
    DESCRIPTION
    "One entry in the STT."
    INDEX    { translationTablePortIndex }
    ::= { switchSelectiveTranslationTable 1 }

TranslationTableEntry ::= SEQUENCE {
    translationTablePortIndex
        INTEGER,
    translationTableEthertype1
        INTEGER,
    translationTableEntryValid1
        INTEGER,
    translationTableEthertype2
        INTEGER,
    translationTableEntryValid2
        INTEGER,
    translationTableEthertype3
        INTEGER,
    translationTableEntryValid3
        INTEGER
  }

translationTablePortIndex OBJECT-TYPE
    SYNTAX INTEGER
    ACCESS read-only
    STATUS mandatory
    DESCRIPTION
    "The table index - the port number on which the STT resides."
    ::= { translationTableEntry 1 }

translationTableEthertype1 OBJECT-TYPE
    SYNTAX INTEGER
    ACCESS read-write
    STATUS mandatory
    DESCRIPTION
    "The first Ethertype for which the Bridge Tunnel Encapsulation Protocol
    should be used."
    ::= { translationTableEntry 2 }

translationTableEntryValid1 OBJECT-TYPE
    SYNTAX INTEGER
    ACCESS read-write
    STATUS mandatory
    DESCRIPTION
    "If this variable is set to TRUE (1), the Bridge Tunnel Encapsulation
    Protocol will be applied to frames containing the first Ethertype.
    If this variable is set to FALSE (0), the protocol will not be applied
    to the Ethertype."
    ::= { translationTableEntry 3 }

translationTableEthertype2 OBJECT-TYPE
    SYNTAX INTEGER
    ACCESS read-write
    STATUS mandatory
    DESCRIPTION
    "The second Ethertype for which the Bridge Tunnel Encapsulation Protocol
    should be used."
    ::= { translationTableEntry 4 }

translationTableEntryValid2 OBJECT-TYPE
    SYNTAX INTEGER
    ACCESS read-write
    STATUS mandatory
    DESCRIPTION
    "If this variable is set to TRUE (1), the Bridge Tunnel Encapsulation
    Protocol will be applied to frames containing the second Ethertype.
    If this variable is set to FALSE (0), the protocol will not be applied
    to the Ethertype."
    ::= { translationTableEntry 5 }

translationTableEthertype3 OBJECT-TYPE
    SYNTAX INTEGER
    ACCESS read-write
    STATUS mandatory
    DESCRIPTION
    "The third Ethertype for which the Bridge Tunnel Encapsulation Protocol
    should be used."
    ::= { translationTableEntry 6 }

translationTableEntryValid3 OBJECT-TYPE
    SYNTAX INTEGER
    ACCESS read-write
    STATUS mandatory
    DESCRIPTION
    "If this variable is set to TRUE (1), the Bridge Tunnel Encapsulation
    Protocol will be applied to frames containing the third Ethertype.
    If this variable is set to FALSE (0), the protocol will not be applied
    to the Ethertype."
    ::= { translationTableEntry 7 }


-- *******************************************************************
-- TRAPS
-- *******************************************************************

switchTouched TRAP-TYPE
    ENTERPRISE vendor
    VARIABLES { switchIdentPressed }
    DESCRIPTION
    "This trap is generated when the IDENTIFY button on the switch is pressed.

    The agent throttles the generation of consecutive switchTouched traps
    so that there is at least a two second gap between them."
    ::= 9

END
