PARAGON-MIB --{ iso org(3) dod(6) internet(1) private(4) 1 }  

--
--Paragon MIB Objects and Traps format#April 30, 1992 11:55 a.m.
--Problem(s) fixed by HP 5/19/95 : See all lines w/ string "Original MIB".
--


DEFINITIONS ::=	BEGIN
 
IMPORTS
	mgmt, OBJECT-TYPE, IpAddress, private,
	Counter, Gauge, TimeTicks
		FROM RFC1065-SMI
	DisplayString
		FROM RFC1158-MIB;


enterprises  
  OBJECT IDENTIFIER ::= { private 1 }

dupont  
 OBJECT IDENTIFIER ::= { enterprises 159 }

products
 OBJECT IDENTIFIER ::=  { dupont 2 }

paragon
 OBJECT IDENTIFIER ::= { products 1 }

--groups in the PARAGON MIB
pgBasicGroup
 OBJECT IDENTIFIER ::= { paragon 1 }
 
pgAgentModuleGroup
 OBJECT IDENTIFIER ::= { paragon 2 }
 
pgMonitorGroup
 OBJECT IDENTIFIER ::= { paragon 3 }

pgConcentratorGroup
 OBJECT IDENTIFIER ::= { paragon 4 }

pgActionGroup
 OBJECT IDENTIFIER ::= { paragon 5 }


pgAgentRevision
 OBJECT IDENTIFIER ::= { pgAgentModuleGroup 1 }
 
pgAgentRevLevels   
 OBJECT IDENTIFIER ::= { pgAgentRevision 1 }

pgAgentSerial
 OBJECT IDENTIFIER  ::= { pgAgentModuleGroup 2 }
 
pgAgentSerialPort 
 OBJECT IDENTIFIER ::= { pgAgentSerial 1 }
 
pgAgentConf
 OBJECT IDENTIFIER ::= { pgAgentModuleGroup 3 }
 
pgAgentConfig         
 OBJECT IDENTIFIER ::= { pgAgentConf 1 }
 
pgAgentStatus
 OBJECT IDENTIFIER ::= { pgAgentModuleGroup 4 }

pgConcentrator
 OBJECT IDENTIFIER ::= { pgConcentratorGroup 1 }

pgConcentratorInfo 
 OBJECT IDENTIFIER ::= { pgConcentrator 1 }
 
pgActionSys
 OBJECT IDENTIFIER ::= { pgActionGroup 1 }
 
pgActionSystem  
 OBJECT IDENTIFIER  ::= { pgActionSys 1 }

temporary OBJECT IDENTIFIER ::= { dupont 1 } 

dupHubMgmt OBJECT IDENTIFIER ::= { temporary 1 } 

duphmBasicCapability OBJECT IDENTIFIER ::= { dupHubMgmt 1 } 

duphmSelfTestCapability OBJECT IDENTIFIER ::= { dupHubMgmt 2 } 

duphmPerfMonCapability OBJECT IDENTIFIER ::= { dupHubMgmt 3 } 

duphmAddrTrackCapability OBJECT IDENTIFIER ::= { dupHubMgmt 4 } 


--
--The pg Basic Group
--


--The pg Basic Channel Table

pgBasicChannelTable OBJECT-TYPE
	SYNTAX  SEQUENCE OF PgBasicChannelEntry
        ACCESS  not-accessible 
        STATUS  mandatory
        DESCRIPTION
		"Status and configuration information for a collection of 
                 channels in the Paragon system concentrator."

	::= { pgBasicGroup 1 }

pgBasicChannelEntry OBJECT-TYPE
 	SYNTAX  PgBasicChannelEntry
	ACCESS  not-accessible
	STATUS  mandatory
        DESCRIPTION
		"Status and configuration information for a particular
		 channel in the Paragon system concentrator."
        INDEX { pgChannelID }
	::= { pgBasicChannelTable 1 }

PgBasicChannelEntry ::=
 	SEQUENCE { 
	    pgChannelID
		INTEGER,
	    pgChannelIPGCount
		Counter,
	    pgChannelIPGThreshold
		Counter,
            pgChannelMinimumIPG
                Counter,
            pgChannelStatus
		INTEGER,
            pgChannelNumOfCards
                INTEGER
	 }

pgChannelID OBJECT-TYPE
	SYNTAX INTEGER (1..2)
        ACCESS read-only
        STATUS mandatory
	DESCRIPTION
		"The value of the Paragon Channel ID is assigned 
                 so as to uniquely identify a channel in the Paragon system 
                 where a single agent manages multiple channels."

	::= { pgBasicChannelEntry 1 }

pgChannelIPGCount OBJECT-TYPE
 	SYNTAX  Counter
	ACCESS  read-only
	STATUS  mandatory
        DESCRIPTION
		"pgChannelIPGCount object counts the number of
                 IPGs below the object pgMonRptrIPGThreshold,
                 since agent reset."

	::= { pgBasicChannelEntry 2 }

pgChannelIPGThreshold OBJECT-TYPE
 	SYNTAX  Counter
	ACCESS  read-write
	STATUS  mandatory
        DESCRIPTION
                 "This object can be set to trigger a proprietary Threshold
                Crossed Trap.  The IPG Threshold is measured in bit times.
                (e.g. If the inter-packet gap is 9.6 us,
                this is equivalent to 96 bit times)."        
	::= { pgBasicChannelEntry 3 }
	
pgChannelMinimumIPG OBJECT-TYPE
 	SYNTAX  Counter 
	ACCESS  read-only
	STATUS  mandatory
        DESCRIPTION
		"pgChannelMinimumIPG object identifies the lowest inter-packet
                 gap value  in bit times obtained for this repeater
                 since the last agent reset."

	::= { pgBasicChannelEntry 4 }

pgChannelStatus OBJECT-TYPE
	SYNTAX INTEGER { 
                manageable(0),     --able to issue commands on channel and
                                   --monitor statistics
                controllable(1)   --able to issue commands only
                }
        ACCESS read-write
        STATUS mandatory
        DESCRIPTION
		"The pgChannelStatus indicates whether the
                 Paragon system agent can control/monitor
                 the channel effectively."

	::= { pgBasicChannelEntry 5 }


pgChannelNumOfCards OBJECT-TYPE
	SYNTAX   INTEGER (1..20)
        ACCESS   read-only
        STATUS   mandatory
	DESCRIPTION
		"The pgChannelNumOfCards object identifies the number
                 of groups currently in the Paragon system
                 concentrator which can potentially connect to this
                 channel.  Note: A group is connected to a channel when
                 at least one of its ports is connected to the channel."

	::= { pgBasicChannelEntry 6 }

                 
--              
--The paragon Basic Card Table
--

pgBasicCardTable OBJECT-TYPE 
	SYNTAX  SEQUENCE OF PgBasicCardEntry
        ACCESS  not-accessible
        STATUS  mandatory
        DESCRIPTION
		"Table of descriptive information about the groups of 
                ports.  This table will return the same information 
                regardles of the pgCardChannelBasicID"

	::= { pgBasicGroup 2 }
  
pgBasicCardEntry OBJECT-TYPE
 	SYNTAX  PgBasicCardEntry
	ACCESS  not-accessible
	STATUS  mandatory
        DESCRIPTION
		"An entry in the table, containing information about
		a single group of ports."

	INDEX   { pgCardChannelBasicID, pgCardBasicID  }
	::= { pgBasicCardTable 1 }

PgBasicCardEntry ::=
 	SEQUENCE { 
	    pgCardChannelBasicID
		INTEGER,
            pgCardBasicID
		INTEGER,
            pgCardType
                DisplayString,
            pgCardSize
                INTEGER,
            pgCardSerialID
                DisplayString
	 }

pgCardChannelBasicID OBJECT-TYPE
	SYNTAX   INTEGER (1..2)
        ACCESS   read-only
        STATUS   mandatory
        DESCRIPTION
		"Channel ID for identifying the card."

        ::= { pgBasicCardEntry 1 }

pgCardBasicID OBJECT-TYPE
	SYNTAX   INTEGER (1..20)
        ACCESS   read-only
        STATUS   mandatory
        DESCRIPTION
                "A value unique within the Paragon system concentrator,
        where the slots are numbered from left to right."

	::= { pgBasicCardEntry 2 }

pgCardType  OBJECT-TYPE
	SYNTAX   DisplayString (SIZE (1..16))
        ACCESS   read-only
        STATUS   mandatory
        DESCRIPTION
		"The pgCardType object is a text string that contains 
	        the product code for order entry purposes (e.g. EOM-0601)."

        ::= { pgBasicCardEntry 3 }


pgCardSize  OBJECT-TYPE
	SYNTAX   INTEGER (1..3)
        ACCESS   read-only
        STATUS   mandatory
        DESCRIPTION
		"The pgCardSize object indicates the number of slots
                the card occupies in the Paragon system concentrator." 

        ::= { pgBasicCardEntry 4 }

pgCardSerialID  OBJECT-TYPE
	SYNTAX   DisplayString (SIZE (1..16))
        ACCESS   read-only
        STATUS   mandatory
        DESCRIPTION
		"The pgCardSerialID object contains a unique 
                serial code."  
        ::= { pgBasicCardEntry 5 }


--
--The pg Basic Port Table
--
pgBasicPortTable OBJECT-TYPE 
	SYNTAX  SEQUENCE OF PgBasicPortEntry
        ACCESS  not-accessible
        STATUS  mandatory
        DESCRIPTION
		"Table of descriptive information about the ports."

	::= { pgBasicGroup 3 }
  
pgBasicPortEntry OBJECT-TYPE
 	SYNTAX  PgBasicPortEntry
	ACCESS  not-accessible
	STATUS  mandatory
        DESCRIPTION
		"An entry in the table, containing information about
		a single port."

        INDEX { pgPortChannelBasicID, pgPortCardBasicID, pgPortBasicID }
	::= { pgBasicPortTable 1 }

PgBasicPortEntry ::=
 	SEQUENCE { 
	    pgPortChannelBasicID
		INTEGER,
            pgPortCardBasicID
		INTEGER,
            pgPortBasicID
		INTEGER,
            pgPortMediaType
                INTEGER
	 }

pgPortChannelBasicID OBJECT-TYPE
	SYNTAX   INTEGER (1..2)
        ACCESS   read-only
        STATUS   mandatory
      DESCRIPTION
		"Channel ID for identifying the port."

        ::= { pgBasicPortEntry 1 }

pgPortCardBasicID OBJECT-TYPE
	SYNTAX   INTEGER (1..20)
        ACCESS   read-only
        STATUS   mandatory
        DESCRIPTION
                "Card ID for identifying the port."

	::= { pgBasicPortEntry 2 }


pgPortBasicID OBJECT-TYPE
	SYNTAX  INTEGER (1..12)
	ACCESS  read-only
	STATUS  mandatory
	DESCRIPTION
		"A value unique  on the card indicating the port ID."

	::= { pgBasicPortEntry 3 }

pgPortMediaType OBJECT-TYPE
	SYNTAX INTEGER { 
		not-Applicabl(0),
		combined-Media-Types(1), 
		nm850-Fiber-Optic(2),
		twisted-Pair(3),
		unshielded-Twisted-Pair(4),
		shielded-Twisted-Pair(5),
		ohm50-Thin-Coax(6),
		aUI-DTE(7), 
		aUI-MAU(8)
	}	
	ACCESS read-only
	STATUS mandatory
	DESCRIPTION
	"The pgPortMediaType object describes the port's media 
	type.  The ETM-1201-50 card will support either Shielded
	or Unshielded Twisted Pair through jumper selection.  The 
	pgPortMediaType will always return Twisted Pair since this
	selection is not manageable."

        ::= { pgBasicPortEntry 4 }
--
--The Agent Module Group
--

--
--The Agent Module Revision Levels
--

pgAgentSerialNum  OBJECT-TYPE
	SYNTAX   DisplayString (SIZE (1..16))
        ACCESS   read-only
        STATUS   mandatory
        DESCRIPTION
		"The pgAgentSerialNum object contains a unique 
                serial code for the agent module hardware."  

        ::= { pgAgentRevLevels 1 }


pgAgentSoftware  OBJECT-TYPE
	SYNTAX   DisplayString (SIZE (1..10))
        ACCESS   read-only
        STATUS   mandatory
        DESCRIPTION
		"The pgAgentSoftware object contains the agent module's
                 software revision level." 

        ::= { pgAgentRevLevels 2 }

pgAgentROM  OBJECT-TYPE
	SYNTAX   DisplayString (SIZE (1..10))
        ACCESS   read-only
        STATUS   mandatory
        DESCRIPTION
		"The pgAgentROM object contains the agent module's ROM
                revision level."  

        ::= { pgAgentRevLevels 3 }


--
--The Agent Module Serial Port Information
--


pgAgentFlowControl OBJECT-TYPE
	SYNTAX INTEGER { 
		disabled(0),      --Flow Control is disabled
                enabled(1)       --Flow Control is enabled
                }
        ACCESS read-write
        STATUS mandatory
        DESCRIPTION
		"The pgAgentFlowControl indicates whether the
                 flow control for the serial port is enabled."

        ::= { pgAgentSerialPort 1 }

pgAgentBaud OBJECT-TYPE
	SYNTAX INTEGER { 
		  bps300(300),        --bps
                  bps1200(1200),       --bps
                  bps2400(2400),       --bps
                  bps4800(4800),       --bps
                  bps9600(9600),       --bps
                  bps19200(19200)      --bps
                }
        ACCESS read-write
        STATUS mandatory
        DESCRIPTION
		"The pgAgentBaud indicates the baud rate for the
                 agent module's serial port."

        ::= { pgAgentSerialPort 2 }

pgAgentStopBits OBJECT-TYPE
	SYNTAX INTEGER (1..2)
        ACCESS read-write
        STATUS mandatory
        DESCRIPTION
		"The pgAgentStopBits object indicates  the
                 number of stop bits in use for the agent`s serial
                 port."

        ::= { pgAgentSerialPort 3 }

pgAgentParity OBJECT-TYPE
	SYNTAX INTEGER { 
		  none(0),      
                  even(1),       
                  odd(2)      
                  }
        ACCESS read-write
        STATUS mandatory
        DESCRIPTION
		"The pgAgentParity indicates the parity in use for
                 the agent module's serial port."

        ::= { pgAgentSerialPort 4 }

--
--The Agent Module Configuration
--


pgAgentCommBandType  OBJECT-TYPE
        SYNTAX   INTEGER { 
                  in-band(0),   --in-band
                  out-of-band(1)   --out-of-band
                   }
        ACCESS   read-only
        STATUS   mandatory
        DESCRIPTION
                 "pgAgentCommBandType object indicates whether communication 
                  between the agent module and the pgAgentCurrentPrimary 
                  network management station is in-band or
                  out-of-band."

        ::= { pgAgentConfig 1 }

pgAgentTimeout  OBJECT-TYPE
        SYNTAX   INTEGER 
        ACCESS   read-write
        STATUS   mandatory
        DESCRIPTION
                 "pgAgentTimeout object indicates the amount of
         	  time before an agent will search for a new NMS upon
                  receiving no communication from the current NMS. A
                  zero value inhibits the agent from ever searching for
                  a new NMS."

         ::= { pgAgentConfig 2 }

pgAgentDesignatedPrimary  OBJECT-TYPE
        SYNTAX   IpAddress
        ACCESS   read-only
        STATUS   mandatory
        DESCRIPTION
                 "pgAgentDesignatedPrimary  object identifies the network
         	  address of the 'Primary' network management station.
                  The 'Primary' NMS is designated by the agent's download
                  server."

        ::= { pgAgentConfig 3 }


pgAgentLastAuthFail  OBJECT-TYPE
        SYNTAX   IpAddress
        ACCESS   read-only
        STATUS   mandatory
        DESCRIPTION
                 "pgAgentLastAuthFail  object identifies the last 
                  SNMP entity which caused the agent to issue a standard
                  SNMP authentiction trap."

        ::= { pgAgentConfig 4 }

pgAgentLastSecurityFail  OBJECT-TYPE
        SYNTAX   IpAddress
        ACCESS   read-only
        STATUS   mandatory
        DESCRIPTION
                 "pgAgentLastSecurityFail  object identifies the last 
                  SNMP entity which caused the agent to issue a proprietary
                  Security Failure trap."

        ::= { pgAgentConfig 5 }

pgAgentCurrentPrimary  OBJECT-TYPE
        SYNTAX   IpAddress
        ACCESS   read-write
        STATUS   mandatory
        DESCRIPTION
                 "pgAgentCurrentPrimary  object identifies the current 
                  'Primary' network management station by network address.
                  Note: this variable is only read-write for a SNMP 
                  Set-Request delivered from the pgAgentDesignatedPrimary."
 
        ::= { pgAgentConfig 6 }

pgAgentDownloadServer  OBJECT-TYPE
        SYNTAX   IpAddress
        ACCESS   read-only
        STATUS   mandatory
        DESCRIPTION
                 "pgAgentDownloadServer  object identifies the download 
                  server station by network address."

        ::= { pgAgentConfig 7 }

pgAgentLastSetRequest  OBJECT-TYPE
        SYNTAX   IpAddress
        ACCESS   read-only
        STATUS   mandatory
        DESCRIPTION
                 "pgAgentLastSetRequest  object identifies the last 
                  SNMP entity that sent a SET-REQUEST to the agent."

        ::= { pgAgentConfig 8 }

pgAgentDipSwitches  OBJECT-TYPE
        SYNTAX   OCTET STRING (SIZE(1..2))   --bit map
        ACCESS   read-only
        STATUS   mandatory
        DESCRIPTION
                 "This octet string represents the current configuration
                  of the agent's dipswitch settings, encoded as a bit
                  string.  Each dipswitch is represented by a single bit.
                  When the value of a bit=1, it indicates that the dipswitch is
                  set to the ON position.  The number of octets is 2 to 
                  represent the 10 dipswitches.  The first octet will encode the
                  configuration of dipswitches 1-8, where 1 represents the
                  Serial Port Access, 2 represents the Timeout Feature, and
                  3 represents the Security Feature,7 represents agent
                  configuration, and 8 represents talking through a router.
                  The rest of the dipswitches are currently not used."

        ::= { pgAgentConfig 9 }
        
pgAgentNetPackAddr1  OBJECT-TYPE
        SYNTAX   IpAddress
        ACCESS   read-only
        STATUS   mandatory
        DESCRIPTION
                 "pgAgentNetPackAddr1 object contains the network
                  address for the NetPack1." 
        ::= { pgAgentConfig 10 }
        
pgAgentNetPackAddr2  OBJECT-TYPE
        SYNTAX   IpAddress
        ACCESS   read-only
        STATUS   mandatory
        DESCRIPTION
                 "pgAgentNetPackAddr2 object contains the network
                  address for the NetPack2." 

        ::= { pgAgentConfig 11 }
        
pgAgentNetPackAddr3  OBJECT-TYPE
        SYNTAX   IpAddress
        ACCESS   read-only
        STATUS   mandatory
        DESCRIPTION
                 "pgAgentNetPackAddr3 object contains the network
                  address for the NetPack3." 

        ::= { pgAgentConfig 12 }
        
pgAgentNetPackAddr4  OBJECT-TYPE
        SYNTAX   IpAddress
        ACCESS   read-only
        STATUS   mandatory
        DESCRIPTION
                 "pgAgentNetPackAddr4 object contains the network
                  address for the NetPack4." 

        ::= { pgAgentConfig 13 }
        
pgAgentNetPackAddr5  OBJECT-TYPE
        SYNTAX   IpAddress
        ACCESS   read-only
        STATUS   mandatory
        DESCRIPTION
                 "pgAgentNetPackAddr5 object contains the network
                  address for the NetPack5." 

        ::= { pgAgentConfig 14 }
        
pgAgentNetPackAddr6  OBJECT-TYPE
        SYNTAX   IpAddress
        ACCESS   read-only
        STATUS   mandatory
        DESCRIPTION
                 "pgAgentNetPackAddr6 object contains the network
                  address for the NetPack6." 

        ::= { pgAgentConfig 15 }

pgAgentLearnedNMSTable  OBJECT-TYPE
        SYNTAX   SEQUENCE OF PgAgentLearnedNMSEntry
        ACCESS   not-accessible
        STATUS   mandatory
        DESCRIPTION
                 "Table of information about the network management
                 stations which have communicated with the agent." 
        ::= { pgAgentConfig 16 }

pgAgentLearnedNMSEntry  OBJECT-TYPE
        SYNTAX   PgAgentLearnedNMSEntry
        ACCESS   not-accessible
        STATUS   mandatory
        DESCRIPTION
                 "An entry in the table, containing information about
                 a network management station which has communicated
                 with the agent." 
        ::= { pgAgentLearnedNMSTable 1 }

PgAgentLearnedNMSEntry ::=
	SEQUENCE {
		pgAgentLearnedNMSAddr
			IpAddress
	}
	
pgAgentLearnedNMSAddr  OBJECT-TYPE
        SYNTAX   IpAddress
        ACCESS   read-only
        STATUS   mandatory
        DESCRIPTION
                 "pgAgentLearnedNMSAddr object identifies the 
                 address of the NMS which has communicated with
                 this agent." 
        ::= { pgAgentLearnedNMSEntry 1 }


pgAgentNetPackMACAddr1  OBJECT-TYPE
        SYNTAX   OCTET STRING (SIZE(6))
        ACCESS   read-only
        STATUS   mandatory
        DESCRIPTION
                 "pgAgentNetPackMACAddr1 object contains the MAC
                  address for the NetPack1."
        ::= { pgAgentConfig 17 }
        
pgAgentNetPackMACAddr2  OBJECT-TYPE
        SYNTAX   OCTET STRING (SIZE(6))
        ACCESS   read-only
        STATUS   mandatory
        DESCRIPTION
                 "pgAgentNetPackMACAddr2 object contains the MAC
                  address for the NetPack2."

        ::= { pgAgentConfig 18 }
        
pgAgentNetPackMACAddr3  OBJECT-TYPE
        SYNTAX   OCTET STRING (SIZE(6))
        ACCESS   read-only
        STATUS   mandatory
        DESCRIPTION
                 "pgAgentNetPackMACAddr3 object contains the MAC
                  address for the NetPack3."

        ::= { pgAgentConfig 19 }
        
pgAgentNetPackMACAddr4  OBJECT-TYPE
        SYNTAX   OCTET STRING (SIZE(6))
        ACCESS   read-only
        STATUS   mandatory
        DESCRIPTION
                 "pgAgentNetPackMACAddr4 object contains the MAC
                  address for the NetPack4."

        ::= { pgAgentConfig 20 }
        
pgAgentNetPackMACAddr5  OBJECT-TYPE
        SYNTAX   OCTET STRING (SIZE(6))
        ACCESS   read-only
        STATUS   mandatory
        DESCRIPTION
                 "pgAgentNetPackMACAddr5 object contains the MAC
                  address for the NetPack5."

        ::= { pgAgentConfig 21 }
        
pgAgentNetPackMACAddr6  OBJECT-TYPE
        SYNTAX   OCTET STRING (SIZE(6))
        ACCESS   read-only
        STATUS   mandatory
        DESCRIPTION
                 "pgAgentNetPackMACAddr6 object contains the MAC
                  address for the NetPack6."

        ::= { pgAgentConfig 22 }


pgAgentNetPackState1  OBJECT-TYPE
        SYNTAX   INTEGER { 
                 notInstalled(0),     
                 initializing(1),   
                 monitoring(2),
                 nms-netpack(3),
                 installed-not-in-use(4) 
                 }
            
        ACCESS   read-only
        STATUS   mandatory
        DESCRIPTION
                 "pgAgentNetPackState1 object identifies the state  
                  of the NetPack1."

        ::= { pgAgentConfig 23 }
        
pgAgentNetPackState2  OBJECT-TYPE
        SYNTAX   INTEGER { 
                 notInstalled(0),     
                 initializing(1),   
                 monitoring(2),
                 nms-netpack(3),
                 installed-not-in-use(4)   
                 }
            
        ACCESS   read-only
        STATUS   mandatory
        DESCRIPTION
                 "pgAgentNetPackState2 object identifies the state  
                  of the NetPack2."

        ::= { pgAgentConfig 24 }
        
pgAgentNetPackState3  OBJECT-TYPE
        SYNTAX   INTEGER { 
                 notInstalled(0),     
                 initializing(1),   
                 monitoring(2),
                 nms-netpack(3),
                 installed-not-in-use(4)    
                 }
            
        ACCESS   read-only
        STATUS   mandatory
        DESCRIPTION
                 "pgAgentNetPackState3 object identifies the state  
                  of the NetPack3."

        ::= { pgAgentConfig 25 }
pgAgentNetPackState4  OBJECT-TYPE
        SYNTAX   INTEGER { 
                 notInstalled(0),     
                 initializing(1),   
                 monitoring(2),
                 nms-netpack(3),
                 installed-not-in-use(4)   
                 }
            
        ACCESS   read-only
        STATUS   mandatory
        DESCRIPTION
                 "pgAgentNetPackState4 object identifies the state  
                  of the NetPack4."

        ::= { pgAgentConfig 26 }
        
pgAgentNetPackState5  OBJECT-TYPE
        SYNTAX   INTEGER { 
                 notInstalled(0),     
                 initializing(1),   
                 monitoring(2),
                 nms-netpack(3),
                 installed-not-in-use(4)    
                 }
            
        ACCESS   read-only
        STATUS   mandatory
        DESCRIPTION
                 "pgAgentNetPackState5 object identifies the state  
                  of the NetPack5."

        ::= { pgAgentConfig 27 }

pgAgentNetPackState6  OBJECT-TYPE
        SYNTAX   INTEGER { 
                 notInstalled(0),     
                 initializing(1),   
                 monitoring(2),
                 nms-netpack(3),
                 installed-not-in-use(4)   
                 }
            
        ACCESS   read-only
        STATUS   mandatory
        DESCRIPTION
                 "pgAgentNetPackState6 object identifies the state  
                  of the NetPack6."

        ::= { pgAgentConfig 28 }
        
pgAgentConfigChanges OBJECT-TYPE
        SYNTAX   INTEGER { 
                 no-Change(0),     
                 change-Found(1)  
                 }

        ACCESS   read-only
        STATUS   mandatory
        DESCRIPTION
                 "Denotes whether a configuration change has been noted in
                  the Concentrator after a power-up condition. This object 
                  is bound as part of the ColdStart Trap optional variables."

        ::= { pgAgentConfig 29 }


--
--The Agent Module Status Information
--


pgAgentDaughterboard  OBJECT-TYPE
        SYNTAX   INTEGER { 
                 notInstalled(1),
                 normal(2),
                 fault(3)
                  }
        ACCESS   read-only
        STATUS   mandatory
        DESCRIPTION
                 "Status condition for the Agent Module optional Daughterboard."

	::= { pgAgentStatus 1 }

pgAgentInternalBus  OBJECT-TYPE
        SYNTAX   INTEGER { 
                 reserved(1),
                 normal(2),
                 fault(3)
                 }
        ACCESS   read-only
        STATUS   mandatory
        DESCRIPTION
                 "Status condition for the Agent Module MCI Bus"

	::= { pgAgentStatus 2 }

pgAgentCorrelator  OBJECT-TYPE
        SYNTAX   INTEGER {
                reserved(1),          
                normal(2),
                fault(3),
		cant-get-synch(4),          --Unable to achieve Foreground 
				            --Correlation Data Synchronization, 
				            --possible Agent problem or traffic
				            --too high  
		mci-command-timeout(5),     --MCI command request timeout, 
					    --possible MCI hardware problem 
		mci-timeout-error(6),       --MCI pending request timeout, 
				            --possible MCI hardware problem   
		pending-full(7),            --Foreground Pending full error, 
			                    --possible Agent software problem 
		mci-error(8),               --MCI pending request timeout, 
				            --possible Agent software problem 
		fbc-request-full(9),        --Foreground Background
				            --Communication queue full,  
				            --possible Agent software problem 
		amb-cant-send-response(10), --AMB-Comm can't send back to 
					    --Control LAN process, possible 
					    --Agent software problem  
		fore-out-of-buffers(11),    --Out of MCI queue or LAN Pack 
					    --buffers, possible Agent software 
					    --problem  
		mw-out-of-range(12)         --Module Word delivered by the MCI 
					    --is out of slot range, possible MCI
					    --hardware problem  
	}
        ACCESS   read-only
        STATUS   mandatory
        DESCRIPTION
                 "Status condition for the Agent Module Data Acquisition 
                  Foreground Process."

	::= { pgAgentStatus 3 }


pgAgentNetPackStatus1  OBJECT-TYPE
        SYNTAX   INTEGER { 
                 notInstalled(1),
                 normal(2),
                 fault(3)
                }
        ACCESS   read-only
        STATUS   mandatory
        DESCRIPTION
                 "pgAgentNetPackStatus1 object indicates the current 
                  operational status of the Agent's NetPack."

        ::= { pgAgentStatus 4 }

pgAgentNetPackStatus2  OBJECT-TYPE
        SYNTAX   INTEGER { 
                 notInstalled(1),
                 normal(2),
                 fault(3)
                }
        ACCESS   read-only
        STATUS   mandatory
         DESCRIPTION
                 "pgAgentNetPackStatus2 object indicates the current 
                  operational status of the Agent's NetPack."

       ::= { pgAgentStatus 5 }

pgAgentNetPackStatus3  OBJECT-TYPE
        SYNTAX   INTEGER { 
                 notInstalled(1),
                 normal(2),
                 fault(3)
                }
        ACCESS   read-only
        STATUS   mandatory
        DESCRIPTION
                 "pgAgentNetPackStatus3 object indicates the current 
                  operational status of the Agent's NetPack."

        ::= { pgAgentStatus 6 }

pgAgentNetPackStatus4  OBJECT-TYPE
        SYNTAX   INTEGER { 
                 notInstalled(1),
                 normal(2),
                 fault(3)
                }
        ACCESS   read-only
        STATUS   mandatory
        DESCRIPTION
                 "pgAgentNetPackStatus4 object indicates the current 
                  operational status of the Agent's NetPack."

        ::= { pgAgentStatus 7 }

pgAgentNetPackStatus5  OBJECT-TYPE
        SYNTAX   INTEGER { 
                 notInstalled(1),
                 normal(2),
                 fault(3)
                }
        ACCESS   read-only
        STATUS   mandatory
        DESCRIPTION
                 "pgAgentNetPackStatus5 object indicates the current 
                  operational status of the Agent's NetPack."

       ::= { pgAgentStatus 8 }

pgAgentNetPackStatus6  OBJECT-TYPE
        SYNTAX   INTEGER { 
                 notInstalled(1),
                 normal(2),
                 fault(3)
                }
        ACCESS   read-only
        STATUS   mandatory
        DESCRIPTION
                 "pgAgentNetPackStatus6 object indicates the current 
                  operational status of the Agent's NetPack."

        ::= { pgAgentStatus 9 }
        

--
--The paragon Monitor Group
--


--The paragon Monitor Repeater Table

pgMonitorRptrTable OBJECT-TYPE
	SYNTAX  SEQUENCE OF PgMonitorRptrEntry
        ACCESS  not-accessible
        STATUS  mandatory
        DESCRIPTION
                 "Statistics for the current functioning repeater in the 
                  concentrator."

	::= { pgMonitorGroup 1 }

pgMonitorRptrEntry OBJECT-TYPE
 	SYNTAX  PgMonitorRptrEntry
	ACCESS  not-accessible
	STATUS  mandatory
        DESCRIPTION
                 "Entry for the current functioning repeater in the 
                  concentrator."
	INDEX   { pgMonRptrID }

	::= { pgMonitorRptrTable 1 }

PgMonitorRptrEntry ::=
 	SEQUENCE { 
	    pgMonRptrID
		INTEGER,
            pgMonRptrTotalFrames
		Counter,
            pgMonRptrTotalReadFrames
		Counter,
	    pgMonRptrTotalFCSErrs
		Counter,
	    pgMonRptrTotalAlignmentErrs
	        Counter,
	    pgMonRptrTotalRunts
	        Counter,
	    pgMonRptrTotalLateColl
	        Counter,
	    pgMonRptrTotalShortEvents
		Counter,
	    pgMonRptrMPRStatus
		INTEGER,
	    pgMonRptrMPRMJLPCount
		Counter
	 }

pgMonRptrID OBJECT-TYPE
 	SYNTAX  INTEGER (1..2)
	ACCESS  read-only
	STATUS  mandatory
        DESCRIPTION
                 "pgMonRptrID identifies the repeaterfor which this entry
                  contains monitor information."

	::= { pgMonitorRptrEntry 1 }

pgMonRptrTotalFrames OBJECT-TYPE
 	SYNTAX  Counter 
	ACCESS  read-only
	STATUS  mandatory
        DESCRIPTION
                 "pgMonRptrTotalFrames counts the total number of frames that 
                  have been received by the repeater, including error prone 
                  packets."

        ::= { pgMonitorRptrEntry 2 }

pgMonRptrTotalReadFrames OBJECT-TYPE
 	SYNTAX  Counter 
	ACCESS  read-only
	STATUS  mandatory
        DESCRIPTION
                 "pgMonRptrTotalReadFrames counts the total number of frames 
                  that have valid frame length and no FCS Errors."

	::= { pgMonitorRptrEntry 3 }

pgMonRptrTotalFCSErrs OBJECT-TYPE
 	SYNTAX  Counter 
	ACCESS  read-only
	STATUS  mandatory
        DESCRIPTION
                 "pgMonRptrTotalFCSErrs counts the total number of frames 
                  that have FCS Errors and no Framing Errors.  The frame size
                  must also be greater than or equal to 64 octets and less than 
                  or equal to 1518 octets."

	::= { pgMonitorRptrEntry 4 }

pgMonRptrTotalAlignmentErrs OBJECT-TYPE
 	SYNTAX  Counter 
	ACCESS  read-only
	STATUS  mandatory
        DESCRIPTION
                 "pgMonRptrTotalAlignmentErrs counts the total number of frames 
                  that have both FCS Errors and Framing Errors.  The frame size
                  must also be greater than or equal to 64 octets and less than 
                  or equal to 1518 octets."

	::= { pgMonitorRptrEntry 5 }

pgMonRptrTotalRunts OBJECT-TYPE
 	SYNTAX  Counter 
	ACCESS  read-only
	STATUS  mandatory
        DESCRIPTION
                 "pgMonRptrTotalRunts counts the total number of collision 
                  fragments with runt errors (frames longer than 74 bits and 
                  less than 512 bits)."

	::= { pgMonitorRptrEntry 6 }

pgMonRptrTotalLateColl OBJECT-TYPE
 	SYNTAX  Counter 
	ACCESS  read-only
	STATUS  mandatory
        DESCRIPTION
                 "pgMonRptrTotalLateColl counts the total number of collision 
                  fragments with size longer than 512 bits."

	::= { pgMonitorRptrEntry 7 }



pgMonRptrTotalShortEvents OBJECT-TYPE
 	SYNTAX  Counter 
	ACCESS  read-only
	STATUS  mandatory
        DESCRIPTION
                 "pgMonRptrTotalShortEvents of fragments received by the 
                  repeater that are less than 74 bits in length."
  
	::= { pgMonitorRptrEntry 8 }



pgMonRptrMPRStatus  OBJECT-TYPE
	SYNTAX  INTEGER {
		normal(1),
		fIFO-Underrun(2),
		fIFO-Overflowed(3),
		mJLP-Activated(4),
		timed-Out-Reset(5),
		other(6)
		}
	ACCESS	read-only
	STATUS	mandatory
	DESCRIPTION
		"pgMonRptrMPRStatus indicates the current status of the MPR.  
		It will display the value of Normal when the MPR is not 
		experiencing one of the error conditions.  If more than one of 
		the error conditions is present in close succession, a 
		pgMPRErrors trap will be sent for each of the error 
		conditions noted.   pgMonRptrMPRStatus will hold the value 
		of the most recent status."
	::= {pgMonitorRptrEntry 9}


	
pgMonRptrMPRMJLPCount  OBJECT-TYPE
	SYNTAX  Counter 
	ACCESS	read-only
	STATUS	mandatory
	DESCRIPTION
		"pgMonRptrMPRMJLPCount indicates the number of times the MAU 
		Jabber Lockup Protection (MJLP) has been activated.  This 
		variable counts how many times the MPR has noted jabbering on 
		a port and has initiated its MJLP feature to control this 
		jabbering.  After a port has sent 50 milliseconds of constant 
		data, the MJLP feature will interrupt a port and stop data from 
		being sent on that port for 10 microseconds."	
	::= {pgMonitorRptrEntry 10}



--
--The paragon Monitor Port Table
--
pgMonitorPortTable OBJECT-TYPE 
	SYNTAX  SEQUENCE OF PgMonitorPortEntry
        ACCESS  not-accessible
        STATUS  mandatory
        DESCRIPTION
                 "Table of statistical information about the monitored ports."
                 
 	::= { pgMonitorGroup 2 }
  
pgMonitorPortEntry OBJECT-TYPE
 	SYNTAX  PgMonitorPortEntry
	ACCESS  not-accessible
	STATUS  mandatory
         DESCRIPTION
                 "An entry in the pgMonitorPortTable, containing statistical
                  information about a single port."
         INDEX { pgMonPortRptrID, pgMonPortCardID, pgMonPortID }
                
 	::= { pgMonitorPortTable 1 }

PgMonitorPortEntry ::=
 	SEQUENCE { 
	    pgMonPortRptrID
		INTEGER,
            pgMonPortCardID
		INTEGER,
            pgMonPortID
		INTEGER,
            pgMonPortTotalFrames
                Counter,
            pgMonPortTotalCollisions
                Counter,
            pgMonPortCollRate
                INTEGER,
            pgMonPortCollThreshold
             	INTEGER,
            pgMonPortLateCollisions
                Counter,
	    pgMonPortErrorRate
		INTEGER,
	    pgMonPortErrorThreshold
		INTEGER,
	    pgMonPortOutOfRange
	        Counter,
	    pgMonPortCollHysteresis
		INTEGER,
	    pgMonPortErrorHysteresis
		INTEGER,
	    pgMonPortLinkStatus
		INTEGER,
	    pgMonPortJabberStatus
		INTEGER,
	    pgMonPortTransmitCollisions
		Counter
           }

pgMonPortRptrID OBJECT-TYPE
	SYNTAX   INTEGER (1..2)
        ACCESS   read-only
        STATUS   mandatory
        DESCRIPTION
                 "Repeater ID for the specified port."
                  
         ::= { pgMonitorPortEntry 1 }

pgMonPortCardID OBJECT-TYPE
	SYNTAX   INTEGER (1..20)
        ACCESS   read-only
        STATUS   mandatory
        DESCRIPTION
                 "Card ID for the specified port."
 
 	::= { pgMonitorPortEntry 2 }


pgMonPortID OBJECT-TYPE
	SYNTAX  INTEGER (1..12)
	ACCESS  read-only
	STATUS  mandatory
        DESCRIPTION
                 "A value unique to the card indicating the port ID."
 
 	::= { pgMonitorPortEntry 3 }


pgMonPortTotalFrames OBJECT-TYPE
	SYNTAX Counter
	ACCESS read-only
	STATUS mandatory
        DESCRIPTION
                 "pgMonPortTotalFrames is a count of the number of frames
                  that have been received by the port, including error prone
                  packets."
 
         ::= { pgMonitorPortEntry 4 }
        
pgMonPortTotalCollisions OBJECT-TYPE
	SYNTAX Counter
	ACCESS read-only
	STATUS mandatory
        DESCRIPTION
                 "pgMonPortTotalCollisions is a count of the number of fragments
                  that have size less than 512 bits."
 
         ::= { pgMonitorPortEntry 5 }

pgMonPortCollRate OBJECT-TYPE
	SYNTAX INTEGER
	ACCESS read-only
	STATUS mandatory
        DESCRIPTION
                 "pgMonPortCollRate is a calculation of the total number of 
                  collisions for the last second divided by the frames received 
                  (pgMonPortTotalFrames) for the last second.  This value is 
                  expressed in tenths of a percent."
 
        ::= { pgMonitorPortEntry 6 }
        
pgMonPortCollThreshold OBJECT-TYPE
	SYNTAX INTEGER
	ACCESS read-write
	STATUS mandatory
        DESCRIPTION
                 "pgMonPortCollThreshold is the threshold value for collision 
                  rate in percent which, if reached, causes a proprietary trap
                  notification to be sent to the NMS."
 
        ::= { pgMonitorPortEntry 7 }

pgMonPortLateCollisions OBJECT-TYPE
	SYNTAX Counter
	ACCESS read-only
	STATUS mandatory
        DESCRIPTION
                 "pgMonPortLateCollisions is the count of collisions which
                  occured after 512 bit times."
                  
         ::= { pgMonitorPortEntry 8 }

pgMonPortErrorRate OBJECT-TYPE
	SYNTAX INTEGER
	ACCESS read-only
	STATUS mandatory
        DESCRIPTION
                 "pgMonPortErrorRate is a calculation of the total number of 
                  errors (FCS, Alignment, Short Events, Frames Too Long) for
                  the last second divided by the frames received 
                  (pgMonPortTotalFrames) for the last second.  This value
                  is expressed in tenths of a percent."
                  
       ::= { pgMonitorPortEntry 9 }

pgMonPortErrorThreshold OBJECT-TYPE
	SYNTAX INTEGER
	ACCESS read-write
	STATUS mandatory
        DESCRIPTION
                 "pgMonPortErrorThreshold is the threshold value for error 
                  rate in percent which, if reached, causes a proprietary trap
                  notification to be sent to the NMS."
 
        ::= { pgMonitorPortEntry 10 }
        
pgMonPortOutOfRange OBJECT-TYPE
	SYNTAX Counter
	ACCESS read-only
	STATUS mandatory
        DESCRIPTION
                 "pgMonPortOutOfRange is count of frames which are noted as 
                 having their size out of the range for good frames.  That is 
                 either greater than 1518 octets or less than 64 octets."
 
        ::= { pgMonitorPortEntry 11 }
        
pgMonPortCollHysteresis OBJECT-TYPE
	SYNTAX INTEGER
	ACCESS read-write
	STATUS mandatory
        DESCRIPTION
                 "pgMonPortCollHysteresis is the hysteresis value for the 
                  collision rate in percent which if crossed (after a Threshold 
                  cross) causes a proprietary trap notification to be sent to 
                  the NMS."

        ::= { pgMonitorPortEntry 12 }

pgMonPortErrorHysteresis OBJECT-TYPE
	SYNTAX INTEGER
	ACCESS read-write
	STATUS mandatory
        DESCRIPTION
                 "pgMonPortErrorHysteresis is the hysteresis value for the 
                  error rate in percent which if crossed (after a Threshold 
                  cross) causes a proprietary trap notification to be sent to 
                  the NMS."

        ::= { pgMonitorPortEntry 13 }


		
pgMonPortLinkStatus  OBJECT-TYPE			
	SYNTAX  INTEGER {
		not-Applicable(1),
		link-Pass-State(2),
		link-Fail-State(3)

		}
		
	ACCESS	read-only
	STATUS	mandatory
	DESCRIPTION
		"pgMonPortLinkStatus indicates whether the port state is link 
		pass or link fail.  This status is applicable to 
		the following cards:  Ethernet Twisted Pair, Ethernet 
		Optical Module.  Ports on other cards will report 
		Not-Applicable for this status."
	::= {pgMonitorPortEntry 14}



pgMonPortJabberStatus  OBJECT-TYPE			
	SYNTAX  INTEGER {
		not-Applicable(1),
		non-Jabber-State(2),
		jabber-State(3)


		}
		
	ACCESS	read-only
	STATUS	mandatory
	DESCRIPTION
		"pgMonPortJabberStatus indicates whether the port is 
		currently jabbering or not.  This status is applicable to 
		the following cards:  Ethernet Twisted Pair, Ethernet 
		Optical Module.  Ports on other cards will report 
		Not-Applicable for this status."	
	::= {pgMonitorPortEntry 15}



pgMonPortTransmitCollisions  OBJECT-TYPE	
	SYNTAX  Counter
	ACCESS	read-only
	STATUS	mandatory
	DESCRIPTION
		"pgMonPortTransmitCollisions is incremented each time
		a port transmits and receives data simultaneously or two
		ports receive data simultaneously."	
	::= {pgMonitorPortEntry 16}



--
--The paragon System Concentrator Group
--

pgConcModel OBJECT-TYPE
	SYNTAX DisplayString (SIZE(1..16))
	ACCESS read-only
	STATUS mandatory
        DESCRIPTION
                 "pgConcModel is the model number of the concentrator for
                  order entry purposes."

        ::= { pgConcentratorInfo 1 }

pgConcSerialNumber OBJECT-TYPE
	SYNTAX DisplayString (SIZE(1..16))
	ACCESS read-only
	STATUS mandatory
        DESCRIPTION
                 "pgConcSerialNumber is the serial number of the concentrator."

        ::= { pgConcentratorInfo 2 }

pgConcTemperature OBJECT-TYPE
	SYNTAX INTEGER { 
               normal(0),
               overTemperature(1)    
               }
	ACCESS read-only
	STATUS mandatory
        DESCRIPTION
                 "pgConcTemperature indicates operating temperature state for
                  the concentrator."

        ::= { pgConcentratorInfo 3 }



pgConcPowerSupply OBJECT-TYPE
	SYNTAX INTEGER { 
               powerSupply2Fault(1),
               powerSupply1Fault(2),
               powerSupplysOK(3)
               }
	ACCESS read-only
	STATUS mandatory
        DESCRIPTION
                 "pgConcPowerSupply indicates dual-redundant power supply status
                  for the concentrator."

        ::= { pgConcentratorInfo 4 }


--
--The paragon Action Group
--



pgWarmStartReset OBJECT-TYPE
 	SYNTAX  INTEGER {
 	          no-reset(0), 
 	          reset(1) 
 		 }
 	ACCESS  read-write
 	STATUS  mandatory
        DESCRIPTION
                 "pgWarmStartReset is an action requesting a warm start of the
                  concentrator system.  All counters are cleared for all Hubs
                  and a Warm Start Trap is issued to the NMS."

  	::= { pgActionSystem 1 }

pgColdStartReset OBJECT-TYPE
 	SYNTAX  INTEGER { 
 	           no-reset(0), 
 		   resetWithCurrentConfig(1),
 		   resetWithDefaultConfig(2)
 		 }
 	ACCESS  read-write
 	STATUS  mandatory
        DESCRIPTION
                 "pgColdStartReset is an action requesting a cold start of the
                  concentrator system.   If the value is resetWithCurrentConfig 
                  then all counters are cleared for all Hubs with the 
                  concentrator configuration kept intact. If the value is 
                  resetWithDefaultConfig then all counters are cleared for all 
                  Hubs with the concentrator configuration reset to default 
                  values. All Repeaters are reset and a Cold Start Trap is 
                  issued to the NMS."

 	::= { pgActionSystem 2 }

pgNetPackSelftest OBJECT-TYPE
 	SYNTAX  INTEGER { 
 		   testNetPack1(0),
 		   testNetPack2(1),
 		   testNetPack3(2),
 		   testNetPack4(3),
 		   testNetPack5(4),
 		   testNetPack6(5)
 		 }
 	ACCESS  read-write
 	STATUS  mandatory
        DESCRIPTION
                 "pgNetPackSelftest is an action requesting the Selftest of any
                  one of the system NetPacks."

 	::= { pgActionSystem 3 }
 	
pgReturnToPrimaryMS OBJECT-TYPE
 	SYNTAX  INTEGER { 
 		   no-return(0),
 		   return(1)
 		 }
 	ACCESS  read-write
 	STATUS  mandatory
        DESCRIPTION
                 "pgReturnToPrimaryMS is an action requesting the return of the 
                  Agent to the specified primary channel for communication to 
                  its primary NMS."

 	::= { pgActionSystem 4 }
 
 	
pgHubColdReset OBJECT-TYPE
	SYNTAX  INTEGER { 
	          no-reset(0),
	          resetHub1(1),
	          resetHub2(2)
	         }
        ACCESS  read-write
        STATUS  mandatory
        DESCRIPTION
                 "pgHubColdReset is an action requesting the clearing of all
                  counters and statistics for the specified Hub."

	::= { pgActionSystem 5 }

pgHubWarmReset OBJECT-TYPE
	SYNTAX  INTEGER { 
	          no-reset(0),
	          resetHub1(1),
	          resetHub2(2)
	         }
        ACCESS  read-write
        STATUS  mandatory
        DESCRIPTION
                 "pgHubWarmReset is an action requesting the Reset of counters 
                  for the specified Hub in the System, without any affect on
                  the configuration.  The MPR for the specified Hub will not
                  be reset."

        ::= { pgActionSystem 6 }

duphmBasicHubTable OBJECT-TYPE 
	SYNTAX SEQUENCE OF DuphmBasicHubEntry 
	ACCESS not-accessible 
	STATUS mandatory 
        DESCRIPTION
                 "duphmBasicHubTable is table depicting the basic 802.3 Hub 
                  Management objects."

	::= { duphmBasicCapability 1 } 

duphmBasicHubEntry OBJECT-TYPE
	SYNTAX DuphmBasicHubEntry 
	ACCESS not-accessible 
	STATUS mandatory 
        DESCRIPTION
                 "duphmBasicHubEntry is the entry for a specifed Hub in the 
                  duphmBasicHubTable."
	INDEX { duphubID }

	::= { duphmBasicHubTable 1 } 

DuphmBasicHubEntry ::= 
	SEQUENCE { 
		dupHubID
		 INTEGER, 
		duphubGroupCapacity
		 INTEGER, 
		duphubGroupMap 
	 	 OCTET STRING
	} 

duphubID OBJECT-TYPE 
	SYNTAX INTEGER  
	ACCESS read-only 
	STATUS mandatory 
DESCRIPTION ""
	::= { duphmBasicHubEntry 1 } 


duphubGroupCapacity OBJECT-TYPE 
	SYNTAX INTEGER (1..255) 
	ACCESS read-only 
	STATUS mandatory 
DESCRIPTION ""
	::= { duphmBasicHubEntry 2 } 


duphubGroupMap OBJECT-TYPE 
	SYNTAX OCTET STRING  
	ACCESS read-only 
	STATUS mandatory 
DESCRIPTION ""
	::= { duphmBasicHubEntry 3 } 


duphmBasicGroupTable OBJECT-TYPE 
	SYNTAX SEQUENCE OF DuphmBasicGroupEntry 
	ACCESS not-accessible 
	STATUS mandatory 
DESCRIPTION ""
	::= { duphmBasicCapability 2 } 


duphmBasicGroupEntry OBJECT-TYPE 
	SYNTAX DuphmBasicGroupEntry 
	ACCESS not-accessible 
	STATUS mandatory 
DESCRIPTION ""
	INDEX { dupgroupHubID, dupgroupID }
	::= { duphmBasicGroupTable 1 } 

DuphmBasicGroupEntry ::= 
	SEQUENCE { 
	dupgroupHubID 
	INTEGER, 
	dupgroupID 
	INTEGER, 
	dupgroupNumberOfPorts 
	INTEGER
	} 

dupgroupHubID OBJECT-TYPE 
	SYNTAX INTEGER 
	ACCESS read-only 
	STATUS mandatory 
DESCRIPTION ""
	::= { duphmBasicGroupEntry 1 } 

dupgroupID OBJECT-TYPE 
	SYNTAX INTEGER (1..255) 
	ACCESS read-only 
	STATUS mandatory 
DESCRIPTION ""
 
	::= { duphmBasicGroupEntry 2 } 


dupgroupNumberOfPorts OBJECT-TYPE 
	SYNTAX INTEGER (1..255) 
	ACCESS read-only 
	STATUS mandatory 
DESCRIPTION ""
	::= { duphmBasicGroupEntry 3 } 


duphmBasicPortTable OBJECT-TYPE 
	SYNTAX SEQUENCE OF DuphmBasicPortEntry 
	ACCESS not-accessible 
	STATUS mandatory 
DESCRIPTION ""
	::= { duphmBasicCapability 3 } 


duphmBasicPortEntry OBJECT-TYPE 
	SYNTAX DuphmBasicPortEntry 
	ACCESS not-accessible 
	STATUS mandatory 
DESCRIPTION ""
	INDEX { dupportHubBasicID, dupportGroupBasicID, dupportBasicID }
	::= { duphmBasicPortTable 1 } 

DuphmBasicPortEntry ::= 
	SEQUENCE { 
	dupportHubBasicID 
	OCTET STRING, 
	dupportGroupBasicID 
	INTEGER, 
	dupportBasicID 
	INTEGER, 
	dupportType 
	INTEGER, 
	dupportAdminState 
	INTEGER, 
	dupportAutoPartitionState 
	INTEGER 
	} 

dupportHubBasicID OBJECT-TYPE 
	SYNTAX INTEGER 
	ACCESS read-only 
	STATUS mandatory 
DESCRIPTION ""
	::= { duphmBasicPortEntry 1 } 


dupportGroupBasicID OBJECT-TYPE 
	SYNTAX INTEGER (1..255) 
	ACCESS read-only 
	STATUS mandatory 
DESCRIPTION ""
	::= { duphmBasicPortEntry 2 } 


dupportBasicID OBJECT-TYPE 
	SYNTAX INTEGER (1..255) 
	ACCESS read-only 
	STATUS mandatory 
DESCRIPTION ""
	::= { duphmBasicPortEntry 3 } 


dupportType OBJECT-TYPE 
	SYNTAX INTEGER { 
	   	other(1), 
	   	repeater(2), 
		tenBASE-FAsync(3), 
		tenBASE-FSynch(4) } 
	ACCESS read-only 
	STATUS mandatory 
DESCRIPTION ""
	::= { duphmBasicPortEntry 4 } 


dupportAdminState OBJECT-TYPE 
	SYNTAX INTEGER { other(1), disabled(2), enabled(3) } 
	ACCESS read-write 
	STATUS mandatory 
DESCRIPTION ""
	::= { duphmBasicPortEntry 5 } 


dupportAutoPartitionState OBJECT-TYPE 
	SYNTAX INTEGER { other(1), notAutoPartitioned(2), 
		autoPartitioned(3) } 
	ACCESS read-only 
	STATUS mandatory 
DESCRIPTION ""
	::= { duphmBasicPortEntry 6 } 


duphmSelfTestHubTable OBJECT-TYPE 
	SYNTAX SEQUENCE OF DuphmSelfTestHubEntry 
	ACCESS not-accessible 
	STATUS mandatory 
DESCRIPTION ""
	::= { duphmSelfTestCapability 1 } 


duphmSelfTestHubEntry OBJECT-TYPE 
	SYNTAX DuphmSelfTestHubEntry 
	ACCESS not-accessible 
	STATUS mandatory
DESCRIPTION ""
	INDEX { duphubSelfTestID } 
	::= { duphmSelfTestHubTable 1 } 

DuphmSelfTestHubEntry ::=
	SEQUENCE {
	duphubSelfTestID
	INTEGER,
	duptimeSinceHubSystemReset
	INTEGER,
	duphubResetTimeStamp
	INTEGER,
	duphubHealthState
	INTEGER,
	duphubHealthText
	DisplayString,
	duphubHealthData
	OCTET STRING,
	duphubSystemResetting
	INTEGER,
	duphubResetting
	INTEGER,
	duphubExecutingSelfTest
	INTEGER
	}

duphubSelfTestID OBJECT-TYPE 
	SYNTAX INTEGER
	ACCESS read-only 
	STATUS mandatory 
DESCRIPTION ""
	::= { duphmSelfTestHubEntry 1 } 


duptimeSinceHubSystemReset OBJECT-TYPE 
	SYNTAX INTEGER 
	ACCESS read-only 
	STATUS mandatory 
DESCRIPTION ""
	::= { duphmSelfTestHubEntry 2 } 

duphubResetTimeStamp OBJECT-TYPE 
	SYNTAX INTEGER 
	ACCESS read-only 
	STATUS mandatory 
DESCRIPTION ""
	::= { duphmSelfTestHubEntry 3 } 


duphubHealthState OBJECT-TYPE 
	SYNTAX INTEGER { other(1), ok(2), failed(3) } 
	ACCESS read-only 
	STATUS mandatory 
DESCRIPTION ""
	::= { duphmSelfTestHubEntry 4 } 


duphubHealthText OBJECT-TYPE 
	SYNTAX DisplayString (SIZE (0..255)) 
	ACCESS read-only 
	STATUS mandatory 
DESCRIPTION ""

	::= { duphmSelfTestHubEntry 5 } 


duphubHealthData OBJECT-TYPE 
	SYNTAX OCTET STRING (SIZE (0..255)) 
	ACCESS read-only 
	STATUS mandatory 
DESCRIPTION ""
	::= { duphmSelfTestHubEntry 6 } 


duphubSystemResetting OBJECT-TYPE 
	SYNTAX INTEGER { notResetting(1), resetting(2) } 
	ACCESS read-write 
	STATUS mandatory 
DESCRIPTION ""
	::= { duphmSelfTestHubEntry 7 } 


duphubResetting OBJECT-TYPE 
	SYNTAX INTEGER { notResetting(1), resetting(2) } 
	ACCESS read-write 
	STATUS mandatory 
DESCRIPTION ""
	::= { duphmSelfTestHubEntry 8 } 


duphubExecutingSelfTest OBJECT-TYPE 
	SYNTAX INTEGER { notSelfTesting(1), selfTesting(2) } 
	ACCESS read-write 
	STATUS mandatory 
DESCRIPTION ""
	::= { duphmSelfTestHubEntry 9 } 


duphmPerfMonRelayTable OBJECT-TYPE  
	SYNTAX SEQUENCE OF DuphmPerfMonRelayEntry 
	ACCESS not-accessible 
	STATUS mandatory 
DESCRIPTION ""
	::= { duphmPerfMonCapability 1 } 

duphmPerfMonRelayEntry OBJECT-TYPE  
	SYNTAX DuphmPerfMonRelayEntry 
	ACCESS not-accessible 
	STATUS mandatory 
DESCRIPTION ""
	INDEX { duprelayHubPerfID, duprelayPerfID }
	::= { duphmPerfMonRelayTable 1 } 

DuphmPerfMonRelayEntry ::= 
	SEQUENCE { 
	duprelayHubPerfID
	INTEGER,
	duprelayPerfID
	INTEGER,
	duprelayTotalCollisions
	INTEGER
	} 

duprelayHubPerfID OBJECT-TYPE 
	SYNTAX INTEGER
	ACCESS read-only 
	STATUS mandatory 
DESCRIPTION ""
	::= { duphmPerfMonRelayEntry 1 } 


	duprelayPerfID OBJECT-TYPE 
	SYNTAX INTEGER  
	ACCESS read-only 
	STATUS mandatory 
DESCRIPTION ""
	::= { duphmPerfMonRelayEntry 2 } 


duprelayTotalCollisions OBJECT-TYPE 
	SYNTAX Counter 
	ACCESS read-only 
	STATUS mandatory 
DESCRIPTION ""
	::= { duphmPerfMonRelayEntry 3 } 


duphmPerfMonPortTable OBJECT-TYPE 
	SYNTAX SEQUENCE OF DuphmPerfMonPortEntry 
	ACCESS not-accessible 
	STATUS mandatory 
DESCRIPTION ""
	::= { duphmPerfMonCapability 2 } 


duphmPerfMonPortEntry OBJECT-TYPE 
	SYNTAX DuphmPerfMonPortEntry 
	ACCESS not-accessible 
	STATUS mandatory 
DESCRIPTION ""
	INDEX { dupportHubPerfID, dupportGroupPerfID, dupportPerfID }
	::= { duphmPerfMonPortTable 1 } 

DuphmPerfMonPortEntry ::= 
	SEQUENCE { 
		dupportHubPerfID 
		INTEGER, 
		dupportGroupPerfID 
		INTEGER, 
		dupportPerfID 
		INTEGER, 
		dupportReadableFrames 
		Counter, 
		dupportReadableOctets 
		Counter, 
		dupportShortEvents 
		Counter, 
		dupportRunts 
		Counter, 
		dupportFrameCheckSeqErrs 
		Counter, 
		dupportAlignmentErrors 
		Counter, 
		dupportFramesTooLong 
		Counter, 
		dupportAutoPartitionCount 
		Counter 
} 

dupportHubPerfID OBJECT-TYPE 
	SYNTAX INTEGER 
	ACCESS read-only 
	STATUS mandatory 
DESCRIPTION ""
	::= { duphmPerfMonPortEntry 1 } 


dupportGroupPerfID OBJECT-TYPE 
	SYNTAX INTEGER (1..255) 
	ACCESS read-only 
	STATUS mandatory 
DESCRIPTION ""
	::= { duphmPerfMonPortEntry 2 } 


dupportPerfID OBJECT-TYPE 
	SYNTAX INTEGER (1..255) 
	ACCESS read-only 
	STATUS mandatory 
DESCRIPTION ""
	::= { duphmPerfMonPortEntry 3 } 


dupportReadableFrames OBJECT-TYPE 
	SYNTAX Counter 
	ACCESS read-only 
	STATUS mandatory 
DESCRIPTION ""
	::= { duphmPerfMonPortEntry 4 } 


dupportReadableOctets OBJECT-TYPE 
	SYNTAX Counter 
	ACCESS read-only 
	STATUS mandatory 
DESCRIPTION ""
	::= { duphmPerfMonPortEntry 5 } 


dupportShortEvents OBJECT-TYPE 
	SYNTAX Counter 
	ACCESS read-only 
	STATUS mandatory 
DESCRIPTION ""
	::= { duphmPerfMonPortEntry 6 } 


dupportRunts OBJECT-TYPE 
	SYNTAX Counter 
	ACCESS read-only 
	STATUS mandatory 
DESCRIPTION ""
	::= { duphmPerfMonPortEntry 7 } 


dupportFrameCheckSeqErrs OBJECT-TYPE 
	SYNTAX Counter 
	ACCESS read-only 
	STATUS mandatory 
DESCRIPTION ""
	::= { duphmPerfMonPortEntry 8 } 


dupportAlignmentErrors OBJECT-TYPE 
	SYNTAX Counter 
	ACCESS read-only 
	STATUS mandatory 
DESCRIPTION ""
	::= { duphmPerfMonPortEntry 9 } 


dupportFramesTooLong OBJECT-TYPE 
	SYNTAX Counter 
	ACCESS read-only 
	STATUS mandatory 
DESCRIPTION ""
	::= { duphmPerfMonPortEntry 10 } 


dupportAutoPartitionCount OBJECT-TYPE 
	SYNTAX Counter 
	ACCESS read-only 
	STATUS mandatory 
DESCRIPTION ""
	::= { duphmPerfMonPortEntry 11 } 


duphmAddrTrackPortTable OBJECT-TYPE 
	SYNTAX SEQUENCE OF DuphmAddrTrackPortEntry 
	ACCESS not-accessible 
	STATUS mandatory 
DESCRIPTION ""
	::= { duphmAddrTrackCapability 1 } 


duphmAddrTrackPortEntry OBJECT-TYPE 
	SYNTAX DuphmAddrTrackPortEntry 
	ACCESS not-accessible 
	STATUS mandatory 
DESCRIPTION ""
	INDEX { dupportHubAddrID, dupportGroupAddrID, dupportAddrID }
	::= { duphmAddrTrackPortTable 1 } 

DuphmAddrTrackPortEntry ::= 
	SEQUENCE { 
		dupportHubAddrID 
		INTEGER, 
		dupportGroupAddrID 
		INTEGER, 
		dupportAddrID 
		INTEGER, 
		dupportLastSourceAddress 
		OCTET STRING, 
		dupportSourceAddrChanges 
		Counter 
		} 

dupportHubAddrID OBJECT-TYPE 
	SYNTAX INTEGER 
	ACCESS read-only 
	STATUS mandatory 
DESCRIPTION ""
	::= { duphmAddrTrackPortEntry 1 } 


dupportGroupAddrID OBJECT-TYPE 
	SYNTAX INTEGER (1..255) 
	ACCESS read-only 
	STATUS mandatory 
DESCRIPTION ""
	::= { duphmAddrTrackPortEntry 2 } 


dupportAddrID OBJECT-TYPE 
	SYNTAX INTEGER (1..255) 
	ACCESS read-only 
	STATUS mandatory 
DESCRIPTION ""
	::= { duphmAddrTrackPortEntry 3 } 


dupportLastSourceAddress OBJECT-TYPE 
	SYNTAX OCTET STRING (SIZE (6)) 
	ACCESS read-only 
	STATUS mandatory 
DESCRIPTION ""
	::= { duphmAddrTrackPortEntry 4 } 


dupportSourceAddrChanges OBJECT-TYPE 
	SYNTAX Counter 
	ACCESS read-only 
	STATUS mandatory 
DESCRIPTION ""
	::= { duphmAddrTrackPortEntry 5 } 




-- DuPont Paragon Proprietary Traps 1/9/92

pgSetSuccess TRAP-TYPE
	ENTERPRISE  dupont
	VARIABLES   { pgAgentLastSetRequest }
	DESCRIPTION
		"The pgSetSuccess trap is generated by the agent upon the 
		successful completion of a Set Request that set the 
		value of the dupportadminState variable.  This response 
		is not to be confused with the Get Response message which 
		is automatically generated by the agent in response to a 
		Set Request.  This trap is used to verify at the Management 
		Station that Set Requests which require reliance on external 
		hardware have completed successfully.  It is also designed to 
		notify other management stations monitoring the agent that a
		Set Request has successfully occurred and the concentrator 
		configuration should be appropriately updated."  
	::= 100
	
	
pgSetFailure TRAP-TYPE
	ENTERPRISE  dupont
	VARIABLES   { pgAgentLastSetRequest }
	DESCRIPTION
		"The pgSetFailure trap is generated by the agent upon the 
		unsuccessful completion of an unsuccessful Set Request that 
		attempted to set the value of the dupportadminState  
		variable.  This response is not to be confused with the Get 
		Response message which is automatically generated by 
		the agent in response to a  Set Request.  This trap is used
		to notify the Management Station of the failure of a Set 
		Request which has already sent a Get Response reply to the 
		Management Station."  
	::= 200
	
	
pgThresholdCrossed TRAP-TYPE
	ENTERPRISE  dupont
	DESCRIPTION
		"The pgThresholdCrossed trap is generated by the agent upon 
		recognition of a threshold being crossed as defined by the 
		user.  The variables sent in the trap are first the rate of 
		the variable whose threshold has crossed and second the 
		threshold that has been crossed.  These two variables must be 
		present for this trap to process correctly.  Allowable variable 
		combinations are pgChannelIPGCount and 
		pgChannelIPGThreshold, pgMonPortCollRate and 
		pgMonPortCollThreshold, and pgMonPortErrorRate and 
		pgMonPortErrorThreshold."  
	::= 300
	
	
pgHysteresisCrossed TRAP-TYPE
	ENTERPRISE  dupont
	DESCRIPTION
		"The pgHysteresisCrossed trap is generated by the agent upon 
		recognition of a hysteresis value being crossed as defined by 
		the user.  The trap is sent to notify the management station 
		that the variable has recovered from the condition that caused 
		the pgThresholdCrossed trap to occur.  This trap will always be
		preceded by a pgThresholdCrossed trap.  The variables sent in 
		the trap are first the rate of the variable whose hysteresis 
		value has crossed and second the hysteresis value that has been 
		crossed.  These two variables must be present for this trap to 
		process correctly.  Allowable variable combinations are 
		pgMonPortCollRate and pgMonPortCollHysteresis, and 
		pgMonPortErrorRate and pgMonPortErrorHysteresis."  
	::= 400
	
	
pgGroupMapChange TRAP-TYPE
	ENTERPRISE  dupont
	VARIABLES   { duphubGroupMap }
	DESCRIPTION
		"This trap is generated upon recognition of a change in the 
		group map as described in IEEE 802.3 Hub Management 
		Specification.  The trap is sent when a change occurs in the 
		concentrator's group map, resulting from the insertion or 
		removal of a card from a concentrator." 
	REFERENCE
		"Reference IEEE 802.3 Hub Management Specification, 
		groupMapChange notification."
	::= 600

	
pgSelfTestResults TRAP-TYPE
	ENTERPRISE  dupont
	DESCRIPTION
		"The pgSelfTestResults trap is generated upon finding that a 
		command request for a selftest has completed execution.  This 
		trap is issued on completion of a self test requested by a Set 
		Request.  The variables in this trap include the statuses of
		the object or objects that performed selftests and their 
		current values.  There must be at least one variable for this 
		trap to process correctly, and there may be multiple variables. 
		Allowable variables are pgAgentDaughterboard, 
		pgAgentInternalBus, pgAgentCorrelator,  
		pgAgentNetPackStatus1, pgAgentNetPackStatus2, 
		pgAgentNetPackStatus3, pgAgentNetPackStatus4, 
		pgAgentNetPackStatus5,and pgAgentNetPackStatus6."  
	::= 700

	
pgDaughterboardTimeout TRAP-TYPE
	ENTERPRISE  dupont
	VARIABLES   { pgAgentDaughterboard }
	DESCRIPTION
		"The pgDaughterboardTimeout trap is sent if the communication 
		between the Agent Module and the Daughterboard has ceased. 
		This trap may only be sent if the Daughterboard is installed 
		on the Agent Module."  
	::= 800
	
	
pgInternalBusTimeout TRAP-TYPE
	ENTERPRISE  dupont
	VARIABLES   { pgAgentInternalBus }
	DESCRIPTION
		"The pgInternalBusTimeout trap is sent if the communication 
		between the Agent Module Foreground and the Internal Bus has 
		timed out.  This trap denotes a hardware failure. "  
	::= 900
	
	
pgInternalBusHardwareError TRAP-TYPE
	ENTERPRISE  dupont
	VARIABLES   { pgAgentInternalBus }
	DESCRIPTION
		"The pgInternalBusHardwareError trap is sent if the response 
		received from the Internal Bus does not match the expected 
		response.  The receipt of this trap signifies an Internal Bus 
		hardware failure."  
	::= 1000
	
	
pgOverTemperature TRAP-TYPE
	ENTERPRISE  dupont
	VARIABLES   { pgConcTemperature }
	DESCRIPTION
		"The pgOverTemperature trap is generated upon finding that an 
		Over Temperature condition has been reported by the 
		temperature sensing mechanism in the Agent Module."  
	::= 1100
	
	
pgPowerSupplyFailure TRAP-TYPE
	ENTERPRISE  dupont
	VARIABLES   { pgConcPowerSupply }
	DESCRIPTION
		"The pgPowerSupplyFailure trap is generated upon finding that 
		a failure has been noted in one of the Dual-Redundant Power 
		Supplies as reported by the Agent Module power supply sensing 
		mechanism."  
	::= 1200
	
	
pgErrorCondition TRAP-TYPE
	ENTERPRISE  dupont
	DESCRIPTION
		"The pgErrorCondition trap is generated upon finding that an 
		error condition has occurred in the Agent Module.  The 
		variables in this trap include the object or objects that were 
		involved in the error and their error statuses.  There must be 
		at least one variable for this trap to process correctly, and 
		there may be multiple variables.  Allowable variables are 
		pgAgentDaughterboard, pgAgentInternalBus, pgAgentCorrelator, 
		pgAgentSerialPrt, pgAgentNetPackStatus1, pgAgentNetPackStatus2, 
		pgAgentNetPackStatus3, pgAgentNetPackStatus4, 
		pgAgentNetPackStatus5,and pgAgentNetPackStatus6."  
	::= 1300
	
	
pgSecurityViolation TRAP-TYPE
	ENTERPRISE  dupont
	VARIABLES   { pgAgentLastSecurityFail }
	DESCRIPTION
		"The pgSecurityViolation trap is generated upon finding that 
		a security violation has occurred.  This proprietary security 
		mechanism is fully explained in the Agent Module User's 
		Manual." 
	REFERENCE
		"Reference the Paragon Intelligent Networking System Owner's 
		Manual SNMP Agent Module." 
	::= 1400
	
	
pgHubHealth TRAP-TYPE
	ENTERPRISE  dupont
	VARIABLES   { duphubHealthState, duphubHealthText,
		duphubHealthData }
	DESCRIPTION
		"The pgHubHealth trap is generated upon finding that the health 
		of the concentrator or some element in it has changed.  The 
		value of  duphubHealthData and the corresponding text in 
		duphubHealthText notify the management station of the specific 
		change that has occurred.  Depending on the change and the 
		corresponding values of duphubHealthData and duphubHealthText 
		the fourth variable will be either dupportAdminState or 
		duphubAutoPartitionState.  This fourth variable provides 
		additional information to the management station about the 
		change in the system that was noted."  
	REFERENCE
		"Reference 802.3 Hub Management Specification for more detail
		 on HubHealth." 
	::= 1500
	
	
pgLinkStatus  TRAP-TYPE
	ENTERPRISE  dupont
	VARIABLES   { pgMonPortLinkStatus }
	DESCRIPTION
		"The pgLinkStatus is generated by the agent upon finding 
		that the link status of a port has changed.  The variable
		pgMonPortLinkStatus will hold the current link status of
		the port identified by the instance."
	::= 1600

	
pgMPRErrors  TRAP-TYPE
	ENTERPRISE  dupont
	-- Apparent bug in duPont's Original MIB definition file.
 	-- Unidentified OID named "pgMonGroupMPRStatus" in next line changed.
 	VARIABLES   { pgMonRptrMPRStatus }
	DESCRIPTION
		"The pgMPRErrors trap is generated by the agent to notify the 
		Management Station that the MPR is experiencing an error 
		condition.  The variable pgMonGroupMPRStatus indicates 
		the error condition."
	::= 1700

END
