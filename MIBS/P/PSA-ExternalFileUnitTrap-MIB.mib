PSA-ExternalFileUnitTrap-MIB DEFINITIONS ::= BEGIN

--PRIMEQUEST system management MIB for Partition
--
--
--$Copyright$
--Copyright Fujitsu Limited 2006 - 2008
--All rights reserved
--
--
--MIB Revision: 01160000
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaExternalFileUnitTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise		OBJECT IDENTIFIER  ::={ partition 201 }
     psaComTrap				OBJECT IDENTIFIER  ::={ partitionEnterprise 1 }
     psaLinLanComTrap			OBJECT IDENTIFIER  ::={ partitionEnterprise 2 }
     psaLinIntelE100Trap		OBJECT IDENTIFIER  ::={ partitionEnterprise 3 }
     psaLinIntelE1000Trap		OBJECT IDENTIFIER  ::={ partitionEnterprise 4 }
     psaLinBcm5700Trap			OBJECT IDENTIFIER  ::={ partitionEnterprise 5 }
     psaLinEmulexTrap			OBJECT IDENTIFIER  ::={ partitionEnterprise 6 }
     psaLinLsiLogicTrap		OBJECT IDENTIFIER  ::={ partitionEnterprise 7 }
     psaLinScsiComTrap			OBJECT IDENTIFIER  ::={ partitionEnterprise 8 }
     psaLinGrmpdTrap			OBJECT IDENTIFIER  ::={ partitionEnterprise 9 }
     psaLinGdsTrap				OBJECT IDENTIFIER  ::={ partitionEnterprise 10 }
     psaLinGlsTrap				OBJECT IDENTIFIER  ::={ partitionEnterprise 11 }
     psaLinTg3Trap				OBJECT IDENTIFIER  ::={ partitionEnterprise 12 }
     psaLinIbTrap				OBJECT IDENTIFIER  ::={ partitionEnterprise 13 }
     psaLinXframe2Trap			OBJECT IDENTIFIER  ::={ partitionEnterprise 14 }
     psaGschTrap				OBJECT IDENTIFIER  ::={ partitionEnterprise 15 }
     psaExternalFileUnitTrap	OBJECT IDENTIFIER  ::={ partitionEnterprise 101 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

trapFlagcode OBJECT-TYPE
   SYNTAX   DisplayString
   ACCESS   not-accessible
   STATUS   mandatory
   DESCRIPTION " "
   ::= { trapVarDivInfo 28 }

--***************************************************************************************
--
--FUJITSU PRIMEQUEST system management TRAP definition for Partition
--	Trap enterprise:	psaExternalFileUnitTrap (.1.3.6.1.4.1.211.1.31.1.2.201.101)
--
--***************************************************************************************

externalFileUnitEvent0 TRAP-TYPE
   ENTERPRISE   psaExternalFileUnitTrap
   VARIABLES {
      trapPartitionName,
      trapPartitionId,
      trapEventLevel,
      trapEventId,
      trapUnitName,
      trapSuspect,
      trapErrCode,
      trapMmbVip
   }
   DESCRIPTION "ExternalFileUnit: Detected failure on the fan"
   --#TYPE			"External File Unit Event 0"
   --#SUMMARY		"%s(PID=%d) %s %d %s %s Detected failure on the fan (status=%s)"
   --#ARGUMENTS		{ 0, 1, 2, 3, 4, 5, 6 }
   --#SEVERITY		MINOR
   ::= 30000

externalFileUnitEvent1 TRAP-TYPE
   ENTERPRISE   psaExternalFileUnitTrap
   VARIABLES {
      trapPartitionName,
      trapPartitionId,
      trapEventLevel,
      trapEventId,
      trapUnitName,
      trapSuspect,
      trapErrCode,
      trapMmbVip
   }
   DESCRIPTION "ExternalFileUnit: Detected failure on the power supply unit"
   --#TYPE			"External File Unit Event 1"
   --#SUMMARY		"%s(PID=%d) %s %d %s %s Detected failure on the power supply unit (status=%s)"
   --#ARGUMENTS		{ 0, 1, 2, 3, 4, 5, 6 }
   --#SEVERITY		MINOR
   ::= 30001

externalFileUnitEvent2 TRAP-TYPE
   ENTERPRISE   psaExternalFileUnitTrap
   VARIABLES {
      trapPartitionName,
      trapPartitionId,
      trapEventLevel,
      trapEventId,
      trapUnitName,
      trapSuspect,
      trapErrCode,
      trapMmbVip
   }
   DESCRIPTION "ExternalFileUnit: Fan not installed"
   --#TYPE			"External File Unit Event 2"
   --#SUMMARY		"%s(PID=%d) %s %d %s %s Not Installed (status=%s)"
   --#ARGUMENTS		{ 0, 1, 2, 3, 4, 5, 6 }
   --#SEVERITY		MINOR
   ::= 30002

externalFileUnitEvent3 TRAP-TYPE
   ENTERPRISE   psaExternalFileUnitTrap
   VARIABLES {
      trapPartitionName,
      trapPartitionId,
      trapEventLevel,
      trapEventId,
      trapUnitName,
      trapSuspect,
      trapErrCode,
      trapMmbVip
   }
   DESCRIPTION "ExternalFileUnit: Power supply unit not installed"
   --#TYPE			"External File Unit Event 3"
   --#SUMMARY		"%s(PID=%d) %s %d %s %s Not Installed (status=%s)"
   --#ARGUMENTS		{ 0, 1, 2, 3, 4, 5, 6 }
   --#SEVERITY		MINOR
   ::= 30003

externalFileUnitEvent4 TRAP-TYPE
   ENTERPRISE   psaExternalFileUnitTrap
   VARIABLES {
      trapPartitionName,
      trapPartitionId,
      trapEventLevel,
      trapEventId,
      trapUnitName,
      trapSuspect,
      trapMmbVip
   }
   DESCRIPTION "ExternalFileUnit: Enclosure access failed"
   --#TYPE			"External File Unit Event 4"
   --#SUMMARY		"%s(PID=%d) %s %d %s %s Enclosure access failed"
   --#ARGUMENTS		{ 0, 1, 2, 3, 4, 5 }
   --#SEVERITY		MINOR
   ::= 30004

externalFileUnitEvent5 TRAP-TYPE
   ENTERPRISE   psaExternalFileUnitTrap
   VARIABLES {
      trapPartitionName,
      trapPartitionId,
      trapEventLevel,
      trapEventId,
      trapUnitName,
      trapSuspect,
      trapMmbVip
   }
   DESCRIPTION "ExternalFileUnit: FAN is Non-Redundant: Sufficient Resources"
   --#TYPE			"External File Unit Event 5"
   --#SUMMARY		"%s(PID=%d) %s %d %s %s FAN is Non-Redundant: Sufficient Resources"
   --#ARGUMENTS		{ 0, 1, 2, 3, 4, 5 }
   --#SEVERITY		MINOR
   ::= 30005

externalFileUnitEvent6 TRAP-TYPE
   ENTERPRISE   psaExternalFileUnitTrap
   VARIABLES {
      trapPartitionName,
      trapPartitionId,
      trapEventLevel,
      trapEventId,
      trapUnitName,
      trapSuspect,
      trapMmbVip
   }
   DESCRIPTION "ExternalFileUnit: Power Supply Unit is Non-Redundant: Sufficient Resources"
   --#TYPE			"External File Unit Event 6"
   --#SUMMARY		"%s(PID=%d) %s %d %s %s Power Supply Unit is Non-Redundant: Sufficient Resources"
   --#ARGUMENTS		{ 0, 1, 2, 3, 4, 5 }
   --#SEVERITY		MINOR
   ::= 30006

externalFileUnitEvent7 TRAP-TYPE
   ENTERPRISE   psaExternalFileUnitTrap
   VARIABLES {
      trapPartitionName,
      trapPartitionId,
      trapEventLevel,
      trapEventId,
      trapUnitName,
      trapSuspect,
      trapMmbVip
   }
   DESCRIPTION "ExternalFileUnit: FAN is Non-Redundant: Insufficient Resources"
   --#TYPE			"External File Unit Event 7"
   --#SUMMARY		"%s(PID=%d) %s %d %s %s FAN is Non-Redundant: Insufficient Resources"
   --#ARGUMENTS		{ 0, 1, 2, 3, 4, 5 }
   --#SEVERITY		MAJOR
   ::= 30007

externalFileUnitEvent8 TRAP-TYPE
   ENTERPRISE   psaExternalFileUnitTrap
   VARIABLES {
      trapPartitionName,
      trapPartitionId,
      trapEventLevel,
      trapEventId,
      trapUnitName,
      trapSuspect,
      trapMmbVip
   }
   DESCRIPTION "ExternalFileUnit: Power Supply Unit is Non-Redundant: Insufficient Resources"
   --#TYPE			"External File Unit Event 8"
   --#SUMMARY		"%s(PID=%d) %s %d %s %s Power Supply Unit is Non-Redundant: Insufficient Resources"
   --#ARGUMENTS		{ 0, 1, 2, 3, 4, 5 }
   --#SEVERITY		MAJOR
   ::= 30008

externalFileUnitEvent9 TRAP-TYPE
   ENTERPRISE   psaExternalFileUnitTrap
   VARIABLES {
      trapPartitionName,
      trapPartitionId,
      trapEventLevel,
      trapEventId,
      trapUnitName,
      trapSuspect,
      trapPartNo,
      trapErrCode,
      trapMmbVip
   }
   DESCRIPTION "ExternalFileUnit: Detected failure on the fan"
   --#TYPE			"External File Unit Event 9"
   --#SUMMARY		"%s(PID=%d) %s %d %s %s Detected failure on the fan (%s;status=%s)"
   --#ARGUMENTS		{ 0, 1, 2, 3, 4, 5, 6, 7 }
   --#SEVERITY		MINOR
   ::= 30009

externalFileUnitEvent10 TRAP-TYPE
   ENTERPRISE   psaExternalFileUnitTrap
   VARIABLES {
      trapPartitionName,
      trapPartitionId,
      trapEventLevel,
      trapEventId,
      trapUnitName,
      trapSuspect,
      trapPartNo,
      trapErrCode,
      trapMmbVip
   }
   DESCRIPTION "ExternalFileUnit: Detected failure on the power supply unit"
   --#TYPE			"External File Unit Event 10"
   --#SUMMARY		"%s(PID=%d) %s %d %s %s Detected failure on the power supply unit (%s;status=%s)"
   --#ARGUMENTS		{ 0, 1, 2, 3, 4, 5, 6, 7 }
   --#SEVERITY		MINOR
   ::= 30010

externalFileUnitEvent11 TRAP-TYPE
   ENTERPRISE   psaExternalFileUnitTrap
   VARIABLES {
      trapPartitionName,
      trapPartitionId,
      trapEventLevel,
      trapEventId,
      trapUnitName,
      trapSuspect,
      trapPartNo,
      trapErrCode,
      trapMmbVip
   }
   DESCRIPTION "ExternalFileUnit: Fan is not installed"
   --#TYPE			"External File Unit Event 11"
   --#SUMMARY		"%s(PID=%d) %s %d %s %s Not Installed (%s;status=%s)"
   --#ARGUMENTS		{ 0, 1, 2, 3, 4, 5, 6, 7 }
   --#SEVERITY		MINOR
   ::= 30011

externalFileUnitEvent12 TRAP-TYPE
   ENTERPRISE   psaExternalFileUnitTrap
   VARIABLES {
      trapPartitionName,
      trapPartitionId,
      trapEventLevel,
      trapEventId,
      trapUnitName,
      trapSuspect,
      trapPartNo,
      trapErrCode,
      trapMmbVip
   }
   DESCRIPTION "ExternalFileUnit: Power supply unit is not installed"
   --#TYPE			"External File Unit Event 12"
   --#SUMMARY		"%s(PID=%d) %s %d %s %s Not Installed (%s;status=%s)"
   --#ARGUMENTS		{ 0, 1, 2, 3, 4, 5, 6, 7 }
   --#SEVERITY		MINOR
   ::= 30012

externalFileUnitEvent13 TRAP-TYPE
   ENTERPRISE   psaExternalFileUnitTrap
   VARIABLES {
      trapPartitionName,
      trapPartitionId,
      trapEventLevel,
      trapEventId,
      trapUnitName,
      trapSuspect,
      trapPartNo,
      trapMmbVip
   }
   DESCRIPTION "ExternalFileUnit: Enclosure access failed"
   --#TYPE			"External File Unit Event 13"
   --#SUMMARY		"%s(PID=%d) %s %d %s %s Enclosure access failed (%s)"
   --#ARGUMENTS		{ 0, 1, 2, 3, 4, 5, 6 }
   --#SEVERITY		MINOR
   ::= 30013

END
