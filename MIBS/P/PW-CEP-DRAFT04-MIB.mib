-- extracted from draft-ietf-pwe3-cep-mib-05.txt
-- at Tue Jun  8 06:20:49 2004

PW-CEP-DRAFT04-MIB DEFINITIONS ::= BEGIN 

IMPORTS 
  MODULE-IDENTITY, OBJECT-TYPE,  
  Integer32, Counter32, Unsigned32, Counter64 
     FROM SNMPv2-SMI 

  MODULE-COMPLIANCE, OBJECT-GROUP 
     FROM SNMPv2-CONF 

  TEXTUAL-CONVENTION, TruthValue, RowStatus, StorageType, 
  TimeStamp 
     FROM SNMPv2-TC 

  InterfaceIndexOrZero, InterfaceIndex 
     FROM IF-MIB 

  PerfCurrentCount, PerfIntervalCount 
     FROM PerfHist-TC-MIB 
 
  pwStdMIB 
     FROM PW-TC-DRAFT04-MIB 

  pwVcIndex  
     FROM PW-DRAFT04-MIB 

  SnmpAdminString 
     FROM SNMP-FRAMEWORK-MIB; 


-- The CEP MIB 

pwVcCepMIB MODULE-IDENTITY 
 

  LAST-UPDATED "200311301200Z"  --  November 30 2003 12:00:00 EST 
  ORGANIZATION "Pseudo-Wire Emulation Edge-to-Edge (PWE3) 
                Working Group" 
  CONTACT-INFO 
      "        Dave Danenberg 
       Postal: Litchfield Communications, Inc. 
               27 Princeton Rd 
               Princeton Center West 
               Watertown, CT 06795 
       Tel:    203-591-7062 
       Email:  dave_danenberg@litchfieldcomm.com 
        
               Thomas D. Nadeau 
       Postal: Cisco Systems, Inc. 
               250 Apollo Drive 
               Chelmsford, MA 01824 
       Tel:    978-244-3051 
       Email:  tnadeau@cisco.com 
        
               David Zelig (Editor) 
       Postal: Corrigent Systems LTD. 
               126, Yigal Alon St. 
               Tel Aviv, ISRAEL 
               Phone: +972-3-6945273 
       E-mail: davidz@corrigent.com 

               Andrew G. Malis  
       Postal: Tellabs, Inc.  
               2730 Orchard Parkway  
               San Jose, CA 95134  
       Email:  Andy.Malis@tellabs.com 

               Ron Cohen 
       Postal: Lycium Networks 
               2480 Sand Hill Road, 
               Menlo-Park, CA 94025 
       Email:  ronc@lyciumnetworks.com 
 
       The PWE3 Working Group (email distribution pwe3@ietf.org, 
       http://www.ietf.org/html.charters/pwe3-charter.html) 
       " 

  DESCRIPTION 
      "This MIB contains managed object definitions for Circuit 
       Emulation over Packet (CEP) as in: Malis, A., Prayson, P., 
       Cohen, R. and Zelig, D. 'SONET/SDH Circuit Emulation 
       Over Packet (CEP) encapsulation', Internet Draft <draft- 
       ietf-pwe3-sonet>. 

       This MIB reports to the PW-STD-MIB as in: Zelig, D., Nadeau, 
       T. 'Pseudo Wire (PW) Management Information Base'. The  
       PW-STD-MIB contains structures and MIB associations generic 
       to Pseudo-Wire (PW) emulation. PW-specific 
       MIBs (such as this) contain config and stats for specific 
 

       PW types. 
        
       Copyright (C) The Internet Society (date).  This version 
       of this MIB module is part of RFC yyyy;  see the RFC 
       itself for full legal notices. 
-- RFC Ed.: replace yyyy with actual RFC number & remove this note 
       " 

   
  -- Revision history. 
  REVISION 
      "200311301200Z"  --  November 30 2003 12:00:00 EST 
  DESCRIPTION 
      "- Update description clause of main module. 
       - Module Identity adapted to PWE3 tree. 
       - Remove notifications (PW-STD-MIB now contains the 
         PW level up/down notification). 
      " 

  REVISION 
      "200310261200Z"  -- 26 Oct 2003 12:00:00 EST 
  DESCRIPTION 
      "- Change pwVcCepFractTable to be rowCreated, and indexed 
         by a virtual interface. Change the description in the  
         main table to reflect this. 
      " 

  REVISION 
      "200210231200Z"  -- 23 Oct 2002 12:00:00 EST 
  DESCRIPTION 
      "- Added RTP header suppression config object. 
       - Deleted jitter buffer rebuild objects. 
       - Add VT and fractional SPE support. 
       - Adding textual conventions. 
       - Adding types to pwVcCepType. 
       - Changind description of pwVcCepSonetIfIndex, 
         pwVcCepSonetTimeSlot. 
       - Adding badHdrStack as error code. 
       - Change pwVcCepCfgNormalPktLength to  
         pwVcCepSonetPayloadLength to more generally convey  
         fractional SPE modes and VT modes. 
       - Adding pwVcCepFracTable. 
      " 

  REVISION 
      "200208161200Z"  -- 16 Aug 2002 12:00:00 EST 
  DESCRIPTION 
      "- Updated to become IETF PWE3 working group doc. 
       - Updated references to CEP draft." 
        
  REVISION 
      "200205291200Z"  -- 29 May 2002 12:00:00 EST 
  DESCRIPTION 
      "- Renamed EsTimeStamp to LastErrorTimeStamp. 
 

       - Renamed LastDefectsAtEs to LatchedIndications. 
       - Renamed CurrentDefects to CurrentIndications.  
       - Renamed defect indications (cepAis, cepRdi). 
       - Renamed DBA bit settings (ais and unequipped). 
       - Added objects: CfgJtrBfrResetOorange and  
         CfgJtrBfrResetOorangeCnt. 

       - Moved SONET Time Slot and Time Slot cfg error 
         to CEP table from SONET extension table. Deleted 
         SONET extension table. 
       - Added Failure Counts (FCs) to stats tables. 
       - Removed pwVcCepPerfCurrentTimeElapsed (it is 
         a duplicate of pwVcCepTimeElapsed). 
       - Removed 32-bit counters that were duplicates 
         of 64-bit (HC) counters.  
       - Other minor changes." 
       
  REVISION 
      "200202271200Z"  -- 27 February 2002 12:00:00 EST 
  DESCRIPTION 
      "- Added objects pwVcCepTimeElapsed and 
         pwVcCepValidIntervals for more accurate knowledge 
         of interval data. 
       - Changed pwVcCepCfgJtrBfrDepth units from packets 
         to microseconds, and updated description. 
       - Changed JtrBfrOoseqDropped to JtrBfrOoRngDropped 
         (i.e, 'out of sequence' to 'out of range'). 
       - Removed JtrBfrOverruns counter objects. This info 
         is now contained within the JtrBfrOoRngDropped 
         object. 
       - Changed description of JtrBfrUnderrun. 
       - Moved LastDefectsAtEs, LastEsTimeStamp, and 
         DiscontinuityTime to the pwVcCepTable table. 
         Removed them as conformance config objects. 
       - Created new CurrentDefects in CepTable. 
       - Added cepAis to and changed rdi to cepRdi 
         (both are now in LastDefectsAtEs). Added note 
         to cepAis - it must not (in itself) cause a 
         cep down notification. 
       - Changed the pwVcCepSonetExtTable to augment 
         the sonetPathCurrentTable in RFC 2558. Imported 
         sonetPathCurrentTable from the SONET-MIB. 
       - Renamed PktResequence to PktReorder." 

  REVISION 
      "200111161200Z"  -- 16 November 2001 12:00:00 EST 
  DESCRIPTION 
      "- Changed CEM to CEP. 
       - Removed: 'unstructured' CEP type, ECC references, 
         and signaling (CEP options) references, multiple 
         VC instances references, and APS references. 
       - Improved descriptions and some improved object names. 
       - New conformance section. New ConformanceCfg table. 
       - PktResequence is now read-only.  
 

       - ConfMaxPktLength is now ConfNormalPktLength. 
       - Replaced User Error Action with PlayOutValue.  
       - New cfg object  : consecutive non-SESs to exit UAS. 
       - New cfg objects : elapsed time for stats intervals. 
       - New stats object: summary packet error. 
       - New object      : added ConfigError to SonetExt table. 

       - NOTE: Many objects added, deleted, or moved - so many 
         OIDs have been re-ordered." 

  REVISION 
      "200109071200Z"  -- 07 September 2001 12:00:00 EST 
  DESCRIPTION 
      "- Separated Top level Cfg objects from Total CEM stats. 
       - Removed references to VC instances." 

  REVISION 
      "200107191200Z"  -- 19 July 2001 12:00:00 EST 
  DESCRIPTION 
      "Based on the PWE3 Requirements/Framework, the original 
       CEM MIB (draft-danenberg-sonet-ces-mpls-mib-00.txt) has 
       Been split into 3 drafts: 

         - PW-STD-MIB     (Zelig, et al).  Service-independent MIB. 
         - PW-TC-STD-MIB  (Nadeau, et al). Textual Conventions. 
         - PW-CEP-STD-MIB (Danenberg, et al). Service-specific MIB. 

       Aside from the split, then PW-CEM-MIB has undergone 
       other changes: 

         - Ability to define LOPS (loss of packet sync), SES 
           and UAS. 
         - Support for 'unstructured' operation. 
         - Support for CEM-RDI. 
         - Many more minor changes and clarifications." 

  ::= { pwStdMIB 4 } --To be assigned by IANA 

-- Local Textual conventions 
PwVcCepCfgIndex ::= TEXTUAL-CONVENTION 
  STATUS      current 
  DESCRIPTION 
       "Index into the pwVcCepCfgTable." 
  SYNTAX  Unsigned32 


PwVcCepSonetEbm ::= TEXTUAL-CONVENTION 
  STATUS      current 
  DESCRIPTION 
       "Equipped Bit Mask (EBM) as defined in draft-ietf-pwe3- 
        sonet-vt used for fractional STS-1/VC-3. The EBM bits are  
        the 28 least significant bits out of the 32 bit value" 
  SYNTAX  Unsigned32 

 


PwVcCepSdhVc4Ebm ::= TEXTUAL-CONVENTION 
  STATUS      current 
  DESCRIPTION 
       "Equipped Bit Mask (EBM) as defined in draft-ietf-pwe3- 
        sonet-vt used for each TUG-3 in fractional VC-4 circuits.  
        The EBM bits are the 30 least significant bits out of the  
        32 bit value " 
  SYNTAX  Unsigned32 

PwVcCepSonetVtgMap ::= TEXTUAL-CONVENTION 
  STATUS      current 
  DESCRIPTION 
       "The VT/VC types carried in the 7 VTG/TUG-2s. The format is  
        28 bits in the form of an Equipped Bit Mask (EBM) as  
        defined in draft-ietf-pwe3-sonet-vt used for fractional  
        STS-1/VC-3. The mapping specifies the maximal occupancies  
        of VT/VC within each VTG/TUG-2. For example, all four bits  
        are set to 1 in this objects it represents a VTG carrying  
        VT1.5s, while only three are set when VT2 are carried  
        within this VTG. 
        The relevant bits are the 28 least significant bits out of  
        the 32 bit value." 

  SYNTAX  Unsigned32 

PwVcCepFracAsyncMap ::= TEXTUAL-CONVENTION 
  STATUS      current 
  DESCRIPTION 
       "The type of Asynchronous mapping carried inside STS-1, VC-3  
        or TUG-3 containing TU-3 circuit. The value of 'other' MUST  
        be used if the Use of this object is not applicable." 

  SYNTAX INTEGER { 
           other ( 0),  
           ds3   ( 1), 
           e3    ( 2) 
         } 


-- Top level components of this MIB module. 


-- Tables, Scalars 
pwVcCepObjects       OBJECT IDENTIFIER 
                             ::= { pwVcCepMIB 1 } 
-- Conformance 
pwVcCepConformance   OBJECT IDENTIFIER  
                             ::= { pwVcCepMIB 2 } 

-- CEP PW table 

pwVcCepTable OBJECT-TYPE 
  SYNTAX        SEQUENCE OF PwVcCepEntry 
 

  MAX-ACCESS    not-accessible 
  STATUS        current 
  DESCRIPTION 
      "This table contains the index to the entry SONET path 
       table for this CEP PW, and the index to the CEP config 
       table." 
  ::= { pwVcCepObjects 1 } 

pwVcCepEntry OBJECT-TYPE 
  SYNTAX        PwVcCepEntry 
  MAX-ACCESS    not-accessible 
  STATUS        current 
  DESCRIPTION 
      "This MIB reports to the PW-STD-MIB. This table is indexed by 
       the same index that was created for the associated entry 
       in the PW Table (in the PW-STD-MIB). 

         - The PwVcIndex. 

       An entry is created in this table by the agent for every 
       entry in the pwVcTable with a pwVcType of 'cep'." 

  INDEX  { pwVcIndex } 

     ::= { pwVcCepTable 1 } 

PwVcCepEntry ::= SEQUENCE { 

     pwVcCepType                       INTEGER, 
     pwVcCepSonetIfIndex               InterfaceIndexOrZero, 
     pwVcCepSonetTimeSlot              Unsigned32, 
     pwVcCepSonetConfigError           BITS, 
     pwVcCepCfgIndex                   PwVcCepCfgIndex, 
     pwVcCepTimeElapsed                Integer32, 
     pwVcCepValidIntervals             Integer32, 
     pwVcCepCurrentIndications         BITS, 
     pwVcCepLatchedIndications         BITS, 
     pwVcCepLastEsTimeStamp            TimeStamp, 
     pwVcCepPeerCepOption              Unsigned32 
     } 

pwVcCepType OBJECT-TYPE 
  SYNTAX INTEGER { 
        spe      (1), 
        vt       (2), 
        fracSpe  (3) 
  } 
  MAX-ACCESS    read-write 
  STATUS        current 
  DESCRIPTION 
      "Specifies the type of CEP PW. Currently only 
       structured types are supported. Other CEP Types 
       may be defined in the future. 

 

       Currently supported CEP types are: 
        
       1 - spe     : SONET STS-Nc signals. 
       2 - vt      : SONET VT-x (x=1.5,2,3,6) signals. 
       3 - fracSpe : SONET fractional STS-1 or SDH fractional  
           VC-3 or VC-4 carrying tributaries or Asynchronous 
           signals. 

       Support of vt and fracSpe is optional." 
    

  DEFVAL { spe } 
  ::= { pwVcCepEntry 1 } 
        

pwVcCepSonetIfIndex OBJECT-TYPE 
  SYNTAX        InterfaceIndexOrZero 
  MAX-ACCESS    read-write 
  STATUS        current 
  DESCRIPTION 
      "This is a unique index within the ifTable. It represents  
       the interface index for the SONET path for SPE emulation 
       (RFC2558 section 3.3), an interface index for the SONET 
       VT (RFC2558 section 3.4) if the VT to be emulated is  
       extracted a SONET signal, or the ifIndex of the physical  
       port emulated in VT mode if the VT to be emulated is  
       directly feeded from a physical interface. It may represent  
       an internal (virtual) interface if an NSP function exists 
       between the physical interface and the emulation process. 

       A value of zero indicates an interface index that has yet 
       to be determined. 
       Once set, if the SONET ifIndex is (for some reason) later 
       removed, the agent MAY delete the associated PW rows  
       (e.g., this pwVcCep table entry). If the agent does not  
       delete the rows, it is recommended that the agent set this 
       object to zero." 
  ::= { pwVcCepEntry 2 } 

pwVcCepSonetTimeSlot OBJECT-TYPE 
  SYNTAX        Unsigned32 (1..192) 
  MAX-ACCESS    read-write 
  STATUS        current 
  DESCRIPTION 
       "In structured SPE CEP, this object indicates the starting 
        time-slot for this SONET path within the SONET line 
        and section. For OC-48, this value could range from 1 
        to 48. The SONET path width must be taken into  
        consideration here. For example, in an OC-48, an 
        STS-3c could not start at time-slot 47. 
        In structured VT CEP, this object indicates the starting 
        time slot for this tributary within the SONET path. 
        For example, for VT1.5 tributary within STS-1, this value 
        could range from 1 to 28." 
 


  REFERENCE "RFC 2558, sonetPathCurrentWidth." 
  ::= { pwVcCepEntry 3 } 

pwVcCepSonetConfigError OBJECT-TYPE 
  SYNTAX BITS { 
        other                 ( 0), 
        timeslotInUse         ( 1), 
        timeslotMisuse        ( 2), 
        peerDbaIncompatible   ( 3), 
        peerEbmIncompatible   ( 4), 
        peerRtpIncompatible   ( 5), 
        peerPidIncompatible   ( 6), 
        peerAsyncIncompatible ( 7) 
  } 
  MAX-ACCESS    read-only 
  STATUS        current 
  DESCRIPTION 
      "timeslotInUse is when another CEP PW (via SONET ifIndex) 
       has already reserved a timeslot(s) that this CEP PW 
       is attempting to reserved. 
       timeslotMisuse is set, for example, if specifying a 
       starting timeslot of 45 for a SONET path of an STS-12c 
       width. 
       peerIncompatible bits are set if the local configuration is  
       not compatible with the peer configuration as available from  
       the CEP option received from the peer. for example if the 
       remote is not capable of accepting DBA packets but the local 
       node is configured to send DBA packets for this PW, 
       peerDbaIncompatible will be set." 
  ::= { pwVcCepEntry 4 } 

pwVcCepCfgIndex OBJECT-TYPE 
  SYNTAX        PwVcCepCfgIndex 
  MAX-ACCESS    read-write 
  STATUS        current 
  DESCRIPTION 
      "Index to CEP configuration table below. It is likely that 
       multiple CEP PWs will share 1 CEP Cfg table entry." 
  ::= { pwVcCepEntry 5 } 

pwVcCepTimeElapsed OBJECT-TYPE 
   SYNTAX  Integer32 (1..900) 
   MAX-ACCESS  read-only 
   STATUS  current 
   DESCRIPTION 
      "The number of seconds, including partial seconds, 
       that have elapsed since the beginning of the current 
       measurement period. If, for some reason, such as an 
       adjustment in the system's time-of-day clock, the 
       current interval exceeds the maximum value, the 
       agent will return the maximum value." 
   ::= { pwVcCepEntry 6 } 

 

pwVcCepValidIntervals OBJECT-TYPE 
   SYNTAX  Integer32 (0..96) 
   MAX-ACCESS  read-only 
   STATUS  current 
   DESCRIPTION 
      "The number of previous 15-minute intervals for which data  
       was collected.  
       An agent with CEP capability must be capable of supporting  
       at least n intervals. The minimum value of n is 4, The  
       default of n is 32 and the maximum value of n is 96. 
       The value will be <n> unless the measurement was (re-)  
       started within the last (<n>*15) minutes, in which case the  
       value will be the number of complete 15 minute intervals for  
       which the agent has at least some data. In certain cases  
       (e.g., in the case where the agent is a proxy) it is  
       possible that some intervals are unavailable.  In this case,  
       this interval is the maximum interval number for which data  
       is available. " 
   ::= { pwVcCepEntry 7 } 

pwVcCepCurrentIndications OBJECT-TYPE 
  SYNTAX BITS { 
        missingPkt  ( 0), 
        ooRngDropped( 1), 
        jtrBfrUnder ( 2), 
        pktBadLength( 3), 
        lops        ( 4), 
        cepRdi      ( 5), 
        cepAis      ( 6), 
        badHdrStack ( 7) 

  } 
  MAX-ACCESS    read-only                 
  STATUS        current 
  DESCRIPTION 
      "Definitions: 
       
       missingPkt - While playing out a sequence of packets, a  
       packet(s) was determined to be missing based on a gap in the  
       CEP sequence number. Note: If the implementation supports  
       packet re-ordering, detecting gaps should not take place as  
       packets arrive, only as they are played out - this gives  
       time for mis-ordered packets to arrive late. 
        
       ooRngDropped - Packet(s) arrives that is outside the 
       range of the jitter buffer. This may be because the 
       jitter buffer is full, or the sequence number addresses 
       a buffer outside the current jitter buffer range, or 
       addresses an already occupied buffer within range. 
       Whether or not packet re-ordering is supported by the 
       implementation, this indication MUST be supported. 
        
       jtrBfrUnder - The jitter buffer underflowed due to 
       not enough packets arriving as packets were being 
 

       played out.  
        
       pktBadLength - Non-bandwidth-saving packet arrives 
       larger or smaller than pwVcCepCfgSonetPayloadLength, or when 
       a fractional SPE packet length does not match the extension 
       header or manual configuration indicating the number of  
       equipped VTs.  
        
       lops - Loss Of Packet Sync. See draft-ietf-pwe3-sonet. 
        
       cepRdi - Circuit Emulation over Packet Remote Defect  
       Indication. Generated by the remote CEP de-packetizer when  
       detecting LOPS. Note: not generated by the remote SONET  
       function. See draft-ietf-pwe3-sonet. 
        
       cepAis - Remote CEP packetizer has detected AIS 
       on its incoming SONET stream. See draft-ietf-pwe3- 
       sonet. Note: cepAis MUST NOT (in itself) cause a CEP 
       down notification. This would be a layer violation. 

       badHdrStack - This indication is set when the number of 
       CEP header extensions detected in incoming packets does 
       not match the expected number. 
       
       Note: currently there is no hierarchy of CEP defects. 

       Note: the algorithm used to capture these indications 
       is implementation specific." 
  ::= { pwVcCepEntry 8 } 

pwVcCepLatchedIndications OBJECT-TYPE 
  SYNTAX BITS { 
        missingPkt  ( 0), 
        ooRngDropped( 1), 
        jtrBfrUnder ( 2), 
        pktBadLength( 3), 
        lops        ( 4), 
        cepRdi      ( 5), 
        cepAis      ( 6), 
        badHdrStack ( 7) 

  } 
  MAX-ACCESS    read-only                 
  STATUS        current 
  DESCRIPTION 
      "The state of CEP indicators when the CEP PW last declared 
       an errored second (either as ES, SES or a second with 
       errors inside a UAS) condition. At this time, only LOPS 
       can create a failure. Since indicators other than LOPS are 
       useful, all are latched here. For bit definitions, see 
       pwVcCepCurrentIndications above.  
        
       Note: the algorithm used to latch these indications when 
       entering an defect state is implementation specific." 
 

  ::= { pwVcCepEntry 9 } 

pwVcCepLastEsTimeStamp OBJECT-TYPE 
  SYNTAX      TimeStamp 
  MAX-ACCESS  read-only 
  STATUS      current 
  DESCRIPTION 
      "The value of sysUpTime on the most recent occasion at 
       which the CEP PW entered the ES or SES state." 
  ::= { pwVcCepEntry 10 } 

pwVcCepPeerCepOption OBJECT-TYPE 
  SYNTAX      Unsigned32 
  MAX-ACCESS  read-only 
  STATUS      current 
  DESCRIPTION 
      "The value of CEP option parameter as received from the peer 
       by the PW signaling protocol." 
  ::= { pwVcCepEntry 11 } 

-- End of CEP PW table 


-- Obtain index for PW CEP Configuration table entries 

pwVcCepCfgIndexNext OBJECT-TYPE 
  SYNTAX            PwVcCepCfgIndex 
  MAX-ACCESS        read-only 
  STATUS            current 
  DESCRIPTION 
      "This object contains an appropriate value to be used 
       for pwVcCepCfgIndex when creating entries in the 
       pwVcCepCfgTable. The value 0 indicates that no 
       unassigned entries are available.  To obtain the 
       value of pwVcCepCfgIndex for a new entry in the 
       pwVcCepCfgTable, the manager issues a management 
       protocol retrieval operation to obtain the current 
       value of pwVcCepCfgIndex. After each retrieval 
       operation, the agent should modify the value to 
       reflect the next unassigned index.  After a manager 
       retrieves a value the agent will determine through 
       its local policy when this index value will be made 
       available for reuse." 
  ::= { pwVcCepObjects 2 } 

-- PW CEP PW Configuration Table 

pwVcCepCfgTable   OBJECT-TYPE 
  SYNTAX                  SEQUENCE OF PwVcCepCfgEntry 
  MAX-ACCESS              not-accessible 
  STATUS                  current 
  DESCRIPTION 
    "This table contains a set of parameters that may be 
     referenced by 1 or more CEP PWs by pwVcCepTable." 
 

  ::= { pwVcCepObjects 3 } 

pwVcCepCfgEntry   OBJECT-TYPE 
  SYNTAX            PwVcCepCfgEntry 
  MAX-ACCESS        not-accessible 
  STATUS            current 
  DESCRIPTION 
       "These parameters define the characteristics of a 
        CEP PW. They are grouped here to ease NMS burden. 
        Once an entry is created here it may be re-used 
        by many PWs." 

  INDEX  { pwVcCepCfgTableIndex } 

     ::= { pwVcCepCfgTable 1 } 

PwVcCepCfgEntry ::= SEQUENCE { 
     pwVcCepCfgTableIndex            PwVcCepCfgIndex, 
     pwVcCepConfigError              BITS, 

     pwVcCepSonetPayloadLength       Unsigned32, 
     pwVcCepCfgMinPktLength          Unsigned32, 
     pwVcCepCfgPktReorder            TruthValue, 
     pwVcCepCfgEnableDBA             BITS, 
     pwVcCepCfgRtpHdrSuppress        TruthValue, 

     pwVcCepCfgJtrBfrDepth           Unsigned32, 

     pwVcCepCfgConsecPktsInsync      Unsigned32, 
     pwVcCepCfgConsecMissingOutSync  Unsigned32, 

     pwVcCepCfgPktErrorPlayOutValue  Unsigned32, 

     pwVcCepCfgMissingPktsToSes      Unsigned32,      
     pwVcCepCfgSesToUas              Unsigned32, 
     pwVcCepCfgSecsToExitUas         Unsigned32, 

     pwVcCepCfgRowStatus             RowStatus, 
     pwVcCepCfgStorageType           StorageType 
     } 

pwVcCepCfgTableIndex   OBJECT-TYPE 
  SYNTAX        PwVcCepCfgIndex 
  MAX-ACCESS    not-accessible 
  STATUS        current 
  DESCRIPTION 
      "Primary index to this table" 
  ::= { pwVcCepCfgEntry 1 } 

pwVcCepConfigError OBJECT-TYPE 
  SYNTAX BITS { 
        other         ( 0), 
        dba           ( 1), 
        lopsPktCount  ( 2), 
 

        pktLength     ( 3), 
        jtrBfrDepth   ( 4) 
  } 
  MAX-ACCESS    read-only 
  STATUS        current 
  DESCRIPTION 
      "Various configurations errors. Illegal settings within 
       the pwVcCepCfg or pwVcCepSonetExt tables." 
  ::= { pwVcCepCfgEntry 2 } 

pwVcCepSonetPayloadLength OBJECT-TYPE 
  SYNTAX        Unsigned32 
  MAX-ACCESS    read-create 
  STATUS        current 
  DESCRIPTION 
      "The number of SONET bytes of the Path or VT carried as  
      payload within one packet. For example, for STS-1 SPE  
      circuits, value of 783 bytes indicates that each packet  
      carries payload equivalent to one frame. For VT1.5 circuits,  
      a payload length of 104 bytes indicates that each packet  
      carries payload equivalent to one VT1.5 super-frame. The  
      actual payload size may be different, due to bandwidth  
      reduction modes, e.g. DBA mode or dynamically assigned  
      fractional SPE. This length applies to 
      inbound and outbound packets carrying user payload.  
      Although there is no control over inbound packets, those 
      of illegal length are discarded and accounted for (see  
      pwVcCepPerf...PktsBadLength.) " 


  REFERENCE 
      "For use of payload bytes see Malis, A., et al, <draft-ietf- 
       pwe3-sonet>."  
  ::= { pwVcCepCfgEntry 3 } 

pwVcCepCfgMinPktLength OBJECT-TYPE 
  SYNTAX        Unsigned32 
  MAX-ACCESS    read-create 
  STATUS        current 
  DESCRIPTION 
      "This is the minimum CEP packet length in number of 
       bytes (including CEP header and payload). It applies 
       to CEP's bandwidth-savings packets. Currently DBA is 
       the only bandwidth-savings packet type (in the future, 
       CEP may support compression). Minimum packet length is 
       necessary in some systems or networks. 
        
       Setting Zero here indicates that there is no minimum 
       packet restriction."  

  DEFVAL { 0 } 
  ::= { pwVcCepCfgEntry 4 } 


 

pwVcCepCfgPktReorder OBJECT-TYPE 
  SYNTAX        TruthValue 
  MAX-ACCESS    read-only 
  STATUS        current 
  DESCRIPTION 
      "If set True: as inbound packets are queued in the 
       jitter buffer, out of order packets are re-ordered. The  
       maximum sequence number differential (i.e., the range in 
       which re-sequencing can occur) is dependant on the depth 
       of the jitter buffer. See pwVcCepCfgJtrBfrDepth. 
        
       NOTE: Some implementations may not support this feature. 
       The agent is then required to set this False." 
  ::= { pwVcCepCfgEntry 5 } 


pwVcCepCfgEnableDBA OBJECT-TYPE 
  SYNTAX BITS { 
        ais        (0), 
        unequipped (1) 
  } 
  MAX-ACCESS    read-create 
  STATUS        current 
  DESCRIPTION 
      "Bits set here MUST enable the DBA (dynamic bandwidth 
       allocation) feature for the specified condition. Setting 
       'ais' MUST cause CEP packet payload suppression  
       when AIS is detected on the associated SONET path.  
       Similarly, 'unequipped' MUST cause payload suppression 
       when an un-equipped condition is detected on the SONET 
       path. During these conditions, CEP packets will continue 
       to be sent, but with indicators set in the CEP header 
       instructing the remote to play all ones (for AIS) or all 
       zeros (for un-equipped) onto its SONET path. 

       NOTE: Some implementations may not support this feature. 
       In these cases, if the 'ais' or 'unequipped' bits are set, 
       then 'dba' error code MUST be set in pwVcCepConfigError." 

  REFERENCE 
   "See Malis, A., et al, <draft-ietf-pwe3-sonet>." 

  DEFVAL { { unequipped } } 

  ::= { pwVcCepCfgEntry 6 } 

pwVcCepCfgRtpHdrSuppress OBJECT-TYPE 
  SYNTAX        TruthValue 
  MAX-ACCESS    read-only 
  STATUS        current 
  DESCRIPTION 
      "If set True: an RTP header is not pre-pended to the 
       CEP packet." 

 

  REFERENCE 
   "See Malis, A., et al, <draft-ietf-pwe3-sonet>."  
  DEFVAL { false } 

  ::= { pwVcCepCfgEntry 7 } 

pwVcCepCfgJtrBfrDepth OBJECT-TYPE 
  SYNTAX        Unsigned32 
  UNITS         "micro-seconds" 
  MAX-ACCESS    read-create 
  STATUS        current 
  DESCRIPTION 
      "This setting configures the number of microseconds  
       of expected packet delay variation for this CEP PW 
       over the PSN. 
 
       The actual jitter buffer MUST be at least twice this 
       value for proper operation, and is implementation 
       specific. 

       If configured to a value not supported by the 
       implementation, the agent MUST return an error code 
       'jtrBfrDepth' in 'pwVcCepConfigError ' 

       NOTE: Like bandwidth and time-slots, jitter buffers 
       are a limited resource to be managed." 

  ::= { pwVcCepCfgEntry 8 } 

-- 
-- The following counters work together to integrate (filter) 
-- errors and the lack of errors on the CEP PW. An error is 
-- caused by a missing packet. Missing packet can be a result 
-- of: packet loss in the network, (uncorrectable) packet out 
-- of sequence, packet length error, jitter buffer overflow, 
-- and jitter buffer underflow. The result is declaring whether 
-- or not the CEP PW is in Loss of Packet Sync (LOPS) state. 
-- 
pwVcCepCfgConsecPktsInsync      OBJECT-TYPE 
  SYNTAX        Unsigned32 
  MAX-ACCESS    read-create 
  STATUS        current 
  DESCRIPTION   "Consecutive pkts with sequential sequence 
                 numbers required to exit the LOPS state." 
  REFERENCE 
   "See Malis, A., et al, <draft-ietf-pwe3-sonet>." 
  DEFVAL { 2 } 
  ::= { pwVcCepCfgEntry 9 } 

pwVcCepCfgConsecMissingOutSync  OBJECT-TYPE 
  SYNTAX        Unsigned32 
  MAX-ACCESS    read-create 
  STATUS        current 
  DESCRIPTION   "Consecutive missing pkts required to enter 
 

                 the LOPS state." 
  REFERENCE 
   "See Malis, A., et al, <draft-ietf-pwe3-sonet>." 
  DEFVAL { 10 } 
  ::= { pwVcCepCfgEntry 10 } 

pwVcCepCfgPktErrorPlayOutValue OBJECT-TYPE 
  SYNTAX        Unsigned32 (0..255) 
  MAX-ACCESS    read-create 
  STATUS        current 
  DESCRIPTION 
      "This is the value played when inbound packets have 
       over/underflowed the jitter buffer, or are missing 
       for any reason. This byte pattern is sent (played) on 
       the SONET path."  
  DEFVAL { 255 } -- Play all ones 
  ::= { pwVcCepCfgEntry 11 } 

pwVcCepCfgMissingPktsToSes OBJECT-TYPE 
  SYNTAX        Unsigned32 
  UNITS         "seconds" 
  MAX-ACCESS    read-create 
  STATUS        current 
  DESCRIPTION 
      "Number of missing packets detected (consecutive or not) 
       within a 1 second window to cause a Severely Errored 
       Second (SES) to be counted." 
  DEFVAL { 3 } 
  ::= { pwVcCepCfgEntry 12 } 

pwVcCepCfgSesToUas OBJECT-TYPE 
  SYNTAX        Unsigned32 
  UNITS         "seconds" 
  MAX-ACCESS    read-create 
  STATUS        current 
  DESCRIPTION 
      "Number of consecutive SESs before declaring PW in UAS 
       state (and at which point pwVcCepPerfUASs starts counting). 
       The SesToUas default value is 10 seconds. 
        
       NOTE: Similar to RFC 3592, If the agent chooses to update 
       the various performance statistics in real time then it must 
       be prepared to retroactively reduce the ES, SES, counts by 
       this value and increase the UAS count by this value when it 
       determines that UAS state has been entered.   

       NOTE: See pwVcCepPerfSESs and pwVcCepPerfUASs." 
  DEFVAL { 10 } 
  ::= { pwVcCepCfgEntry 13 } 

pwVcCepCfgSecsToExitUas OBJECT-TYPE 
  SYNTAX        Unsigned32 
  UNITS         "seconds" 
  MAX-ACCESS    read-create 
 

  STATUS        current 
  DESCRIPTION 
      "Number of consecutive nonSESs before declaring PW is NOT 
       in UAS state (and at which point pwVcCepPerfUASs stops 
       counting)." 
  DEFVAL { 10 } 
  ::= { pwVcCepCfgEntry 14 } 

pwVcCepCfgRowStatus    OBJECT-TYPE 
  SYNTAX               RowStatus 
  MAX-ACCESS           read-create 
  STATUS               current 
  DESCRIPTION 
      "For creating, modifying, and deleting this row." 
  ::= { pwVcCepCfgEntry 16 } 

pwVcCepCfgStorageType  OBJECT-TYPE 
  SYNTAX                      StorageType 
  MAX-ACCESS                  read-create 
  STATUS                      current 
  DESCRIPTION 
      "This variable indicates the storage type for this 
       row." 
  ::= { pwVcCepCfgEntry 15 } 

-- End of CEP PW Configuration Parameter Table 

-- Fractional CEP Configuration Table 

pwVcCepFracTable   OBJECT-TYPE 
  SYNTAX                  SEQUENCE OF PwVcCepFracEntry 
  MAX-ACCESS              not-accessible 
  STATUS                  current 
  DESCRIPTION 
    "This table contains a set of parameters for CEP PWs with  
     pwVcCepType FRAC type." 
  ::= { pwVcCepObjects 4 } 

pwVcCepFracEntry   OBJECT-TYPE 
  SYNTAX            PwVcCepFracEntry 
  MAX-ACCESS        not-accessible 
  STATUS            current 
  DESCRIPTION 
      "An entry of this table can be created in two options: 
       - By the EMS in advance for creating the PW. 
       - By the agent automatically when the PW is set up. 
        
       The first option is typically used when there is an NSP 
       cross-connect option between the physical ports and the 
       emulated (virtual ports), while the second MAY be used  
       when there is a one-to-one mapping between the emulated 
       signal and the incoming signal. " 

  INDEX  { pwVcCepFracIndex } 
 



     ::= { pwVcCepFracTable 1 } 

PwVcCepFracEntry ::= SEQUENCE { 

     pwVcCepFracIndex                InterfaceIndex, 
     pwVcCepFracMode                 INTEGER, 
     pwVcCepFracConfigError          BITS, 
     pwVcCepFracAsync                PwVcCepFracAsyncMap, 
     pwVcCepFracVtgMap               PwVcCepSonetVtgMap, 
     pwVcCepFracEbm                  PwVcCepSonetEbm, 
     pwVcCepFracPeerEbm              PwVcCepSonetEbm, 
     pwVcCepFracSdhVc4Mode           INTEGER, 
     pwVcCepFracSdhVc4Tu3Map1        PwVcCepFracAsyncMap, 
     pwVcCepFracSdhVc4Tu3Map2        PwVcCepFracAsyncMap, 
     pwVcCepFracSdhVc4Tu3Map3        PwVcCepFracAsyncMap, 
     pwVcCepFracSdhVc4Tug2Map1       PwVcCepSonetVtgMap, 
     pwVcCepFracSdhVc4Tug2Map2       PwVcCepSonetVtgMap, 
     pwVcCepFracSdhVc4Tug2Map3       PwVcCepSonetVtgMap, 
     pwVcCepFracSdhVc4Ebm1           PwVcCepSdhVc4Ebm, 
     pwVcCepFracSdhVc4Ebm2           PwVcCepSdhVc4Ebm, 
     pwVcCepFracSdhVc4Ebm3           PwVcCepSdhVc4Ebm, 
     pwVcCepFracSdhVc4PeerEbm1       PwVcCepSdhVc4Ebm, 
     pwVcCepFracSdhVc4PeerEbm2       PwVcCepSdhVc4Ebm, 
     pwVcCepFracSdhVc4PeerEbm3       PwVcCepSdhVc4Ebm, 
     pwVcCepFracRowStatus            RowStatus, 
     pwVcCepFracStorageType          StorageType 
     } 

pwVcCepFracIndex OBJECT-TYPE 
  SYNTAX InterfaceIndex 
  MAX-ACCESS    not-accessible 
  STATUS        current 
  DESCRIPTION 

      "This is the primary index of this table. It is a unique  
       index within the ifTable. It represents the interface index  
       for the SONET path (RFC 3592 section 3.3) for fractional SPE  
       emulation. 
       It may represent an internal (virtual) interface if an NSP  
       function exists between the physical interface and the  
       emulation process." 

  ::= { pwVcCepFracEntry 1 } 


pwVcCepFracMode OBJECT-TYPE 
  SYNTAX INTEGER { 
           notApplicable ( 0), 
           dynamic       ( 1),  
           static        ( 2),  
           staticWithEbm ( 3), 
           staticAsync   ( 4)  
 

  } 
  MAX-ACCESS    read-create 
  STATUS        current 
  DESCRIPTION 

      "Fractional mode for STS-1/VC-3 circuits: 

       notApplicable - When this is not STS-1/VC-3 signal. 
       dynamic - EBM carried within the CEP header. Unequipped  
                 VTs are removed from the payload on the fly.   
       static  - EBM not carried within the CEP header. Only VTs  
                 defined in the EBM are carried within the payload. 
       staticWithEbm - EBM carried within the CEP header. Only  
                 VTs defined in the EBM are carried within the  
                 payload.                            
       staticAsync - Asynchronous E3/T3 fixed byte removal only. "        

  DEFVAL { dynamic } 
  ::= { pwVcCepFracEntry 2 } 

pwVcCepFracConfigError OBJECT-TYPE 
  SYNTAX BITS { 
        other               ( 0), 
        vtgMapEbmconflict   ( 1),  
        vtgMapAsyncConflict ( 2) 
  } 
  MAX-ACCESS    read-create 
  STATUS        current 
  DESCRIPTION 

      "vtgMapEbmConflict is set when the configured static EBM 
       does not match the configured vtgMap for fractional  
       STS-1/VC-3 circuits, or when the TUG2Map is in conflict with  
       the static EBM for VC-4 circuits. For example, if the vtgMap  
       specifies that VTG#1 carries VT2 VTs while the EBM indicate  
       that four VTs are equipped within VTG#1. 
       vtgMapAsyncConflict is set when there is a conflict between  
       the mode, the async indication and the vtgMap fields. For  
       example, fractional mode is set to Static Async while the  
       VtgMap indicate that the STS-1/VC-3 carries VTs. Or in  
       fractional VC-4 circuits both async1 and Tug2Map are set." 

 ::= { pwVcCepFracEntry 3 } 

pwVcCepFracAsync OBJECT-TYPE 
  SYNTAX PwVcCepFracAsyncMap 
  MAX-ACCESS    read-create 
  STATUS        current 
     DESCRIPTION  
       "The Asynchronous payload carried within the STS-1/VC-3.  
        This variable should be set when 'staticAsync' Fractional  
        STS-1/VC-3 pwVcCepFracMode is selected, and hold the value 
        of 'other' otherwise." 
       
 

  DEFVAL { other } 
  ::= { pwVcCepFracEntry 4 } 

pwVcCepFracVtgMap OBJECT-TYPE 
  SYNTAX        PwVcCepSonetVtgMap 
  MAX-ACCESS    read-create 
  STATUS        current 
  DESCRIPTION 
       "The VT/VC types of the seven VTG/TUG-2 within the  
        STS-1/VC-3. 
        This variable should be set when 'dynamic', 'static' 
        or 'staticWithEbm' Fractional STS-1/VC-3 pwVcCepFracMode  
        is selected. " 

  ::= { pwVcCepFracEntry 5 } 

pwVcCepFracEbm OBJECT-TYPE 
  SYNTAX        PwVcCepSonetEbm 
  MAX-ACCESS    read-create 
  STATUS        current 
  DESCRIPTION 
       "Static Equipped Bit Mask (EBM) for STS-1/VC-3 channel. 
        This variable should be set when 'static' or  
        'staticWithEbm' Fractional STS-1/VC-3 pwVcCepFracMode is  
        selected. " 

  ::= { pwVcCepFracEntry 6 } 

pwVcCepFracPeerEbm OBJECT-TYPE 
  SYNTAX        PwVcCepSonetEbm 
  MAX-ACCESS    read-create 
  STATUS        current 
  DESCRIPTION 
       "Equipped Bit Mask (EBM) for STS-1/VC-3 channel received 
        from the peer within the CEP extension header." 

  ::= { pwVcCepFracEntry 7 } 


pwVcCepFracSdhVc4Mode OBJECT-TYPE 
  SYNTAX INTEGER { 
           notApplicable ( 0), 
           dynamic       ( 1),  
           static        ( 2),  
           staticWithEbm ( 3) 
  } 
  MAX-ACCESS    read-create 
  STATUS        current 
  DESCRIPTION 

      "Fractional mode for VC-4 circuits: 

       notApllicable - When this is not VC-4 circuit. 
       dynamic - EBM carried within the CEP header. Unequipped  
 

                 VTs are removed from the payload on the fly.   
       static  - EBM not carried within the CEP header. Only VTs  
                 defined in the EBM are carried within the payload. 
       staticWithEbm - EBM carried within the CEP header. Only  
                 VTs defined in the EBM are carried within the  
                 payload. " 

  DEFVAL { notApplicable } 
  ::= { pwVcCepFracEntry 8 } 


pwVcCepFracSdhVc4Tu3Map1 OBJECT-TYPE 
  SYNTAX PwVcCepFracAsyncMap 
  MAX-ACCESS    read-create 
  STATUS        current 
     DESCRIPTION  
       "If the first TUG-3 within the VC-4 contains a TU-3, this 
        variable must be set. " 

  DEFVAL { other } 
  ::= { pwVcCepFracEntry 9 } 


pwVcCepFracSdhVc4Tu3Map2 OBJECT-TYPE 
  SYNTAX PwVcCepFracAsyncMap 
  MAX-ACCESS    read-create 
  STATUS        current 
     DESCRIPTION  
       "If the second TUG-3 within the VC-4 contains a TU-3, this 
        variable must be set."  

  DEFVAL { other } 
  ::= { pwVcCepFracEntry 10 } 

pwVcCepFracSdhVc4Tu3Map3 OBJECT-TYPE 
  SYNTAX PwVcCepFracAsyncMap 
  MAX-ACCESS    read-create 
  STATUS        current 
     DESCRIPTION  
       "If the third TUG-3 within the VC-4 contains a TU-3, this 
        variable must be set. " 

  DEFVAL { other } 
  ::= { pwVcCepFracEntry 11 } 


pwVcCepFracSdhVc4Tug2Map1 OBJECT-TYPE 
  SYNTAX        PwVcCepSonetVtgMap 
  MAX-ACCESS    read-create 
  STATUS        current 
  DESCRIPTION 
       "The VC types of the seven TUG-2 within the first 
        TUG-3 of the VC-4. " 

 

  ::= { pwVcCepFracEntry 12 } 

pwVcCepFracSdhVc4Tug2Map2 OBJECT-TYPE 
  SYNTAX        PwVcCepSonetVtgMap 
  MAX-ACCESS    read-create 
  STATUS        current 
  DESCRIPTION 
       "The VC types of the seven TUG-2 within the second 
        TUG-3 of the VC-4. " 

  ::= { pwVcCepFracEntry 13 } 

pwVcCepFracSdhVc4Tug2Map3 OBJECT-TYPE 
  SYNTAX        PwVcCepSonetVtgMap 
  MAX-ACCESS    read-create 
  STATUS        current 
  DESCRIPTION 
       "The VC types of the seven TUG-2 within the third 
        TUG-3 of the VC-4. " 

  ::= { pwVcCepFracEntry 14 } 

pwVcCepFracSdhVc4Ebm1 OBJECT-TYPE 
  SYNTAX        PwVcCepSdhVc4Ebm 
  MAX-ACCESS    read-create 
  STATUS        current 
  DESCRIPTION 
       "Static Equipped Bit Mask (EBM) for first TUG-3 within 
        the VC-4. 
        This variable should be set when 'static' or  
        'staticWithEbm' Fractional VC-4 pwVcCepFracMode is  
        selected. " 

  ::= { pwVcCepFracEntry 15 } 

pwVcCepFracSdhVc4Ebm2 OBJECT-TYPE 
  SYNTAX        PwVcCepSdhVc4Ebm 
  MAX-ACCESS    read-create 
  STATUS        current 
  DESCRIPTION 
       "Static Equipped Bit Mask (EBM) for second TUG-3 within 
        the VC-4. 
        This variable should be set when 'static' or  
        'StaticWithEbm' Fractional VC-4 pwVcCepFracMode is  
        selected. " 

  ::= { pwVcCepFracEntry 16 } 

pwVcCepFracSdhVc4Ebm3 OBJECT-TYPE 
  SYNTAX        PwVcCepSdhVc4Ebm 
  MAX-ACCESS    read-create 
  STATUS        current 
  DESCRIPTION 
       "Static Equipped Bit Mask (EBM) for third TUG-3 within 
 

        the VC-4. 
        This variable should be set when 'Static' or  
        'staticWithEbm' Fractional VC-4 pwVcCepFracMode is  
        selected. " 

  ::= { pwVcCepFracEntry 17 } 


pwVcCepFracSdhVc4PeerEbm1 OBJECT-TYPE 
  SYNTAX        PwVcCepSdhVc4Ebm 
  MAX-ACCESS    read-create 
  STATUS        current 
  DESCRIPTION 
       "Equipped Bit Mask (EBM) for the first TUG-3 within  
        the fractional VC-4 channel received from peer  
        within the CEP extension header." 

  ::= { pwVcCepFracEntry 18 } 

pwVcCepFracSdhVc4PeerEbm2 OBJECT-TYPE 
  SYNTAX        PwVcCepSdhVc4Ebm 
  MAX-ACCESS    read-create 
  STATUS        current 
  DESCRIPTION 
       "Equipped Bit Mask (EBM) for the second TUG-3 within  
        the fractional VC-4 channel received from peer  
        within the CEP extension header." 

  ::= { pwVcCepFracEntry 19 } 

pwVcCepFracSdhVc4PeerEbm3 OBJECT-TYPE 
  SYNTAX        PwVcCepSdhVc4Ebm 
  MAX-ACCESS    read-create 
  STATUS        current 
  DESCRIPTION 
       "Equipped Bit Mask (EBM) for the third TUG-3 within  
        the fractional VC-4 channel received from peer  
        within the CEP extension header." 

  ::= { pwVcCepFracEntry 20 } 

pwVcCepFracRowStatus OBJECT-TYPE 
  SYNTAX        RowStatus 
  MAX-ACCESS    read-create 
  STATUS        current 
  DESCRIPTION 
       "For creating, modifying, and deleting this row." 

  ::= { pwVcCepFracEntry 21 } 

pwVcCepFracStorageType OBJECT-TYPE 
  SYNTAX        StorageType 
  MAX-ACCESS    read-create 
  STATUS        current 
 

  DESCRIPTION 
       "This variable indicates the storage type for this 
        object." 

  ::= { pwVcCepFracEntry 22 } 


-- End Fractional CEP Configuration Table 


-- CEP PW Performance Current Interval Table. 

pwVcCepPerfCurrentTable OBJECT-TYPE 
  SYNTAX        SEQUENCE OF PwVcCepPerfCurrentEntry 
  MAX-ACCESS    not-accessible 
  STATUS        current 
  DESCRIPTION 
      "CEP bridges the SONET and packet worlds. In the packet 
       world, counts typically start from the time of service 
       creation - and don't stop. In the SONET world, counts are 
       kept in 15 minute intervals. The CEP-MIB supports both 
       methods. The current 15 minute interval counts are in  
       this table. The interval and total stats are in tables 
       following this. 
               
       This table provides per CEP PW performance information. 
       HC (high capacity) counters are required for some counts 
       due to the high speeds expected with CEP services. A SONET 
       path of width 48 (STS-48c) can rollover non-HC counters in 
       a few minutes." 
  ::= { pwVcCepObjects 5 } 

pwVcCepPerfCurrentEntry OBJECT-TYPE 
  SYNTAX        PwVcCepPerfCurrentEntry 
  MAX-ACCESS    not-accessible 
  STATUS        current 
  DESCRIPTION 
      "An entry in this table is created by the agent for every  
       pwVcCep entry. After 15 minutes, the contents of this table 
       entry are copied to a new entry in the pwVcCepPerfInterval 
       table and the counts in this entry are reset to zero." 

  INDEX  { pwVcIndex } 
 
  ::= { pwVcCepPerfCurrentTable 1 } 

PwVcCepPerfCurrentEntry ::= SEQUENCE { 
     pwVcCepPerfCurrentDbaInPacketsHC     Counter64, 
     pwVcCepPerfCurrentDbaOutPacketsHC    Counter64, 

     pwVcCepPerfCurrentInNegPtrAdjust     Counter32, 
     pwVcCepPerfCurrentInPosPtrAdjust     Counter32, 
     pwVcCepPerfCurrentInPtrAdjustSecs    Counter32, 
     pwVcCepPerfCurrentOutNegPtrAdjust    Counter32, 
 

     pwVcCepPerfCurrentOutPosPtrAdjust    Counter32, 
     pwVcCepPerfCurrentOutPtrAdjustSecs   Counter32, 
     pwVcCepPerfCurrentAbsPtrAdjust       Integer32, 

     pwVcCepPerfCurrentMissingPkts        Counter32, 
     pwVcCepPerfCurrentPktsOoseq          Counter32, 
     pwVcCepPerfCurrentPktsOoRngDropped   Counter32,  
     pwVcCepPerfCurrentJtrBfrUnderruns    Counter32, 
     pwVcCepPerfCurrentPktsBadLength      Counter32, 
     pwVcCepPerfCurrentSummaryErrors      Counter32, 

     pwVcCepPerfCurrentESs                PerfCurrentCount, 
     pwVcCepPerfCurrentSESs               PerfCurrentCount, 
     pwVcCepPerfCurrentUASs               PerfCurrentCount, 
     pwVcCepPerfCurrentFC                 PerfCurrentCount 
  } 

pwVcCepPerfCurrentDbaInPacketsHC OBJECT-TYPE 
  SYNTAX        Counter64 
  MAX-ACCESS    read-only 
  STATUS        current 
  DESCRIPTION 
      "Number of DBA packets received." 
  ::= { pwVcCepPerfCurrentEntry 1 } 

pwVcCepPerfCurrentDbaOutPacketsHC OBJECT-TYPE 
  SYNTAX        Counter64 
  MAX-ACCESS    read-only 
  STATUS        current 
  DESCRIPTION 
      "Number of DBA packets sent." 
  ::= { pwVcCepPerfCurrentEntry 2 } 


-- Pointer adjustment stats 

pwVcCepPerfCurrentInNegPtrAdjust OBJECT-TYPE 
  SYNTAX        Counter32 
  MAX-ACCESS    read-only 
  STATUS        current 
  DESCRIPTION 
      "Number of negative pointer adjustments sent on the 
       SONET path based on CEP pointer adjustments received." 
  ::= { pwVcCepPerfCurrentEntry 3 } 

pwVcCepPerfCurrentInPosPtrAdjust OBJECT-TYPE 
  SYNTAX        Counter32 
  MAX-ACCESS    read-only 
  STATUS        current 
  DESCRIPTION 
      "Number of positive pointer adjustments sent on the 
       SONET path based on CEP pointer adjustments received." 
  ::= { pwVcCepPerfCurrentEntry 4 } 

 

pwVcCepPerfCurrentInPtrAdjustSecs OBJECT-TYPE 
  SYNTAX        Counter32 
  MAX-ACCESS    read-only 
  STATUS        current 
  DESCRIPTION 
      "Number of seconds in which a pos or neg pointer 
       adjustment was sent on the SONET path." 
  ::= { pwVcCepPerfCurrentEntry 5 } 

pwVcCepPerfCurrentOutNegPtrAdjust OBJECT-TYPE 
  SYNTAX        Counter32 
  MAX-ACCESS    read-only 
  STATUS        current 
  DESCRIPTION 
      "Number of negative pointer adjustments seen on the 
       SONET path and encoded onto sent CEP packets." 
  ::= { pwVcCepPerfCurrentEntry 6 } 

pwVcCepPerfCurrentOutPosPtrAdjust OBJECT-TYPE 
  SYNTAX        Counter32 
  MAX-ACCESS    read-only 
  STATUS        current 
  DESCRIPTION 
      "Number of positive pointer adjustments seen on the 
       SONET path and encoded onto sent CEP packets." 
  ::= { pwVcCepPerfCurrentEntry 7 } 

pwVcCepPerfCurrentOutPtrAdjustSecs OBJECT-TYPE 
  SYNTAX        Counter32 
  MAX-ACCESS    read-only 
  STATUS        current 
  DESCRIPTION 
      "Number of seconds in which a pos or neg pointer 
       adjustment was seen on the SONET path." 
  ::= { pwVcCepPerfCurrentEntry 8 } 

pwVcCepPerfCurrentAbsPtrAdjust OBJECT-TYPE 
  SYNTAX        Integer32 
  MAX-ACCESS    read-only 
  STATUS        current 
  DESCRIPTION 
      "Absolute Pointer adjustments is relative adjustment 
       drifts between inbound and outbound streams. It is 
       calculated as absolute value of : 
          ( InPosPtrAdjust  -   InNegPtrAdjust ) -  
          (OutPosPtrAdjust  -   OutNegPtrAdjust)     " 
  ::= { pwVcCepPerfCurrentEntry 9 } 

pwVcCepPerfCurrentMissingPkts OBJECT-TYPE 
  SYNTAX        Counter32 
  MAX-ACCESS    read-only 
  STATUS        current 
  DESCRIPTION 
      "Number of missing packets (as detected via CEP header 
 

       sequence number gaps)." 
  ::= { pwVcCepPerfCurrentEntry 10 } 

pwVcCepPerfCurrentPktsOoseq OBJECT-TYPE 
  SYNTAX        Counter32 
  MAX-ACCESS    read-only 
  STATUS        current 
  DESCRIPTION 
      "Number of packets detected out of sequence (via CEP  
       header sequence numbers), but successfully re-ordered. 
       Note: some implementations may not support this 
       feature (see pwVcCepCfgPktReorder)." 
  ::= { pwVcCepPerfCurrentEntry 11 } 

pwVcCepPerfCurrentPktsOoRngDropped OBJECT-TYPE 
  SYNTAX        Counter32 
  MAX-ACCESS    read-only 
  STATUS        current 
  DESCRIPTION 
      "Number of packets detected out of range (via CEP  
       header sequence numbers), and could not be re- 
       ordered, or could not fit in the jitter buffer." 
  ::= { pwVcCepPerfCurrentEntry 12 } 

pwVcCepPerfCurrentJtrBfrUnderruns OBJECT-TYPE 
  SYNTAX        Counter32 
  MAX-ACCESS    read-only 
  STATUS        current 
  DESCRIPTION 
      "Number of times a packet needed to be played 
       out and the jitter buffer was empty." 
  ::= { pwVcCepPerfCurrentEntry 13 } 


pwVcCepPerfCurrentPktsBadLength OBJECT-TYPE 
  SYNTAX        Counter32 
  MAX-ACCESS    read-only 
  STATUS        current 
  DESCRIPTION 
      "Number of normal (non-bandwidth-saving packets received) 
       larger or smaller than pwVcCepCfgNormalPktLength." 
  ::= { pwVcCepPerfCurrentEntry 14 } 

pwVcCepPerfCurrentSummaryErrors OBJECT-TYPE 
  SYNTAX        Counter32 
  MAX-ACCESS    read-only 
  STATUS        current 
  DESCRIPTION 
      "A summary of all the packet error types above (from 
       missing packets to bad length packets)." 
  ::= { pwVcCepPerfCurrentEntry 15 } 

pwVcCepPerfCurrentESs OBJECT-TYPE 
   SYNTAX       PerfCurrentCount 
 

   MAX-ACCESS   read-only 
   STATUS       current 
   DESCRIPTION 
       "The counter associated with the number of Errored 
        Seconds encountered." 
   ::= { pwVcCepPerfCurrentEntry 16 } 

pwVcCepPerfCurrentSESs OBJECT-TYPE 
   SYNTAX        PerfCurrentCount 
   MAX-ACCESS    read-only 
   STATUS        current 
   DESCRIPTION 
       "The counter associated with the number of 
        Severely Errored Seconds encountered." 
   ::= { pwVcCepPerfCurrentEntry 17 } 

pwVcCepPerfCurrentUASs OBJECT-TYPE 
   SYNTAX        PerfCurrentCount 
   MAX-ACCESS    read-only 
   STATUS        current 
   DESCRIPTION 
       "The counter associated with the number of 
        Unavailable Seconds encountered." 
   ::= { pwVcCepPerfCurrentEntry 18 } 

pwVcCepPerfCurrentFC OBJECT-TYPE 
   SYNTAX        PerfCurrentCount 
   MAX-ACCESS    read-only 
   STATUS        current 
   DESCRIPTION 
       "CEP Failure Counts (FC-CEP). The number of CEP failure 
        events. A failure event begins when the LOPS failure 
        is declared, and ends when the failure is cleared. A 
        failure event that begins in one period and ends in 
        another period is counted only in the period in which 
        it begins." 
   ::= { pwVcCepPerfCurrentEntry 19 } 

-- End CEP PW Performance Current Interval Table 


-- CEP PW Performance Interval Table. 

pwVcCepPerfIntervalTable OBJECT-TYPE 
  SYNTAX        SEQUENCE OF PwVcCepPerfIntervalEntry 
  MAX-ACCESS    not-accessible 
  STATUS        current 
  DESCRIPTION 
      "This table provides per CEP PW performance information 
       much like the pwVcCepPerfCurrentTable above. However, 
       these counts represent historical 15 minute intervals. 
       Typically, this table will have a maximum of 96 entries 
       for a 24 hour period, but is not limited to this. 
       NOTE: Counter64 objects are used here, Counter32 is 
 

       too small for OC-768 CEP PWs." 
  ::= { pwVcCepObjects 6 } 

pwVcCepPerfIntervalEntry OBJECT-TYPE 
  SYNTAX        PwVcCepPerfIntervalEntry 
  MAX-ACCESS    not-accessible 
  STATUS        current 
  DESCRIPTION 
      "An entry in this table is created by the agent for 
       every pwVcCepPerfCurrentEntry that is 15 minutes old. 
       The contents of the Current entry are copied to the new 
       entry here. The Current entry, then resets its counts 
       to zero for the next current 15 minute interval. 
       pwVcCepIndex is found in the pwVcCepCfg table." 

  INDEX  { pwVcIndex, pwVcCepPerfIntervalNumber } 

  ::= { pwVcCepPerfIntervalTable 1 } 

PwVcCepPerfIntervalEntry ::= SEQUENCE { 
     pwVcCepPerfIntervalNumber             Unsigned32, 
     pwVcCepPerfIntervalValidData          TruthValue, 
     pwVcCepPerfIntervalReset              INTEGER, 
     pwVcCepPerfIntervalTimeElapsed        Integer32, 

     pwVcCepPerfIntervalDbaInPacketsHC     Counter64, 
     pwVcCepPerfIntervalDbaOutPacketsHC    Counter64, 

     pwVcCepPerfIntervalInNegPtrAdjust     Counter32, 
     pwVcCepPerfIntervalInPosPtrAdjust     Counter32, 
     pwVcCepPerfIntervalInPtrAdjustSecs    Counter32, 
     pwVcCepPerfIntervalOutNegPtrAdjust    Counter32, 
     pwVcCepPerfIntervalOutPosPtrAdjust    Counter32, 
     pwVcCepPerfIntervalOutPtrAdjustSecs   Counter32, 
     pwVcCepPerfIntervalAbsPtrAdjust       Integer32, 

     pwVcCepPerfIntervalMissingPkts        Counter32, 
     pwVcCepPerfIntervalPktsOoseq          Counter32, 
     pwVcCepPerfIntervalPktsOoRngDropped   Counter32,  
     pwVcCepPerfIntervalJtrBfrUnderruns    Counter32, 
     pwVcCepPerfIntervalPktsBadLength      Counter32, 
     pwVcCepPerfIntervalSummaryErrors      Counter32, 

     pwVcCepPerfIntervalESs                PerfIntervalCount, 
     pwVcCepPerfIntervalSESs               PerfIntervalCount, 
     pwVcCepPerfIntervalUASs               PerfIntervalCount, 
     pwVcCepPerfIntervalFC                 PerfIntervalCount 
     } 

pwVcCepPerfIntervalNumber OBJECT-TYPE 
  SYNTAX        Unsigned32 
  MAX-ACCESS    not-accessible 
  STATUS        current 
  DESCRIPTION 
 

      "A number (normally between 1 and 96 to cover a 24 hour 
       period) which identifies the interval for which the set 
       of statistics is available. The interval identified by 1 
       is the most recently completed 15 minute interval, and 
       the interval identified by N is the interval immediately 
       preceding the one identified by N-1. The minimum range of 
       N is 1 through 4. The default range is 1 through 32. The 
       maximum value of N is 1 through 96." 
  ::= { pwVcCepPerfIntervalEntry 1 } 


pwVcCepPerfIntervalValidData OBJECT-TYPE 
  SYNTAX        TruthValue 
  MAX-ACCESS    read-only 
  STATUS        current 
  DESCRIPTION 
      "This variable indicates if the data for this interval 
       is valid." 
  ::= { pwVcCepPerfIntervalEntry 2 } 

pwVcCepPerfIntervalReset OBJECT-TYPE 
  SYNTAX        INTEGER { 
        reset (1), 
        normal(2) 
  } 
  MAX-ACCESS    read-create 
  STATUS        current 
  DESCRIPTION 
      "Used in cases where the user knows that the errors 

       within this interval should not be counted. Writing 
       'reset' sets all error counts to zero." 
  ::= { pwVcCepPerfIntervalEntry 3 } 

pwVcCepPerfIntervalTimeElapsed OBJECT-TYPE 
   SYNTAX      Integer32  
   MAX-ACCESS  read-only 
   STATUS      current 
   DESCRIPTION 
     "The duration of a particular interval in seconds, 
      Adjustments in the system's time-of-day clock, may 
      cause the interval to be greater or less than, the 
      normal value. Therefore this actual interval value 
      is provided." 
   ::= { pwVcCepPerfIntervalEntry 4 } 

pwVcCepPerfIntervalDbaInPacketsHC OBJECT-TYPE 
  SYNTAX        Counter64 
  MAX-ACCESS    read-only 
  STATUS        current 
  DESCRIPTION 
      "Number of DBA packets received." 
  ::= { pwVcCepPerfIntervalEntry 5 } 

 

pwVcCepPerfIntervalDbaOutPacketsHC OBJECT-TYPE 
  SYNTAX        Counter64 
  MAX-ACCESS    read-only 
  STATUS        current 
  DESCRIPTION 
      "Number of DBA packets sent." 
  ::= { pwVcCepPerfIntervalEntry 6 } 


-- Pointer adjustment stats 
pwVcCepPerfIntervalInNegPtrAdjust OBJECT-TYPE 
  SYNTAX        Counter32 
  MAX-ACCESS    read-only 
  STATUS        current 
  DESCRIPTION 
      "Number of negative pointer adjustments sent on the 
       SONET path based on CEP pointer adjustments received." 
  ::= { pwVcCepPerfIntervalEntry 7 } 

pwVcCepPerfIntervalInPosPtrAdjust OBJECT-TYPE 
  SYNTAX        Counter32 
  MAX-ACCESS    read-only 
  STATUS        current 
  DESCRIPTION 
      "Number of positive pointer adjustments sent on the 
       SONET path based on CEP pointer adjustments received." 
  ::= { pwVcCepPerfIntervalEntry 8 } 

pwVcCepPerfIntervalInPtrAdjustSecs OBJECT-TYPE 
  SYNTAX        Counter32 
  MAX-ACCESS    read-only 
  STATUS        current 
  DESCRIPTION 
      "Number of seconds in which a pos or neg pointer 
       adjustment was sent on the SONET path." 
  ::= { pwVcCepPerfIntervalEntry 9 } 

pwVcCepPerfIntervalOutNegPtrAdjust OBJECT-TYPE 
  SYNTAX        Counter32 
  MAX-ACCESS    read-only 
  STATUS        current 
  DESCRIPTION 
      "Number of negative pointer adjustments seen on the 
       SONET path and encoded onto sent CEP packets." 
  ::= { pwVcCepPerfIntervalEntry 10 } 

pwVcCepPerfIntervalOutPosPtrAdjust OBJECT-TYPE 
  SYNTAX        Counter32 
  MAX-ACCESS    read-only 
  STATUS        current 
  DESCRIPTION 
      "Number of positive pointer adjustments seen on the 
       SONET path and encoded onto sent CEP packets." 
  ::= { pwVcCepPerfIntervalEntry 11 } 
 


pwVcCepPerfIntervalOutPtrAdjustSecs OBJECT-TYPE 
  SYNTAX        Counter32 
  MAX-ACCESS    read-only 
  STATUS        current 
  DESCRIPTION 
      "Number of seconds in which a pos or neg pointer 
       adjustment was seen on the SONET path." 
  ::= { pwVcCepPerfIntervalEntry 12 } 

pwVcCepPerfIntervalAbsPtrAdjust OBJECT-TYPE 
  SYNTAX        Integer32 
  MAX-ACCESS    read-only 
  STATUS        current 
  DESCRIPTION 
      "Absolute Pointer adjustments is relative adjustment 
       drifts between inbound and outbound streams. It is 
       calculated as absolute value of : 
          ( InPosPtrAdjust  -   InNegPtrAdjust) -  
          (OutPosPtrAdjust  -  OutNegPtrAdjust)     " 
  ::= { pwVcCepPerfIntervalEntry 13 } 

pwVcCepPerfIntervalMissingPkts OBJECT-TYPE 
  SYNTAX        Counter32 
  MAX-ACCESS    read-only 
  STATUS        current 
  DESCRIPTION 
      "Number of missing packets (as detected via CEP header 
       sequence number gaps)." 
  ::= { pwVcCepPerfIntervalEntry 14 } 

pwVcCepPerfIntervalPktsOoseq OBJECT-TYPE 
  SYNTAX        Counter32 
  MAX-ACCESS    read-only 
  STATUS        current 
  DESCRIPTION 
      "Number of packets detected out of sequence (via CEP  
       header sequence numbers), but successfully re-ordered. 
       Note: some implementations mat not support this 
       feature (see pwVcCepCfgPktReorder)." 
  ::= { pwVcCepPerfIntervalEntry 15 } 

pwVcCepPerfIntervalPktsOoRngDropped OBJECT-TYPE 
  SYNTAX        Counter32 
  MAX-ACCESS    read-only 
  STATUS        current 
  DESCRIPTION 
      "Number of packets detected out of range (via CEP  
       header sequence numbers), and could not be re- 
       ordered, or could not fit in the jitter buffer." 
  ::= { pwVcCepPerfIntervalEntry 16 } 

pwVcCepPerfIntervalJtrBfrUnderruns OBJECT-TYPE 
  SYNTAX        Counter32 
 

  MAX-ACCESS    read-only 
  STATUS        current 
  DESCRIPTION 
      "Number of times a packet needed to be played 
       out and the jitter buffer was empty." 
  ::= { pwVcCepPerfIntervalEntry 17 } 

pwVcCepPerfIntervalPktsBadLength OBJECT-TYPE 
  SYNTAX        Counter32 
  MAX-ACCESS    read-only 
  STATUS        current 
  DESCRIPTION 
      "Number of packets received larger or smaller than 
       pwVcCepCfgNormalPktLength." 
  ::= { pwVcCepPerfIntervalEntry 18 } 

pwVcCepPerfIntervalSummaryErrors OBJECT-TYPE 
  SYNTAX        Counter32 
  MAX-ACCESS    read-only 
  STATUS        current 
  DESCRIPTION 
      "A summary of all the packet error types above (from 
       missing packets to bad length packets)." 
  ::= { pwVcCepPerfIntervalEntry 19 } 

pwVcCepPerfIntervalESs OBJECT-TYPE 
  SYNTAX       PerfIntervalCount 
  MAX-ACCESS   read-only 
  STATUS       current 
  DESCRIPTION 
      "The counter associated with the number of Errored 
       Seconds encountered." 
  ::= { pwVcCepPerfIntervalEntry 20 } 

pwVcCepPerfIntervalSESs OBJECT-TYPE 
  SYNTAX        PerfIntervalCount 
  MAX-ACCESS    read-only 
  STATUS        current 
  DESCRIPTION 
      "The counter associated with the number of 
       Severely Errored Seconds encountered." 
  ::= { pwVcCepPerfIntervalEntry 21 } 

pwVcCepPerfIntervalUASs OBJECT-TYPE 
  SYNTAX        PerfIntervalCount 
  MAX-ACCESS    read-only 
  STATUS        current 
  DESCRIPTION 
      "The counter associated with the number of 
       Unavailable Seconds encountered." 
  ::= { pwVcCepPerfIntervalEntry 22 } 

pwVcCepPerfIntervalFC OBJECT-TYPE 
  SYNTAX        PerfIntervalCount 
 

  MAX-ACCESS    read-only 
  STATUS        current 
  DESCRIPTION 
      "CEP Failure Counts (FC-CEP). The number of CEP failure 
       events. A failure event begins when the LOPS failure 
       is declared, and ends when the failure is cleared. A 
       failure event that begins in one period and ends in 
       another period is counted only in the period in which 
       it begins." 
  ::= { pwVcCepPerfIntervalEntry 23 } 
    
-- End CEP PW Performance Interval Table 
                                  
                                  
-- CEP PW Total Performance Table  

pwVcCepPerfTotalTable OBJECT-TYPE 
  SYNTAX        SEQUENCE OF PwVcCepPerfTotalEntry 
  MAX-ACCESS    not-accessible 
  STATUS        current 
  DESCRIPTION 
      "This table provides per CEP PW performance information 
       much like the pwVcCepPerfIntervalTable above. However, 
       these counts represent complete historical information. 
       NOTE: Counter64 objects are used here, Counter32 is 
       too small for OC-768 CEP PWs." 
  ::= { pwVcCepObjects 7 } 

pwVcCepPerfTotalEntry OBJECT-TYPE 
  SYNTAX        PwVcCepPerfTotalEntry 
  MAX-ACCESS    not-accessible 
  STATUS        current 
  DESCRIPTION 
      "An entry is created in this table by the agent for  
       every entry in the pwVcCep table." 

  INDEX  { pwVcIndex } 

     ::= { pwVcCepPerfTotalTable 1 } 

PwVcCepPerfTotalEntry ::= SEQUENCE { 
    
     pwVcCepPerfTotalDbaInPacketsHC         Counter64, 
     pwVcCepPerfTotalDbaOutPacketsHC        Counter64, 

     pwVcCepPerfTotalInNegPtrAdjust         Counter32, 
     pwVcCepPerfTotalInPosPtrAdjust         Counter32, 
     pwVcCepPerfTotalInPtrAdjustSecs        Counter32, 
     pwVcCepPerfTotalOutNegPtrAdjust        Counter32, 
     pwVcCepPerfTotalOutPosPtrAdjust        Counter32, 
     pwVcCepPerfTotalOutPtrAdjustSecs       Counter32, 
     pwVcCepPerfTotalAbsPtrAdjust           Integer32, 

     pwVcCepPerfTotalMissingPkts            Counter32, 
 

     pwVcCepPerfTotalPktsOoseq              Counter32, 
     pwVcCepPerfTotalPktsOoRngDropped       Counter32,  
     pwVcCepPerfTotalJtrBfrUnderruns        Counter32, 
     pwVcCepPerfTotalPktsBadLength          Counter32, 
     pwVcCepPerfTotalSummaryErrors          Counter32, 

     pwVcCepPerfTotalESs                    Counter32, 
     pwVcCepPerfTotalSESs                   Counter32, 
     pwVcCepPerfTotalUASs                   Counter32, 
     pwVcCepPerfTotalFC                     Counter32, 
     pwVcCepPerfTotalDiscontinuityTime      TimeStamp 
     } 

pwVcCepPerfTotalDbaInPacketsHC OBJECT-TYPE 
  SYNTAX        Counter64 
  MAX-ACCESS    read-only 
  STATUS        current 
  DESCRIPTION 
      "Number of DBA packets received." 
  ::= { pwVcCepPerfTotalEntry 1 } 

pwVcCepPerfTotalDbaOutPacketsHC OBJECT-TYPE 
  SYNTAX        Counter64 
  MAX-ACCESS    read-only 
  STATUS        current 
  DESCRIPTION 
      "Number of DBA packets sent." 
  ::= { pwVcCepPerfTotalEntry 2 } 


-- Pointer adjustment stats 
pwVcCepPerfTotalInNegPtrAdjust OBJECT-TYPE 
  SYNTAX        Counter32 
  MAX-ACCESS    read-only 
  STATUS        current 
  DESCRIPTION 
      "Number of negative pointer adjustments sent on the 
       SONET path based on CEP pointer adjustments received." 
  ::= { pwVcCepPerfTotalEntry 3 } 

pwVcCepPerfTotalInPosPtrAdjust OBJECT-TYPE 
  SYNTAX        Counter32 
  MAX-ACCESS    read-only 
  STATUS        current 
  DESCRIPTION 
      "Number of positive pointer adjustments sent on the 
       SONET path based on CEP pointer adjustments received." 
  ::= { pwVcCepPerfTotalEntry 4 } 

pwVcCepPerfTotalInPtrAdjustSecs OBJECT-TYPE 
  SYNTAX        Counter32 
  MAX-ACCESS    read-only 
  STATUS        current 
  DESCRIPTION 
 

      "Number of seconds in which a pos or neg pointer 
       adjustment was sent on the SONET path." 
  ::= { pwVcCepPerfTotalEntry 5 } 

pwVcCepPerfTotalOutNegPtrAdjust OBJECT-TYPE 
  SYNTAX        Counter32 
  MAX-ACCESS    read-only 
  STATUS        current 
  DESCRIPTION 
      "Number of negative pointer adjustments seen on the 
       SONET path and encoded onto sent CEP packets." 
  ::= { pwVcCepPerfTotalEntry 6 } 

pwVcCepPerfTotalOutPosPtrAdjust OBJECT-TYPE 
  SYNTAX        Counter32 
  MAX-ACCESS    read-only 
  STATUS        current 
  DESCRIPTION 
      "Number of positive pointer adjustments seen on the 
       SONET path and encoded onto sent CEP packets." 
  ::= { pwVcCepPerfTotalEntry 7 } 

pwVcCepPerfTotalOutPtrAdjustSecs OBJECT-TYPE 
  SYNTAX        Counter32 
  MAX-ACCESS    read-only 
  STATUS        current 
  DESCRIPTION 
      "Number of seconds in which a pos or neg pointer 
       adjustment was seen on the SONET path." 
  ::= { pwVcCepPerfTotalEntry 8 } 

pwVcCepPerfTotalAbsPtrAdjust OBJECT-TYPE 
  SYNTAX        Integer32 
  MAX-ACCESS    read-only 
  STATUS        current 
  DESCRIPTION 
      "Absolute Pointer adjustments is relative adjustment 
       drifts between inbound and outbound streams. It is 
       calculated as absolute value of : 
          ( InPosPtrAdjust  -   InNegPtrAdjust) -  
          (OutPosPtrAdjust  -  OutNegPtrAdjust)     " 
  ::= { pwVcCepPerfTotalEntry 9 } 

pwVcCepPerfTotalMissingPkts OBJECT-TYPE 
  SYNTAX        Counter32 
  MAX-ACCESS    read-only 
  STATUS        current 
  DESCRIPTION 
      "Number of missing packets (as detected via CEP header 
       sequence number gaps)." 
  ::= { pwVcCepPerfTotalEntry 10 } 

pwVcCepPerfTotalPktsOoseq OBJECT-TYPE 
  SYNTAX        Counter32 
 

  MAX-ACCESS    read-only 
  STATUS        current 
  DESCRIPTION 
      "Number of packets detected out of sequence (via CEP  
       header sequence numbers), but successfully re-ordered. 
       Note: some implementations may not support this feature 
       (see pwVcCepCfgPktReorder)." 
  ::= { pwVcCepPerfTotalEntry 11 } 

pwVcCepPerfTotalPktsOoRngDropped OBJECT-TYPE 
  SYNTAX        Counter32 
  MAX-ACCESS    read-only 
  STATUS        current 
  DESCRIPTION 
      "Number of packets detected out of range (via CEP  
       header sequence numbers), and could not be re- 
       ordered, or could not fit in the jitter buffer." 
  ::= { pwVcCepPerfTotalEntry 12 } 

pwVcCepPerfTotalJtrBfrUnderruns OBJECT-TYPE 
  SYNTAX        Counter32 
  MAX-ACCESS    read-only 
  STATUS        current 
  DESCRIPTION 
      "Number of times a packet needed to be played 
       out and the jitter buffer was empty." 
  ::= { pwVcCepPerfTotalEntry 13 } 

pwVcCepPerfTotalPktsBadLength OBJECT-TYPE 
  SYNTAX        Counter32 
  MAX-ACCESS    read-only 
  STATUS        current 
  DESCRIPTION 
      "Number of packets received larger or smaller than 
       pwVcCepCfgNormalPktLength." 
  ::= { pwVcCepPerfTotalEntry 14 } 

pwVcCepPerfTotalSummaryErrors OBJECT-TYPE 
  SYNTAX        Counter32 
  MAX-ACCESS    read-only 
  STATUS        current 
  DESCRIPTION 
      "A summary of all the packet error types above (from 
       missing packets to bad length packets)." 
  ::= { pwVcCepPerfTotalEntry 15 } 

pwVcCepPerfTotalESs OBJECT-TYPE 
  SYNTAX       Counter32 
  MAX-ACCESS   read-only 
  STATUS       current 
  DESCRIPTION 
      "The counter associated with the number of Errored 
       Seconds encountered. See draft-ietf-pwe3-sonet for 
       definition of ES." 
 

  ::= { pwVcCepPerfTotalEntry 16 } 

pwVcCepPerfTotalSESs OBJECT-TYPE 
  SYNTAX        Counter32 
  MAX-ACCESS    read-only 
  STATUS        current 
  DESCRIPTION 
      "The counter associated with the number of Severely 
       Errored Seconds. See pwVcCepCfgMissingPktsToSes. 
       Also see draft-ietf-pwe3-sonet for definition." 
  ::= { pwVcCepPerfTotalEntry 17 } 

pwVcCepPerfTotalUASs OBJECT-TYPE 
  SYNTAX        Counter32 
  MAX-ACCESS    read-only 
  STATUS        current 
  DESCRIPTION 
      "The counter associated with the number of 
       UnAvailable Seconds. See pwVcCepCfgSesToUAS. 
         
       NOTE: When first entering the UAS state, the number 
       of SesToUas is added to this object, then as each 
       additional UAS occurs, this object increments by one. 

       NOTE: Similar to RFC 2558, If the agent chooses to update 
       the various performance statistics in real time then it must 
       be prepared to retroactively reduce the ES, SES, counts (by 
       the value of pwVcCepCfgSesToUas) and increase the UAS 
       count (by that same value) when it determines that UAS  
       state has been entered." 
  ::= { pwVcCepPerfTotalEntry 18 } 

pwVcCepPerfTotalFC OBJECT-TYPE 
  SYNTAX        Counter32 
  MAX-ACCESS    read-only 
  STATUS        current 
  DESCRIPTION 
      "CEP Failure Counts (FC-CEP). The number of CEP failure 
       events. A failure event begins when the LOPS failure 
       is declared, and ends when the failure is cleared." 
  ::= { pwVcCepPerfTotalEntry 19 } 
    
pwVcCepPerfTotalDiscontinuityTime OBJECT-TYPE 
  SYNTAX      TimeStamp 
  MAX-ACCESS  read-only 
  STATUS      current 

  DESCRIPTION 
      "The value of sysUpTime on the most recent occasion at 
       which any one or more of this segment's Counter32 or 
       Counter64 suffered a discontinuity. If no such 
       discontinuities have occurred since the last re- 
       initialization of the local management subsystem, then 
       this object contains a zero value." 
 

  ::= { pwVcCepPerfTotalEntry 20 } 

-- End of PW CEP Total Performance table 


-- Conformance Configuration table 

pwVcCepConformanceCfgTable OBJECT-TYPE 
  SYNTAX        SEQUENCE OF PwVcCepConformanceCfgEntry 
  MAX-ACCESS    not-accessible 
  STATUS        current 
  DESCRIPTION 
      "This table provides the means for the agent to 
       declare whether certain CEP PW statistics objects 
       are supported (conformed to) or not. If not 
       supported, then the object MUST be return 0." 
  ::= { pwVcCepObjects 9 } 

pwVcCepConformanceCfgEntry OBJECT-TYPE 
  SYNTAX        PwVcCepConformanceCfgEntry 
  MAX-ACCESS    not-accessible 
  STATUS        current 
  DESCRIPTION 
      "The agent MUST create a single entry in this table."  

  INDEX  { pwVcCepConformanceCfgIndex } 

  ::= { pwVcCepConformanceCfgTable 1 } 

PwVcCepConformanceCfgEntry ::= SEQUENCE { 
     pwVcCepConformanceCfgIndex            INTEGER, 

     pwVcCepPerfDbaInPacketsHCTruth        TruthValue, 
     pwVcCepPerfDbaInPacketsHCDesc         SnmpAdminString, 

     pwVcCepPerfDbaOutPacketsHCTruth       TruthValue, 
     pwVcCepPerfDbaOutPacketsHCDesc        SnmpAdminString, 

     pwVcCepPerfPktsOoseqTruth             TruthValue, 
     pwVcCepPerfPktsOoseqDesc              SnmpAdminString, 

     pwVcCepPerfPktsOoRngDroppedTruth      TruthValue, 
     pwVcCepPerfPktsOoRngDroppedDesc       SnmpAdminString, 

     pwVcCepPerfSummaryErrorsTruth         TruthValue, 
     pwVcCepPerfSummaryErrorsDesc          SnmpAdminString 

  } 

pwVcCepConformanceCfgIndex OBJECT-TYPE 
  SYNTAX        INTEGER  (0..128) 
  MAX-ACCESS    not-accessible 
  STATUS        current 
  DESCRIPTION 
 

      "Any arbitrary number" 
  ::= { pwVcCepConformanceCfgEntry 1 } 

pwVcCepPerfDbaInPacketsHCTruth OBJECT-TYPE 
  SYNTAX        TruthValue 
  MAX-ACCESS    read-only 
  STATUS        current 
  DESCRIPTION 
      "Tells whether the pwVcCepPerf...DbaInPacketsHC 
       in the pwVcCepPerf...Table is supported." 
  ::= { pwVcCepConformanceCfgEntry 2 } 

pwVcCepPerfDbaInPacketsHCDesc  OBJECT-TYPE 
  SYNTAX        SnmpAdminString 
  MAX-ACCESS    read-only 
  STATUS        current 
  DESCRIPTION 
      "Explanation for pwVcCepPerf...DbaInPacketsHC 
       support in the pwVcCepPerf...Table." 
  ::= { pwVcCepConformanceCfgEntry 3 } 

pwVcCepPerfDbaOutPacketsHCTruth OBJECT-TYPE 
  SYNTAX        TruthValue 
  MAX-ACCESS    read-only 
  STATUS        current 
  DESCRIPTION 
      "Tells whether the pwVcCepPerf...DbaOutPacketsHC 
       in the pwVcCepPerf...Table is supported." 
  ::= { pwVcCepConformanceCfgEntry 4 } 

pwVcCepPerfDbaOutPacketsHCDesc  OBJECT-TYPE 
  SYNTAX        SnmpAdminString 
  MAX-ACCESS    read-only 
  STATUS        current 
  DESCRIPTION 
      "Explanation for pwVcCepPerf...DbaOutPacketsHC 
       support in the pwVcCepPerf...Table." 
  ::= { pwVcCepConformanceCfgEntry 5 } 

pwVcCepPerfPktsOoseqTruth OBJECT-TYPE 
  SYNTAX        TruthValue 
  MAX-ACCESS    read-only 
  STATUS        current 
  DESCRIPTION 
      "Tells whether the pwVcCepPerf...PktsOoseq 
       in the pwVcCepPerf...Table is supported." 
  ::= { pwVcCepConformanceCfgEntry 6 } 

pwVcCepPerfPktsOoseqDesc  OBJECT-TYPE 
  SYNTAX        SnmpAdminString 
  MAX-ACCESS    read-only 
  STATUS        current 
  DESCRIPTION 
      "Explanation for pwVcCepPerf...PktsOoseq 
 

       support in the pwVcCepPerf...Table." 
  ::= { pwVcCepConformanceCfgEntry 7 } 

pwVcCepPerfPktsOoRngDroppedTruth OBJECT-TYPE 
  SYNTAX        TruthValue 
  MAX-ACCESS    read-only 
  STATUS        current 
  DESCRIPTION 
      "Tells whether the pwVcCepPerf...PktsOoRngDropped 
       in the pwVcCepPerf...Table is supported." 
  ::= { pwVcCepConformanceCfgEntry 8 } 

pwVcCepPerfPktsOoRngDroppedDesc  OBJECT-TYPE 
  SYNTAX        SnmpAdminString 
  MAX-ACCESS    read-only 
  STATUS        current 
  DESCRIPTION 
      "Explanation for pwVcCepPerf...PktsOoRngDropped 
       support in the pwVcCepPerf...Table." 
  ::= { pwVcCepConformanceCfgEntry 9 } 


pwVcCepPerfSummaryErrorsTruth  OBJECT-TYPE 
  SYNTAX        TruthValue 
  MAX-ACCESS    read-only 
  STATUS        current 
  DESCRIPTION 
      "Tells whether the pwVcCepPerf...SummaryError 
       in the pwVcCepPerf...Table is supported." 
  ::= { pwVcCepConformanceCfgEntry 10 } 

pwVcCepPerfSummaryErrorsDesc  OBJECT-TYPE 
  SYNTAX        SnmpAdminString 
  MAX-ACCESS    read-only 
  STATUS        current 
  DESCRIPTION 
      "Explanation for pwVcCepPerf...SummaryError  
       support in the pwVcCepPerf...Table." 
  ::= { pwVcCepConformanceCfgEntry 11 } 

-- End of CEP PW Conformance Configuration table 


-- Conformance Information 

  -- Note: Conformance at the object access and values level is  
  -- still FFS, therefore current conformance is defined at the 
  -- object existence level only. 

pwVcCepGroups      OBJECT IDENTIFIER ::= { pwVcCepConformance 1 } 
pwVcCepCompliances OBJECT IDENTIFIER ::= { pwVcCepConformance 2 } 


pwCepModuleCompliance MODULE-COMPLIANCE 
 

   STATUS  current 
   DESCRIPTION 
           "The compliance statement for agent that support PW  
            over CEP PSN operation." 

   MODULE  -- this module 
       MANDATORY-GROUPS { pwVcCepGroup, 
                          pwVcCepCfgGroup, 
                          pwVcCepPerfCurrentGroup, 
                          pwVcCepPerfIntervalGroup, 
                          pwVcCepPerfTotalGroup, 
                          pwVcCepConformanceCfgGroup 
                        } 
   ::= { pwVcCepCompliances 1 } 

-- Units of conformance. 

pwVcCepGroup OBJECT-GROUP  
  OBJECTS { 
           pwVcCepType, 
           pwVcCepSonetIfIndex, 
           pwVcCepSonetTimeSlot, 
           pwVcCepSonetConfigError, 
           pwVcCepCfgIndex, 
           pwVcCepTimeElapsed, 
           pwVcCepValidIntervals, 
           pwVcCepCurrentIndications, 
           pwVcCepLatchedIndications, 
           pwVcCepLastEsTimeStamp, 
           pwVcCepPeerCepOption 
           } 
  STATUS  current 
  DESCRIPTION 
         "Collection of objects for basic CEP PW config and 
          status." 
  ::= { pwVcCepGroups 1 } 


pwVcCepCfgGroup OBJECT-GROUP  
  OBJECTS { 
           pwVcCepCfgIndexNext, 

           pwVcCepConfigError, 

           pwVcCepSonetPayloadLength, 
           pwVcCepCfgMinPktLength, 
           pwVcCepCfgPktReorder, 
           pwVcCepCfgEnableDBA, 

           pwVcCepCfgRtpHdrSuppress, 
            
           pwVcCepCfgJtrBfrDepth, 

           pwVcCepCfgConsecPktsInsync, 
 

           pwVcCepCfgConsecMissingOutSync, 

           pwVcCepCfgPktErrorPlayOutValue, 

           pwVcCepCfgMissingPktsToSes, 
           pwVcCepCfgSesToUas, 
           pwVcCepCfgSecsToExitUas, 

           pwVcCepCfgRowStatus, 
           pwVcCepCfgStorageType 
  }           
  STATUS  current 
  DESCRIPTION 
         "Collection of detailed objects needed to 
          configure CEP PWs." 
  ::= { pwVcCepGroups 2 } 


pwVcCepPerfCurrentGroup OBJECT-GROUP  
  OBJECTS { 
           pwVcCepPerfCurrentDbaInPacketsHC, 
           pwVcCepPerfCurrentDbaOutPacketsHC, 

           pwVcCepPerfCurrentInNegPtrAdjust, 
           pwVcCepPerfCurrentInPosPtrAdjust, 
           pwVcCepPerfCurrentInPtrAdjustSecs, 
           pwVcCepPerfCurrentOutNegPtrAdjust, 
           pwVcCepPerfCurrentOutPosPtrAdjust, 
           pwVcCepPerfCurrentOutPtrAdjustSecs, 
           pwVcCepPerfCurrentAbsPtrAdjust, 

           pwVcCepPerfCurrentMissingPkts, 
           pwVcCepPerfCurrentPktsOoseq, 
           pwVcCepPerfCurrentPktsOoRngDropped, 
           pwVcCepPerfCurrentJtrBfrUnderruns, 
           pwVcCepPerfCurrentPktsBadLength, 
           pwVcCepPerfCurrentSummaryErrors, 

           pwVcCepPerfCurrentESs, 
           pwVcCepPerfCurrentSESs, 
           pwVcCepPerfCurrentUASs, 
           pwVcCepPerfCurrentFC 
           }          
  STATUS  current 
  DESCRIPTION 
         "Collection of statistics objects for CEP PWs." 
  ::= { pwVcCepGroups 3 } 


pwVcCepPerfIntervalGroup OBJECT-GROUP  
  OBJECTS { 
           pwVcCepPerfIntervalValidData, 
           pwVcCepPerfIntervalReset, 
           pwVcCepPerfIntervalTimeElapsed, 
 


           pwVcCepPerfIntervalDbaInPacketsHC, 
           pwVcCepPerfIntervalDbaOutPacketsHC, 

           pwVcCepPerfIntervalInNegPtrAdjust, 
           pwVcCepPerfIntervalInPosPtrAdjust, 
           pwVcCepPerfIntervalInPtrAdjustSecs, 
           pwVcCepPerfIntervalOutNegPtrAdjust, 
           pwVcCepPerfIntervalOutPosPtrAdjust, 
           pwVcCepPerfIntervalOutPtrAdjustSecs, 
           pwVcCepPerfIntervalAbsPtrAdjust, 

           pwVcCepPerfIntervalMissingPkts, 
           pwVcCepPerfIntervalPktsOoseq, 
           pwVcCepPerfIntervalPktsOoRngDropped, 
           pwVcCepPerfIntervalJtrBfrUnderruns, 
           pwVcCepPerfIntervalPktsBadLength, 
           pwVcCepPerfIntervalSummaryErrors, 

           pwVcCepPerfIntervalESs, 
           pwVcCepPerfIntervalSESs, 
           pwVcCepPerfIntervalUASs, 
           pwVcCepPerfIntervalFC 
                        
  }              
  STATUS  current 
  DESCRIPTION 
         "Collection of statistics objects for CEP PWs." 
  ::= { pwVcCepGroups 4 } 


pwVcCepPerfTotalGroup OBJECT-GROUP  
  OBJECTS { 
           pwVcCepPerfTotalDbaInPacketsHC, 
           pwVcCepPerfTotalDbaOutPacketsHC, 

           pwVcCepPerfTotalInNegPtrAdjust, 
           pwVcCepPerfTotalInPosPtrAdjust, 
           pwVcCepPerfTotalInPtrAdjustSecs, 
           pwVcCepPerfTotalOutNegPtrAdjust, 
           pwVcCepPerfTotalOutPosPtrAdjust, 
           pwVcCepPerfTotalOutPtrAdjustSecs, 
           pwVcCepPerfTotalAbsPtrAdjust, 

           pwVcCepPerfTotalMissingPkts, 
           pwVcCepPerfTotalPktsOoseq, 
           pwVcCepPerfTotalPktsOoRngDropped, 
           pwVcCepPerfTotalJtrBfrUnderruns, 
           pwVcCepPerfTotalPktsBadLength, 
           pwVcCepPerfTotalSummaryErrors, 

           pwVcCepPerfTotalESs, 
           pwVcCepPerfTotalSESs, 
           pwVcCepPerfTotalUASs, 
 

           pwVcCepPerfTotalFC, 
           pwVcCepPerfTotalDiscontinuityTime          
           }          
  STATUS  current 
  DESCRIPTION 
         "Collection of statistics objects for CEP PWs." 
  ::= { pwVcCepGroups 5 } 


pwVcCepFracGroup OBJECT-GROUP  
  OBJECTS { 
                  pwVcCepFracMode, 
                  pwVcCepFracConfigError, 
                  pwVcCepFracAsync, 
                  pwVcCepFracVtgMap, 
                  pwVcCepFracEbm, 
                  pwVcCepFracPeerEbm, 
                  pwVcCepFracSdhVc4Mode, 
                  pwVcCepFracSdhVc4Tu3Map1, 
                  pwVcCepFracSdhVc4Tu3Map2, 
                  pwVcCepFracSdhVc4Tu3Map3, 
                  pwVcCepFracSdhVc4Tug2Map1, 
                  pwVcCepFracSdhVc4Tug2Map2, 
                  pwVcCepFracSdhVc4Tug2Map3, 
                  pwVcCepFracSdhVc4Ebm1, 
                  pwVcCepFracSdhVc4Ebm2, 
                  pwVcCepFracSdhVc4Ebm3, 
                  pwVcCepFracSdhVc4PeerEbm1, 
                  pwVcCepFracSdhVc4PeerEbm2, 
                  pwVcCepFracSdhVc4PeerEbm3, 
                  pwVcCepFracRowStatus, 
                  pwVcCepFracStorageType 
  }              
  STATUS  current 
  DESCRIPTION 
         "Collection of fractional SPE groups. These objects are  
          optional and should be supported only if fractional SPE 
          is supported within the network element. " 
  ::= { pwVcCepGroups 6 } 

pwVcCepConformanceCfgGroup OBJECT-GROUP  
  OBJECTS { 
           pwVcCepPerfDbaInPacketsHCTruth, 
           pwVcCepPerfDbaInPacketsHCDesc, 

           pwVcCepPerfDbaOutPacketsHCTruth, 
           pwVcCepPerfDbaOutPacketsHCDesc, 

           pwVcCepPerfPktsOoseqTruth, 
           pwVcCepPerfPktsOoseqDesc, 

           pwVcCepPerfPktsOoRngDroppedTruth, 
           pwVcCepPerfPktsOoRngDroppedDesc, 

 

           pwVcCepPerfSummaryErrorsTruth, 
           pwVcCepPerfSummaryErrorsDesc 
         }              
  STATUS  current 
  DESCRIPTION 
         "Collection of objects declaring conformance to 
          other objects." 
  ::= { pwVcCepGroups 7 } 


END 

-- 
-- "Copyright (C) The Internet Society (2001). All Rights Reserved. This 
-- document and translations of it may be copied and furnished to 
-- others, and derivative works that comment on or otherwise explain it 
-- or assist in its implementation may be prepared, copied, published 
-- and distributed, in whole or in part, without restriction of any 
-- kind, provided that the above copyright notice and this paragraph are 
-- included on all such copies and derivative works. However, this 
-- document itself may not be modified in any way, such as by removing 
-- the copyright notice or references to the Internet Society or other 
-- Internet organizations, except as needed for the purpose of 
-- developing Internet standards in which case the procedures for 
-- copyrights defined in the Internet Standards process must be 
-- followed, or as required to translate it into languages other than 
-- English.  
--     
-- The limited permissions granted above are perpetual and will not be 
-- revoked by the Internet Society or its successors or assigns.  
--     
-- This document and the information contained herein is provided on an 
-- "AS IS" basis and THE INTERNET SOCIETY AND THE INTERNET ENGINEERING 
-- TASK FORCE DISCLAIMS ALL WARRANTIES, EXPRESS OR IMPLIED, INCLUDING 
-- BUT NOT LIMITED TO ANY WARRANTY THAT THE USE OF THE INFORMATION 
-- HEREIN WILL NOT INFRINGE ANY RIGHTS OR ANY IMPLIED WARRANTIES OF 
-- MERCHANTABILITY OR FITNESS FOR A PARTICULAR PURPOSE.  
--
