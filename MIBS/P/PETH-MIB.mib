-- extracted from draft-ietf-hubmib-power-ethernet-mib-00.txt
-- at Wed Jun 27 06:04:49 2001

   PETH-MIB DEFINITIONS ::= BEGIN

      IMPORTS
           MODULE-IDENTITY, OBJECT-TYPE, Integer32 , Gauge32,NOTIFICATION-TYPE
                   FROM SNMPv2-SMI
           dot3
                   FROM EtherLike-MIB
           TruthValue
                   FROM SNMPv2-TC
           MODULE-COMPLIANCE, OBJECT-GROUP ,NOTIFICATION-GROUP
                   FROM SNMPv2-CONF;

      powerEthernetMIB MODULE-IDENTITY
           LAST-UPDATED "200106200000Z"  -- June 20, 2001
           ORGANIZATION "IETF Ethernet Interfaces and Hub MIB
                         Working Group"
           CONTACT-INFO
           "

                       Chair: Dan Romascanu
                                  Avaya Inc.
                                  Tel:  +972-3-645-8414
                                  Email: dromasca@avaya.com


                     Editor: Avi Berger
                                 PowerDsine Inc.
                                    Tel:    972-9-7755100 Ext 307
                                    Fax:    972-9-7755120
                                    E-mail: avib@PowerDsine.com
           "

          DESCRIPTION
                   "The MIB module for for managing Powered Devices (PD) or
                   Power Source Equipment (PSE) working according to the IEEE
                   802.af Powere Ethernet (DTE Power via MDI) standard."
           ::= { dot3 20 }

   pethObjects       OBJECT IDENTIFIER ::= { powerEthernetMIB 1 }
   pethNotifications OBJECT IDENTIFIER ::= { powerEthernetMIB 2 }
   pethConformance   OBJECT IDENTIFIER ::= { powerEthernetMIB 3 }

   -- pethAgentControl MIB group defines the control objects for the power
   -- Ethernet Agent

     pethPsePortTable OBJECT-TYPE
          SYNTAX      SEQUENCE OF PethPsePortEntry
          MAX-ACCESS  not-accessible
          STATUS      current
          DESCRIPTION
              "A table of objects that display and control the power
               characteristics power Ethernet ports on a Power Source
               Entity (PSE) device. This group will be implemented in
               managed power Ethernet switches and mid-span devices."
          ::= { pethObjects 1 }

      pethPsePortEntry OBJECT-TYPE
          SYNTAX      PethPsePortEntry
          MAX-ACCESS  not-accessible
          STATUS      current
          DESCRIPTION
                  "A set of objects that display and control the power
               characteristics of a power Ethernet PSE port."
          INDEX    { pethPsePortGroupIndex , pethPsePortIndex  }
          ::= { pethPsePortTable 1 }


      PethPsePortEntry ::= SEQUENCE {
          pethPsePortGroupIndex
             INTEGER,
          pethPsePortIndex
             INTEGER,
          pethPsePortPowerEnable
              INTEGER,
          pethPsePortPowerIdPairsControl
              TruthValue,
          pethPsePortPowerIdPairs
              INTEGER,
          pethPsePortPowerDetectionStatus
              INTEGER,
          pethPsePortDetectionOperStatus
              INTEGER,
          pethPsePortPowerPriority
              INTEGER,
          pethPsePortDenyError
              INTEGER,
          pethPsePortStatus
              INTEGER,
          pethPsePortStatusClear
              INTEGER,
          pethPsePortType
              INTEGER,
          pethPsePortPowerClassifications
                INTEGER
      }

        pethPsePortGroupIndex OBJECT-TYPE
          SYNTAX      INTEGER (1..2147483647)
          MAX-ACCESS  not-accessible
          STATUS      current
          DESCRIPTION
              "This variable uniquely identifies the group
               containing the port to which power Ethernet PSE is connected.
               Group means a box in the stack, or a module in a rack.
               For non-modular devices the value 1 is recommended."
          ::= { pethPsePortEntry 1 }

        pethPsePortIndex OBJECT-TYPE
          SYNTAX      INTEGER(1..2147483647)
          MAX-ACCESS  not-accessible
          STATUS      current
          DESCRIPTION
              "This variable uniquely identifies the power Ethernet PSE
               port within group pethPseGroupIndex to which the
               power Ethernet PSE entry is connected."
          ::= { pethPsePortEntry 2 }


        pethPsePortPowerEnable OBJECT-TYPE
       SYNTAX INTEGER   {
                  auto(1),
                  off(2)
        }
       MAX-ACCESS read-write
       STATUS current
       DESCRIPTION
           "Enables power supply on this port.
            Setting this object at a value auto(1) enables power
            and detection mechanism for this port.
            Setting this object at a value off(2) disables power
            and detection mechanism for this port."
       ::= { pethPsePortEntry 3 }

        pethPsePortPowerIdPairsControl OBJECT-TYPE
       SYNTAX TruthValue
       MAX-ACCESS read-only
       STATUS current
       DESCRIPTION
           "Describes the capability of controlling the power
            pairs functionality to switch pins for sourcing power."
       ::= { pethPsePortEntry 4 }

        pethPsePortPowerIdPairs OBJECT-TYPE
       SYNTAX INTEGER   {
                  signal(1),
                  spare(2),
                  both(3)
        }
       MAX-ACCESS read-write
       STATUS current
       DESCRIPTION
           "Describes or controls the pairs in use. If the value of
            pethPsePortPowerIdpairsControl is true, thisobject is
            writable.
            A value of signal(1) menas that the signal pairs
            only are in use.
            A value of spare(2) means that the spare pairs
            only are in use.
            A value of both(3) means that both the signal
            and the spare pairs are in use."
       ::= { pethPsePortEntry 5 }

        pethPsePortPowerDetectionStatus OBJECT-TYPE
       SYNTAX INTEGER   {
                  auto(1),
                  off(2),
                  test(3)
        }
       MAX-ACCESS read-write
       STATUS current
       DESCRIPTION
           "Controls the power detection mechanism of the port.
            Setting the value auto(1) enables the power detection
            mechanism of the port.
            Setting the value off(2) disables the power detection
            mechanism of the port.
            Setting the value test(3) puts the port in a
            test mode forcing continuous discovery without applying
            power regardless of whether PD detected."
       ::= { pethPsePortEntry 6 }

        pethPsePortDetectionOperStatus OBJECT-TYPE
       SYNTAX INTEGER   {
                  deliveringPower(1),
                  off(2),
                  searching(3),
                  fault(4)
        }
       MAX-ACCESS read-only
       STATUS current
       DESCRIPTION
           "Describes the operational status of the port detection.
            A value of deliveringPower(1) indicates that the port
            executed the detection algorithm, found a PD connection
            and is currently delivering power.
            A value of off(2) indicates that the port did not find
            a PD connection and is not in serching mode.
            A value of searching(3) indicates that the detection
            algorithm is in work, and did not detect a valid PD. No
            power is currently provided.
            A value of fault(4) indicates that a fault was detected
            on the port . "
       ::= { pethPsePortEntry 7 }
        pethPsePortPowerPriority OBJECT-TYPE
       SYNTAX INTEGER   {
                  critical(1),
                  high(2),
                  low(3)
        }
       MAX-ACCESS read-write
       STATUS current
       DESCRIPTION
           "This object controls the priority of the port from the point
            of view of a power management algorithm. The priority that
            is set by this variable could be used by a control mechanism
            that prevents over current situations by disconnecting first
            ports with lower power priority. Ports that connect devices
            critical to the operation of the network - like the E911
            telephones ports - should be set to higher priority."
       ::= { pethPsePortEntry 8 }

        pethPsePortDenyError OBJECT-TYPE
       SYNTAX INTEGER   {
                  other(1),
                  lowPriority(2)
        }
       MAX-ACCESS read-only
       STATUS current
       DESCRIPTION
           "This object describes an error resulted from an action of the
             power management mechanism. The value lowPriority(2) indicates
             that the port was disabled by the power management system, in
             order to keep active higher priority ports."
       ::= { pethPsePortEntry 9 }

        pethPsePortStatus OBJECT-TYPE
       SYNTAX INTEGER   {
                  ok(1),
                  underCurrent(2),
                  overCurrent(3),
                  both(4)
        }
       MAX-ACCESS read-only
       STATUS current
       DESCRIPTION
           "Describes a current port status related to the power generation
            The value underCurrent(2) indicates that the port current
            is below the minimal value.
            The value overCurrent(3) indicates that the port current
            exceeds the maximal value.
            The value both(4) indicates that both underCurrent and overCurrent
            status happend from the lase Clear."
       ::= { pethPsePortEntry 10 }

        pethPsePortStatusClear OBJECT-TYPE
       SYNTAX INTEGER   {
                  clear(1),
                  off(2)
   }
       MAX-ACCESS read-write
       STATUS current
       DESCRIPTION
           "Setting the value of this object to clear(1) clears the value
            of the pethPsePortStatus to none(1)."
       ::= { pethPsePortEntry 11 }

        pethPsePortType OBJECT-TYPE
       SYNTAX INTEGER   {
                  other(1),
                  telephone(2),
                  webcam(3),
                  wireless(4)
        }
       MAX-ACCESS read-write
       STATUS current
       DESCRIPTION
           "A manager will set the value of this variable to a value
            that indicates the type of the device that is connected
            to theport. This value can be the result of the mapping
            the address of the station connected to the port and of
            the value of the pethPdPortType of the respective PD port."
       ::= { pethPsePortEntry 12 }

       pethPsePortPowerClassifications OBJECT-TYPE
        SYNTAX INTEGER   {
                  class0(1),
                  class1(2),
                  class2(3),
                  class3(4),
                  class4(5),
                  class5(6)
        }
       MAX-ACCESS read-only
       STATUS current
       DESCRIPTION
           "Classification is a way to tag different terminals on the
           power over LAN network according to their power consumption.
           Devices such as IP telephones, WLAN access points and others,
           will be classified according to their power requirements.
             Class     Usage          Maximum Power
                   0        Default        0.5 - 15.0 W
                   1        Optional  0.5 - 4.0 W
                   2        Optional  4.0 - 7.0 W
                   3        Optional  7.0 - 15.0 W
                   4        Optional  Future Use
                   5        Optional  Future Use
              "
       ::= { pethPsePortEntry 13 }

   -- PD Port table

   pethPdPortTable OBJECT-TYPE
          SYNTAX      SEQUENCE OF PethPdPortEntry
          MAX-ACCESS  not-accessible
          STATUS      current
          DESCRIPTION
              "A table of objects that display and control the power
               characteristics power Ethernet ports on a Powered
               Device(PD) device. This group will be implemented in
               managed powered and mid-span devices."
          ::= { pethObjects 2 }

      pethPdPortEntry OBJECT-TYPE
          SYNTAX      PethPdPortEntry
          MAX-ACCESS  not-accessible
          STATUS      current
          DESCRIPTION
                  "A set of objects that display and control the power
               characteristics of a Powered Device port."
          INDEX    { pethPdPortIndex }
          ::= { pethPdPortTable 1 }

      PethPdPortEntry ::= SEQUENCE {
          pethPdPortIndex
              INTEGER,
          pethPdPortPowerPairs
              INTEGER,
          pethPdPortDetectionOperStatus
              INTEGER,
          pethPdPortType
              INTEGER
      }

        pethPdPortIndex OBJECT-TYPE
          SYNTAX      INTEGER (0..65535)
          MAX-ACCESS  not-accessible
          STATUS      current
          DESCRIPTION
                  "An index value that uniquely identifies an
               interface to a PD device.  The
               interface identified by a particular value of
               this index is the same interface as identified
               by the same value of ifIndex. The mapping
               between the ifIndex values and the numbering of
               the port on the device is an implementation
               issue."
          ::= { pethPdPortEntry 1 }

        pethPdPortPowerPairs OBJECT-TYPE
       SYNTAX INTEGER   {
                  signal(1),
                  spare(2),
                  both(3)
        }
       MAX-ACCESS read-only
       STATUS current
       DESCRIPTION
           "Describes the pairs in use.
            A value of signal(1) menas that the signal pairs
            only are in use.
            A value of spare(2) means that the spare pairs
            only are in use.
            A value of both(3) means that both the signal
            and the spare pairs are inuse."
       ::= { pethPdPortEntry 2 }

        pethPdPortDetectionOperStatus OBJECT-TYPE
       SYNTAX INTEGER   {
                  off(1),
                  receivingPower(2)
        }
       MAX-ACCESS read-only
       STATUS current
       DESCRIPTION
           "Describes the operational status of the port detection.
            The value off(1) means that the port does not receive
            power and the detection algorithm might still be operating.
            The value receivingPower(2) means that the port is
            receiving power. "
       ::= { pethPdPortEntry 3 }

        pethPdPortType OBJECT-TYPE
       SYNTAX INTEGER   {
                  other(1),
                  telephone(2),
                  webcam(3),
                  wireless(4)
        }
       MAX-ACCESS read-only
       STATUS current
       DESCRIPTION
           "The type of the device. A management application may read
             the value of this variable and use it for setting the
             corresponding value of pethPsePortType of the port that
             connects the device."
       ::= { pethPdPortEntry 4 }

   -- Main PSE Objects

   pethMainPseObjects       OBJECT IDENTIFIER ::= { pethObjects 3 }

   pethMainPseTable OBJECT-TYPE
          SYNTAX      SEQUENCE OF PethMainPseEntry
          MAX-ACCESS  not-accessible
          STATUS      current
          DESCRIPTION
              "A table of objects that display and control the Main power
             on a PSE  device."
          ::= { pethMainPseObjects 1 }

      pethMainPseEntry OBJECT-TYPE
          SYNTAX      PethMainPseEntry
          MAX-ACCESS  not-accessible
          STATUS      current
          DESCRIPTION
               "A set of objects that display and control the Main power
                of a PSE."
          INDEX    { pethMainPseGroupIndex }
          ::= { pethMainPseTable 1 }

      PethMainPseEntry ::= SEQUENCE {
          pethMainPseGroupIndex
              INTEGER,
          pethMainPsePower
              Integer32,
          pethMainPseOperStatus
              INTEGER,
          pethMainPseConsumptionPower
              Gauge32,
          pethMainPseBackupPresent
                INTEGER,
           pethMainPseBackupActivated
                INTEGER,

          pethMainPseUsageThreshold
              INTEGER
      }
        pethMainPseGroupIndex OBJECT-TYPE
          SYNTAX      INTEGER (0..65535)
          MAX-ACCESS  not-accessible
          STATUS      current
          DESCRIPTION
              "This variable uniquely identifies the group to which
              power Ethernet PSE is connected. Group means box in the stack,
              module in a rack.  It is recommended that the value 1 be
              used for non-modular devices "
          ::= { pethMainPseEntry 1 }

        pethMainPsePower OBJECT-TYPE
          SYNTAX      Integer32 (0..65535)
          MAX-ACCESS  read-write
          STATUS      current
          DESCRIPTION
                  "The nominal power of the PSE expressed in Watts."
          ::= { pethMainPseEntry 2 }


        pethMainPseOperStatus OBJECT-TYPE
          SYNTAX INTEGER   {
                  on(1),
                  off(2),
                  faulty(3)
             }
          MAX-ACCESS  read-only
          STATUS      current
          DESCRIPTION
                  "The operational status of the main PSE."
          ::= { pethMainPseEntry 3 }

        pethMainPseConsumptionPower OBJECT-TYPE
          SYNTAX      Gauge32
          MAX-ACCESS  read-only
          STATUS      current
          DESCRIPTION
                  "Measured usage power expressed in Watts."
          ::= { pethMainPseEntry 4 }


        pethMainPseBackupPresent  OBJECT-TYPE
          SYNTAX  INTEGER    {
                                 present(1),
                                 notPresent(2),
                                 faulty(3)
          }
          MAX-ACCESS         read-only
          STATUS             current
          DESCRIPTION
             "This value reflects the presence and status
                of a backup PSE ."
          ::= { pethMainPseEntry 5 }

        pethMainPseBackupActivated  OBJECT-TYPE
                  SYNTAX   INTEGER    {
                                 activated(1),
                                 notActivated(2)
                  }
                  MAX-ACCESS         read-only
                  STATUS             current
                  DESCRIPTION
                       "This variable reflects the activation status
                            of the backup PSE"
                  ::= { pethMainPseEntry 6 }

        pethMainPseUsageThreshold OBJECT-TYPE
          SYNTAX      INTEGER (1..99)
          MAX-ACCESS  read-write
          STATUS      current
          DESCRIPTION
                  "The usage threshold expressed in percents for
                   comparing the measured power and initiating
                   an alarm if the threshold is exceeded."
          ::= { pethMainPseEntry 7 }


   -- Traps  Control  Objects

   pethTrapsControl        OBJECT IDENTIFIER ::= { pethObjects 4 }

   pethTrapsControlTable OBJECT-TYPE
          SYNTAX      SEQUENCE OF PethTrapsControlEntry
          MAX-ACCESS  not-accessible
          STATUS      current
          DESCRIPTION
              "A table of objects that display and control the Main power
             on a PSE  device."
          ::= { pethTrapsControl 1 }

      pethTrapsControlEntry OBJECT-TYPE
          SYNTAX      PethTrapsControlEntry
          MAX-ACCESS  not-accessible
          STATUS      current
          DESCRIPTION
               "A set of objects that control the Trap events."
          INDEX    { pethTrapsControlGroupIndex }
          ::= { pethTrapsControlTable 1 }

      PethTrapsControlEntry ::= SEQUENCE {
          pethTrapsControlGroupIndex
              INTEGER,
          pethTrapsControlEnable
                INTEGER
      }
        pethTrapsControlGroupIndex OBJECT-TYPE
          SYNTAX      INTEGER (0..65535)
          MAX-ACCESS  not-accessible
          STATUS      current
          DESCRIPTION
              "This variable uniquely identifies the group. Group means
              box in the stack, or module in a rack. It is recommended
              that the value 1 is used for non-modular devices."
          ::= { pethTrapsControlEntry 1 }


         pethTrapsControlEnable  OBJECT-TYPE
             SYNTAX             INTEGER
                  {
                       enable(1),
                       disable(2)
                  }
             MAX-ACCESS         read-write
             STATUS             current
             DESCRIPTION
                  "Enable Traps from Agent"
          ::= { pethTrapsControlEntry 2 }


   --
   -- Notifications Section
   --
   --

        pethPsePortOnOffTrap NOTIFICATION-TYPE
            OBJECTS     { pethPsePortGroupIndex,pethPsePortIndex,pethPsePortDetectionOperStatus }
            STATUS      current
            DESCRIPTION " This trap indicate if Pse Port is  delivering  or not power to the PD."
             ::= { pethNotifications 1 }

        pethPsePortDenyTrap NOTIFICATION-TYPE
            OBJECTS     { pethPsePortGroupIndex,pethPsePortIndex,pethPsePortDenyError }
            STATUS      current
            DESCRIPTION
                  " This trap indicate Port Deny service."
            ::= { pethNotifications 2 }

        pethPsePortStatusTrap NOTIFICATION-TYPE
            OBJECTS     { pethPsePortGroupIndex,pethPsePortIndex,pethPsePortStatus }
            STATUS      current
            DESCRIPTION
                  " This trap indicate Port Change Status."
            ::= { pethNotifications 3 }

        pethMainPseBackUpActivatedTrap NOTIFICATION-TYPE
            OBJECTS     { pethPsePortGroupIndex,pethMainPseBackupActivated }
            STATUS      current
            DESCRIPTION
                  " This trap indicates that BackUp PSE is Activated ."
            ::= { pethNotifications 4 }

        pethMainPowerUsageTrap NOTIFICATION-TYPE
            OBJECTS     { pethPsePortGroupIndex }
            STATUS      current
            DESCRIPTION
                  " This trap indicate PSE Threshold  usage indication ."
            ::= { pethNotifications 5 }



   --
   -- Conformance Section
   --
   pethCompliances OBJECT IDENTIFIER ::= { pethConformance 1 }
   pethGroups      OBJECT IDENTIFIER ::= { pethConformance 2 }

   pethCompliance MODULE-COMPLIANCE
       STATUS  current
       DESCRIPTION
               "Describes the requirements for conformance to the
               Power Ethernet MIB."
       MODULE  -- this module
           GROUP   pethPsePortGroup
           DESCRIPTION
               "The pethPsePortGroup is mandatory for systems which
               implement PSE ports."
           GROUP   pethPdPortGroup
           DESCRIPTION
               "The pethPdPortGroup is mandatory for systems which
               implement PD Ports."
           GROUP   pethMainPseGroup
           DESCRIPTION
               "The pethMainPseGroup is mandatory for systems which
               implement main power supply within a PSE Device."
           GROUP   pethTrapsControlGroup
           DESCRIPTION
               "The pethTrapsControlGroup is mandatory for systems which
               implement PSE ports."
       ::= { pethCompliances 1 }

   pethPsePortGroup OBJECT-GROUP
       OBJECTS {
          pethPsePortPowerEnable,
          pethPsePortPowerIdPairsControl,
          pethPsePortPowerIdPairs,
          pethPsePortPowerDetectionStatus,
          pethPsePortDetectionOperStatus,
          pethPsePortPowerPriority,
          pethPsePortDenyError,
          pethPsePortStatus,
          pethPsePortStatusClear,
          pethPsePortType,
          pethPsePortPowerClassifications
       }
       STATUS  current
       DESCRIPTION
               "PSE Port Objects."
       ::= { pethGroups 1 }

   pethPdPortGroup OBJECT-GROUP
       OBJECTS {
          pethPdPortPowerPairs,
          pethPdPortDetectionOperStatus,
          pethPdPortType
       }
       STATUS  current
       DESCRIPTION
               "PD Port Objects."
       ::= { pethGroups 2 }

   pethMainPseGroup OBJECT-GROUP
       OBJECTS {
          pethMainPsePower,
          pethMainPseOperStatus,
          pethMainPseConsumptionPower,
          pethMainPseBackupPresent,
          pethMainPseBackupActivated,
          pethMainPseUsageThreshold
       }
       STATUS  current
       DESCRIPTION
               "Main PSE Objects. "
       ::= { pethGroups 3 }

   pethTrapsControlGroup OBJECT-GROUP
       OBJECTS {
          pethTrapsControlEnable
       }
       STATUS  current
       DESCRIPTION
               "Trap Control  Objects. "
       ::= { pethGroups 4 }
   END

-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
