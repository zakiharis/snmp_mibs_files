-- extracted from draft-stephan-pce-pcedp-pcc-mib-00.txt
-- at Thu Jun 22 06:06:28 2006

   PCEDP-PCC-MIB DEFINITIONS ::= BEGIN

   IMPORTS
      MODULE-IDENTITY, OBJECT-TYPE, NOTIFICATION-TYPE,
      Counter32, Unsigned32, Gauge32, Integer32, IpAddress,
      experimental FROM SNMPv2-SMI
      RowStatus,
      TEXTUAL-CONVENTION,
      TimeStamp

         FROM SNMPv2-TC
      Ipv6Address
         FROM IPV6-TC
      MODULE-COMPLIANCE,
      OBJECT-GROUP,
      NOTIFICATION-GROUP
         FROM SNMPv2-CONF;

   pcedpPccMIB MODULE-IDENTITY
      LAST-UPDATED "200606150000Z" -- June 15, 2006
      ORGANIZATION "PCE Working Group"
      CONTACT-INFO "WG-email: pce@ietf.org
      WG-URL: http://www.ietf.org/html.charters/pce-charter.html

      TODO: This section has to be completed with chairs and authors
      addresses
      "
   DESCRIPTION
      "This MIB module defines a collection of objects for managing Path
      Computation Elements (PCEs) Discovery Protocol inside a Path
      Computation Client (PCC) application."
   ::= { experimental 10000 } -- Temporary node ( for smilint)
   -- Textual Conventions used in this MIB module --

   -- empty for now

   -- Notification --

   pcedpPccNotifications OBJECT IDENTIFIER ::= { pcedpPccMIB 0 }

   -- empty for now

   pcedpPccMIBObjects OBJECT IDENTIFIER ::= { pcedpPccMIB 1 }

   pcedpPccDiscoveryGroup OBJECT IDENTIFIER ::= { pcedpPccMIBObjects 1 }

   pcedpPccPceDiscoveryAdminStatus OBJECT-TYPE
      SYNTAX INTEGER {
         enabled(1),
         disabled(2)
      }
      MAX-ACCESS read-write
      STATUS current
      DESCRIPTION
         "Setting this object to disabled(2) disables the discovery of
         PCEs.  Once disabled, The discovery must be explicitly enabled
         to restore discovery of PCEs.  Setting this object to
         enabled(1) enables the discovery of PCEs."
      ::= { pcedpPccDiscoveryGroup 1 }

   pcedpPccPceDiscoveryTable OBJECT-TYPE
      SYNTAX SEQUENCE OF PcedpPccPceDiscoveryEntry
      MAX-ACCESS not-accessible
      STATUS current
      DESCRIPTION
         "Information describing the PCEs discovered by the PCC."
      ::= { pcedpPccDiscoveryGroup 2 }

   pcedpPccPceDiscoveryEntry OBJECT-TYPE
      SYNTAX PcedpPccPceDiscoveryEntry
      MAX-ACCESS not-accessible
      STATUS current
      DESCRIPTION
         "Information describing the general information of each PCE
         discovered by the PCC."
      INDEX { pcedpPccPceIndex }
      ::= { pcedpPccPceDiscoveryTable 1 }

   PcedpPccPceDiscoveryEntry ::= SEQUENCE {
      pcedpPccPceIndex Integer32,
      pcedpPccPceIPv4Address IpAddress,
      pcedpPccPceIPv6Address Ipv6Address,
      pcedpPccPceTimeDiscovered TimeStamp,
      pcedpPccPceLastUpdated TimeStamp
   }

   pcedpPccPceIndex OBJECT-TYPE
      SYNTAX Integer32 (1..2147483647)
      MAX-ACCESS not-accessible
      STATUS current
      DESCRIPTION
         "This object identifies locally the PCE for which this entry
         contains information."
      ::= { pcedpPccPceDiscoveryEntry 1 }

   pcedpPccPceIPv4Address OBJECT-TYPE
      SYNTAX IpAddress
      MAX-ACCESS read-only
      STATUS current
      DESCRIPTION
         "The IP address to be used to reach the PCE.  A value of
         0.0.0.0 indicates the absence of this address."
      ::= { pcedpPccPceDiscoveryEntry 2 }

   pcedpPccPceIPv6Address OBJECT-TYPE
      SYNTAX Ipv6Address
      MAX-ACCESS read-only
      STATUS current
      DESCRIPTION
         "The IP address to be used to reach the PCE.  A value of ::0
         indicates the absence of this address."
      ::= { pcedpPccPceDiscoveryEntry 3 }

   pcedpPccPceTimeDiscovered OBJECT-TYPE
      SYNTAX TimeStamp
      MAX-ACCESS read-only
      STATUS current
      DESCRIPTION
         "The value of sysUpTime at the time this entry was created.
         Static entry: the value of sysUpTime at the time PCC
         restarted."
      ::= { pcedpPccPceDiscoveryEntry 4 }

   pcedpPccPceLastUpdated OBJECT-TYPE
      SYNTAX TimeStamp
      MAX-ACCESS read-only
      STATUS current
      DESCRIPTION
         "The value of sysUpTime at the time this entry was last
         updated.
         Static entry: if the entry values keep unchanged since the re-
         initialization of the PCC then this object contains a zero
         value."
      ::= { pcedpPccPceDiscoveryEntry 5 }

   -- pcedpPccPceDomains

   -- Table to be defined

   -- pcedpPccPceDestDomains

   -- table to be defined

   pcedpPccPcesCapabilityGroup OBJECT IDENTIFIER ::= {
   pcedpPccMIBObjects 2 }

   -- empty for now: TODO

   pcedpPccPcesActivityGroup OBJECT IDENTIFIER ::= { pcedpPccMIBObjects
   3 }

   -- empty for now: TODO

   --

   -- PCC agents conformance statement

   --

   pcedpPccConformance OBJECT IDENTIFIER ::= { pcedpPccMIB 2 }

   pcedpPccGroups OBJECT IDENTIFIER ::= { pcedpPccConformance 1 }

   pcedpPccCompliances OBJECT IDENTIFIER ::= { pcedpPccConformance 2 }

   -- PCC agent compliance statements

   pcedpPccGeneralPceInformation MODULE-COMPLIANCE
      STATUS current
      DESCRIPTION
      "The compliance statement for SNMP entities that monitors only
      general information as proposed in the 2nd S. of the section 6.1
      of [I-D.ietf-pce-discovery-reqs]."
      MODULE
   ::= { pcedpPccCompliances 1 }

   pcedpPccDetailledPceInformation MODULE-COMPLIANCE
      STATUS current
      DESCRIPTION
      "The compliance statement for SNMP entities that implement
      detailled monitoring as proposed in the 3rd S. of the section 6.1
      of [I-D.ietf-pce-discovery-reqs]."
      MODULE
   ::= { pcedpPccCompliances 2 }

   END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
