PDN-SPECTRUMMGMT-MIB DEFINITIONS ::= BEGIN
----------------------------------------------------------------
-- Copyright (C) 2003, Paradyne. All rights reserved.
----------------------------------------------------------------
IMPORTS
	Integer32, Unsigned32,
	OBJECT-TYPE, MODULE-IDENTITY 
	    FROM SNMPv2-SMI
	MODULE-COMPLIANCE, OBJECT-GROUP
            FROM SNMPv2-CONF
	entPhysicalIndex
            FROM ENTITY-MIB
	ifIndex, ifType
	    FROM IF-MIB
	pdn-interfaces
	    FROM PDN-HEADER-MIB;
	
pdnSpectrumMgmt	MODULE-IDENTITY
	    LAST-UPDATED "200212091500Z"
	    ORGANIZATION "Paradyne Corp MIB Working Group"
	    CONTACT-INFO "Paradyne Networks, Inc.
			  8545 126th Ave North
			  Largo, FL 33733
			  www.paradyne.com

			  General Comments to:
			    mibwg_team@eng.paradyne.com

			  Editors: R.A.Bowhall,
				   Jesus Pinto"

	    DESCRIPTION "R.A.Bowhall
	    	The Paradyne enterprise SPECTRUM MIB.
	    	This MIB is written to facilitate spectrum
		management of any xDSL interfaces. This mib
	 	replaces older versions of the spectrum 
		management including the reachDSL.mib."

	    REVISION "200301151300Z"
	    DESCRIPTION "Jesus Pinto
		1. Changed indexes on GeneralConfigTable.
		2. Removed DSL Line Table.
		3. Renamed newSpectrumMgmtAturMaxTxRate
		4. Renamed newSpectrumMgmtAturMinTxRate
		5. Renamed newSpectrumMgmtAturTxPower
		6. Renamed newSpectrumMgmtAtucMinTxRate
		7. Renamed newSpectrumMgmtAtucMaxTxRate
		8. Renamed newSpectrumMgmtAtucTxPower
		9. Added   newSpectrumMgmtXturMax2TxRate
		10.Added   newSpectrumMgmtXturMin2TxRate
		11.Added   newSpectrumMgmtXtucMax2TxRate
		12.Added   newSpectrumMgmtXtucMax2TxRate"

	    REVISION "200301091500Z"
	    DESCRIPTION "Jesus Pinto
		1. Deprecated spectrumMgmtTable and all its objects.
		2. Added newSpectrumMgmtTable.
		3. Added newSpectrumMgmtMode.
		4. Added newSpectrumMgmtEWLUnits.
		5. Added newSpectrumMgmtLoopMeasurementMethod.
		6. Added newSpectrumMgmtLineInfoTable.
		7. Added newSpectrumMgmtGeneralConfigTable."

	    REVISION "0105161530Z"
	    DESCRIPTION "R.A.Bowhall
	    	Added DEFVAL caluse,  Added the pdnSpecMgmtTraps,
	    	and pdnSpecMgmtMIBConformance info.
		Added an Informational Note at the Beginning of
		this MIB."

	    REVISION "0105080550Z"
	    DESCRIPTION "R.A.Bowhall
	    	Added the EWL Deployment Guidelines Table
	    	and Changed spectrumMgmtAllowedSpeeds to
		spectrumMgmtAllowedSpeedsMin1, spectrumMgmtAllowedSpeedsMax1,
		spectrumMgmtAllowedSpeedsMin2, spectrumMgmtAllowedSpeedsMax2"

	    ::= { pdn-interfaces 19 }

pdnSpecMgmtObjects		OBJECT IDENTIFIER ::= { pdnSpectrumMgmt 1 }
pdnNewSpecMgmtObjects		OBJECT IDENTIFIER ::= { pdnSpectrumMgmt 2 }

--
-- START OF Spectrum Management definitions
--

--
-- General options for spectrum management
--
newSpectrumMgmtGeneralConfigTable OBJECT-TYPE
     SYNTAX  SEQUENCE OF NewSpectrumMgmtGeneralConfigEntry
     MAX-ACCESS  not-accessible
     STATUS  current
     DESCRIPTION
	"General Configuration of the spectrum management.
	This table contains an entry for each technology
	managed by this device."
     ::= { pdnNewSpecMgmtObjects 1 }

newSpectrumMgmtGeneralConfigEntry OBJECT-TYPE
     SYNTAX  NewSpectrumMgmtGeneralConfigEntry
     MAX-ACCESS  not-accessible
     STATUS  current
     DESCRIPTION
	"An entry with the general spectrum mgmt configuration
	 parameters for a specific DSL technology."
    INDEX   { entPhysicalIndex, ifType }
    ::= { newSpectrumMgmtGeneralConfigTable 1 }

NewSpectrumMgmtGeneralConfigEntry ::= SEQUENCE {
     newSpectrumMgmtSelection		  INTEGER,
     newSpectrumMgmtMode		  INTEGER,
     newSpectrumMgmtLoopMeasurementMethod INTEGER,
     newSpectrumMgmtEWLUnits		  INTEGER
}

newSpectrumMgmtSelection OBJECT-TYPE
     SYNTAX  INTEGER {
		enabled(1),
		disabled(2)
	 }
     MAX-ACCESS read-write
     STATUS  	current
     DESCRIPTION
	"This object is used to Enable or Disable 
	 Spectrum Management on DSL interfaces 
	 managed by this device. Enabling this object
	 limits the DSL speeds on each port based on
	 line length in order to meet ANSI T1.417
	 Spectrum Management requirements or BT Access
	 Network Spectrum requirements.

	The values that this object can accept are
        controlled by the -Mode- object."

     ::= { newSpectrumMgmtGeneralConfigEntry 1 }

newSpectrumMgmtMode OBJECT-TYPE
    SYNTAX      INTEGER {
                    enableOnly(1),
                    disableOnly(2),
                    both(3)
                }
    MAX-ACCESS  read-only
    STATUS      current
    DESCRIPTION
       "This object restricts the MAX-ACCESS of the 'Selection'
        object.
        Following are the details of each of the values:

            enableOnly(1)  - Indicates that the 'Selection' object
                             IS always 'enabled' and cannot be set
                             to 'disabled'.
            disableOnly(2) - Indicates that the 'Selection' object
                             IS always 'disabled' and cannot be set
                             to 'enabled'.
            both(3)        - Indicates that the 'Selection' object
                             will accept both the 'enabled' and
                             'disabled' values."

    ::= { newSpectrumMgmtGeneralConfigEntry 2 }

newSpectrumMgmtLoopMeasurementMethod OBJECT-TYPE
    SYNTAX      INTEGER {
                    none(1),
                    loopLength(2),
                    ewl(3),
                    quadMode(4)
                }
    MAX-ACCESS  read-only
    STATUS      current
    DESCRIPTION
       "This object indicates the measurement method used in
        describing the Loop Length of a circuit. Following are the
        details of each of the options:

            none(1)       - Indicates that the Spectral Compliance
                            is NOT dependant on any Loop Length
                            measurements or configurations.
            loopLength(2) - The 'ConfLoopLength' object is used to
                            determine spectral compliance. The
                            'ConfEWL' &amp; 'ConfQuadMode' objects are
                            not used in this mode.
            ewl(3)        - The 'ConfEWL' object is used to
                            configure the estimated loop length,
                            which is used to determine spectral
                            compliance. In this mode the
                            'ConfLoopLength' &amp; 'ConfQuadMode'
                            objects are not used.
            quadMode(4)   - The 'ConfQuadMode' object is used to
                            determine spectral compliance. The
                            'ConfEWL' &amp; 'ConfLoopLength' objects
                            are not used in this mode.

        This object determines which of the three objects :
        'ConfEWL', 'ConfLoopLength' or 'ConfQuadMode' is used
        (if any) to enforce spectrally compliant maximum
        'Tx Rates' and the maximum allowed 'Tx Power' on a given
        circuit."

    ::= { newSpectrumMgmtGeneralConfigEntry 3 }

newSpectrumMgmtEWLUnits OBJECT-TYPE
    SYNTAX      INTEGER {
                    none(1),
                    feet(2),
                    meters(3)
                }
    MAX-ACCESS  read-only
    STATUS      current
    DESCRIPTION
       "This object indicates the units of measurement used in
        describing the Estimated Working Length of a circuit.
        Following are the details of each of the units:

            none(1)     - Indicates that the Spectral Compliance is
                          NOT dependant on the 'ConfEWL' object.
            feet(2)     - The 'ConfEWL' is measured and configured
                          in feet.
            meters(3)   - The 'ConfEWL' is measured and configured
                          in meters."

    ::= { newSpectrumMgmtGeneralConfigEntry 4 }

--
-- Spectrum Mgmt Configuration Table
--
newSpectrumMgmtConfTable OBJECT-TYPE
    SYNTAX      SEQUENCE OF NewSpectrumMgmtConfEntry
    MAX-ACCESS  not-accessible
    STATUS      current
    DESCRIPTION
       "The new Spectrum Management Configuration Table
        This table is used for configuring spectrum management
        objects on any DSL interface." 

    ::= { pdnNewSpecMgmtObjects 2 }

newSpectrumMgmtConfEntry OBJECT-TYPE
    SYNTAX      NewSpectrumMgmtConfEntry
    MAX-ACCESS  not-accessible
    STATUS      current
    DESCRIPTION
       "An entry in the xDSL Spectrum Management 
        Configuration table.

        Note: This entry can be accessed only for ifIndex 
              values that belong to a physical interface. 
              e.g. for ifType = 'shdsl' (IANAifType=169)."

    INDEX   { ifIndex }

    ::= { newSpectrumMgmtConfTable 1 }

NewSpectrumMgmtConfEntry ::= 
    SEQUENCE {
        newSpectrumMgmtConfEWL            	Unsigned32,
        newSpectrumMgmtConfLoopLength     	INTEGER,
        newSpectrumMgmtConfQuadMode       	INTEGER
    }

newSpectrumMgmtConfEWL OBJECT-TYPE
    SYNTAX      Unsigned32
    MAX-ACCESS  read-write
    STATUS      current
    DESCRIPTION
       "The Equivalent Working Length (EWL).  The value selected
        corresponds to the estimated length of the line in

            feet   - if 'EWLUnits' object is 'feet'.
            meters - if 'EWLUnits' object is 'meters'. 

        This value is usually specified by the carrier and MUST
        be in integral multiples of 

            500 feet, if 'EWLUnits' is 'feet'.
            200 meters, if 'EWLUnits' is 'meters'.

        The range of values that this object can take is determined
        by the 'MinEWL' and 'MaxEWL' objects.
        Changing this object may limit the maximum transmit power
        and the effective DSL speeds at which the ports train up.

        Note: This object will be used only if Spectrum Management
              is enabled and 'LoopMeasurementMethod' is 'ewl'.
              This object shares a mutual exclusion relationship
              with the 'ConfLoopLength' &amp; 'ConfQuadMode' objects, 
	      as only one of the two will be used for configuration
	      at any time."

    ::= { newSpectrumMgmtConfEntry 1 }

newSpectrumMgmtConfLoopLength OBJECT-TYPE
    SYNTAX      INTEGER {
                    short(1),
                    medium(2),
                    long(3)
                }
    MAX-ACCESS  read-write
    STATUS      current
    DESCRIPTION
       "This entry specifies the loop length for the line. The
        configurable values are short(1), medium(2) and long(3).
        The 'Loop Length' feature can be used only if the 
        'shdslSpectrumMgmtSelection' object is Enabled and
        the 'LoopMeasurementMethod' is 'loopLength'. Changing this
        object may limit the maximum transmit power and the
        effective DSL speeds at which ports train up.

        Note: This object shares a mutual exclusion relationship 
              with the 'ConfEWL'  objects. i.e. only one of the
	      three can be used for configuration at one time."

    ::= { newSpectrumMgmtConfEntry 2 }

newSpectrumMgmtConfQuadMode OBJECT-TYPE
    SYNTAX      INTEGER {
                    sameQuad(1),
                    segregatedQuadUpto3km(2),
                    segregatedQuadAbove3km(3)
                }
    MAX-ACCESS  read-write
    STATUS      current
    DESCRIPTION
       "This entry specifies the quad cable configuration &amp;
        length for the line. The configurable values are
        sameQuad(1), segregatedQuadUpto3km(2) and
        segregatedQuadAbove3km(3). The 'Quad Mode' feature can be
        used only if the 'reachDSLSpectrumMgmtSelection' object
        is Enabled and the 'LoopMeasurementMethod' is 'quadMode'.
        Changing this object may limit the maximum transmit power
        and the effective DSL speeds at which ports train up.

        Note: This object shares a mutual exclusion relationship 
              with the 'ConfEWL' &amp; 'ConfLoopLength' objects.
              i.e. only one of the three can be used for
              configuration at one time."

    ::= { newSpectrumMgmtConfEntry 3 }

--
-- Spectrum Management Line Info Table
--
newSpectrumMgmtLineInfoTable OBJECT-TYPE
    SYNTAX      SEQUENCE OF NewSpectrumMgmtLineInfoEntry
    MAX-ACCESS  not-accessible
    STATUS      current
    DESCRIPTION
       "The Spectrum Management Line Info Table.
        This table gives information about the spectrum 
        management ranges that are applicable for each port,
        based on the spectral requirements for the device."

    ::= { pdnNewSpecMgmtObjects 3 }

newSpectrumMgmtLineInfoEntry OBJECT-TYPE
    SYNTAX      NewSpectrumMgmtLineInfoEntry
    MAX-ACCESS  not-accessible
    STATUS      current
    DESCRIPTION
       "An entry in the newSpectrumMgmtLineInfoTable table.

        Note: This entry can be accessed only for ifIndex values
              that belong to a physical interface. 
              e.g. for ifType = 'adsl'."

    INDEX   { ifIndex }

    ::= { newSpectrumMgmtLineInfoTable 1 }

NewSpectrumMgmtLineInfoEntry ::= 
    SEQUENCE {
        newSpectrumMgmtXtucMax1TxRate  Unsigned32,
        newSpectrumMgmtXtucMin1TxRate  Unsigned32,
        newSpectrumMgmtXtucMax2TxRate  Unsigned32,
        newSpectrumMgmtXtucMin2TxRate  Unsigned32,
        newSpectrumMgmtXtucMaxTxPower  INTEGER,
        newSpectrumMgmtXturMax1TxRate  Unsigned32,
        newSpectrumMgmtXturMin1TxRate  Unsigned32,
        newSpectrumMgmtXturMax2TxRate  Unsigned32,
        newSpectrumMgmtXturMin2TxRate  Unsigned32,
        newSpectrumMgmtXturMaxTxPower  INTEGER,
        newSpectrumMgmtMinEWL          Unsigned32,
        newSpectrumMgmtMaxEWL          Unsigned32
    }

newSpectrumMgmtXtucMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	
	Some measurement methods may have more than one range for
	the TxRate. Min1TxRate and Max1TxRate will always have
	the first range of values and the Min2TxRate and Max2TxRate
	will have the second range if the method demands it."
 
    ::= { newSpectrumMgmtLineInfoEntry 1 }

newSpectrumMgmtXtucMin1TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 2 }


newSpectrumMgmtXtucMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUC in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 3 }

newSpectrumMgmtXtucMin2TxRate OBJECT-TYPE
    SYNTAX      Unsigned32
    UNITS       "bps"
    MAX-ACCESS  read-only
    STATUS      current
    DESCRIPTION
       "This rate will be the min allowed Tx Rate based on the
        spectrum management requirements for the XTUC. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 4 }


newSpectrumMgmtXtucMaxTxPower OBJECT-TYPE
    SYNTAX      INTEGER(-140..120)
    UNITS       "tenth dB"
    MAX-ACCESS  read-only
    STATUS      current
    DESCRIPTION
       "The maximum transmit power at the ATUC (in tenth dB).  
        This value will be based on the spectrum management
        selection."

    ::= { newSpectrumMgmtLineInfoEntry 5 }


newSpectrumMgmtXturMax1TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	This object is the 
	
	Some measurement methods may have more than one range for
	the TxRate. Min1TxRate and Max1TxRate will always have
	the first range of values and the Min2TxRate and Max2TxRate
	will have the second range if the method demands it."
 
    ::= { newSpectrumMgmtLineInfoEntry 6 }

newSpectrumMgmtXturMin1TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXturMax1TxRate' object.

	Some measurement methods may have more than one range for
	the TxRate. Min1TxRate and Max1TxRate will always have
	the first range of values and the Min2TxRate and Max2TxRate
	will have the second range if the method demands it."

    ::= { newSpectrumMgmtLineInfoEntry 7 }


newSpectrumMgmtXturMax2TxRate OBJECT-TYPE
    SYNTAX      Unsigned32
    UNITS       "bps"
    MAX-ACCESS  read-only
    STATUS      current
    DESCRIPTION
       "This rate will be the max allowed Tx Rate(in bps) for 
        the port based on the Spectrum Management requirements for
        XTUR in a particular spectral compliance configuration.
	
	Some measurement methods may have more than one range for
	the TxRate. Min1TxRate and Max1TxRate will always have
	the first range of values and the Min2TxRate and Max2TxRate
	will have the second range if the method demands it."
 
    ::= { newSpectrumMgmtLineInfoEntry 8 }

newSpectrumMgmtXturMin2TxRate OBJECT-TYPE
    SYNTAX      Unsigned32
    UNITS       "bps"
    MAX-ACCESS  read-only
    STATUS      current
    DESCRIPTION
       "This rate will be the min allowed Tx Rate based on the
        spectrum management requirements for the XTUR. The
        MinTxRate will be upper bounded by 
	'newSpectrumMgmtXtucMax1TxRate' object.

	Some measurement methods may have more than one range for
	the TxRate. Min1TxRate and Max1TxRate will always have
	the first range of values and the Min2TxRate and Max2TxRate
	will have the second range if the method demands it."

    ::= { newSpectrumMgmtLineInfoEntry 9 }

newSpectrumMgmtXturMaxTxPower OBJECT-TYPE
    SYNTAX      INTEGER(-140..120)
    UNITS       "tenth dB"
    MAX-ACCESS  read-only
    STATUS      current
    DESCRIPTION
       "The maximum transmit power at the ATUR (in tenth dB).  This
        value will be based on the spectrum management selection."

    ::= { newSpectrumMgmtLineInfoEntry 10 }

newSpectrumMgmtMinEWL OBJECT-TYPE
    SYNTAX      Unsigned32
    MAX-ACCESS  read-only
    STATUS      current
    DESCRIPTION
       "The minimum value (in feet, if 'EWLUnits' is 'feet, or in
        meters, if 'EWLUnits' is 'meters') that the 'ConfEWL'
        object can accept. Together with the 'MaxEWL' object,
        this object indicates the range of EWL when 'EWLUnits' is
        either 'feet' or 'meters'.

        Note : This object is valid only if the
               'LoopMeasurementMethod' object is 'ewl'."

    ::= { newSpectrumMgmtLineInfoEntry 11 }

newSpectrumMgmtMaxEWL OBJECT-TYPE
    SYNTAX      Unsigned32
    MAX-ACCESS  read-only
    STATUS      current
    DESCRIPTION
       "The maximum value (in feet, if 'EWLUnits' is 'feet, or in
        meters, if 'EWLUnits' is 'meters') that the 'ConfEWL'
        object can accept. Together with the 'MinEWL' object,
        this object indicates the range of EWL when 'EWLUnits' is
        either 'feet' or 'meters'.

        Note : This object is valid only if the
               'LoopMeasurementMethod' object is 'ewl'."

    ::= { newSpectrumMgmtLineInfoEntry 12 }

-- 
--		D E P R E C A T E D
--  
-- The following objects are supported for the first version
-- of the shdsl cards. They are now deprecated and should not
-- be used for future products.
--
spectrumMgmtCountryCode OBJECT-TYPE
     SYNTAX  INTEGER {
		usa(1),
		uk(2)
	 }
     MAX-ACCESS  read-write
     STATUS  deprecated
     DESCRIPTION
	"This object selects which Spectrum Management 
	 standard will be used on this device to calculate the 
	 'allowed speeds' to comply with Spectrum Management.

	 Note:Spectrum Management must be Enabled for 'Country
	 Code' to take effect. 

	 'USA' is the only valid selection for Region Setting
	 'Annex A', 'UK' will not be selectable.

	 'UK' for is the only valid selecton for Region Setting
	 'Annex B', 'USA' will not be selectable."

       DEFVAL { usa }
     ::= { pdnSpecMgmtObjects 2 }


spectrumMgmtTable OBJECT-TYPE
     SYNTAX  SEQUENCE OF SpectrumMgmtEntry
     MAX-ACCESS  not-accessible
     STATUS  deprecated
     DESCRIPTION
	"The Spectrum Management Table."
	::= { pdnSpecMgmtObjects 3 }

spectrumMgmtEntry OBJECT-TYPE
     SYNTAX  SpectrumMgmtEntry
     MAX-ACCESS  not-accessible
     STATUS  deprecated
     DESCRIPTION
	"An entry in the Spectrum Management table."
    INDEX   { ifIndex }
    ::= { spectrumMgmtTable 1 }

SpectrumMgmtEntry ::= SEQUENCE {
     spectrumMgmtEWL			Integer32,
     spectrumMgmtLineLength		INTEGER,
     spectrumMgmtAllowedSpeedsMin1	Integer32,
     spectrumMgmtAllowedSpeedsMax1	Integer32,
     spectrumMgmtAllowedSpeedsMin2	Integer32,
     spectrumMgmtAllowedSpeedsMax2	Integer32
 }

spectrumMgmtEWL OBJECT-TYPE
     SYNTAX Integer32
     MAX-ACCESS read-write
     STATUS deprecated
     DESCRIPTION
	"The Estimated Working Length [EWL(ft)].  The value
	selected is the estimated length of the line in ft.
	See the Deployment guideline Table below.
	This value is usually specified by the carrier.  This 
	value is only required if spectrumMgmt is Enabled and
	the spectrumMgmtCountryCode selected is 'USA'."
     ::= { spectrumMgmtEntry 1 }

--  Estimated Working Length Deployment guidelines for G.shdsl
--  --------------------------------------------------------- 
-- | Line Bit Rate(kbps)  | Deployment guideline,EWL (ft)    |
--  --------------------------------------------------------- 
-- |     LBR &lt;= 592       |          15500                   |
--  --------------------------------------------------------- 
-- |  600 &lt;= LBR &lt;= 616   |          15000                   |
-- |  624 &lt;= LBR &lt;= 648   |          14500                   |
-- |---------------------------------------------------------|
-- |  656 &lt;= LBR &lt;= 688   |          14000                   |
-- |  696 &lt;= LBR &lt;= 800   |          13500                   |
-- |---------------------------------------------------------|
-- |  808 &lt;= LBR &lt;= 832   |          12500                   |
-- |  840 &lt;= LBR &lt;= 896   |          12000                   |
-- |---------------------------------------------------------|
-- |  904 &lt;= LBR &lt;= 952   |          13000                   |
-- |  960 &lt;= LBR &lt;= 1000  |          12500                   |
-- |---------------------------------------------------------|
-- | 1008 &lt;= LBR &lt;= 1088  |          12000                   |
-- | 1096 &lt;= LBR &lt;= 1160  |          11500                   |
-- |---------------------------------------------------------|
-- | 1168 &lt;= LBR &lt;= 1320  |          11000                   |
-- | 1328 &lt;= LBR &lt;= 1472  |          10500                   |
-- |---------------------------------------------------------|
-- | 1480 &lt;= LBR &lt;= 1536  |          10000                   |
-- | 1544 &lt;= LBR &lt;= 1552  |          10500                   |
-- |---------------------------------------------------------|
-- | 1560 &lt;= LBR &lt;= 1664  |          10000                   |
-- | 1672 &lt;= LBR &lt;= 1880  |           9500                   |
-- |---------------------------------------------------------|
-- | 1888 &lt;= LBR &lt;= 2008  |           9000                   |
-- | 2016 &lt;= LBR &lt;= 2320  |           8500                   |
--  --------------------------------------------------------- 
-- Where LBR = Line Bit Rate
--
-- Note:Equivalent Working Length(EWL):EWL=L26+3(L24)/4,
--      where L26 is the total length of 26-gauge cable
--      in the loop excluding any bridged tap and L24 is
--      the total length of 19,22 or 24-gauge cable in
--      the loop excluding any bridged tap.   All lengths
--      are in kilofeet (ft). This formula is suitable for
--      use with systems operating below 1.1MHz.  
--
--      Note: Some EWL may have more then one range i.e., EWL
--      =12.5 Kft - ranges 192 Kbit/s to 832Kbits and 960 kbits
--      to 1000 kbits
--

spectrumMgmtAllowedSpeedsMin1 OBJECT-TYPE
     SYNTAX  Integer32
     MAX-ACCESS  read-only
     STATUS  deprecated
     DESCRIPTION
	"This rate will be the Minimum Line Bit Rate based
	 on the Line Length selected. 
	 See the Deployment guideline Table above.
	 Example: EWL=12.5 this value may be 808kbps"
     ::= { spectrumMgmtEntry 2 }

spectrumMgmtAllowedSpeedsMax1 OBJECT-TYPE
     SYNTAX  Integer32
     MAX-ACCESS  read-only
     STATUS  deprecated
     DESCRIPTION
	"This rate will be the Maximum Line Bit Rate based
	 on the Line Length selected
	 See the Deployment guideline Table above.
	 Example: EWL=12.5 this value may be 832kbps"
     ::= { spectrumMgmtEntry 3 }

spectrumMgmtAllowedSpeedsMin2 OBJECT-TYPE
     SYNTAX  Integer32
     MAX-ACCESS  read-only
     STATUS  deprecated
     DESCRIPTION
	"This rate will be the Minimum Line Bit Rate based
	 on the Line Length selected.
	 See the Deployment guideline Table above.
	 Example: EWL=12.5 this value may be 960kbps"
     ::= { spectrumMgmtEntry 4 }

spectrumMgmtAllowedSpeedsMax2 OBJECT-TYPE
     SYNTAX  Integer32
     MAX-ACCESS  read-only
     STATUS  deprecated
     DESCRIPTION
	"This rate will be the Maximum Line Bit Rate based
	 on the Line Length selected.
	 See the Deployment guideline Table above.
	 Example: EWL=12.5 this value may be 1000kbps"
     ::= { spectrumMgmtEntry 5 }

spectrumMgmtLineLength OBJECT-TYPE
     SYNTAX INTEGER {
		short(1),
		medium(2),
		long(3)
	 }
     MAX-ACCESS read-write
     STATUS deprecated
     DESCRIPTION
	"This 'Line Length' feature is only required if the
	 SpectrumMgmt is Enabled and the spectrumMgmtCountryCode
	 selected is 'UK'.
	 'Short' Line Length from the exchange can support speeds
	 up to 2056 Kbps.
	 'Medium' Line Length can support speeds up to 1496 Kbps.
	 'Long' Line Length can suppport speeds up to 872 Kbps."

       DEFVAL { short }
     ::= { spectrumMgmtEntry 6 }



--
--	C O N F O R M A N C E       S T A T E M E N T S
--

   pdnSpecMgmtConformance	OBJECT IDENTIFIER 
		::= { pdnSpectrumMgmt 3 }

   pdnSpecMgmtGroups		OBJECT IDENTIFIER
		::= { pdnSpecMgmtConformance 1 }

   pdnSpecMgmtCompliances	OBJECT IDENTIFIER
		::= { pdnSpecMgmtConformance 2 }


-- 
-- 	C O M P L I A N C E       S T A T E M E N T S
--

pdnSpecMgmtCompliance 	MODULE-COMPLIANCE
    STATUS      current
    DESCRIPTION
       "The compliance statement for SNMP entities that control
        spectrum management on interfaces."

    MODULE   -- this module
        MANDATORY-GROUPS { 
            pdnGeneralConfigGroup,
            pdnLineInfoGroup
        }

--
-- Groups
--
-- pdnEWLModeGroup,
-- pdnLoopLengthModeGroup,
-- pdnQuadModeGroup
--
-- are mutually exclusive; that is, at most one of these groups
-- is implemented for a particular DSL interface. If the
-- Loop Measurement Method is 'none', then none of these groups
-- should be implemented.
--
    GROUP   pdnEWLModeGroup
    DESCRIPTION
       "This group is mandatory for DSL interfaces whose
        loop/line length measurement method is EWL.
        i.e.the newSpectrumMgmtLoopMeasurementMethod object
        is 'ewl'."

    GROUP   pdnLoopLengthModeGroup
    DESCRIPTION
       "This group is mandatory for DSL interfaces whose
        loop/line length measurement method is LoopLength.
        i.e.the newSpectrumMgmtLoopMeasurementMethod object
        is 'loopLength'."

    GROUP   pdnQuadModeGroup
    DESCRIPTION
       "This group is mandatory for DSL interfaces whose
        loop/line length measurement method is based on Quads.
        i.e.the newSpectrumMgmtLoopMeasurementMethod object
        is 'quadMode'."

    OBJECT  	newSpectrumMgmtSelection
    MIN-ACCESS  read-only
    DESCRIPTION 
       "Write access is not required."

    ::= { pdnSpecMgmtCompliances 1 }

	
--
-- 	U N I T S    O F    C O N F O R M A N C E
--

-- Mandatory group
pdnGeneralConfigGroup	OBJECT-GROUP
	OBJECTS {
		newSpectrumMgmtSelection,
		newSpectrumMgmtMode,
		newSpectrumMgmtLoopMeasurementMethod,
		newSpectrumMgmtEWLUnits
	}
	STATUS	current
	DESCRIPTION
		"A collection of general configuration objects
		required for the spectrum management of
		interfaces."

	::= { pdnSpecMgmtGroups 1 }

-- Mandatory group
pdnLineInfoGroup	OBJECT-GROUP
	OBJECTS {
	        newSpectrumMgmtXtucMax1TxRate,
        	newSpectrumMgmtXtucMin1TxRate,
	        newSpectrumMgmtXtucMax2TxRate,
        	newSpectrumMgmtXtucMin2TxRate,
         	newSpectrumMgmtXtucMaxTxPower,
        	newSpectrumMgmtXturMax1TxRate,
        	newSpectrumMgmtXturMin1TxRate,
        	newSpectrumMgmtXturMax2TxRate,
        	newSpectrumMgmtXturMin2TxRate,
        	newSpectrumMgmtXturMaxTxPower,
        	newSpectrumMgmtMinEWL,
        	newSpectrumMgmtMaxEWL
	}
	STATUS	current
	DESCRIPTION
		"A collection of objects providing information
		regarding spectrum management of interfaces."

	::= { pdnSpecMgmtGroups 2 }

--
-- Optional group
-- (pdnEWLModeGroup, pdnLineLoopModeGroup or pdnQuadModeGroup
--  should be implemented)
--
pdnEWLModeGroup	OBJECT-GROUP
	OBJECTS {
		newSpectrumMgmtConfEWL,
		newSpectrumMgmtMinEWL,
		newSpectrumMgmtMaxEWL
	}
	STATUS	current
	DESCRIPTION
		" A collection of configuration objects used to
		  control spectrum management of DSL intfs when
		  the measurement method is 'EWL'."

	::= { pdnSpecMgmtGroups 3 }

--
-- Optional group
-- (pdnEWLModeGroup, pdnLineLoopModeGroup or pdnQuadModeGroup
--  should be implemented)
--
pdnLoopLengthModeGroup	OBJECT-GROUP
	OBJECTS {
		newSpectrumMgmtConfLoopLength
	}
	STATUS	current
	DESCRIPTION
		" A collection of configuration objects used to
		  control spectrum management of DSL intfs when
		  the measurement method is 'LoopLength' "

	::= { pdnSpecMgmtGroups 4 }

--
-- Optional group
-- (pdnEWLModeGroup, pdnLineLoopModeGroup or pdnQuadModeGroup
--  should be implemented)
--
pdnQuadModeGroup OBJECT-GROUP
    	OBJECTS {
        	newSpectrumMgmtConfQuadMode
    	}
	STATUS      current
    	DESCRIPTION 
       		"A collection of object(s) providing configuration
        	access and information specific to DSL interfaces
        	whose loop/line length measurement method is based on the
        	Quad configuration.
        	i.e.the newSpectrumMgmtLoopMeasurementMethod object
        	is 'quadMode'."

    	::= { pdnSpecMgmtGroups 5 }

--
--		D E P R E C A T E D       G R O U P S
--
pdnSpectrumMgmtDeprecatedGroup	OBJECT-GROUP
	OBJECTS {
		spectrumMgmtCountryCode,
		spectrumMgmtEWL,
		spectrumMgmtLineLength,
		spectrumMgmtAllowedSpeedsMin1,
		spectrumMgmtAllowedSpeedsMax1,
		spectrumMgmtAllowedSpeedsMin2,
		spectrumMgmtAllowedSpeedsMax2
	}
	STATUS	deprecated
	DESCRIPTION
		" Deprecated objects "

	::= { pdnSpecMgmtGroups 7 }

END
