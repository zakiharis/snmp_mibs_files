-- MIB File Generated on 31-Aug-1995 at 18:35:17

PB-MIB DEFINITIONS ::= BEGIN

IMPORTS
   enterprises,
   experimental,
   IpAddress,
   TimeTicks,
   Gauge,
   Counter
      FROM RFC1155-SMI
   DisplayString
      FROM RFC1213-MIB
   OBJECT-TYPE
      FROM RFC-1212;


usr OBJECT IDENTIFIER ::= { enterprises 429 }

nas OBJECT IDENTIFIER ::= { usr 1 }

pb OBJECT IDENTIFIER ::= { nas 12 }

pbCfg OBJECT IDENTIFIER ::= { pb 1 }

pbCfgTable OBJECT-TYPE
SYNTAX SEQUENCE OF PbCfgEntry
ACCESS not-accessible
STATUS mandatory
DESCRIPTION
"A table containing an configuration information for each 
Gateway NAC in the NAS chassis."
::= { pbCfg 1 }

pbCfgEntry OBJECT-TYPE
SYNTAX PbCfgEntry
ACCESS not-accessible
STATUS mandatory
DESCRIPTION
"There is one Configuration row for each Gateway Card in the 
NAS chassis."
INDEX { pbCfgIndex }
::= { pbCfgTable 1 }

PbCfgEntry ::=
SEQUENCE {
pbCfgIndex
    INTEGER,
pbCfgMaxSessions
    INTEGER
}

pbCfgIndex OBJECT-TYPE
SYNTAX INTEGER
ACCESS read-only
STATUS mandatory
DESCRIPTION
"A unique value for each Gateway Card in the chassis. The 
value of this object matches the value of the index of the 
corresponding Gateway Card's entry in the entity table of 
the chassis MIB."
::= { pbCfgEntry 1 }

pbCfgMaxSessions OBJECT-TYPE
SYNTAX INTEGER
ACCESS read-only
STATUS mandatory
DESCRIPTION
"This read-only object defines the maximum number of packet 
bus sessions supported by this entity. This value is used 
to determine the number of rows present in the 
pbSessionTable for this entity."
::= { pbCfgEntry 2 }

pbSession OBJECT IDENTIFIER ::= { pb 2 }

pbSessionTable OBJECT-TYPE
SYNTAX SEQUENCE OF PbSessionEntry
ACCESS not-accessible
STATUS mandatory
DESCRIPTION
"The Packet Bus Session table contains an entry for each 
manageable Gateway NAC in the chassis.  It provides a means 
to configure packet bus connections and determine the 
status of the defined connections.  This table resides in 
the NAC and can be impemented as either a dense or sparse 
table."
::= { pbSession 1 }

pbSessionEntry OBJECT-TYPE
SYNTAX PbSessionEntry
ACCESS not-accessible
STATUS mandatory
DESCRIPTION
"There is an row for each Packet Bus connection."
INDEX { pbSessionEntityIndex, pbSessionIndex }
::= { pbSessionTable 1 }

PbSessionEntry ::=
SEQUENCE {
pbSessionEntityIndex
    INTEGER,
pbSessionIndex
    INTEGER,
pbSessionDestSlot
    INTEGER,
pbSessionDestChan
    INTEGER,
pbSessionDestSess
    INTEGER,
pbSessionRowState
    INTEGER,
pbSessionStatus
    INTEGER,
pbSessionReqStatus
    INTEGER,
pbSessionLastRequest
    INTEGER,
pbSessionPktSents
    Counter,
pbSessionPktRcvds
    Counter,
pbSessionPktSize
    INTEGER,
pbSessionBusTimeOuts
    Counter,
pbSessionErrorStatus
    INTEGER
}

pbSessionEntityIndex OBJECT-TYPE
SYNTAX INTEGER
ACCESS read-only
STATUS mandatory
DESCRIPTION
"A unique value for each entity in the chassis.  The value 
of this object matches the value of the index of the 
corresponding entry in the entity table of the chassis MIB."
::= { pbSessionEntry 1 }

pbSessionIndex OBJECT-TYPE
SYNTAX INTEGER
ACCESS read-only
STATUS mandatory
DESCRIPTION
"An index that uniquely identifies the packet bus session 
for this entity."
::= { pbSessionEntry 2 }

pbSessionDestSlot OBJECT-TYPE
SYNTAX INTEGER (1..64)
ACCESS read-write
STATUS mandatory
DESCRIPTION
"A number that identifies the slot of the entity in the 
chassis to which a packet bus session has been assigned."
::= { pbSessionEntry 3 }

pbSessionDestChan OBJECT-TYPE
SYNTAX INTEGER (1..255)
ACCESS read-write
STATUS mandatory
DESCRIPTION
"A number that identifies a particular entity in a slot."
::= { pbSessionEntry 4 }

pbSessionDestSess OBJECT-TYPE
SYNTAX INTEGER (0..255)
ACCESS read-only
STATUS mandatory
DESCRIPTION
"A number that identifies the particular session from the 
other  communicating Gateway."
::= { pbSessionEntry 5 }

pbSessionRowState OBJECT-TYPE
SYNTAX INTEGER{
  free(1),
  used(2)
}
ACCESS read-write
STATUS mandatory
DESCRIPTION
"Set availability for this row of packet bus session. 
Default=free(1)."
::= { pbSessionEntry 6 }

pbSessionStatus OBJECT-TYPE
SYNTAX INTEGER{
  unassigned(1),
  assigned(2),
  connected(3)
}
ACCESS read-only
STATUS mandatory
DESCRIPTION
"Displays the current status of the packet bus session.  A 
status of Unassigned coupled with a state of used indicates 
that a packet bus failure has occured."
::= { pbSessionEntry 7 }

pbSessionReqStatus OBJECT-TYPE
SYNTAX INTEGER{
  disconnected(1),
  connected(2)
}
ACCESS read-write
STATUS mandatory
DESCRIPTION
"Used to assign or delete a session between the entities 
specified by the table indecies. A request connect is a 
issue of packet bus session link start, and a request 
disconnect is a issue of packet bus session link terminate. 
Default=disconnected(1)."
::= { pbSessionEntry 8 }

pbSessionLastRequest OBJECT-TYPE
SYNTAX INTEGER{
  unknown(1),
  open(2),
  close(3),
  listen(4),
  dial(5),
  disconnect(6),
  transmit(7),
  receive(8),
  setMode(9),
  query(10),
  flush(11),
  kill(12),
  reserve(13),
  answer(14),
  attach(15)
}
ACCESS read-only
STATUS optional
DESCRIPTION
"Indicates the type of communications contained in the last 
packet sent to the destination entity."
::= { pbSessionEntry 9 }

pbSessionPktSents OBJECT-TYPE
SYNTAX Counter
ACCESS read-only
STATUS mandatory
DESCRIPTION
"A counter that indicates number of packets that have been 
sent."
::= { pbSessionEntry 10 }

pbSessionPktRcvds OBJECT-TYPE
SYNTAX Counter
ACCESS read-only
STATUS mandatory
DESCRIPTION
"A counter that indicates number of packets that have been 
received."
::= { pbSessionEntry 11 }

pbSessionPktSize OBJECT-TYPE
SYNTAX INTEGER
ACCESS read-only
STATUS mandatory
DESCRIPTION
"A number that indicates the packet size of the current or 
last established session."
::= { pbSessionEntry 12 }

pbSessionBusTimeOuts OBJECT-TYPE
SYNTAX Counter
ACCESS read-only
STATUS mandatory
DESCRIPTION
"A counter that indicates number of packet bus timeout that 
have occurred."
::= { pbSessionEntry 13 }

pbSessionErrorStatus OBJECT-TYPE
SYNTAX INTEGER{
  noError(1),
  invalidParm(2),
  socketNotOpened(3),
  noMoreSocket(4),
  connectionExist(5),
  connectionFailed(6),
  noMoreConnObj(7),
  noActiveConn(8),
  ackWaitTimeout(9),
  hwNakRcvd(10),
  otherBusError(11),
  linkStartRcvd(12),
  outOfSeqFrame(13),
  noMemory(14),
  nullPointer(15),
  invalidBlock(16),
  notInitialized(17),
  failedToRecv(18),
  invalidMsgType(19),
  exceedMaxSends(20),
  connectionReset(21),
  socketClosed(22),
  uiReqPending(23),
  heartbeatTimeout(24),
  remoteBusy(25),
  localBusy(26),
  noResponse(27),
  linkdownNoTx(28),
  noDataToTx(29),
  txPreAck(30),
  txTardyAck(31),
  txBusTimeOut(32),
  rxBusTimeOut(33),
  txTAL(34),
  rxTAL(35),
  txMasterTimeOut(36),
  clkVanished(37),
  clkReturned(38),
  shutdown(39),
  frameError(40),
  xIDTimeOut(41),
  recvLSinInfoTransferState(42),
  recvIFrameWithWrongSeq(43),
  rxMsgBufferOverflow(44),
  linkDown(45),
  listenFailed(46),
  listenRcvFailed(47),
  dtrDrop(48),
  answerFailed(49),
  openFailed(50),
  closeFailed(51),
  readFailed(52),
  writeFailed(53),
  autoParityFailed(54),
  setmodeFailed(55),
  badDataBase(56),
  padStreamsError(57),
  padError(58)
}
ACCESS read-only
STATUS mandatory
DESCRIPTION
"Error return status from last packet command."
::= { pbSessionEntry 14 }

pbTrapEna OBJECT IDENTIFIER ::= { pb 3 }

pbTrapEnaTable OBJECT-TYPE
SYNTAX SEQUENCE OF PbTrapEnaEntry
ACCESS not-accessible
STATUS mandatory
DESCRIPTION
"A table containing an enable for each trap that a 
manageable Gateway entity is capable of generating."
::= { pbTrapEna 1 }

pbTrapEnaEntry OBJECT-TYPE
SYNTAX PbTrapEnaEntry
ACCESS not-accessible
STATUS mandatory
DESCRIPTION
"There is one Gateway trap enable row for each Gateway card 
in the NAS chassis."
INDEX { pbTrapEnaIndex, pbTrapSessionIndex }
::= { pbTrapEnaTable 1 }

PbTrapEnaEntry ::=
SEQUENCE {
pbTrapEnaIndex
    INTEGER,
pbTrapSessionIndex
    INTEGER,
pbTrapEnaSessActive
    INTEGER,
pbTrapEnaPktBusCongest
    INTEGER,
pbTrapEnaPktBusSessLost
    INTEGER,
pbTrapEnaSessionInactive
    INTEGER,
pbTrapEnaSessionError
    INTEGER
}

pbTrapEnaIndex OBJECT-TYPE
SYNTAX INTEGER
ACCESS read-only
STATUS mandatory
DESCRIPTION
"A unique value for each Gateway Card in the chassis. The 
value of this object matches the value of the index of the 
corresponding Gateway Card's entry in the entity table of 
the chassis MIB."
::= { pbTrapEnaEntry 1 }

pbTrapSessionIndex OBJECT-TYPE
SYNTAX INTEGER
ACCESS read-only
STATUS mandatory
DESCRIPTION
"A value that identifies the packet bus session for trap 
enable/disable."
::= { pbTrapEnaEntry 2 }

pbTrapEnaSessActive OBJECT-TYPE
SYNTAX INTEGER{
  enable(1),
  disable(2)
}
ACCESS read-write
STATUS mandatory
DESCRIPTION
"An object which enables or disables the Active Session 
trap."
::= { pbTrapEnaEntry 3 }

pbTrapEnaPktBusCongest OBJECT-TYPE
SYNTAX INTEGER{
  enable(1),
  disable(2)
}
ACCESS read-write
STATUS mandatory
DESCRIPTION
"An object to enable or disable the Packet Bus Congestion 
trap. The Packet Bus Congestion trap is generated when a 
valid packet bus session is in progress but either the 
Modem or the Gateway packet bus driver is experiencing 
congestion problem."
::= { pbTrapEnaEntry 4 }

pbTrapEnaPktBusSessLost OBJECT-TYPE
SYNTAX INTEGER{
  enable(1),
  disable(2)
}
ACCESS read-write
STATUS mandatory
DESCRIPTION
"An object to enable or disable the trap that is generated 
when a valid Packet Bus session has been lost."
::= { pbTrapEnaEntry 5 }

pbTrapEnaSessionInactive OBJECT-TYPE
SYNTAX INTEGER{
  enable(1),
  disable(2)
}
ACCESS read-write
STATUS mandatory
DESCRIPTION
"An object to enable or disable a trap which is generated 
when a request is made to change a packet bus session from 
the active to inactive state."
::= { pbTrapEnaEntry 6 }

pbTrapEnaSessionError OBJECT-TYPE
SYNTAX INTEGER{
  enable(1),
  disable(2)
}
ACCESS read-write
STATUS mandatory
DESCRIPTION
"An object which enables or disables the packet bus session 
error trap."
::= { pbTrapEnaEntry 7 }

END
