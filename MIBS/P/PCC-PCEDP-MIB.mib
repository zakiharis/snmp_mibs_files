-- extracted from draft-stephan-pce-pcedp-pcc-mib-01.txt
-- at Thu Jun 29 06:06:37 2006

   PCC-PCEDP-MIB DEFINITIONS ::= BEGIN

   IMPORTS
      MODULE-IDENTITY, OBJECT-TYPE, NOTIFICATION-TYPE,
      Counter32, Unsigned32, Gauge32, Integer32, IpAddress,
      experimental FROM SNMPv2-SMI
      RowStatus,
      TEXTUAL-CONVENTION,
      TimeStamp,
      TruthValue

         FROM SNMPv2-TC
      Ipv6Address
         FROM IPV6-TC
      MODULE-COMPLIANCE,
      OBJECT-GROUP,
      NOTIFICATION-GROUP
         FROM SNMPv2-CONF
      AddressFamilyNumbers
         FROM IANA-ADDRESS-FAMILY-NUMBERS-MIB
      IANAipRouteProtocol
         FROM IANA-RTPROTO-MIB;

   pccPcedpMIB MODULE-IDENTITY
      LAST-UPDATED "200606150000Z" -- June 15, 2006
      ORGANIZATION "PCE Working Group"
      CONTACT-INFO "WG-email: pce@ietf.org
      WG-URL: http://www.ietf.org/html.charters/pce-charter.html

      TODO: This section has to be completed with chairs and authors
      addresses
      "
   DESCRIPTION
      "This MIB module defines a collection of objects for managing Path
      Computation Elements (PCEs) Discovery Protocol inside a Path
      Computation Client (PCC) application."
   ::= { experimental 10000 } -- Temporary node ( for smilint)

   -- Textual Conventions used in this MIB module --

   PccPceDpRoutingDomainID ::= TEXTUAL-CONVENTION
      STATUS current
      DESCRIPTION
         "A PCE-DOMAINS information element or a A PCE-DEST-DOMAINS
         information element carries the identifier of a routing domain
         (area,as) which type depends on both the routing protocol and
         on the version of Internet protocol in use in this routing
         domain.

         This TC defines a common SMI type for the different kinds of
         routing domain identifiers.

         An PccPceDpRoutingDomainID value is always interpreted within
         the context of an AddressFamilyNumbers value.  Every usage of
         the PccPceDpRoutingDomainID textual convention is required to
         specify the AddressFamilyNumbers object which provides the
         context.

         The value of an PccPceDpRoutingDomainID object must always be
         consistent with the value of the associated
         AddressFamilyNumbers object.

         Following is the mapping between AddressFamilyNumbers type and
         PccPceDpRoutingDomainID size:
            ipV4(1):
               PccPceDpRoutingDomainID is an InetAddressIPv4
               corresponding to the name of an OSPF area;
            ipV6(2):
               PccPceDpRoutingDomainID is an InetAddressIPv6
               corresponding to the name of an OSPF area;

            nsap(3):
               PccPceDpRoutingDomainID type is OCTET STRING (SIZE
               (0..20)), corresponding to the name of an ISIS area (see
               RFC 1195);
            asNumber(18)
               PccPceDpRoutingDomainID type is OCTET STRING (SIZE (2))
               corresponding to the name of an Autonomous System.
         "
      SYNTAX OCTET STRING (SIZE (0..20))

   -- Notification --

   pccPcedpNotifications OBJECT IDENTIFIER ::= { pccPcedpMIB 0 }

   -- empty for now

   pccPcedpMIBObjects OBJECT IDENTIFIER ::= { pccPcedpMIB 1 }

   pccPcedpDiscoveryObjects OBJECT IDENTIFIER ::= { pccPcedpMIBObjects 1
   }

   pccPcedpDiscAdminStatus OBJECT-TYPE
      SYNTAX INTEGER {
         enabled(1),
         disabled(2)
      }
      MAX-ACCESS read-write
      STATUS current
      DESCRIPTION
         "Setting this object to disabled(2) disables the discovery of
         PCEs.  Once disabled, The discovery must be explicitly enabled
         to restore discovery of PCEs.  Setting this object to
         enabled(1) enables the discovery of PCEs."
      ::= { pccPcedpDiscoveryObjects 1 }

   pccPcedpDiscKnowPCEs OBJECT-TYPE
      SYNTAX Counter32
      MAX-ACCESS read-only
      STATUS current
      DESCRIPTION
         "The number of PCEs the PCC is potentially in relation with.
         This includes PCE manually declared and active PCEs"
      ::= { pccPcedpDiscoveryObjects 2 }

   pccPcedpDiscActivePCEs OBJECT-TYPE
      SYNTAX Counter32
      MAX-ACCESS read-only
      STATUS current
      DESCRIPTION
         "The number of active PCEs.
         The detection of the activity a a PCE depends on the nature
         discovery mechanism.
         PCE discovered using PCED information received:
            The relation between the PCC and a PCE is active while the
            PCE discovery protocol maintains a communication between the
            PCC and this PCE.
         PCE Manually declared:
            The relation between the PCC and a PCE is active and the
            discovery mechanism is implementation specific;
         "
      ::= { pccPcedpDiscoveryObjects 3 }

   pccPcedpDiscPceTable OBJECT-TYPE
      SYNTAX SEQUENCE OF PccPcedpDiscPceEntry
      MAX-ACCESS not-accessible
      STATUS current
      DESCRIPTION
         "Information describing the PCEs discovered by the PCC."
      ::= { pccPcedpDiscoveryObjects 4 }

   pccPcedpDiscPceEntry OBJECT-TYPE
      SYNTAX PccPcedpDiscPceEntry
      MAX-ACCESS not-accessible
      STATUS current
      DESCRIPTION
         "Information describing the general information of each PCE
         discovered by the PCC.
         "
      INDEX { pccPcedpDiscPceIndex }
      ::= { pccPcedpDiscPceTable 1 }

   PccPcedpDiscPceEntry ::= SEQUENCE {
      pccPcedpDiscPceIndex Integer32,
      pccPcedpDiscMechanism IANAipRouteProtocol,
      pccPcedpDiscPceIPv4Address IpAddress,
      pccPcedpDiscPceIPv6Address Ipv6Address,
      pccPcedpDiscPceTime TimeStamp,
      pccPcedpDiscPceLastUpdated TimeStamp
   }

   pccPcedpDiscPceIndex OBJECT-TYPE
      SYNTAX Integer32 (1..2147483647)
      MAX-ACCESS not-accessible
      STATUS current
      DESCRIPTION
         "This object identifies locally the PCE for which this entry
         contains information."
      ::= { pccPcedpDiscPceEntry 1 }

   pccPcedpDiscMechanism OBJECT-TYPE
      SYNTAX IANAipRouteProtocol
      MAX-ACCESS read-only
      STATUS current
      DESCRIPTION
         "This object identifies the type of discovery mechanism used by
         PCC to discover the PCE.
         The acceptable value are :
            local (2), -- local interface
            isIs (9), -- Dual IS-IS
            ospf (13), -- Open Shortest Path First
            bgp (14), -- Border Gateway Protocol
         "
      ::= { pccPcedpDiscPceEntry 2 }

   pccPcedpDiscPceIPv4Address OBJECT-TYPE
      SYNTAX IpAddress
      MAX-ACCESS read-only
      STATUS current
      DESCRIPTION
         "This object is the IP address to be used to reach the PCE.  It
         corresponds to the PCED PCE-ADDRESS.
         .
         A value of 0.0.0.0 indicates the absence of this address."
      ::= { pccPcedpDiscPceEntry 3 }

   pccPcedpDiscPceIPv6Address OBJECT-TYPE
      SYNTAX Ipv6Address
      MAX-ACCESS read-only
      STATUS current
      DESCRIPTION
         "This object is the IPv6 address to be used to reach the PCE.
         It corresponds to the PCED PCE-ADDRESS.
         A value of ::0 indicates the absence of this address."
      ::= { pccPcedpDiscPceEntry 4 }

   pccPcedpDiscPceTime OBJECT-TYPE
      SYNTAX TimeStamp
      MAX-ACCESS read-only
      STATUS current
      DESCRIPTION
         "The value of sysUpTime at the time this entry was created.
         local entry: the value of sysUpTime at the time PCC restarted."
      ::= { pccPcedpDiscPceEntry 5 }

   pccPcedpDiscPceLastUpdated OBJECT-TYPE
      SYNTAX TimeStamp
      MAX-ACCESS read-only
      STATUS current
      DESCRIPTION
         "The value of sysUpTime at the time this entry was last
         updated.
         Static entry: if the entry values keep unchanged since the re-
         initialization of the PCC then this object contains a zero
         value."
      ::= { pccPcedpDiscPceEntry 6 }


   --

   -- pccPcedpDiscActTable;

   --

   pccPcedpDiscActTable OBJECT-TYPE
      SYNTAX SEQUENCE OF PccPcedpDiscActEntry
      MAX-ACCESS not-accessible
      STATUS current
      DESCRIPTION
         "Information describing for each PCE the activity of the
         discovery mechanism."
      ::= { pccPcedpDiscoveryObjects 5 }

   pccPcedpDiscActEntry OBJECT-TYPE
      SYNTAX PccPcedpDiscActEntry
      MAX-ACCESS not-accessible
      STATUS current
      DESCRIPTION
         "Information describing the activity of the discovery mechanism
         of a PCE discovered by the PCC."
      INDEX { pccPcedpDiscPceIndex }
      ::= { pccPcedpDiscActTable 1 }

   PccPcedpDiscActEntry ::= SEQUENCE {
      pccPcedpDiscActCongestion TruthValue,
      pccPcedpDiscActCongestionDuration Unsigned32
   }

   pccPcedpDiscActCongestion OBJECT-TYPE
      SYNTAX TruthValue
      MAX-ACCESS read-only
      STATUS current
      DESCRIPTION
         "This object indicates whether a PCE experiences a processing
         congestion state or not.
         "
      ::= { pccPcedpDiscActEntry 1 }

   pccPcedpDiscActCongestionDuration OBJECT-TYPE
      SYNTAX Unsigned32
      MAX-ACCESS read-only
      STATUS current
      DESCRIPTION
         "This object specifies, in seconds, the congestion duration.
         When the value of pccPcedpDiscActCongestion is 'false' then
         this objet MUST be to '0'"
      ::= { pccPcedpDiscActEntry 2 }

   pccPcedpCapabilityObjects OBJECT IDENTIFIER ::= { pccPcedpMIBObjects
   2 }

   --

   -- PCE-PATHSCOPE informations elements

   --

   pccPcedpCapPathScopeTable OBJECT-TYPE
      SYNTAX SEQUENCE OF PccPcedpCapPathScopeEntry
      MAX-ACCESS not-accessible
      STATUS current
      DESCRIPTION
         "Information describing the capacity of the PCEs discovered by
         the PCC."
      ::= { pccPcedpCapabilityObjects 1 }

   pccPcedpCapPathScopeEntry OBJECT-TYPE
      SYNTAX PccPcedpCapPathScopeEntry
      MAX-ACCESS not-accessible
      STATUS current
      DESCRIPTION
         "Information describing the capacity of each PCE discovered by
         the PCC."
      INDEX { pccPcedpDiscPceIndex }
      ::= { pccPcedpCapPathScopeTable 1 }

   PccPcedpCapPathScopeEntry ::= SEQUENCE {
      pccPcedpCapPathScopeIntraArea TruthValue,
      pccPcedpCapPathScopeInterArea TruthValue,
      pccPcedpCapPathScopeDefaultInterArea TruthValue,
      pccPcedpCapPathScopeInterAS TruthValue,
      pccPcedpCapPathScopeDefaultInterAS TruthValue,
      pccPcedpCapPathScopeInterLayer TruthValue,
      pccPcedpCapPathScopePrefIntraArea Integer32,
      pccPcedpCapPathScopePrefInterArea Integer32,
      pccPcedpCapPathScopePrefInterAS Integer32,
      pccPcedpCapPathScopePrefInterLayer Integer32
   }

   pccPcedpCapPathScopeIntraArea OBJECT-TYPE
      SYNTAX TruthValue
      MAX-ACCESS read-only
      STATUS current
      DESCRIPTION
         "Indicates whether the PCE supports the L option of the PATH-
         SCOPE sub TLV:
            The value is 'true' if the PCE can compute intra-area path."
      ::= { pccPcedpCapPathScopeEntry 1 }

   pccPcedpCapPathScopeInterArea OBJECT-TYPE
      SYNTAX TruthValue
      MAX-ACCESS read-only
      STATUS current
      DESCRIPTION
         "Indicates whether the PCE supports the R option of the PATH-
         SCOPE sub TLV:
            The value is 'true' if the PCE can act as PCE for inter-area
            TE LSPs computation."
      ::= { pccPcedpCapPathScopeEntry 2 }

   pccPcedpCapPathScopeDefaultInterArea OBJECT-TYPE
      SYNTAX TruthValue
      MAX-ACCESS read-only
      STATUS current
      DESCRIPTION
         "Indicates whether the PCE supports the Rd option of the PATH-
         SCOPE sub TLV:
            The value is 'true' if the PCE can act as a default PCE for
            inter-area TE LSPs computation."
      ::= { pccPcedpCapPathScopeEntry 3 }

   pccPcedpCapPathScopeInterAS OBJECT-TYPE
      SYNTAX TruthValue
      MAX-ACCESS read-only
      STATUS current
      DESCRIPTION
         "Indicates whether the PCE supports the S option of the PATH-
         SCOPE sub TLV:
            The value is 'true' if the PCE can act as PCE for inter-AS
            TE LSPs computation."
      ::= { pccPcedpCapPathScopeEntry 4 }

   pccPcedpCapPathScopeDefaultInterAS OBJECT-TYPE
      SYNTAX TruthValue
      MAX-ACCESS read-only
      STATUS current
      DESCRIPTION
         "Indicates whether the PCE supports the Sd option of the PATH-
         SCOPE sub TLV:
            The value is 'true' if the PCE can act as a default PCE for
            inter-AS TE LSPs computation."
      ::= { pccPcedpCapPathScopeEntry 5 }

   pccPcedpCapPathScopeInterLayer OBJECT-TYPE
      SYNTAX TruthValue
      MAX-ACCESS read-only
      STATUS current
      DESCRIPTION
         "Indicates whether the PCE supports the Y option of the PATH-
         SCOPE sub TLV:
            The value is 'true' if the PCE can compute or take part into
            the computation of paths across layers."
      ::= { pccPcedpCapPathScopeEntry 6}

   pccPcedpCapPathScopePrefIntraArea OBJECT-TYPE
      SYNTAX Integer32 (0..7)
      MAX-ACCESS read-only
      STATUS current
      DESCRIPTION
         "Indicates the level of preference of the option of computation
         'L' compared to other computation options:
            A value of 7 reflects the highest preference.
            When the value of PccPcedpCapCompIntraArea is 'false' then
            this objet MUST be to '0'."
      ::= { pccPcedpCapPathScopeEntry 7}

   pccPcedpCapPathScopePrefInterArea OBJECT-TYPE
      SYNTAX Integer32 (0..7)
      MAX-ACCESS read-only
      STATUS current
      DESCRIPTION
         "Indicates the level of preference of the option of computation
         'R' compared to other computation options:
            A value of 7 reflects the highest preference.
            When the value of PccPcedpCapCompInterArea is 'false' then
            this objet MUST be to '0'."
      ::= { pccPcedpCapPathScopeEntry 8}

   pccPcedpCapPathScopePrefInterAS OBJECT-TYPE
      SYNTAX Integer32 (0..7)
      MAX-ACCESS read-only
      STATUS current
      DESCRIPTION
         "Indicates the level of preference of the option of computation
         'S' compared to other computation options:
            A value of 7 reflects the highest preference.
            When the value of PccPcedpCapCompInterAS is 'false' then
            this objet MUST be to '0'."
      ::= { pccPcedpCapPathScopeEntry 9}

   pccPcedpCapPathScopePrefInterLayer OBJECT-TYPE
      SYNTAX Integer32 (0..7)
      MAX-ACCESS read-only
      STATUS current
      DESCRIPTION
         "Indicates the level of preference of the option of computation
         'Y' compared to other computation options:
            A value of 7 reflects the highest preference.
            When the value of PccPcedpCapCompInterLayer is 'false' then
            this objet MUST be to '0'."
      ::= { pccPcedpCapPathScopeEntry 10}

   --

   -- PCE-DOMAINS information elements

   --

   pccPcedpCapDomainTable OBJECT-TYPE
      SYNTAX SEQUENCE OF PccPcedpCapDomainEntry
      MAX-ACCESS not-accessible
      STATUS current
      DESCRIPTION
         "Information describing the set of domains where the PCE has
         topology visibility and can compute paths."
      ::= { pccPcedpCapabilityObjects 2 }

   pccPcedpCapDomainEntry OBJECT-TYPE
      SYNTAX PccPcedpCapDomainEntry
      MAX-ACCESS not-accessible
      STATUS current
      DESCRIPTION
         "Information describing the domains of each PCE discovered by
         the PCC."
      INDEX { pccPcedpDiscPceIndex, pccPcedpCapDomainIndex }
      ::= { pccPcedpCapDomainTable 1 }

   PccPcedpCapDomainEntry ::= SEQUENCE {
      pccPcedpCapDomainIndex Integer32,
      pccPcedpCapDomainIDType AddressFamilyNumbers,
      pccPcedpCapDomainID PccPceDpRoutingDomainID
   }

   pccPcedpCapDomainIndex OBJECT-TYPE
      SYNTAX Integer32 (1..2147483647)
      MAX-ACCESS not-accessible
      STATUS current
      DESCRIPTION
         "This object identifies locally a domain for which the PCE
         identified by pccPcedpDiscPceIndex has topology visibility and
         can compute paths."
      ::= { pccPcedpCapDomainEntry 1 }

   pccPcedpCapDomainIDType OBJECT-TYPE
      SYNTAX AddressFamilyNumbers
      MAX-ACCESS read-only
      STATUS current
      DESCRIPTION
         "This object identifies the type of the domainID of a PCE-
         DOMAIN SUB TLV.
         Acceptable types are :
            ipV4(1) and ipV6(2) for an OSPF area ID;
            nsap(3) for and ISIS area ID;
            asNumber(18) for an BGP AS number"
      ::= { pccPcedpCapDomainEntry 2 }

   pccPcedpCapDomainID OBJECT-TYPE
      SYNTAX PccPceDpRoutingDomainID
      MAX-ACCESS read-only
      STATUS current
      DESCRIPTION
         "The ID (area,AS) of the routing domain for which this entry
         contains information."
      ::= { pccPcedpCapDomainEntry 3 }

   --

   -- PCE-DEST-DOMAINS information elements

   --

   pccPcedpCapDestDomainTable OBJECT-TYPE
      SYNTAX SEQUENCE OF PccPcedpCapDestDomainEntry
      MAX-ACCESS not-accessible
      STATUS current
      DESCRIPTION
         "Information describing the set of destination domains toward
         which a PCE can compute path."
      ::= { pccPcedpCapabilityObjects 3 }

   pccPcedpCapDestDomainEntry OBJECT-TYPE
      SYNTAX PccPcedpCapDestDomainEntry
      MAX-ACCESS not-accessible
      STATUS current
      DESCRIPTION
         "Information describing the destination domains of each PCE."
      INDEX { pccPcedpDiscPceIndex, pccPcedpCapDestDomainIndex }
      ::= { pccPcedpCapDestDomainTable 1 }

   PccPcedpCapDestDomainEntry ::= SEQUENCE {
      pccPcedpCapDestDomainIndex Integer32,
      pccPcedpCapDestDomainIDType AddressFamilyNumbers,
      pccPcedpCapDestDomainID PccPceDpRoutingDomainID
   }

   pccPcedpCapDestDomainIndex OBJECT-TYPE
      SYNTAX Integer32 (1..2147483647)
      MAX-ACCESS not-accessible
      STATUS current
      DESCRIPTION
         "This object identifies locally a destination domain toward
         which a PCE identified by pccPcedpDiscPceIndex can compute
         path."
      ::= { pccPcedpCapDestDomainEntry 1 }

   pccPcedpCapDestDomainIDType OBJECT-TYPE
      SYNTAX AddressFamilyNumbers
      MAX-ACCESS read-only
      STATUS current
      DESCRIPTION
         "This object identifies the type of the routing domain.
         Acceptable types are :
            ipV4(1) and ipV6(2) for an OSPF area ID;
            nsap(3) for and ISIS area ID;
            asNumber(18) for an BGP AS number"
      ::= { pccPcedpCapDestDomainEntry 2 }

   pccPcedpCapDestDomainID OBJECT-TYPE
      SYNTAX PccPceDpRoutingDomainID
      MAX-ACCESS read-only
      STATUS current
      DESCRIPTION
         "The ID (area,AS) of the routing domain for which this entry
         contains information."
      ::= { pccPcedpCapDestDomainEntry 3 }


   -- PATH-COMP-CAP sub-TLV

   -- TODO

   -- CONGESTION sub-TLV

   -- TODO

   pccPcedpPceActivityGroup OBJECT IDENTIFIER ::= { pccPcedpMIBObjects 3
   }

   -- empty for now: TODO

   --

   -- PCC agents conformance statement

   --

   pccPcedpConformance OBJECT IDENTIFIER ::= { pccPcedpMIB 2 }

   pccPcedpGroups OBJECT IDENTIFIER ::= { pccPcedpConformance 1 }

   pccPcedpCompliances OBJECT IDENTIFIER ::= { pccPcedpConformance 2 }

   -- PCC agent compliance statements
   pccPcedpGeneralPceInformation MODULE-COMPLIANCE
      STATUS current
      DESCRIPTION
      "The compliance statement for SNMP entities that implement only
      general information monitoring as proposed in the 2nd S. of the
      section 6.1 of [I-D.ietf-pce-discovery-reqs]."
      MODULE
      --
      -- objets of pccPcedpDiscTable
      -- objects of pccPcedpPathScopeTable
      --
   ::= { pccPcedpCompliances 1 }

   pccPcedpDetailledPceInformation MODULE-COMPLIANCE
      STATUS current
      DESCRIPTION
      "The compliance statement for SNMP entities that implement
      detailled monitoring as proposed in the 3rd S. of the section 6.1
      of [I-D.ietf-pce-discovery-reqs]."
      MODULE
      --
      -- objets of pccPcedpDiscTable;
      -- objects of pccPcedpDiscActTable;
      -- objects of pccPcedpPathScopeTable;
      -- objects of pccPcedpDomainTable;
      -- objects of pccPcedpDestDomainTable
      --
   ::= { pccPcedpCompliances 2 }

   END

-- 
--    Copyright (C) The Internet Society (2006).  This document is subject
--    to the rights, licenses and restrictions contained in BCP 78, and
--    except as set forth therein, the authors retain all their rights.
-- 
-- 
-- Acknowledgment
-- 
--    Funding for the RFC Editor function is currently provided by the
--    Internet Society.
