-- extracted from draft-ietf-ipoib-perf-mgmt-agent-mib-04.txt
-- at Wed Sep 14 06:35:50 2005

PMA-MIB DEFINITIONS ::= BEGIN 
    
IMPORTS  
   MODULE-IDENTITY, OBJECT-TYPE,                
   NOTIFICATION-TYPE, Unsigned32, Counter32     FROM SNMPv2-SMI  
   MODULE-COMPLIANCE, OBJECT-GROUP              FROM SNMPv2-CONF  
   IbDataPort, infinibandMIB                    FROM IB-TC-MIB;
  
ibPmaMIB MODULE-IDENTITY  
   LAST-UPDATED    "200509011200Z"   --  September 1, 2005 12:00:00 GMT
   ORGANIZATION    "IETF IP Over IB (IPOIB) Working Group"
   CONTACT-INFO  
       "Sean Harnedy (sharnedy@mangrovesystems.com)
        Mangrove Systems, Inc."
   DESCRIPTION  
      "Copyright (C) The Internet Society (2005).  The initial 
       version of this MIB module was published in RFC XXXX; for
       full legal notices see the RFC itself.  Supplementary 
       information may be available on 
       http://www.ietf.org/copyrights/ianamib.html.

       This module contains managed object definitions for 
       the Performance Management Agent instrumentation for an 
       InfiniBand Performance Management Agent (PMA)."  
   REVISION
        "200509011200Z"   --  September 1, 2005 12:00:00 GMT
   DESCRIPTION 
      "Initial version published as part of RFC XXXX."  
   ::= { infinibandMIB 6 }
    
--**************************************************************** 
--  Object Indentifiers for the IPOIB PMA MIB  
--**************************************************************** 

ibPmaObjects OBJECT IDENTIFIER ::= { ibPmaMIB 1 }  
ibPmaConformance OBJECT IDENTIFIER ::= { ibPmaMIB 2 }  

--**************************************************************** 
-- Port Counters Group
--
-- DESCRIPTION: This Group provides basic performance and exception 
--     statistics for a port. This group contains 2 tables: one for
--     the mandatory counters and one for the optional counters. 
--     These objects are based on the PortCounters attribute.
--
-- NOTE: during operation, instead of "overflowing" these counters
--     stop at all 1's (until reset by the PMA).
--**************************************************************** 
ibPmaPortCntrsInfo OBJECT IDENTIFIER ::= { ibPmaObjects 1 }  

--**************************************************************** 
-- The Mandatory Port Counters Table
--**************************************************************** 

ibPmaPortCntrsTable OBJECT-TYPE 
   SYNTAX SEQUENCE OF IbPmaPortCntrsEntry 
   MAX-ACCESS not-accessible  
   STATUS current 
   DESCRIPTION 
      "A table containing PMA Port Counters information." 
   ::= { ibPmaPortCntrsInfo 1 } 
 
ibPmaPortCntrsEntry OBJECT-TYPE 
   SYNTAX IbPmaPortCntrsEntry 
   MAX-ACCESS not-accessible 
   STATUS current 
   DESCRIPTION 
      "A conceptual row of the ibPmaPortCntrsTable containing 
       information about the basic performance and exception
       statistics for a particular data port." 
   INDEX { ibPmaPortCntrsIndex }  
   ::= { ibPmaPortCntrsTable 1 } 

IbPmaPortCntrsEntry ::= SEQUENCE { 
   ibPmaPortCntrsIndex IbDataPort,
   ibPmaSymbolErrCounter Unsigned32,
   ibPmaLinkErrRecoveryCntr Unsigned32,
   ibPmaLinkDownedCntr Unsigned32,
   ibPmaPortRcvErr Unsigned32,
   ibPmaPortRcvRemPhysErr Unsigned32,
   ibPmaPortRcvSwitchRelayErr Unsigned32,
   ibPmaPortXmitDiscard Unsigned32,
   ibPmaPortXmitConstraintErr Unsigned32,
   ibPmaPortRcvConstraintErr Unsigned32,
   ibPmaLocalLinkIntegrityErr Unsigned32,
   ibPmaExcessBufOverrunErr Unsigned32,
   ibPmaVl15Dropped Unsigned32
   }

ibPmaPortCntrsIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortCntrsEntry 1 } 

ibPmaSymbolErrCounter OBJECT-TYPE
   SYNTAX Unsigned32(0..65535)
   MAX-ACCESS read-only
   STATUS current
   DESCRIPTION
      "Total number of symbol errors detected on one or more 
       physical lanes."
   REFERENCE
      "InfiniBand Architecture Release 1.1. Vol. 1. Section 16.1.3.5;
       Table 191 PortCounters::PortSymbolErrorCounter." 
   ::= { ibPmaPortCntrsEntry 2 } 
 
ibPmaLinkErrRecoveryCntr OBJECT-TYPE
   SYNTAX Unsigned32(0..255)
   MAX-ACCESS read-only
   STATUS current
   DESCRIPTION
      "Total number of times the Port Training state machine has
       successfully completed the link error recovery process."
   REFERENCE
      "InfiniBand Architecture Release 1.1. Vol. 1. Section 16.1.3.5;
       Table 191 PortCounters::LinkErrorRecoveryCounters." 
   ::= { ibPmaPortCntrsEntry 3 } 

ibPmaLinkDownedCntr OBJECT-TYPE
   SYNTAX Unsigned32(0..255)
   MAX-ACCESS read-only
   STATUS current
   DESCRIPTION
      "Total number of times the Port Training state machine has
       failed the link error recovery process and downed the link."
   REFERENCE
      "InfiniBand Architecture Release 1.1. Vol. 1. Section 16.1.3.5;
       Table 191 PortCounters::LinkDownedCounter." 
   ::= { ibPmaPortCntrsEntry 4 } 

ibPmaPortRcvErr OBJECT-TYPE
   SYNTAX Unsigned32(0..65535)
   MAX-ACCESS read-only
   STATUS current
   DESCRIPTION
      "Total number of packets containing an error that were
       received on the port.  These errors include:
       - Local physical errors (ICRC, VCRC, FCCRC, and all physical
         errors that cause entry into the BAD PACKET of BAD PACKET
         DISCARD states of the packet receiver state machine)
       - Malformed data packet errors (LVer, length, VL)
       - Malformed link packet errors (operand, length, VL)
       - Packets discarded due to buffer overrun."
   REFERENCE
      "InfiniBand Architecture Release 1.1. Vol. 1. Section 16.1.3.5;
       Table 191 PortCounters::PortRcvErrors." 
   ::= { ibPmaPortCntrsEntry 5 } 

ibPmaPortRcvRemPhysErr OBJECT-TYPE
   SYNTAX Unsigned32(0..65535)
   MAX-ACCESS read-only
   STATUS current
   DESCRIPTION
      "Total number of packets marked with the End-of-Bad-Packets (EBP)
       delimeter received on the port."
   REFERENCE
      "InfiniBand Architecture Release 1.1. Vol. 1. Section 16.1.3.5;
       Table 191 PortCounters::PortRcvRemotePhysicalErrors."
   ::= { ibPmaPortCntrsEntry 6 } 

ibPmaPortRcvSwitchRelayErr OBJECT-TYPE
   SYNTAX Unsigned32(0..65535)
   MAX-ACCESS read-only
   STATUS current
   DESCRIPTION
      "Total number of packets received on the port that are
       discarded because they could not be forwarded by the
       switch relay.  Reasons for this include:
       - DLID mapping
       - VL mapping
       - looping (output port = input port)"
   REFERENCE
      "InfiniBand Architecture Release 1.1. Vol. 1. Section 16.1.3.5;
       Table 191 PortCounters::PortRcvSwitchRelayErrors."
   ::= { ibPmaPortCntrsEntry 7 } 

ibPmaPortXmitDiscard OBJECT-TYPE
   SYNTAX Unsigned32(0..65535)
   MAX-ACCESS read-only
   STATUS current
   DESCRIPTION
      "Total number of outbound packets discarded by the port because
       the port is down or congested.  Reasons for this include:
       - output port is in the inactive state
       - packet length exceeded neighbor MTU 
       - switch lifetime limit exceeded
       - switch HOQ limit exceeded
       May also include packets discarded while in VLStalled state."
   REFERENCE
      "InfiniBand Architecture Release 1.1. Vol. 1. Section 16.1.3.5;
       Table 191 PortCounters::PortXmitDiscards."
   ::= { ibPmaPortCntrsEntry 8 } 

ibPmaPortXmitConstraintErr OBJECT-TYPE
   SYNTAX Unsigned32(0..255)
   MAX-ACCESS read-only
   STATUS current
   DESCRIPTION
      "Total number of packets not transmitted from the port 
       for the following reasons:
       - FilterRawOutbound is true and packet is raw
       - PartitionEnforcementOutbound is true and packet fails
         partition key check or IP version check."
   REFERENCE
      "InfiniBand Architecture Release 1.1. Vol. 1. Section 16.1.3.5;
       Table 191 PortCounters::PortXmitConstraintErrors." 
   ::= { ibPmaPortCntrsEntry 9 } 

ibPmaPortRcvConstraintErr OBJECT-TYPE
   SYNTAX Unsigned32(0..255)
   MAX-ACCESS read-only
   STATUS current
   DESCRIPTION
      "Total number of packets received on the port that are
       discarded for the following reasons:
       - FilterRawInbound is true and packet is raw
       - PartitionEnforcementInbound is true and packet fails
         partition key check or IP version check."
   REFERENCE
      "InfiniBand Architecture Release 1.1. Vol. 1. Section 16.1.3.5;
       Table 191 PortCounters::PortRcvConstraintErrors." 
   ::= { ibPmaPortCntrsEntry 10 } 

ibPmaLocalLinkIntegrityErr OBJECT-TYPE
   SYNTAX Unsigned32(0..15)
   MAX-ACCESS read-only
   STATUS current
   DESCRIPTION
      "The number of times that the count of packets containing
       local physical errors exceeded the local physical errors
       threshold."
   REFERENCE
      "InfiniBand Architecture Release 1.1. Vol. 1. Section 16.1.3.5;
       Table 191 PortCounters::LocalLinkIntegrityErrors."
   ::= { ibPmaPortCntrsEntry 11 } 

ibPmaExcessBufOverrunErr OBJECT-TYPE
   SYNTAX Unsigned32(0..15)
   MAX-ACCESS read-only
   STATUS current
   DESCRIPTION
      "The number of times that overrun errors consecutive flow
       control update periods occurred with at least one overrun
       error in each period."
   REFERENCE
      "InfiniBand Architecture Release 1.1. Vol. 1. Section 16.1.3.5;
       Table 191 PortCounters::ExcessiveBufferOverrunErrors."
   ::= { ibPmaPortCntrsEntry 12 } 

ibPmaVl15Dropped OBJECT-TYPE
   SYNTAX Unsigned32(0..255)
   MAX-ACCESS read-only
   STATUS current
   DESCRIPTION
      "Number of incoming VL 15 packets dropped due to resource
       limitations on port due to lack of buffers."
   REFERENCE
      "InfiniBand Architecture Release 1.1. Vol. 1. Section 16.1.3.5;
       Table 191 PortCounters::VL15Dropped."
   ::= { ibPmaPortCntrsEntry 13 } 

--**************************************************************** 
-- The Optional Port Counters Table
--**************************************************************** 

ibPmaPortCntrsOptTable OBJECT-TYPE 
   SYNTAX SEQUENCE OF IbPmaPortCntrsOptEntry 
   MAX-ACCESS not-accessible  
   STATUS current 
   DESCRIPTION 
      "A table containing the optional PMA Port Counters information." 
   ::= { ibPmaPortCntrsInfo 2 } 

ibPmaPortCntrsOptEntry OBJECT-TYPE 
   SYNTAX IbPmaPortCntrsOptEntry 
   MAX-ACCESS not-accessible 
   STATUS current 
   DESCRIPTION 
      "A conceptual row of the ibPmaPortCntrsOptTable containing 
       information about the optional performance and exception
       statistics for a particular data port." 
   INDEX { ibPmaPortCntrsOptIndex }  
   ::= { ibPmaPortCntrsOptTable 1 }

IbPmaPortCntrsOptEntry ::= SEQUENCE { 
   ibPmaPortCntrsOptIndex IbDataPort,
   ibPmaPortXmitData Unsigned32,
   ibPmaPortRcvData Unsigned32,
   ibPmaPortXmitPkts Unsigned32,
   ibPmaPortRcvPkts Unsigned32
   }

ibPmaPortCntrsOptIndex OBJECT-TYPE 
   SYNTAX IbDataPort
   MAX-ACCESS not-accessible 
   STATUS current 
   DESCRIPTION  
      "Index that identifies the InfiniBand data port.  The IBA
       defines a range of valid data ports from 1 to N, where  
       N can have a maximum value of 254."
   ::= { ibPmaPortCntrsOptEntry 1 } 

ibPmaPortXmitData OBJECT-TYPE
   SYNTAX Unsigned32(0..65535)
   MAX-ACCESS read-only
   STATUS current
   DESCRIPTION
      "Total number of data octets divided by 4, transmitted on
       all VLs from the port.  This includes all octets between (and
       not including) the start of packet delimeter and the VCRC.  It
       excludes all link packets but may include packets containing
       errors.  NOTE: This counter is optional and should have a 0 
       value if not implemented." 
   REFERENCE
      "InfiniBand Architecture Release 1.1. Vol. 1. Section 16.1.3.5;
       Table 191 PortCounters::PortXmitData."
   ::= { ibPmaPortCntrsOptEntry 2 } 

ibPmaPortRcvData OBJECT-TYPE
   SYNTAX Unsigned32(0..65535)
   MAX-ACCESS read-only
   STATUS current
   DESCRIPTION
      "Total number of data octets divided by 4, received on
       all VLs from the port.  This includes all octets between (and
       not including) the start of packet delimeter and the VCRC.  It
       excludes all link packets but may include packets containing
       errors.  NOTE: This counter is optional and should have a 0 
       value if not implemented." 
   REFERENCE
      "InfiniBand Architecture Release 1.1. Vol. 1. Section 16.1.3.5;
       Table 191 PortCounters::PortRcvData."
   ::= { ibPmaPortCntrsOptEntry 3 } 

ibPmaPortXmitPkts OBJECT-TYPE
   SYNTAX Unsigned32(0..65535)
   MAX-ACCESS read-only
   STATUS current
   DESCRIPTION
      "Total number of packets, excluding link packets, transmitted on
       all VLs from the port.  It may include packets with errors.
       NOTE: This counter is optional and should have a 0 value if
       not implemented." 
   REFERENCE
      "InfiniBand Architecture Release 1.1. Vol. 1. Section 16.1.3.5;
       Table 191 PortCounters::PortXmitPkts."
   ::= { ibPmaPortCntrsOptEntry 4 } 

ibPmaPortRcvPkts OBJECT-TYPE
   SYNTAX Unsigned32(0..65535)
   MAX-ACCESS read-only
   STATUS current
   DESCRIPTION
      "Total number of packets, including packets containing errors
       and excluding link packets, received on all VLs on this port. 
       It may include packets with errors.  NOTE: This counter is 
       optional and should have a 0 value if not implemented." 
   REFERENCE
      "InfiniBand Architecture Release 1.1. Vol. 1. Section 16.1.3.5;
       Table 191 PortCounters::PortRcvPkts."
   ::= { ibPmaPortCntrsOptEntry 5 } 

--**************************************************************** 
-- Port Transmit and Receive Error Group
--
-- DESCRIPTION: This Group provides details for receive errors and 
--     transmit discard details for each port.  This group contains
--     three tables: The Port Receive Error Details table, The Port
--     Transmit Discard Details table, and The Port Flow Control 
--     Counters Table.
--     These three tables are optional.
--
-- NOTE: during operation, instead of "overflowing" these counters
--     stop at all 1's (until reset by the PMA).
--**************************************************************** 

ibPmaPortXmitRecvInfo OBJECT IDENTIFIER ::= { ibPmaObjects 2 }  

--**************************************************************** 
-- The Port Receive Error Details Table
--**************************************************************** 

ibPmaPortRcvErrTable OBJECT-TYPE
   SYNTAX SEQUENCE OF IbPmaPortRcvErrEntry 
   MAX-ACCESS not-accessible  
   STATUS current 
   DESCRIPTION 
      "A table containing PMA Port Receive Error information."
   ::= { ibPmaPortXmitRecvInfo 1 } 

ibPmaPortRcvErrEntry OBJECT-TYPE
   SYNTAX IbPmaPortRcvErrEntry 
   MAX-ACCESS not-accessible 
   STATUS current 
   DESCRIPTION 
      "A conceptual row of the ibPmaPortRcvErrTable containing 
       information about the receive error statistics for a 
       particular data port." 
   INDEX   { ibPmaPortRcvErrIndex }  
   ::= { ibPmaPortRcvErrTable 1 } 

IbPmaPortRcvErrEntry ::= SEQUENCE { 
   ibPmaPortRcvErrIndex IbDataPort,
   ibPmaPortRcvErrLocalPhysErrs Unsigned32,
   ibPmaPortMalformedPacketErrs Unsigned32,
   ibPmaPortBufferOverrunErrs Unsigned32,
   ibPmaPortDLIDMappingErrs Unsigned32,
   ibPmaPortVLMappingErrs Unsigned32,
   ibPmaPortLoopingErrs Unsigned32
   }

ibPmaPortRcvErrIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortRcvErrEntry 1 } 

ibPmaPortRcvErrLocalPhysErrs OBJECT-TYPE
   SYNTAX Unsigned32(0..65535)
   MAX-ACCESS read-only
   STATUS current
   DESCRIPTION
      "Total number of packets received on the port that contain local
       physical errors (ICRC, VCRC, FCCRC, and all physical errors that
       cause entry into the BAD PACKET or BAD PACKET DISCARD states of
       the packet receiver state machine)."
   REFERENCE
      "InfiniBand Architecture Release 1.1. Vol. 1. Section 16.1.4.1;
       Table 194 PortRcvErrorDetails::PortLocalPhysicalErrors."
   ::= { ibPmaPortRcvErrEntry 2 } 

ibPmaPortMalformedPacketErrs OBJECT-TYPE
   SYNTAX Unsigned32(0..65535)
   MAX-ACCESS read-only
   STATUS current
   DESCRIPTION
      "Total number of packets received on the port that contain 
       malformed packet errors.
       -data packets: LVer, length, VL
       -link packets: operand, length VL"
   REFERENCE
      "InfiniBand Architecture Release 1.1. Vol. 1. Section 16.1.4.1;
       Table 194 PortRcvErrorDetails::PortMalformedPacketErrors."
   ::= { ibPmaPortRcvErrEntry 3 } 

ibPmaPortBufferOverrunErrs OBJECT-TYPE
   SYNTAX Unsigned32(0..65535)
   MAX-ACCESS read-only
   STATUS current
   DESCRIPTION
      "Total number of packets received on the port that were 
       discarded due to buffer overrun."
   REFERENCE
      "InfiniBand Architecture Release 1.1. Vol. 1. Section 16.1.4.1;
       Table 194 PortRcvErrorDetails::PortBufferOverrunErrors."
   ::= { ibPmaPortRcvErrEntry 4 } 

ibPmaPortDLIDMappingErrs OBJECT-TYPE
   SYNTAX Unsigned32(0..65535)
   MAX-ACCESS read-only
   STATUS current
   DESCRIPTION
      "Total number of packets received on the port that were 
       discarded because they could not be forwarded by the switch
       relay due to DLID mapping errors.  This only applies to 
       switches."
   REFERENCE
      "InfiniBand Architecture Release 1.1. Vol. 1. Section 16.1.4.1;
       Table 194 PortRcvErrorDetails::PortDLIDMappingErrors."
   ::= { ibPmaPortRcvErrEntry 5 } 

ibPmaPortVLMappingErrs OBJECT-TYPE
   SYNTAX Unsigned32(0..65535)
   MAX-ACCESS read-only
   STATUS current
   DESCRIPTION
      "Total number of packets received on the port that were 
       discarded because they could not be forwarded by the switch
       relay due to VL mapping errors."
   REFERENCE
      "InfiniBand Architecture Release 1.1. Vol. 1. Section 16.1.4.1;
       Table 194 PortRcvErrorDetails::PortVLMappingErrors."
   ::= { ibPmaPortRcvErrEntry 6 } 

ibPmaPortLoopingErrs OBJECT-TYPE
   SYNTAX Unsigned32(0..65535)
   MAX-ACCESS read-only
   STATUS current
   DESCRIPTION
      "Total number of packets received on the port that were 
       discarded because they could not be forwarded by the switch
       relay due to looping errors (where the output port =
       the input port).  This only applies to switches."
   REFERENCE
      "InfiniBand Architecture Release 1.1. Vol. 1. Section 16.1.4.1;
       Table 194 PortRcvErrorDetails::PortLoopingErrors."
   ::= { ibPmaPortRcvErrEntry 7 } 

--**************************************************************** 
-- The Port Transmit Discard Details Table
--**************************************************************** 

ibPmaPortXmitDiscardTable OBJECT-TYPE
   SYNTAX SEQUENCE OF IbPmaPortXmitDiscardEntry 
   MAX-ACCESS not-accessible  
   STATUS current 
   DESCRIPTION 
      "A table containing PMA Port Transmit Discard details." 
   ::= { ibPmaPortXmitRecvInfo 2 } 

ibPmaPortXmitDiscardEntry OBJECT-TYPE
   SYNTAX IbPmaPortXmitDiscardEntry 
   MAX-ACCESS not-accessible 
   STATUS current 
   DESCRIPTION 
      "A conceptual row of the ibPmaPortXmitDiscardTable containing 
       information about the transmit discard details for a
       particular data port." 
   INDEX { ibPmaPortXmitDiscardIndex }  
   ::= { ibPmaPortXmitDiscardTable 1 } 

IbPmaPortXmitDiscardEntry ::= SEQUENCE { 
   ibPmaPortXmitDiscardIndex IbDataPort,
   ibPmaPortInactiveDiscards Unsigned32,
   ibPmaPortNeighborMtuDiscards Unsigned32,
   ibPmaPortSwLifetimeLimitDiscards Unsigned32,
   ibPmaPortSwHoqLimitDiscards Unsigned32
   }

ibPmaPortXmitDiscardIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortXmitDiscardEntry 1 } 

ibPmaPortInactiveDiscards OBJECT-TYPE
   SYNTAX Unsigned32(0..255)
   MAX-ACCESS read-only
   STATUS current
   DESCRIPTION
      "Total number of outbound packets discarded by the port because
       it is in the inactive state."
   REFERENCE
      "InfiniBand Architecture Release 1.1. Vol. 1. Section 16.1.4.2;
       Table 195 PortXmitDisacrdDetails::PortInactiveDiscards." 
   ::= { ibPmaPortXmitDiscardEntry 2 } 

ibPmaPortNeighborMtuDiscards OBJECT-TYPE
   SYNTAX Unsigned32(0..255)
   MAX-ACCESS read-only
   STATUS current
   DESCRIPTION
      "Total number of outbound packets discarded by the port because
       packet length exceeded the neighbor MTU."
   REFERENCE
      "InfiniBand Architecture Release 1.1. Vol. 1. Section 16.1.4.2;
       Table 195 PortXmitDisacrdDetails::PortNeighborMTUDiscards."
   ::= { ibPmaPortXmitDiscardEntry 3 } 

ibPmaPortSwLifetimeLimitDiscards OBJECT-TYPE
   SYNTAX Unsigned32(0..255)
   MAX-ACCESS read-only
   STATUS current
   DESCRIPTION
      "Total number of outbound packets discarded by the port because
       the switch lifetime limit was exceeded.  (This value is only
       relevant for switches; otherwise the value should be 0)."
   REFERENCE
      "InfiniBand Architecture Release 1.1. Vol. 1. Section 16.1.4.2;
       Table 195 PortXmitDisacrdDetails::PortSwLifetimeLimitDiscards."
   ::= { ibPmaPortXmitDiscardEntry 4 } 

ibPmaPortSwHoqLimitDiscards OBJECT-TYPE
   SYNTAX Unsigned32(0..255)
   MAX-ACCESS read-only
   STATUS current
   DESCRIPTION
      "Total number of outbound packets discarded by the port because
       the switch HOQ lifetime was exceeded.  (This object applies to 
       switches only. For other InfiniBand entities this should have
       a value of 0)."
   REFERENCE
      "InfiniBand Architecture Release 1.1. Vol. 1. Section 16.1.4.2;
       Table 195 PortXmitDisacrdDetails::PortSwHOQLimitDiscards."
   ::= { ibPmaPortXmitDiscardEntry 5 } 

--**************************************************************** 
-- Port Flow Control Counters Table
--**************************************************************** 

ibPmaPortFlowCtlCntrsTable OBJECT-TYPE
   SYNTAX SEQUENCE OF IbPmaPortXmitDiscardEntry 
   MAX-ACCESS not-accessible  
   STATUS current 
   DESCRIPTION 
      "A table containing PMA Port Flow Control counters
       information."
   ::= { ibPmaPortXmitRecvInfo 3 } 

ibPmaPortFlowCtlCntrsEntry OBJECT-TYPE
   SYNTAX IbPmaPortFlowCtlCntrsEntry 
   MAX-ACCESS not-accessible 
   STATUS current 
   DESCRIPTION 
      "A conceptual row of the ibPmaPortFLowCtlCntrsTable containing 
       information about the flow control statistics for a particular
       data port." 
   INDEX { ibPmaPortFlowCtlCntrsIndex }  
   ::= { ibPmaPortFlowCtlCntrsTable 1 } 

IbPmaPortFlowCtlCntrsEntry ::= SEQUENCE { 
        ibPmaPortFlowCtlCntrsIndex IbDataPort,
        ibPmaPortFlowCtlXmitFlowPkts Unsigned32,
        ibPmaPortFlowCtlRcvFlowPkts Unsigned32
   }

ibPmaPortFlowCtlCntrsIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortFlowCtlCntrsEntry 1 } 

ibPmaPortFlowCtlXmitFlowPkts OBJECT-TYPE
   SYNTAX Unsigned32(0..65535)
   MAX-ACCESS read-only
   STATUS current
   DESCRIPTION
      "Total number of flow control packets transmitted on the port."
   REFERENCE
      "InfiniBand Architecture Release 1.1 Vol. 1. Section 16.1.4.4;
       Table 197 PortFlowCtlCounters::PortXmitFlowPkts."
   ::= { ibPmaPortFlowCtlCntrsEntry 2 } 

ibPmaPortFlowCtlRcvFlowPkts OBJECT-TYPE
   SYNTAX Unsigned32(0..65535)
   MAX-ACCESS read-only
   STATUS current
   DESCRIPTION
      "Total number of flow control packets received on the port."
   REFERENCE
      "InfiniBand Architecture Release 1.1. Vol. 1. Section 16.1.4.4;
       Table 197 PortFlowCtlCounters::PortRcvFlowPkts."
   ::= { ibPmaPortFlowCtlCntrsEntry 3 } 

--**************************************************************** 
-- Port Op Code Group
--
-- DESCRIPTION: This Group provides details for port statistics
--     indexed by op code and port number.  This group contains
--     three tables: The Port Op Code Receive Counters Group, The
--     Port Op Code Virtual Lane Counters Group, and The Port Op
--     Code Virtual Lane Data Counters Group.
--     These three tables are optional.
--
-- NOTE: during operation, instead of "overflowing" these counters
--     stop at all 1's (until reset by the PMA).
--**************************************************************** 

ibPmaPortOpCodeInfo OBJECT IDENTIFIER ::= { ibPmaObjects 3 }  

--**************************************************************** 
-- Port Op Code Receive Counters Group
--**************************************************************** 
ibPmaPortOpCodeRcvCntrsTable OBJECT-TYPE         
   SYNTAX SEQUENCE OF IbPmaPortOpCodeRcvCntrsEntry 
   MAX-ACCESS not-accessible  
   STATUS current 
   DESCRIPTION 
      "A table containing PMA Port Counters per Op Code information." 
   ::= { ibPmaPortOpCodeInfo 1 } 

ibPmaPortOpCodeRcvCntrsEntry OBJECT-TYPE         
   SYNTAX IbPmaPortOpCodeRcvCntrsEntry 
   MAX-ACCESS not-accessible 
   STATUS current 
   DESCRIPTION 
      "A conceptual row of the ibPmaPortOpCodeRcvCntrsTable containing 
       information about the receive counters per op code for a 
       particular data port." 
   INDEX { ibPmaPortOpCodeRcvCntrsPortIndex, 
           ibPmaPortOpCodeRcvCntrsIndex }  
   ::= { ibPmaPortOpCodeRcvCntrsTable 1 } 

IbPmaPortOpCodeRcvCntrsEntry ::= SEQUENCE { 
      ibPmaPortOpCodeRcvCntrsPortIndex IbDataPort, 
      ibPmaPortOpCodeRcvCntrsIndex Unsigned32,
      ibPmaPortOpCodeRcvCntrsRcvPkts Counter32,
      ibPmaPortOpCodeRcvCntrsRcvData Counter32
   }

ibPmaPortOpCodeRcvCntrsPortIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortOpCodeRcvCntrsEntry 1 } 

ibPmaPortOpCodeRcvCntrsIndex OBJECT-TYPE
   SYNTAX Unsigned32(1..255)
   MAX-ACCESS not-accessible
   STATUS current
   DESCRIPTION
      "The op code for which this statistic is being reported.
       Note: this is a 1-based value."
   ::= { ibPmaPortOpCodeRcvCntrsEntry 2 } 

ibPmaPortOpCodeRcvCntrsRcvPkts OBJECT-TYPE
   SYNTAX Counter32
   MAX-ACCESS read-only
   STATUS current
   DESCRIPTION
      "Total number of packets received without error on this
       port for this op code."

   REFERENCE
      "InfiniBand Architecture Release 1.1. Vol. 1. Section 16.1.4.3;
       Table 196 PortOpRcvCounters::PortOpRcvPkts."
   ::= { ibPmaPortOpCodeRcvCntrsEntry 3 } 

ibPmaPortOpCodeRcvCntrsRcvData OBJECT-TYPE
   SYNTAX Counter32
   MAX-ACCESS read-only
   STATUS current
   DESCRIPTION
      "Total number of data octets (divided by 4) received without 
       error for all VLs on this port for this op code.  This includes
       all octets between the start of packet delimeter and the VCRC,
       exclusive. It excludes all link packets."
   REFERENCE
      "InfiniBand Architecture Release 1.1. Vol. 1. Section 16.1.4.3;
       Table 196 PortOpRcvCounters::PortOpRcvData."
   ::= { ibPmaPortOpCodeRcvCntrsEntry 4 } 

--**************************************************************** 
-- Port Op Code Virtual Lane Counters Group
--**************************************************************** 

ibPmaPortOpCodeVlCntrsTable OBJECT-TYPE         
   SYNTAX SEQUENCE OF IbPmaPortOpCodeVlCntrsEntry 
   MAX-ACCESS not-accessible  
   STATUS current 
   DESCRIPTION 
      "A table containing PMA Port virtual lane op code information." 
   ::= { ibPmaPortOpCodeInfo 2 } 

ibPmaPortOpCodeVlCntrsEntry OBJECT-TYPE         
   SYNTAX IbPmaPortOpCodeVlCntrsEntry 
   MAX-ACCESS not-accessible 
   STATUS current 
   DESCRIPTION 
      "A conceptual row of the ibPmaPortOpCodeVlCntrsTable containing 
       information about the virtual lane statistics for a particular
       data port based on op code." 
   INDEX { ibPmaPortOpCodeVlCntrsPortIndex,
           ibPmaPortOpCodeVlCntrsIndex } 
   ::= { ibPmaPortOpCodeVlCntrsTable 1 } 

IbPmaPortOpCodeVlCntrsEntry ::= SEQUENCE { 
      ibPmaPortOpCodeVlCntrsPortIndex IbDataPort, 
      ibPmaPortOpCodeVlCntrsIndex Unsigned32,
      ibPmaPortVlOpPkt0 Unsigned32,
      ibPmaPortVlOpPkt1 Unsigned32,
      ibPmaPortVlOpPkt2 Unsigned32,
      ibPmaPortVlOpPkt3 Unsigned32,
      ibPmaPortVlOpPkt4 Unsigned32,
      ibPmaPortVlOpPkt5 Unsigned32,
      ibPmaPortVlOpPkt6 Unsigned32,
      ibPmaPortVlOpPkt7 Unsigned32,
      ibPmaPortVlOpPkt8 Unsigned32,
      ibPmaPortVlOpPkt9 Unsigned32,
      ibPmaPortVlOpPkt10 Unsigned32,
      ibPmaPortVlOpPkt11 Unsigned32,
      ibPmaPortVlOpPkt12 Unsigned32,
      ibPmaPortVlOpPkt13 Unsigned32,
      ibPmaPortVlOpPkt14 Unsigned32,
      ibPmaPortVlOpPkt15 Unsigned32
   }

ibPmaPortOpCodeVlCntrsPortIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortOpCodeVlCntrsEntry 1 } 

ibPmaPortOpCodeVlCntrsIndex OBJECT-TYPE
   SYNTAX Unsigned32(1..255)
   MAX-ACCESS not-accessible
   STATUS current
   DESCRIPTION
      "The op code for which this statistic is being reported.
       Note: this is a 1-based value."
   ::= { ibPmaPortOpCodeVlCntrsEntry 2 } 

ibPmaPortVlOpPkt0 OBJECT-TYPE
   SYNTAX Unsigned32(0..65535)
   MAX-ACCESS read-only
   STATUS current
   DESCRIPTION
      "Total number of packets received without error on the port
       using this op code for Virtual Lane 0."
   REFERENCE
      "InfiniBand Architecture Release 1.1. Vol. 1. Section 16.1.4.5;
       Table 198 PortVLOpPackets::PortVLOpPacket0."
   ::= { ibPmaPortOpCodeVlCntrsEntry 3 } 

ibPmaPortVlOpPkt1 OBJECT-TYPE
   SYNTAX Unsigned32(0..65535)
   MAX-ACCESS read-only
   STATUS current
   DESCRIPTION
      "Total number of packets received without error on the port
       using this op code for Virtual Lane 1."
   REFERENCE
      "InfiniBand Architecture Release 1.1. Vol. 1. Section 16.1.4.5;
       Table 198 PortVLOpPackets::PortVLOpPacket1."
   ::= { ibPmaPortOpCodeVlCntrsEntry 4 } 

ibPmaPortVlOpPkt2 OBJECT-TYPE
   SYNTAX Unsigned32(0..65535)
   MAX-ACCESS read-only
   STATUS current
   DESCRIPTION
      "Total number of packets received without error on the port
       using this op code for Virtual Lane 2."
   REFERENCE
      "InfiniBand Architecture Release 1.1. Vol. 1. Section 16.1.4.5;
       Table 198 PortVLOpPackets::PortVLOpPacket2."
   ::= { ibPmaPortOpCodeVlCntrsEntry 5 } 

ibPmaPortVlOpPkt3 OBJECT-TYPE
   SYNTAX Unsigned32(0..65535)
   MAX-ACCESS read-only
   STATUS current
   DESCRIPTION
      "Total number of packets received without error on the port
       using this op code for Virtual Lane 3."
   REFERENCE
      "InfiniBand Architecture Release 1.1. Vol. 1. Section 16.1.4.5;
       Table 198 PortVLOpPackets::PortVLOpPacket3."
   ::= { ibPmaPortOpCodeVlCntrsEntry 6 } 

ibPmaPortVlOpPkt4 OBJECT-TYPE
   SYNTAX Unsigned32(0..65535)
   MAX-ACCESS read-only
   STATUS current
   DESCRIPTION
      "Total number of packets received without error on the port
       using this op code for Virtual Lane 4."
   REFERENCE
      "InfiniBand Architecture Release 1.1. Vol. 1. Section 16.1.4.5;
       Table 198 PortVLOpPackets::PortVLOpPacket4."
   ::= { ibPmaPortOpCodeVlCntrsEntry 7 } 

ibPmaPortVlOpPkt5 OBJECT-TYPE
   SYNTAX Unsigned32(0..65535)
   MAX-ACCESS read-only
   STATUS current
   DESCRIPTION
      "Total number of packets received without error on the port
       using this op code for Virtual Lane 5."
   REFERENCE
      "InfiniBand Architecture Release 1.1. Vol. 1. Section 16.1.4.5;
       Table 198 PortVLOpPackets::PortVLOpPacket5."
   ::= { ibPmaPortOpCodeVlCntrsEntry 8 } 

ibPmaPortVlOpPkt6 OBJECT-TYPE
   SYNTAX Unsigned32(0..65535)
   MAX-ACCESS read-only
   STATUS current
   DESCRIPTION
      "Total number of packets received without error on the port
       using this op code for Virtual Lane 6."
   REFERENCE
      "InfiniBand Architecture Release 1.1. Vol. 1. Section 16.1.4.5;
       Table 198 PortVLOpPackets::PortVLOpPacket6."
   ::= { ibPmaPortOpCodeVlCntrsEntry 9 } 

ibPmaPortVlOpPkt7 OBJECT-TYPE
   SYNTAX Unsigned32(0..65535)
   MAX-ACCESS read-only
   STATUS current
   DESCRIPTION
      "Total number of packets received without error on the port
       using this op code for Virtual Lane 7."
   REFERENCE
      "InfiniBand Architecture Release 1.1. Vol. 1. Section 16.1.4.5;
       Table 198 PortVLOpPackets::PortVLOpPacket7."
   ::= { ibPmaPortOpCodeVlCntrsEntry 10 } 

ibPmaPortVlOpPkt8 OBJECT-TYPE
   SYNTAX Unsigned32(0..65535)
   MAX-ACCESS read-only
   STATUS current
   DESCRIPTION
      "Total number of packets received without error on the port
       using this op code for Virtual Lane 8."
   REFERENCE
      "InfiniBand Architecture Release 1.1. Vol. 1. Section 16.1.4.5;
       Table 198 PortVLOpPackets::PortVLOpPacket8."
   ::= { ibPmaPortOpCodeVlCntrsEntry 11 } 

ibPmaPortVlOpPkt9 OBJECT-TYPE
   SYNTAX Unsigned32(0..65535)
   MAX-ACCESS read-only
   STATUS current
   DESCRIPTION
      "Total number of packets received without error on the port
       using this op code for Virtual Lane 9."
   REFERENCE
      "InfiniBand Architecture Release 1.1. Vol. 1. Section 16.1.4.5;
       Table 198 PortVLOpPackets::PortVLOpPacket9."
   ::= { ibPmaPortOpCodeVlCntrsEntry 12 } 

ibPmaPortVlOpPkt10 OBJECT-TYPE
   SYNTAX Unsigned32(0..65535)
   MAX-ACCESS read-only
   STATUS current
   DESCRIPTION
      "Total number of packets received without error on the port
       using this op code for Virtual Lane 10."
   REFERENCE
      "InfiniBand Architecture Release 1.1. Vol. 1. Section 16.1.4.5;
       Table 198 PortVLOpPackets::PortVLOpPacket10."
   ::= { ibPmaPortOpCodeVlCntrsEntry 13 } 

ibPmaPortVlOpPkt11 OBJECT-TYPE
   SYNTAX Unsigned32(0..65535)
   MAX-ACCESS read-only
   STATUS current
   DESCRIPTION
      "Total number of packets received without error on the port
       using this op code for Virtual Lane 11."
   REFERENCE
      "InfiniBand Architecture Release 1.1. Vol. 1. Section 16.1.4.5;
       Table 198 PortVLOpPackets::PortVLOpPacket11."
   ::= { ibPmaPortOpCodeVlCntrsEntry 14 } 

ibPmaPortVlOpPkt12 OBJECT-TYPE
   SYNTAX Unsigned32(0..65535)
   MAX-ACCESS read-only
   STATUS current
   DESCRIPTION
      "Total number of packets received without error on the port
       using this op code for Virtual Lane 12."
   REFERENCE
      "InfiniBand Architecture Release 1.1. Vol. 1. Section 16.1.4.5;
       Table 198 PortVLOpPackets::PortVLOpPacket12."
   ::= { ibPmaPortOpCodeVlCntrsEntry 15 } 

ibPmaPortVlOpPkt13 OBJECT-TYPE
   SYNTAX Unsigned32(0..65535)
   MAX-ACCESS read-only
   STATUS current
   DESCRIPTION
      "Total number of packets received without error on the port
       using this op code for Virtual Lane 13."
   REFERENCE
      "InfiniBand Architecture Release 1.1. Vol. 1. Section 16.1.4.5;
       Table 198 PortVLOpPackets::PortVLOpPacket13."
   ::= { ibPmaPortOpCodeVlCntrsEntry 16 } 

ibPmaPortVlOpPkt14 OBJECT-TYPE
   SYNTAX Unsigned32(0..65535)
   MAX-ACCESS read-only
   STATUS current
   DESCRIPTION
      "Total number of packets received without error on the port
       using this op code for Virtual Lane 14."
   REFERENCE
      "InfiniBand Architecture Release 1.1. Vol. 1. Section 16.1.4.5;
       Table 198 PortVLOpPackets::PortVLOpPacket14."
   ::= { ibPmaPortOpCodeVlCntrsEntry 17 } 

ibPmaPortVlOpPkt15 OBJECT-TYPE
   SYNTAX Unsigned32(0..65535)
   MAX-ACCESS read-only
   STATUS current
   DESCRIPTION
      "Total number of packets received without error on the port
       using this op code for Virtual Lane 15."
   REFERENCE
      "InfiniBand Architecture Release 1.1. Vol. 1. Section 16.1.4.5;
       Table 198 PortVLOpPackets::PortVLOpPacket15."
   ::= { ibPmaPortOpCodeVlCntrsEntry 18 } 

--**************************************************************** 
-- Port Op Code Virtual Lane Data Counters Table
--**************************************************************** 

ibPmaPortOpCodeVlDataCntrsTable OBJECT-TYPE
   SYNTAX SEQUENCE OF IbPmaPortOpCodeVlCntrsEntry 
   MAX-ACCESS not-accessible  
   STATUS current 
   DESCRIPTION 
      "A table containing PMA Port virtual lane op code information
       about the number of data octets received without error." 
   ::= { ibPmaPortOpCodeInfo 3 } 

ibPmaPortOpCodeVlDataCntrsEntry OBJECT-TYPE         
   SYNTAX IbPmaPortOpCodeVlDataCntrsEntry 
   MAX-ACCESS not-accessible 
   STATUS current 
   DESCRIPTION 
      "A conceptual row of the ibPmaPortCntrsTable containing 
       information about the basic performance and exception
       statistics for a particular data port." 
   INDEX { ibPmaPortOpCodeVlDataPortIndex, 
           ibPmaPortOpCodeVlDataIndex }
   ::= { ibPmaPortOpCodeVlDataCntrsTable 1 } 

IbPmaPortOpCodeVlDataCntrsEntry ::= SEQUENCE { 
      ibPmaPortOpCodeVlDataPortIndex IbDataPort, 
      ibPmaPortOpCodeVlDataIndex Unsigned32,
      ibPmaPortVlOpData0 Counter32,
      ibPmaPortVlOpData1 Counter32,
      ibPmaPortVlOpData2 Counter32,
      ibPmaPortVlOpData3 Counter32,
      ibPmaPortVlOpData4 Counter32,
      ibPmaPortVlOpData5 Counter32,
      ibPmaPortVlOpData6 Counter32,
      ibPmaPortVlOpData7 Counter32,
      ibPmaPortVlOpData8 Counter32,
      ibPmaPortVlOpData9 Counter32,
      ibPmaPortVlOpData10 Counter32,
      ibPmaPortVlOpData11 Counter32,
      ibPmaPortVlOpData12 Counter32,
      ibPmaPortVlOpData13 Counter32,
      ibPmaPortVlOpData14 Counter32,
      ibPmaPortVlOpData15 Counter32
      } 

ibPmaPortOpCodeVlDataPortIndex OBJECT-TYPE
   SYNTAX IbDataPort
   MAX-ACCESS not-accessible 
   STATUS current 
   DESCRIPTION  
      "Index that identifies the InfiniBand data port.  The IBA
       defines a range of valid data ports from 1 to N, where  
       N can have a maximum value of 254." 
   ::= { ibPmaPortOpCodeVlDataCntrsEntry 1 } 

ibPmaPortOpCodeVlDataIndex OBJECT-TYPE
   SYNTAX Unsigned32(1..255)
   MAX-ACCESS not-accessible
   STATUS current
   DESCRIPTION
      "The op code for which this statistic is being reported.
       Note: this is a 1-based value."
   ::= { ibPmaPortOpCodeVlDataCntrsEntry 2 } 

ibPmaPortVlOpData0 OBJECT-TYPE
   SYNTAX Counter32
   MAX-ACCESS read-only
   STATUS current
   DESCRIPTION
      "Total number of data octets (divided by 4) that were received on
       VL 0 for this port and op code.  This count includes all octets
       between the start of the packet and VCRC, exclusive.  It excludes
       all link packets."
   REFERENCE
      "InfiniBand Architecture Release 1.1. Vol. 1. Section 16.1.4.6;
       Table 199 PortVLOpData::PortVLOpData0."
   ::= { ibPmaPortOpCodeVlDataCntrsEntry 3 } 

ibPmaPortVlOpData1 OBJECT-TYPE
   SYNTAX Counter32
   MAX-ACCESS read-only
   STATUS current
   DESCRIPTION
      "Total number of data octets (divided by 4) that were received on
       VL 1 for this port and op code.  This count includes all octets
       between the start of the packet and VCRC, exclusive.  It excludes
       all link packets."
   REFERENCE
      "InfiniBand Architecture Release 1.1. Vol. 1. Section 16.1.4.6;
       Table 199 PortVLOpData::PortVLOpData1."
   ::= { ibPmaPortOpCodeVlDataCntrsEntry 4 } 

ibPmaPortVlOpData2 OBJECT-TYPE
   SYNTAX Counter32
   MAX-ACCESS read-only
   STATUS current
   DESCRIPTION
      "Total number of data octets (divided by 4) that were received on
       VL 2 for this port and op code.  This count includes all octets
       between the start of the packet and VCRC, exclusive.  It excludes
       all link packets."
   REFERENCE
      "InfiniBand Architecture Release 1.1. Vol. 1. Section 16.1.4.6;
       Table 199 PortVLOpData::PortVLOpData2."
   ::= { ibPmaPortOpCodeVlDataCntrsEntry 5 } 

ibPmaPortVlOpData3 OBJECT-TYPE
   SYNTAX Counter32
   MAX-ACCESS read-only
   STATUS current
   DESCRIPTION
      "Total number of data octets (divided by 4) that were received on
       VL 3 for this port and op code.  This count includes all octets
       between the start of the packet and VCRC, exclusive.  It excludes
       all link packets."
   REFERENCE
      "InfiniBand Architecture Release 1.1. Vol. 1. Section 16.1.4.6;
       Table 199 PortVLOpData::PortVLOpData3."
   ::= { ibPmaPortOpCodeVlDataCntrsEntry 6 } 

ibPmaPortVlOpData4 OBJECT-TYPE
   SYNTAX Counter32
   MAX-ACCESS read-only
   STATUS current
   DESCRIPTION
      "Total number of data octets (divided by 4) that were received on
       VL 4 for this port and op code.  This count includes all octets
       between the start of the packet and VCRC, exclusive.  It excludes
       all link packets."
   REFERENCE
      "InfiniBand Architecture Release 1.1. Vol. 1. Section 16.1.4.6;
       Table 199 PortVLOpData::PortVLOpData4."
   ::= { ibPmaPortOpCodeVlDataCntrsEntry 7 } 

ibPmaPortVlOpData5 OBJECT-TYPE
   SYNTAX Counter32
   MAX-ACCESS read-only
   STATUS current
   DESCRIPTION
      "Total number of data octets (divided by 4) that were received on
       VL 5 for this port and op code.  This count includes all octets
       between the start of the packet and VCRC, exclusive.  It excludes
       all link packets."
   REFERENCE
      "InfiniBand Architecture Release 1.1. Vol. 1. Section 16.1.4.6;
       Table 199 PortVLOpData::PortVLOpData5."
   ::= { ibPmaPortOpCodeVlDataCntrsEntry 8 } 

ibPmaPortVlOpData6 OBJECT-TYPE
   SYNTAX Counter32
   MAX-ACCESS read-only
   STATUS current
   DESCRIPTION
      "Total number of data octets (divided by 4) that were received on
       VL 6 for this port and op code.  This count includes all octets
       between the start of the packet and VCRC, exclusive.  It excludes
       all link packets."
   REFERENCE
      "InfiniBand Architecture Release 1.1. Vol. 1. Section 16.1.4.6;
       Table 199 PortVLOpData::PortVLOpData6."
   ::= { ibPmaPortOpCodeVlDataCntrsEntry 9 } 

ibPmaPortVlOpData7 OBJECT-TYPE
   SYNTAX Counter32
   MAX-ACCESS read-only
   STATUS current
   DESCRIPTION
      "Total number of data octets (divided by 4) that were received on
       VL 7 for this port and op code.  This count includes all octets
       between the start of the packet and VCRC, exclusive.  It excludes
       all link packets."
   REFERENCE
      "InfiniBand Architecture Release 1.1. Vol. 1. Section 16.1.4.6;
       Table 199 PortVLOpData::PortVLOpData7."
   ::= { ibPmaPortOpCodeVlDataCntrsEntry 10 } 

ibPmaPortVlOpData8 OBJECT-TYPE
   SYNTAX Counter32
   MAX-ACCESS read-only
   STATUS current
   DESCRIPTION
      "Total number of data octets (divided by 4) that were received on
       VL 8 for this port and op code.  This count includes all octets
       between the start of the packet and VCRC, exclusive.  It excludes
       all link packets."
   REFERENCE
      "InfiniBand Architecture Release 1.1. Vol. 1. Section 16.1.4.6;
       Table 199 PortVLOpData::PortVLOpData8."
   ::= { ibPmaPortOpCodeVlDataCntrsEntry 11 } 

ibPmaPortVlOpData9 OBJECT-TYPE
   SYNTAX Counter32
   MAX-ACCESS read-only
   STATUS current
   DESCRIPTION
      "Total number of data octets (divided by 4) that were received on
       VL 9 for this port and op code.  This count includes all octets
       between the start of the packet and VCRC, exclusive.  It excludes
       all link packets."
   REFERENCE
      "InfiniBand Architecture Release 1.1. Vol. 1. Section 16.1.4.6;
       Table 199 PortVLOpData::PortVLOpData9."
   ::= { ibPmaPortOpCodeVlDataCntrsEntry 12 } 

ibPmaPortVlOpData10 OBJECT-TYPE
   SYNTAX Counter32
   MAX-ACCESS read-only
   STATUS current
   DESCRIPTION
      "Total number of data octets (divided by 4) that were received on
       VL 10 for this port and op code.  This count includes all octets
       between the start of the packet and VCRC, exclusive.  It excludes
       all link packets."
   REFERENCE
      "InfiniBand Architecture Release 1.1. Vol. 1. Section 16.1.4.6;
       Table 199 PortVLOpData::PortVLOpData10."
   ::= { ibPmaPortOpCodeVlDataCntrsEntry 13 } 

ibPmaPortVlOpData11 OBJECT-TYPE
   SYNTAX Counter32
   MAX-ACCESS read-only
   STATUS current
   DESCRIPTION
      "Total number of data octets (divided by 4) that were received on
       VL 11 for this port and op code.  This count includes all octets
       between the start of the packet and VCRC, exclusive.  It excludes
       all link packets."
   REFERENCE
      "InfiniBand Architecture Release 1.1. Vol. 1. Section 16.1.4.6;
       Table 199 PortVLOpData::PortVLOpData11."
   ::= { ibPmaPortOpCodeVlDataCntrsEntry 14 } 

ibPmaPortVlOpData12 OBJECT-TYPE
   SYNTAX Counter32
   MAX-ACCESS read-only
   STATUS current
   DESCRIPTION
      "Total number of data octets (divided by 4) that were received on
       VL 12 for this port and op code.  This count includes all octets
       between the start of the packet and VCRC, exclusive.  It excludes
       all link packets."
   REFERENCE
      "InfiniBand Architecture Release 1.1. Vol. 1. Section 16.1.4.6;
       Table 199 PortVLOpData::PortVLOpData12."
   ::= { ibPmaPortOpCodeVlDataCntrsEntry 15 } 

ibPmaPortVlOpData13 OBJECT-TYPE
   SYNTAX Counter32
   MAX-ACCESS read-only
   STATUS current
   DESCRIPTION
      "Total number of data octets (divided by 4) that were received on
       VL 13 for this port and op code.  This count includes all octets
       between the start of the packet and VCRC, exclusive.  It excludes
       all link packets."

   REFERENCE
      "InfiniBand Architecture Release 1.1. Vol. 1. Section 16.1.4.6;
       Table 199 PortVLOpData::PortVLOpData13."
   ::= { ibPmaPortOpCodeVlDataCntrsEntry 16 } 

ibPmaPortVlOpData14 OBJECT-TYPE
   SYNTAX Counter32
   MAX-ACCESS read-only
   STATUS current
   DESCRIPTION
      "Total number of data octets (divided by 4) that were received on
       VL 14 for this port and op code.  This count includes all octets
       between the start of the packet and VCRC, exclusive.  It excludes
       all link packets."
   REFERENCE
      "InfiniBand Architecture Release 1.1. Vol. 1. Section 16.1.4.6;
       Table 199 PortVLOpData::PortVLOpData14."
   ::= { ibPmaPortOpCodeVlDataCntrsEntry 17 } 

ibPmaPortVlOpData15 OBJECT-TYPE
   SYNTAX Counter32
   MAX-ACCESS read-only
   STATUS current
   DESCRIPTION
      "Total number of data octets (divided by 4) that were received on
       VL 15 for this port and op code.  This count includes all octets
       between the start of the packet and VCRC, exclusive.  It excludes
       all link packets."
   REFERENCE
      "InfiniBand Architecture Release 1.1. Vol. 1. Section 16.1.4.6;
       Table 199 PortVLOpData::PortVLOpData15."
   ::= { ibPmaPortOpCodeVlDataCntrsEntry 18 } 

--**************************************************************** 
-- Port Virtual Lane Group
--
-- DESCRIPTION: This Group provides details for port statistics
--     indexed by the virtual lane within the port.  This group
--     contains three tables: The Port Virtual Lane Transmit Flow
--     Control Error Table, The Port Virtual Lane Transmit Wait
--     Counters Table, and The Port Virtual Lane Software Congestion
--     Table.
--     These three tables are optional.
--
-- NOTE: during operation, instead of "overflowing" these counters
--     stop at all 1's (until reset by the PMA).
--**************************************************************** 

ibPmaPortVlInfo OBJECT IDENTIFIER ::= { ibPmaObjects 4 }  

--**************************************************************** 
-- Port Virtual Lane Transmit Flow Control Error Table
--**************************************************************** 
ibPmaPortVlXmitFCUpErrTable OBJECT-TYPE  
   SYNTAX SEQUENCE OF IbPmaPortCntrsEntry 
   MAX-ACCESS not-accessible  
   STATUS current 
   DESCRIPTION 
      "A table containing PMA Port Virtual Lane Flow Control update
       errors for a particular port." 
   ::= { ibPmaPortVlInfo 1 } 

ibPmaPortVlXmitFCUpErrEntry OBJECT-TYPE 
   SYNTAX IbPmaPortVlXmitFCUpErrEntry 
   MAX-ACCESS not-accessible 
   STATUS current 
   DESCRIPTION 
      "A conceptual row of the ibPmaPortVlXmitFCUpErrTable containing 
       information about the transmit flow control error 
       statistics for the virtual lanes on a particular data port." 
   INDEX { ibPmaPortVlXmitFCUpErrPortIndex }  
   ::= { ibPmaPortVlXmitFCUpErrTable 1 } 

IbPmaPortVlXmitFCUpErrEntry ::= SEQUENCE { 
     ibPmaPortVlXmitFCUpErrPortIndex IbDataPort,
     ibPmaPortVlXmitFCUpErr0 Unsigned32,
     ibPmaPortVlXmitFCUpErr1 Unsigned32,
     ibPmaPortVlXmitFCUpErr2 Unsigned32,
     ibPmaPortVlXmitFCUpErr3 Unsigned32,
     ibPmaPortVlXmitFCUpErr4 Unsigned32,
     ibPmaPortVlXmitFCUpErr5 Unsigned32,
     ibPmaPortVlXmitFCUpErr6 Unsigned32,
     ibPmaPortVlXmitFCUpErr7 Unsigned32,
     ibPmaPortVlXmitFCUpErr8 Unsigned32,
     ibPmaPortVlXmitFCUpErr9 Unsigned32,
     ibPmaPortVlXmitFCUpErr10 Unsigned32,
     ibPmaPortVlXmitFCUpErr11 Unsigned32,
     ibPmaPortVlXmitFCUpErr12 Unsigned32,
     ibPmaPortVlXmitFCUpErr13 Unsigned32,
     ibPmaPortVlXmitFCUpErr14 Unsigned32,
     ibPmaPortVlXmitFCUpErr15 Unsigned32
     }

ibPmaPortVlXmitFCUpErrPortIndex OBJECT-TYPE
   SYNTAX IbDataPort
   MAX-ACCESS not-accessible 
   STATUS current 
   DESCRIPTION  
      "Index that identifies the InfiniBand data port.  The IBA
       defines a range of valid data ports from 1 to N, where  
       N can have a maximum value of 254." 
   ::= { ibPmaPortVlXmitFCUpErrEntry 1 } 

ibPmaPortVlXmitFCUpErr0 OBJECT-TYPE
   SYNTAX Unsigned32(0..255)
   MAX-ACCESS read-only
   STATUS current
   DESCRIPTION
      "Total number of flow control update errors on VL 0 for
       this port."
   REFERENCE
      "InfiniBand Architecture Release 1.1. Vol. 1. 
       Section 16.1.4.7; Table 200 
       PortVLXmitFlowCtlUpdateErrors::PortVLXmitFlowCtlUpdateErrors0."
   ::= { ibPmaPortVlXmitFCUpErrEntry 2 } 

ibPmaPortVlXmitFCUpErr1 OBJECT-TYPE
   SYNTAX Unsigned32(0..255)
   MAX-ACCESS read-only
   STATUS current
   DESCRIPTION
      "Total number of flow control update errors on VL 1 for
       this port."
   REFERENCE
      "InfiniBand Architecture Release 1.1. Vol. 1. 
       Section 16.1.4.7; Table 200 
       PortVLXmitFlowCtlUpdateErrors::PortVLXmitFlowCtlUpdateErrors1."
   ::= { ibPmaPortVlXmitFCUpErrEntry 3 } 

ibPmaPortVlXmitFCUpErr2 OBJECT-TYPE
   SYNTAX Unsigned32(0..255)
   MAX-ACCESS read-only
   STATUS current
   DESCRIPTION
      "Total number of flow control update errors on VL 2 for
       this port."
   REFERENCE
      "InfiniBand Architecture Release 1.1. Vol. 1. 
       Section 16.1.4.7; Table 200 
       PortVLXmitFlowCtlUpdateErrors::PortVLXmitFlowCtlUpdateErrors2."
   ::= { ibPmaPortVlXmitFCUpErrEntry 4 } 

ibPmaPortVlXmitFCUpErr3 OBJECT-TYPE
   SYNTAX Unsigned32(0..255)
   MAX-ACCESS read-only
   STATUS current
   DESCRIPTION
      "Total number of flow control update errors on VL 3 for
       this port."
   REFERENCE
      "InfiniBand Architecture Release 1.1. Vol. 1. 
       Section 16.1.4.7; Table 200 
       PortVLXmitFlowCtlUpdateErrors::PortVLXmitFlowCtlUpdateErrors3."
   ::= { ibPmaPortVlXmitFCUpErrEntry 5 } 

ibPmaPortVlXmitFCUpErr4 OBJECT-TYPE
   SYNTAX Unsigned32(0..255)
   MAX-ACCESS read-only
   STATUS current
   DESCRIPTION
      "Total number of flow control update errors on VL 4 for
       this port."
   REFERENCE
      "InfiniBand Architecture Release 1.1. Vol. 1. 
       Section 16.1.4.7; Table 200 
       PortVLXmitFlowCtlUpdateErrors::PortVLXmitFlowCtlUpdateErrors4."
   ::= { ibPmaPortVlXmitFCUpErrEntry 6 } 

ibPmaPortVlXmitFCUpErr5 OBJECT-TYPE
   SYNTAX Unsigned32(0..255)
   MAX-ACCESS read-only
   STATUS current
   DESCRIPTION
      "Total number of flow control update errors on VL 5 for
       this port."
   REFERENCE
      "InfiniBand Architecture Release 1.1. Vol. 1. 
       Section 16.1.4.7; Table 200 
       PortVLXmitFlowCtlUpdateErrors::PortVLXmitFlowCtlUpdateErrors5."
   ::= { ibPmaPortVlXmitFCUpErrEntry 7 } 

ibPmaPortVlXmitFCUpErr6 OBJECT-TYPE
   SYNTAX Unsigned32(0..255)
   MAX-ACCESS read-only
   STATUS current
   DESCRIPTION
      "Total number of flow control update errors on VL 6 for
       this port."
   REFERENCE
      "InfiniBand Architecture Release 1.1. Vol. 1. 
       Section 16.1.4.7; Table 200 
       PortVLXmitFlowCtlUpdateErrors::PortVLXmitFlowCtlUpdateErrors6."
   ::= { ibPmaPortVlXmitFCUpErrEntry 8 } 

ibPmaPortVlXmitFCUpErr7 OBJECT-TYPE
   SYNTAX Unsigned32(0..255)
   MAX-ACCESS read-only
   STATUS current
   DESCRIPTION
      "Total number of flow control update errors on VL 7 for
       this port."
   REFERENCE
      "InfiniBand Architecture Release 1.1. Vol. 1. 
       Section 16.1.4.7; Table 200 
       PortVLXmitFlowCtlUpdateErrors::PortVLXmitFlowCtlUpdateErrors7."
   ::= { ibPmaPortVlXmitFCUpErrEntry 9 } 

ibPmaPortVlXmitFCUpErr8 OBJECT-TYPE
   SYNTAX Unsigned32(0..255)
   MAX-ACCESS read-only
   STATUS current
   DESCRIPTION
      "Total number of flow control update errors on VL 8 for
       this port."
   REFERENCE
      "InfiniBand Architecture Release 1.1. Vol. 1. 
       Section 16.1.4.7; Table 200 
       PortVLXmitFlowCtlUpdateErrors::PortVLXmitFlowCtlUpdateErrors8."
   ::= { ibPmaPortVlXmitFCUpErrEntry 10 } 

ibPmaPortVlXmitFCUpErr9 OBJECT-TYPE
   SYNTAX Unsigned32(0..255)
   MAX-ACCESS read-only
   STATUS current
   DESCRIPTION
      "Total number of flow control update errors on VL 9 for
       this port."
   REFERENCE
      "InfiniBand Architecture Release 1.1. Vol. 1. 
       Section 16.1.4.7; Table 200 
       PortVLXmitFlowCtlUpdateErrors::PortVLXmitFlowCtlUpdateErrors9."
   ::= { ibPmaPortVlXmitFCUpErrEntry 11 } 

ibPmaPortVlXmitFCUpErr10 OBJECT-TYPE
   SYNTAX Unsigned32(0..255)
   MAX-ACCESS read-only
   STATUS current
   DESCRIPTION
      "Total number of flow control update errors on VL 10 for
       this port."
   REFERENCE
      "InfiniBand Architecture Release 1.1. Vol. 1. 
       Section 16.1.4.7; Table 200 
       PortVLXmitFlowCtlUpdateErrors::PortVLXmitFlowCtlUpdateErrors10."
   ::= { ibPmaPortVlXmitFCUpErrEntry 12 } 

ibPmaPortVlXmitFCUpErr11 OBJECT-TYPE
   SYNTAX Unsigned32(0..255)
   MAX-ACCESS read-only
   STATUS current
   DESCRIPTION
      "Total number of flow control update errors on VL 11 for
       this port."
   REFERENCE
      "InfiniBand Architecture Release 1.1. Vol. 1. 
       Section 16.1.4.7; Table 200 
       PortVLXmitFlowCtlUpdateErrors::PortVLXmitFlowCtlUpdateErrors11."
   ::= { ibPmaPortVlXmitFCUpErrEntry 13 } 

ibPmaPortVlXmitFCUpErr12 OBJECT-TYPE
   SYNTAX Unsigned32(0..255)
   MAX-ACCESS read-only
   STATUS current
   DESCRIPTION
      "Total number of flow control update errors on VL 12 for
       this port."
   REFERENCE
      "InfiniBand Architecture Release 1.1. Vol. 1. 
       Section 16.1.4.7; Table 200 
       PortVLXmitFlowCtlUpdateErrors::PortVLXmitFlowCtlUpdateErrors12."
   ::= { ibPmaPortVlXmitFCUpErrEntry 14 } 

ibPmaPortVlXmitFCUpErr13 OBJECT-TYPE
   SYNTAX Unsigned32(0..255)
   MAX-ACCESS read-only
   STATUS current
   DESCRIPTION
      "Total number of flow control update errors on VL 13 for
       this port."
   REFERENCE
      "InfiniBand Architecture Release 1.1. Vol. 1. 
       Section 16.1.4.7; Table 200 
       PortVLXmitFlowCtlUpdateErrors::PortVLXmitFlowCtlUpdateErrors13."
   ::= { ibPmaPortVlXmitFCUpErrEntry 15 } 

ibPmaPortVlXmitFCUpErr14 OBJECT-TYPE
   SYNTAX Unsigned32(0..255)
   MAX-ACCESS read-only
   STATUS current
   DESCRIPTION
      "Total number of flow control update errors on VL 14 for
       this port."
   REFERENCE
      "InfiniBand Architecture Release 1.1. Vol. 1. 
       Section 16.1.4.7; Table 200 
       PortVLXmitFlowCtlUpdateErrors::PortVLXmitFlowCtlUpdateErrors14."
   ::= { ibPmaPortVlXmitFCUpErrEntry 16 } 

ibPmaPortVlXmitFCUpErr15 OBJECT-TYPE
   SYNTAX Unsigned32(0..255)
   MAX-ACCESS read-only
   STATUS current
   DESCRIPTION
      "Total number of flow control update errors on VL 15 for
       this port."
   REFERENCE
      "InfiniBand Architecture Release 1.1. Vol. 1. 
       Section 16.1.4.7; Table 200 
       PortVLXmitFlowCtlUpdateErrors::PortVLXmitFlowCtlUpdateErrors15."
   ::= { ibPmaPortVlXmitFCUpErrEntry 17 } 

--**************************************************************** 
-- Port Virtual Lane Transmit Wait Counters Table
--**************************************************************** 

ibPmaPortVlXmitWaitCntrsTable OBJECT-TYPE  
   SYNTAX SEQUENCE OF IbPmaPortVlXmitWaitCntrsEntry 
   MAX-ACCESS not-accessible  
   STATUS current 
   DESCRIPTION 
      "A table containing PMA Port Virtual Lane Tranmsit Wait Counters
       information." 
   ::= { ibPmaPortVlInfo 2 } 

ibPmaPortVlXmitWaitCntrsEntry OBJECT-TYPE
   SYNTAX IbPmaPortVlXmitWaitCntrsEntry 
   MAX-ACCESS not-accessible 
   STATUS current 
   DESCRIPTION 
      "A conceptual row of the ibPmaPortVlXmitWaitCntrsTable 
       containing information about the transmit wait counters for     
       a virtual lane for a particular data port." 
   INDEX   { ibPmaPortVlXmitWaitCntrsIndex }  
   ::= { ibPmaPortVlXmitWaitCntrsTable 1 } 

IbPmaPortVlXmitWaitCntrsEntry ::= SEQUENCE { 
     ibPmaPortVlXmitWaitCntrsIndex IbDataPort,
     ibPmaPortVlXmitWait0 Unsigned32,
     ibPmaPortVlXmitWait1 Unsigned32,
     ibPmaPortVlXmitWait2 Unsigned32,
     ibPmaPortVlXmitWait3 Unsigned32,
     ibPmaPortVlXmitWait4 Unsigned32,
     ibPmaPortVlXmitWait5 Unsigned32,
     ibPmaPortVlXmitWait6 Unsigned32,
     ibPmaPortVlXmitWait7 Unsigned32,
     ibPmaPortVlXmitWait8 Unsigned32,
     ibPmaPortVlXmitWait9 Unsigned32,
     ibPmaPortVlXmitWait10 Unsigned32,
     ibPmaPortVlXmitWait11 Unsigned32,
     ibPmaPortVlXmitWait12 Unsigned32,
     ibPmaPortVlXmitWait13 Unsigned32,
     ibPmaPortVlXmitWait14 Unsigned32,
     ibPmaPortVlXmitWait15 Unsigned32
     }

ibPmaPortVlXmitWaitCntrsIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortVlXmitWaitCntrsEntry 1 } 

ibPmaPortVlXmitWait0 OBJECT-TYPE
   SYNTAX Unsigned32(0..255)
   MAX-ACCESS read-only
   STATUS current
   DESCRIPTION
      "Total number of ticks during which the port had data to transmit
       on VL0 but no data was sent during the entire tick either because
       of insufficient credits or because of lack of arbitration."
   REFERENCE
      "InfiniBand Architecture Release 1.1. Vol. 1. Section 16.1.4.6;
       Table 201 PortVLXmitWaitCounters::PortVLXmitWait0."
   ::= { ibPmaPortVlXmitWaitCntrsEntry 2 } 

ibPmaPortVlXmitWait1 OBJECT-TYPE
   SYNTAX Unsigned32(0..255)
   MAX-ACCESS read-only
   STATUS current
   DESCRIPTION
      "Total number of ticks during which the port had data to transmit
       on VL1 but no data was sent during the entire tick either because
       of insufficient credits or because of lack of arbitration."
   REFERENCE
      "InfiniBand Architecture Release 1.1. Vol. 1. Section 16.1.4.6;
       Table 201 PortVLXmitWaitCounters::PortVLXmitWait1."
   ::= { ibPmaPortVlXmitWaitCntrsEntry 3 } 

ibPmaPortVlXmitWait2 OBJECT-TYPE
   SYNTAX Unsigned32(0..255)
   MAX-ACCESS read-only
   STATUS current
   DESCRIPTION
      "Total number of ticks during which the port had data to transmit
       on VL2 but no data was sent during the entire tick either because
       of insufficient credits or because of lack of arbitration."
   REFERENCE
      "InfiniBand Architecture Release 1.1. Vol. 1. Section 16.1.4.6;
       Table 201 PortVLXmitWaitCounters::PortVLXmitWait2."
   ::= { ibPmaPortVlXmitWaitCntrsEntry 4 } 

ibPmaPortVlXmitWait3 OBJECT-TYPE
   SYNTAX Unsigned32(0..255)
   MAX-ACCESS read-only
   STATUS current
   DESCRIPTION
      "Total number of ticks during which the port had data to transmit
       on VL3 but no data was sent during the entire tick either because
       of insufficient credits or because of lack of arbitration."
   REFERENCE
      "InfiniBand Architecture Release 1.1. Vol. 1. Section 16.1.4.6;
       Table 201 PortVLXmitWaitCounters::PortVLXmitWait3."
   ::= { ibPmaPortVlXmitWaitCntrsEntry 5 } 

ibPmaPortVlXmitWait4 OBJECT-TYPE
   SYNTAX Unsigned32(0..255)
   MAX-ACCESS read-only
   STATUS current
   DESCRIPTION
      "Total number of ticks during which the port had data to transmit
       on VL4 but no data was sent during the entire tick either because
       of insufficient credits or because of lack of arbitration."
   REFERENCE
      "InfiniBand Architecture Release 1.1. Vol. 1. Section 16.1.4.6;
       Table 201 PortVLXmitWaitCounters::PortVLXmitWait4."
   ::= { ibPmaPortVlXmitWaitCntrsEntry 6 } 

ibPmaPortVlXmitWait5 OBJECT-TYPE
   SYNTAX Unsigned32(0..255)
   MAX-ACCESS read-only
   STATUS current
   DESCRIPTION
      "Total number of ticks during which the port had data to transmit
       on VL5 but no data was sent during the entire tick either because
       of insufficient credits or because of lack of arbitration."
   REFERENCE
      "InfiniBand Architecture Release 1.1. Vol. 1. Section 16.1.4.6;
       Table 201 PortVLXmitWaitCounters::PortVLXmitWait5."
   ::= { ibPmaPortVlXmitWaitCntrsEntry 7 } 

ibPmaPortVlXmitWait6 OBJECT-TYPE
   SYNTAX Unsigned32(0..255)
   MAX-ACCESS read-only
   STATUS current
   DESCRIPTION
      "Total number of ticks during which the port had data to transmit
       on VL6 but no data was sent during the entire tick either because
       of insufficient credits or because of lack of arbitration."
   REFERENCE
      "InfiniBand Architecture Release 1.1. Vol. 1. Section 16.1.4.6;
       Table 201 PortVLXmitWaitCounters::PortVLXmitWait6."
   ::= { ibPmaPortVlXmitWaitCntrsEntry 8 } 

ibPmaPortVlXmitWait7 OBJECT-TYPE
   SYNTAX Unsigned32(0..255)
   MAX-ACCESS read-only
   STATUS current
   DESCRIPTION
      "Total number of ticks during which the port had data to transmit
       on VL7 but no data was sent during the entire tick either because
       of insufficient credits or because of lack of arbitration."
   REFERENCE
      "InfiniBand Architecture Release 1.1. Vol. 1. Section 16.1.4.6;
       Table 201 PortVLXmitWaitCounters::PortVLXmitWait7."
   ::= { ibPmaPortVlXmitWaitCntrsEntry 9 } 

ibPmaPortVlXmitWait8 OBJECT-TYPE
   SYNTAX Unsigned32(0..255)
   MAX-ACCESS read-only
   STATUS current
   DESCRIPTION
      "Total number of ticks during which the port had data to transmit
       on VL8 but no data was sent during the entire tick either because
       of insufficient credits or because of lack of arbitration."

   REFERENCE
      "InfiniBand Architecture Release 1.1. Vol. 1. Section 16.1.4.6;
       Table 201 PortVLXmitWaitCounters::PortVLXmitWait8."
   ::= { ibPmaPortVlXmitWaitCntrsEntry 10 } 

ibPmaPortVlXmitWait9 OBJECT-TYPE
   SYNTAX Unsigned32(0..255)
   MAX-ACCESS read-only
   STATUS current
   DESCRIPTION
      "Total number of ticks during which the port had data to transmit
       on VL9 but no data was sent during the entire tick either because
       of insufficient credits or because of lack of arbitration."
   REFERENCE
      "InfiniBand Architecture Release 1.1. Vol. 1. Section 16.1.4.6;
       Table 201 PortVLXmitWaitCounters::PortVLXmitWait9."
   ::= { ibPmaPortVlXmitWaitCntrsEntry 11 } 

ibPmaPortVlXmitWait10 OBJECT-TYPE
   SYNTAX Unsigned32(0..255)
   MAX-ACCESS read-only
   STATUS current
   DESCRIPTION
      "Total number of ticks during which the port had data to transmit
       on VL10 but no data was sent during the entire tick because of 
       insufficient credits or because of lack of arbitration."
   REFERENCE
      "InfiniBand Architecture Release 1.1. Vol. 1. Section 16.1.4.6;
       Table 201 PortVLXmitWaitCounters::PortVLXmitWait10."
   ::= { ibPmaPortVlXmitWaitCntrsEntry 12 } 

ibPmaPortVlXmitWait11 OBJECT-TYPE
   SYNTAX Unsigned32(0..255)
   MAX-ACCESS read-only
   STATUS current
   DESCRIPTION
      "Total number of ticks during which the port had data to transmit
       on VL11 but no data was sent during the entire tick because of 
       insufficient credits or because of lack of arbitration."
   REFERENCE
      "InfiniBand Architecture Release 1.1. Vol. 1. Section 16.1.4.6;
       Table 201 PortVLXmitWaitCounters::PortVLXmitWait11."
   ::= { ibPmaPortVlXmitWaitCntrsEntry 13 } 

ibPmaPortVlXmitWait12 OBJECT-TYPE
   SYNTAX Unsigned32(0..255)
   MAX-ACCESS read-only
   STATUS current
   DESCRIPTION
      "Total number of ticks during which the port had data to transmit
       on VL12 but no data was sent during the entire tick because of 
       insufficient credits or because of lack of arbitration."
   REFERENCE
      "InfiniBand Architecture Release 1.1. Vol. 1. Section 16.1.4.6;
       Table 201 PortVLXmitWaitCounters::PortVLXmitWait12."
   ::= { ibPmaPortVlXmitWaitCntrsEntry 14 } 

ibPmaPortVlXmitWait13 OBJECT-TYPE
   SYNTAX Unsigned32(0..255)
   MAX-ACCESS read-only
   STATUS current
   DESCRIPTION
      "Total number of ticks during which the port had data to transmit
       on VL13 but no data was sent during the entire tick because of 
       insufficient credits or because of lack of arbitration."
   REFERENCE
      "InfiniBand Architecture Release 1.1. Vol. 1. Section 16.1.4.6;
       Table 201 PortVLXmitWaitCounters::PortVLXmitWait13."
   ::= { ibPmaPortVlXmitWaitCntrsEntry 15 } 

ibPmaPortVlXmitWait14 OBJECT-TYPE
   SYNTAX Unsigned32(0..255)
   MAX-ACCESS read-only
   STATUS current
   DESCRIPTION
      "Total number of ticks during which the port had data to transmit
       on VL14 but no data was sent during the entire tick because of 
       insufficient credits or because of lack of arbitration."
   REFERENCE
      "InfiniBand Architecture Release 1.1. Vol. 1. Section 16.1.4.6;
       Table 201 PortVLXmitWaitCounters::PortVLXmitWait14."
   ::= { ibPmaPortVlXmitWaitCntrsEntry 16 } 

ibPmaPortVlXmitWait15 OBJECT-TYPE
   SYNTAX Unsigned32(0..255)
   MAX-ACCESS read-only
   STATUS current
   DESCRIPTION
      "Total number of ticks during which the port had data to transmit
       on VL15 but no data was sent during the entire tick because of 
       insufficient credits or because of lack of arbitration."
   REFERENCE
      "InfiniBand Architecture Release 1.1. Vol. 1. Section 16.1.4.6;
       Table 201 PortVLXmitWaitCounters::PortVLXmitWait15."
   ::= { ibPmaPortVlXmitWaitCntrsEntry 17 } 

--**************************************************************** 
-- Port Virtual Lane Software Congestion Table
--**************************************************************** 

ibPmaPortVlSwCongestionTable OBJECT-TYPE
   SYNTAX SEQUENCE OF IbPmaPortVlSwCongestionEntry 
   MAX-ACCESS not-accessible  
   STATUS current 
   DESCRIPTION 
      "A table containing PMA Port Virtual Lane Software Congestion
       information." 
   ::= { ibPmaPortVlInfo 3 } 

ibPmaPortVlSwCongestionEntry OBJECT-TYPE
   SYNTAX IbPmaPortVlSwCongestionEntry 
   MAX-ACCESS not-accessible 
   STATUS current 
   DESCRIPTION 
      "A conceptual row of the ibPmaPortVlSwCongestionTable 
       containing information about the software congestion per         
       virtual lane for a particular data port." 
   INDEX { ibPmaPortVlSwCongestionIndex }  
   ::= { ibPmaPortVlSwCongestionTable 1 } 

IbPmaPortVlSwCongestionEntry ::= SEQUENCE { 
   ibPmaPortVlSwCongestionIndex IbDataPort,
   ibPmaPortVlSwCongestion0 Unsigned32,
   ibPmaPortVlSwCongestion1 Unsigned32,
   ibPmaPortVlSwCongestion2 Unsigned32,
   ibPmaPortVlSwCongestion3 Unsigned32,
   ibPmaPortVlSwCongestion4 Unsigned32,
   ibPmaPortVlSwCongestion5 Unsigned32,
   ibPmaPortVlSwCongestion6 Unsigned32,
   ibPmaPortVlSwCongestion7 Unsigned32,
   ibPmaPortVlSwCongestion8 Unsigned32,
   ibPmaPortVlSwCongestion9 Unsigned32,
   ibPmaPortVlSwCongestion10 Unsigned32,
   ibPmaPortVlSwCongestion11 Unsigned32,
   ibPmaPortVlSwCongestion12 Unsigned32,
   ibPmaPortVlSwCongestion13 Unsigned32,
   ibPmaPortVlSwCongestion14 Unsigned32,
   ibPmaPortVlSwCongestion15 Unsigned32
   }

ibPmaPortVlSwCongestionIndex OBJECT-TYPE 
   SYNTAX IbDataPort
   MAX-ACCESS not-accessible 
   STATUS current 
   DESCRIPTION  
      "Index that identifies the InfiniBand data port.  The IBA
       defines a range of valid data ports from 1 to N, where  
       N can have a maximum value of 254." 
   ::= { ibPmaPortVlSwCongestionEntry 1 } 

ibPmaPortVlSwCongestion0 OBJECT-TYPE
   SYNTAX Unsigned32(0..255)
   MAX-ACCESS read-only
   STATUS current
   DESCRIPTION
      "Total number of packets to be transmitted on VL 0 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion0."
   ::= { ibPmaPortVlSwCongestionEntry 2 } 

ibPmaPortVlSwCongestion1 OBJECT-TYPE
   SYNTAX Unsigned32(0..255)
   MAX-ACCESS read-only
   STATUS current
   DESCRIPTION
      "Total number of packets to be transmitted on VL 1 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion1."
   ::= { ibPmaPortVlSwCongestionEntry 3 } 

ibPmaPortVlSwCongestion2 OBJECT-TYPE
   SYNTAX Unsigned32(0..255)
   MAX-ACCESS read-only
   STATUS current
   DESCRIPTION
      "Total number of packets to be transmitted on VL 2 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion2."
   ::= { ibPmaPortVlSwCongestionEntry 4 } 

ibPmaPortVlSwCongestion3 OBJECT-TYPE
   SYNTAX Unsigned32(0..255)
   MAX-ACCESS read-only
   STATUS current
   DESCRIPTION
      "Total number of packets to be transmitted on VL 3 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion3."
   ::= { ibPmaPortVlSwCongestionEntry 5 } 

ibPmaPortVlSwCongestion4 OBJECT-TYPE
   SYNTAX Unsigned32(0..255)
   MAX-ACCESS read-only
   STATUS current
   DESCRIPTION
      "Total number of packets to be transmitted on VL 4 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion4."
   ::= { ibPmaPortVlSwCongestionEntry 6 } 

ibPmaPortVlSwCongestion5 OBJECT-TYPE
   SYNTAX Unsigned32(0..255)
   MAX-ACCESS read-only
   STATUS current
   DESCRIPTION
      "Total number of packets to be transmitted on VL 5 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion5."
   ::= { ibPmaPortVlSwCongestionEntry 7 } 

ibPmaPortVlSwCongestion6 OBJECT-TYPE
   SYNTAX Unsigned32(0..255)
   MAX-ACCESS read-only
   STATUS current
   DESCRIPTION
      "Total number of packets to be transmitted on VL 6 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion6."
   ::= { ibPmaPortVlSwCongestionEntry 8 } 

ibPmaPortVlSwCongestion7 OBJECT-TYPE
   SYNTAX Unsigned32(0..255)
   MAX-ACCESS read-only
   STATUS current
   DESCRIPTION
      "Total number of packets to be transmitted on VL 7 for
       this output port that were discarded because of congestion.
       This includes the following reasons
       - Switch lifetime limit exceeded
       - Switch HOQ limit exceeded."

   REFERENCE
      "InfiniBand Architecture Release 1.1. Vol. 1. Section 16.1.3.5;
       Table 202 SwPortVLCongestion::SWPortVLCongestion7."
   ::= { ibPmaPortVlSwCongestionEntry 9 } 

ibPmaPortVlSwCongestion8 OBJECT-TYPE
   SYNTAX Unsigned32(0..255)
   MAX-ACCESS read-only
   STATUS current
   DESCRIPTION
      "Total number of packets to be transmitted on VL 8 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion8."
   ::= { ibPmaPortVlSwCongestionEntry 10 } 

ibPmaPortVlSwCongestion9 OBJECT-TYPE
   SYNTAX Unsigned32(0..255)
   MAX-ACCESS read-only
   STATUS current
   DESCRIPTION
      "Total number of packets to be transmitted on VL 9 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion9."
   ::= { ibPmaPortVlSwCongestionEntry 11 } 

ibPmaPortVlSwCongestion10 OBJECT-TYPE
   SYNTAX Unsigned32(0..255)
   MAX-ACCESS read-only
   STATUS current
   DESCRIPTION
      "Total number of packets to be transmitted on VL 10 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion10."
   ::= { ibPmaPortVlSwCongestionEntry 12 } 

ibPmaPortVlSwCongestion11 OBJECT-TYPE
   SYNTAX Unsigned32(0..255)
   MAX-ACCESS read-only
   STATUS current
   DESCRIPTION
      "Total number of packets to be transmitted on VL 11 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion11."
   ::= { ibPmaPortVlSwCongestionEntry 13 } 

ibPmaPortVlSwCongestion12 OBJECT-TYPE
   SYNTAX Unsigned32(0..255)
   MAX-ACCESS read-only
   STATUS current
   DESCRIPTION
      "Total number of packets to be transmitted on VL 12 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion12."
   ::= { ibPmaPortVlSwCongestionEntry 14 } 

ibPmaPortVlSwCongestion13 OBJECT-TYPE
   SYNTAX Unsigned32(0..255)
   MAX-ACCESS read-only
   STATUS current
   DESCRIPTION
      "Total number of packets to be transmitted on VL 13 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion13."
   ::= { ibPmaPortVlSwCongestionEntry 15 } 

ibPmaPortVlSwCongestion14 OBJECT-TYPE
   SYNTAX Unsigned32(0..255)
   MAX-ACCESS read-only
   STATUS current
   DESCRIPTION
      "Total number of packets to be transmitted on VL 14 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion14."
   ::= { ibPmaPortVlSwCongestionEntry 16 } 

ibPmaPortVlSwCongestion15 OBJECT-TYPE
   SYNTAX Unsigned32(0..255)
   MAX-ACCESS read-only
   STATUS current
   DESCRIPTION
      "Total number of packets to be transmitted on VL 15 for
       this output port that were discarded because of congestion.
       This includes the following reasons
       - Switch lifetime limit exceeded
       - Switch HOQ limit exceeded."
   REFERENCE
      "InfiniBand Architecture Release 1.1. Vol. 1. Section 16.1.3.5;
       Table 202 SwPortVLCongestion::SWPortVLCongestion15."
   ::= { ibPmaPortVlSwCongestionEntry 17 } 

--**************************************************************** 
-- Module Conformance Statement 
--
-- DESCRIPTION: The module conformance statement includes the
--    compliance statements and the units of conformance
--    section.
--**************************************************************** 

ibPmaCompliances OBJECT IDENTIFIER ::= { ibPmaConformance 1 }

ibPmaGroups OBJECT IDENTIFIER ::= { ibPmaConformance 2 }

--**************************************************************** 
-- Compliance Statements 
--**************************************************************** 

ibPmaBasicNodeCompliance MODULE-COMPLIANCE
   STATUS current
   DESCRIPTION
      "The basic node implementation requirements for agents that
       support the IPOIB PMA MIB."
   MODULE -- this module
       MANDATORY-GROUPS { 
                        ibPmaPortCntrsMandatoryGroup
                        }
   ::= { ibPmaCompliances 1 }

ibPmaFullNodeCompliance MODULE-COMPLIANCE
   STATUS current
   DESCRIPTION
      "The full node implementation requirements for agents that
       support the IPOIB PMA MIB. This include all of the optional
       counter groups"
   MODULE -- this module
       MANDATORY-GROUPS { 
                        ibPmaPortCntrsMandatoryGroup,
                        ibPmaPortCntrsOptionalGroup,
                        ibPmaPortRcvErrGroup,
                        ibPmaPortXmitDiscardGroup,
                        ibPmaPortFlowCtlCntrsGroup,
                        ibPmaPortOpCodeRcvCntrsGroup,
                        ibPmaPortOpCodeVlCntrsGroup,
                        ibPmaPortOpCodeVlDataCntrsGroup,
                        ibPmaPortVlXmitFCUpErrGroup,
                        ibPmaPortVlXmitWaitGroup,
                        ibPmaPortVlSwCongestionGroup
                        }
   ::= { ibPmaCompliances 2 }

--**************************************************************** 
-- Units Of Conformance 
--**************************************************************** 

ibPmaPortCntrsMandatoryGroup OBJECT-GROUP
   OBJECTS {
       ibPmaSymbolErrCounter,
       ibPmaLinkErrRecoveryCntr,
       ibPmaLinkDownedCntr,
       ibPmaPortRcvErr,
       ibPmaPortRcvRemPhysErr,
       ibPmaPortRcvSwitchRelayErr,
       ibPmaPortXmitDiscard,
       ibPmaPortXmitConstraintErr,
       ibPmaPortRcvConstraintErr,
       ibPmaLocalLinkIntegrityErr,
       ibPmaExcessBufOverrunErr,
       ibPmaVl15Dropped
   }
   STATUS current
   DESCRIPTION
      "The ibPmaPortCntrsMandatoryGroup defines the MIB objects that 
       describe the mandatory counters that must be maintained by the
       Performance Management Agent."
   ::= { ibPmaGroups 1 }

ibPmaPortCntrsOptionalGroup OBJECT-GROUP
   OBJECTS {
       ibPmaPortXmitData,
       ibPmaPortRcvData,
       ibPmaPortXmitPkts,
       ibPmaPortRcvPkts
   }
   STATUS current
   DESCRIPTION
      "The ibPmaPortCntrsOptionalGroup defines the MIB objects that 
       describe the optional counters that must be maintained by the
       Performance Management Agent."
   ::= { ibPmaGroups 2 }

ibPmaPortRcvErrGroup OBJECT-GROUP
   OBJECTS {
       ibPmaPortRcvErrLocalPhysErrs,
       ibPmaPortMalformedPacketErrs,
       ibPmaPortBufferOverrunErrs,
       ibPmaPortDLIDMappingErrs,
       ibPmaPortVLMappingErrs,
       ibPmaPortLoopingErrs
   }
   STATUS current
   DESCRIPTION
      "The ibPmaPortRcvErrGroup defines the MIB objects that describe
       the receive error counters for a particular port by the PMA."
   ::= { ibPmaGroups 3 }

ibPmaPortXmitDiscardGroup OBJECT-GROUP
   OBJECTS {
       ibPmaPortInactiveDiscards,
       ibPmaPortNeighborMtuDiscards,
       ibPmaPortSwLifetimeLimitDiscards,
       ibPmaPortSwHoqLimitDiscards
   }
   STATUS current
   DESCRIPTION
      "The ibPmaPortXmitDiscardGroup defines the MIB objects that
       describe the transmit discard details for a particular port
       by the PMA."
   ::= { ibPmaGroups 4 }

ibPmaPortFlowCtlCntrsGroup OBJECT-GROUP
   OBJECTS {
       ibPmaPortFlowCtlXmitFlowPkts,
       ibPmaPortFlowCtlRcvFlowPkts
   }
   STATUS current
   DESCRIPTION
      "The ibPmaPortFlowCtlCntrsGroup defines the MIB objects that
       describe the transmit and receive flow control counters for
       a particular port by the PMA."
   ::= { ibPmaGroups 5 }

ibPmaPortOpCodeRcvCntrsGroup OBJECT-GROUP
   OBJECTS {
       ibPmaPortOpCodeRcvCntrsRcvPkts,
       ibPmaPortOpCodeRcvCntrsRcvData
   }
   STATUS current
   DESCRIPTION
      "The ibPmaPortOpCodeRcvCntrsGroup defines the MIB objects that
       describe the receive counters for a particular port and op
       code by the PMA."
   ::= { ibPmaGroups 6 }

ibPmaPortOpCodeVlCntrsGroup OBJECT-GROUP
   OBJECTS {
       ibPmaPortVlOpPkt0,
       ibPmaPortVlOpPkt1,
       ibPmaPortVlOpPkt2,
       ibPmaPortVlOpPkt3,
       ibPmaPortVlOpPkt4,
       ibPmaPortVlOpPkt5,
       ibPmaPortVlOpPkt6,
       ibPmaPortVlOpPkt7,
       ibPmaPortVlOpPkt8,
       ibPmaPortVlOpPkt9,
       ibPmaPortVlOpPkt10,
       ibPmaPortVlOpPkt11,
       ibPmaPortVlOpPkt12,
       ibPmaPortVlOpPkt13,
       ibPmaPortVlOpPkt14,
       ibPmaPortVlOpPkt15
   }
   STATUS current
   DESCRIPTION
      "The ibPmaPortOpCodeVlCntrsGroup defines the MIB objects that
       describe the packet counters for a particular port, op code, 
       and virtual lane by the PMA."
   ::= { ibPmaGroups 7 }

ibPmaPortOpCodeVlDataCntrsGroup OBJECT-GROUP
   OBJECTS {
       ibPmaPortVlOpData0,
       ibPmaPortVlOpData1,
       ibPmaPortVlOpData2,
       ibPmaPortVlOpData3,
       ibPmaPortVlOpData4,
       ibPmaPortVlOpData5,
       ibPmaPortVlOpData6,
       ibPmaPortVlOpData7,
       ibPmaPortVlOpData8,
       ibPmaPortVlOpData9,
       ibPmaPortVlOpData10,
       ibPmaPortVlOpData11,
       ibPmaPortVlOpData12,
       ibPmaPortVlOpData13,
       ibPmaPortVlOpData14,
       ibPmaPortVlOpData15
   }
   STATUS current
   DESCRIPTION
      "The ibPmaPortOpCodeVlDataCntrsGroup defines the MIB objects that
       describe the octet counters for a particular port, op code, and
       virtual lane by the PMA."
   ::= { ibPmaGroups 8 }

ibPmaPortVlXmitFCUpErrGroup OBJECT-GROUP
   OBJECTS {
       ibPmaPortVlXmitFCUpErr0,
       ibPmaPortVlXmitFCUpErr1,
       ibPmaPortVlXmitFCUpErr2,
       ibPmaPortVlXmitFCUpErr3,
       ibPmaPortVlXmitFCUpErr4,
       ibPmaPortVlXmitFCUpErr5,
       ibPmaPortVlXmitFCUpErr6,
       ibPmaPortVlXmitFCUpErr7,
       ibPmaPortVlXmitFCUpErr8,
       ibPmaPortVlXmitFCUpErr9,
       ibPmaPortVlXmitFCUpErr10,
       ibPmaPortVlXmitFCUpErr11,
       ibPmaPortVlXmitFCUpErr12,
       ibPmaPortVlXmitFCUpErr13,
       ibPmaPortVlXmitFCUpErr14,
       ibPmaPortVlXmitFCUpErr15
   }
   STATUS current
   DESCRIPTION
      "The ibPmaPortVlXmitFCUpErrGroup defines the MIB objects that
       describe the transmit flow control update counters for a 
       particular port and virtual lane by the PMA."
   ::= { ibPmaGroups 9 }

ibPmaPortVlXmitWaitGroup OBJECT-GROUP
   OBJECTS {
       ibPmaPortVlXmitWait0,
       ibPmaPortVlXmitWait1,
       ibPmaPortVlXmitWait2,
       ibPmaPortVlXmitWait3,
       ibPmaPortVlXmitWait4,
       ibPmaPortVlXmitWait5,
       ibPmaPortVlXmitWait6,
       ibPmaPortVlXmitWait7,
       ibPmaPortVlXmitWait8,
       ibPmaPortVlXmitWait9,
       ibPmaPortVlXmitWait10,
       ibPmaPortVlXmitWait11,
       ibPmaPortVlXmitWait12,
       ibPmaPortVlXmitWait13,
       ibPmaPortVlXmitWait14,
       ibPmaPortVlXmitWait15
   }
   STATUS current
   DESCRIPTION
      "The ibPmaPortVlXmitWaitGroup defines the MIB objects that
       describe the transmit wait counters for a particular port
       and virtual lane by the PMA."
   ::= { ibPmaGroups 10 }

ibPmaPortVlSwCongestionGroup OBJECT-GROUP
   OBJECTS {
       ibPmaPortVlSwCongestion0,
       ibPmaPortVlSwCongestion1,
       ibPmaPortVlSwCongestion2,
       ibPmaPortVlSwCongestion3,
       ibPmaPortVlSwCongestion4,
       ibPmaPortVlSwCongestion5,
       ibPmaPortVlSwCongestion6,
       ibPmaPortVlSwCongestion7,
       ibPmaPortVlSwCongestion8,
       ibPmaPortVlSwCongestion9,
       ibPmaPortVlSwCongestion10,
       ibPmaPortVlSwCongestion11,
       ibPmaPortVlSwCongestion12,
       ibPmaPortVlSwCongestion13,
       ibPmaPortVlSwCongestion14,
       ibPmaPortVlSwCongestion15
   }
   STATUS current
   DESCRIPTION
      "The ibPmaPortVlSwCongestionGroup defines the MIB objects that
       describe the software congestion counters for a particular port
       and virtual lane by the PMA."
   ::= { ibPmaGroups 11 }

END 

--  
--    Copyright (C) The Internet Society (2005).  This document is
--    subject to the rights, licenses and restrictions contained in BCP
--    78, and except as set forth therein, the authors retain all their
--    rights.
--    
--    This document and translations of it may be copied and
--    furnished to others, and derivative works that comment on
--    or otherwise explain it or assist in its implementation may
--    be prepared, copied, published and distributed, in whole or
--    in part, without restriction of any kind, provided that the
--    above copyright notice and this paragraph are included on
--    all such copies and derivative works.  However, this document
--    itself may not be modified in any way, such as by removing the
--    copyright notice or references to the Internet Society or other 
--    Internet organizations, except as needed for the purpose of 
--    developing Internet standards in which case the procedures for 
--    copyrights defined in the Internet Standards process must be 
--    followed, or as required to translate it into languages other 
--    than English.
--    
--    The limited permissions granted above are perpetual and
--    will not be revoked by the Internet Society or its
--    successors or assigns. 
-- 
--    This document and the information contained herein are provided
--    on an "AS IS" basis and THE CONTRIBUTOR, THE ORGANIZATION HE/SHE
--    REPRESENTS OR IS SPONSORED BY (IF ANY), THE INTERNET SOCIETY AND
--    THE INTERNET ENGINEERING TASK FORCE DISCLAIM ALL WARRANTIES,
--    EXPRESS OR IMPLIED, INCLUDING BUT NOT LIMITED TO ANY WARRANTY THAT
--    THE USE OF THE INFORMATION HEREIN WILL NOT INFRINGE ANY RIGHTS OR
--    ANY IMPLIED WARRANTIES OF MERCHANTABILITY OR FITNESS FOR A
--    PARTICULAR PURPOSE.
--
