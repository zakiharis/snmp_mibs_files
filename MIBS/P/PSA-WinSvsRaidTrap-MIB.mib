PSA-WinSvsRaidTrap-MIB DEFINITIONS ::= BEGIN

--PRIMEQUEST system management MIB for Partition
--
--
--$Copyright$
--Copyright Fujitsu Limited 2010
--All rights reserved
--
--
--MIB Revision: 02000009
--

IMPORTS
	OBJECT-TYPE								FROM RFC-1212
	TRAP-TYPE								FROM RFC-1215
	mib-2, DisplayString					FROM RFC1213-MIB
	TimeTicks, Counter, Gauge, IpAddress	FROM RFC1155-SMI
	mgmt, enterprises						FROM RFC1155-SMI;

--enterprises	OBJECT IDENTIFIER ::={ iso org(3) dod(6) internet(1) private(4) 1 }
--
--PRIMEQUEST system management MIB nodes
--fujitsu:                    1.3.6.1.4.1.211
-- products:                  1.3.6.1.4.1.211.1
--  iaServer:                 1.3.6.1.4.1.211.1.31
--   primequest:              1.3.6.1.4.1.211.1.31.1
--    partition:	           1.3.6.1.4.1.211.1.31.1.2
--
--Trap enterprise is "psaWinSvsRaidTrap"

--FUJITSU PRIMEQUEST system management MIB nodes for Partition
  fujitsu        OBJECT IDENTIFIER  ::={ enterprises 211 }
  products       OBJECT IDENTIFIER  ::={ fujitsu 1 }
  iaServer       OBJECT IDENTIFIER  ::={ products 31 }
  primequest     OBJECT IDENTIFIER  ::={ iaServer 1 }
   partition     OBJECT IDENTIFIER  ::={ primequest 2 }
    parititonVariables	OBJECT IDENTIFIER	::={ partition	200 }
    partitionEnterprise      OBJECT IDENTIFIER  ::={ partition 201 }
     psaComTrap              OBJECT IDENTIFIER  ::={ partitionEnterprise 1 }
     psaSVAgentsTrap         OBJECT IDENTIFIER  ::={ partitionEnterprise 102 }
     psaWinIntelE100Trap     OBJECT IDENTIFIER  ::={ partitionEnterprise 51 }
     psaWinIntelE1000Trap    OBJECT IDENTIFIER  ::={ partitionEnterprise 52 }
     psaWinBcm5700Trap       OBJECT IDENTIFIER  ::={ partitionEnterprise 53 }
     psaWinEmulexTrap        OBJECT IDENTIFIER  ::={ partitionEnterprise 54 }
     psaWinLsiLogicTrap      OBJECT IDENTIFIER  ::={ partitionEnterprise 55 }
     psaWinDiskTrap          OBJECT IDENTIFIER  ::={ partitionEnterprise 56 }
     psaWinGrmpdTrap         OBJECT IDENTIFIER  ::={ partitionEnterprise 57 }
     psaWinDiskMirrorTrap    OBJECT IDENTIFIER  ::={ partitionEnterprise 58 }
     psaWinXframe2Trap       OBJECT IDENTIFIER  ::={ partitionEnterprise 59 }
     psaWinIntelE1000expTrap OBJECT IDENTIFIER  ::={ partitionEnterprise 60 }
     psaWinSvsRaidTrap       OBJECT IDENTIFIER  ::={ partitionEnterprise 61 }
     psaWinMpdTrap           OBJECT IDENTIFIER  ::={ partitionEnterprise 62 }
     psaWinGlsTrap           OBJECT IDENTIFIER  ::={ partitionEnterprise 63 }
     psaWinIntele1expressTrap  OBJECT IDENTIFIER  ::={ partitionEnterprise 64 }
     psaWinIntelixgbnTrap  OBJECT IDENTIFIER  ::={ partitionEnterprise 65 }

--***************************************************************************************
--
--FUJITSU PRIMEQUEST system management trap parameter variables for Partition
--	They aren't directly accessibles(can't use snmp get/set command), but sent with trap
--
--***************************************************************************************

     trapVarComInfo	OBJECT IDENTIFIER	::={ parititonVariables 1 }

trapPartitionName OBJECT-TYPE
   SYNTAX   DisplayString
   ACCESS   not-accessible
   STATUS   mandatory
   DESCRIPTION "Partition name which trap is generated."
   ::= { trapVarComInfo 1 }

trapPartitionId OBJECT-TYPE
   SYNTAX   INTEGER
   ACCESS   not-accessible
   STATUS   mandatory
   DESCRIPTION "Paritition identifier which trap is generated."
   ::= { trapVarComInfo 2 }

trapEventLevel OBJECT-TYPE
   SYNTAX   DisplayString
   ACCESS   not-accessible
   STATUS   mandatory
   DESCRIPTION "Event level"
   ::= { trapVarComInfo 3 }

trapEventId OBJECT-TYPE
   SYNTAX   INTEGER
   ACCESS   not-accessible
   STATUS   mandatory
   DESCRIPTION "Event Identifier"
   ::= { trapVarComInfo 4 }

trapUnitName OBJECT-TYPE
   SYNTAX   DisplayString
   ACCESS   not-accessible
   STATUS   mandatory
   DESCRIPTION "Unit name which trap is generated."
   ::= { trapVarComInfo 5 }

trapMmbVip OBJECT-TYPE
   SYNTAX   DisplayString
   ACCESS   not-accessible
   STATUS   mandatory
   DESCRIPTION "Management board vertual IP address."
   ::= { trapVarComInfo 6 }

     trapVarDivInfo	OBJECT IDENTIFIER	::={ parititonVariables 2 }

trapPartNo OBJECT-TYPE
   SYNTAX   DisplayString
   ACCESS   not-accessible
   STATUS   mandatory
   DESCRIPTION "Parts number of trap source."
   ::= { trapVarDivInfo 1 }

trapStepping OBJECT-TYPE
   SYNTAX   DisplayString
   ACCESS   not-accessible
   STATUS   mandatory
   DESCRIPTION " "
   ::= { trapVarDivInfo 2 }

trapSerialNo OBJECT-TYPE
   SYNTAX   DisplayString
   ACCESS   not-accessible
   STATUS   mandatory
   DESCRIPTION "Serial number of trap source. "
   ::= { trapVarDivInfo 3 }

trapModelNo OBJECT-TYPE
   SYNTAX   DisplayString
   ACCESS   not-accessible
   STATUS   mandatory
   DESCRIPTION "Model number of trap source."
   ::= { trapVarDivInfo 4 }

trapSuspect OBJECT-TYPE
   SYNTAX   DisplayString
   ACCESS   not-accessible
   STATUS   mandatory
   DESCRIPTION "Logical name or pci bus number of trap source."
   ::= { trapVarDivInfo 5 }

trapVendorId OBJECT-TYPE
   SYNTAX   DisplayString
   ACCESS   not-accessible
   STATUS   mandatory
   DESCRIPTION "Vendor identifier of trap source."
   ::= { trapVarDivInfo 6 }

trapDeviceId OBJECT-TYPE
   SYNTAX   DisplayString
   ACCESS   not-accessible
   STATUS   mandatory
   DESCRIPTION "Device identifier of trap source."
   ::= { trapVarDivInfo 7 }

trapRevision OBJECT-TYPE
   SYNTAX   DisplayString
   ACCESS   not-accessible
   STATUS   mandatory
   DESCRIPTION "Revision of trap source."
   ::= { trapVarDivInfo 8 }

trapCardName OBJECT-TYPE
   SYNTAX   DisplayString
   ACCESS   not-accessible
   STATUS   mandatory
   DESCRIPTION "Device name of trap source."
   ::= { trapVarDivInfo 9 }

trapErrDetail OBJECT-TYPE
   SYNTAX   DisplayString
   ACCESS   not-accessible
   STATUS   mandatory
   DESCRIPTION " "
   ::= { trapVarDivInfo 10 }

trapErrCode OBJECT-TYPE
   SYNTAX   DisplayString
   ACCESS   not-accessible
   STATUS   mandatory
   DESCRIPTION " "
   ::= { trapVarDivInfo 11 }

trapIrpCode OBJECT-TYPE
   SYNTAX   DisplayString
   ACCESS   not-accessible
   STATUS   mandatory
   DESCRIPTION " "
   ::= { trapVarDivInfo 12 }

trapHbaNo OBJECT-TYPE
   SYNTAX   INTEGER
   ACCESS   not-accessible
   STATUS   mandatory
   DESCRIPTION " "
   ::= { trapVarDivInfo 13 }

trapErrCause OBJECT-TYPE
   SYNTAX   DisplayString
   ACCESS   not-accessible
   STATUS   mandatory
   DESCRIPTION " "
   ::= { trapVarDivInfo 14 }

trapPathNo OBJECT-TYPE
   SYNTAX   INTEGER
   ACCESS   not-accessible
   STATUS   mandatory
   DESCRIPTION " "
   ::= { trapVarDivInfo 15 }

trapDiskId OBJECT-TYPE
   SYNTAX   DisplayString
   ACCESS   not-accessible
   STATUS   mandatory
   DESCRIPTION " "
   ::= { trapVarDivInfo 16 }

trapFmrDiskId OBJECT-TYPE
   SYNTAX   DisplayString
   ACCESS   not-accessible
   STATUS   mandatory
   DESCRIPTION " "
   ::= { trapVarDivInfo 17 }

trapCurDiskId OBJECT-TYPE
   SYNTAX   DisplayString
   ACCESS   not-accessible
   STATUS   mandatory
   DESCRIPTION " "
   ::= { trapVarDivInfo 18 }

trapPathId OBJECT-TYPE
   SYNTAX   DisplayString
   ACCESS   not-accessible
   STATUS   mandatory
   DESCRIPTION " "
   ::= { trapVarDivInfo 19 }

trapPhysIf OBJECT-TYPE
   SYNTAX   DisplayString
   ACCESS   not-accessible
   STATUS   mandatory
   DESCRIPTION " "
   ::= { trapVarDivInfo 20 }

trapVirtualIf OBJECT-TYPE
   SYNTAX   DisplayString
   ACCESS   not-accessible
   STATUS   mandatory
   DESCRIPTION " "
   ::= { trapVarDivInfo 21 }

trapLogicalIp OBJECT-TYPE
   SYNTAX   DisplayString
   ACCESS   not-accessible
   STATUS   mandatory
   DESCRIPTION " "
   ::= { trapVarDivInfo 22 }

trapWatchIp OBJECT-TYPE
   SYNTAX   DisplayString
   ACCESS   not-accessible
   STATUS   mandatory
   DESCRIPTION " "
   ::= { trapVarDivInfo 23 }

trapInterface OBJECT-TYPE
   SYNTAX   DisplayString
   ACCESS   not-accessible
   STATUS   mandatory
   DESCRIPTION " "
   ::= { trapVarDivInfo 24 }

trapSourceIp OBJECT-TYPE
   SYNTAX   DisplayString
   ACCESS   not-accessible
   STATUS   mandatory
   DESCRIPTION " "
   ::= { trapVarDivInfo 25 }

trapDestIp OBJECT-TYPE
   SYNTAX   DisplayString
   ACCESS   not-accessible
   STATUS   mandatory
   DESCRIPTION " "
   ::= { trapVarDivInfo 26 }

trapModelName OBJECT-TYPE
   SYNTAX   DisplayString
   ACCESS   not-accessible
   STATUS   mandatory
   DESCRIPTION "Model name of trap source."
   ::= { trapVarDivInfo 27 }

--***************************************************************************************
--
--FUJITSU PRIMEQUEST system management TRAP definition for Partition
--	Trap enterprise:	psaWinSvsRaidTrap (.1.3.6.1.4.1.211.1.31.1.2.201.61)
--
--***************************************************************************************

svraidWinEvent0 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU temperature out of range)"
   --#TYPE			"Svraid Win Event 0"
   --#SUMMARY		"%s(PID=%d) %s %d %s SV RAID:%s Adapter error (BBU temperature out of range) vendor-id=%s device-id=%s revision=%s"
   --#ARGUMENTS		{ 0, 1, 2, 3, 4, 5, 6, 7, 8 }
   --#SEVERITY		MAJOR
   ::= 28500

svraidWinEvent1 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU temperature unstable)"
   --#TYPE			"Svraid Win Event 1"
   --#SUMMARY		"%s(PID=%d) %s %d %s SV RAID:%s Adapter error (BBU temperature unstable) vendor-id=%s device-id=%s revision=%s"
   --#ARGUMENTS		{ 0, 1, 2, 3, 4, 5, 6, 7, 8 }
   --#SEVERITY		MAJOR
   ::= 28501

svraidWinEvent2 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU temperature above threshold)"
   --#TYPE			"Svraid Win Event 2"
   --#SUMMARY		"%s(PID=%d) %s %d %s SV RAID:%s Adapter error (BBU temperature above threshold) vendor-id=%s device-id=%s revision=%s"
   --#ARGUMENTS		{ 0, 1, 2, 3, 4, 5, 6, 7, 8 }
   --#SEVERITY		MAJOR
   ::= 28502

svraidWinEvent3 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU voltage out of range)"
   --#TYPE			"Svraid Win Event 3"
   --#SUMMARY		"%s(PID=%d) %s %d %s SV RAID:%s Adapter error (BBU voltage out of range) vendor-id=%s device-id=%s revision=%s"
   --#ARGUMENTS		{ 0, 1, 2, 3, 4, 5, 6, 7, 8 }
   --#SEVERITY		MAJOR
   ::= 28503

svraidWinEvent4 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU voltage unstable)"
   --#TYPE			"Svraid Win Event 4"
   --#SUMMARY		"%s(PID=%d) %s %d %s SV RAID:%s Adapter error (BBU voltage unstable) vendor-id=%s device-id=%s revision=%s"
   --#ARGUMENTS		{ 0, 1, 2, 3, 4, 5, 6, 7, 8 }
   --#SEVERITY		MAJOR
   ::= 28504

svraidWinEvent5 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU communication error) "
   --#TYPE			"Svraid Win Event 5"
   --#SUMMARY		"%s(PID=%d) %s %d %s SV RAID:%s Adapter error (BBU communication error) vendor-id=%s device-id=%s revision=%s"
   --#ARGUMENTS		{ 0, 1, 2, 3, 4, 5, 6, 7, 8 }
   --#SEVERITY		MAJOR
   ::= 28505

svraidWinEvent6 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU failed)"
   --#TYPE			"Svraid Win Event 6"
   --#SUMMARY		"%s(PID=%d) %s %d %s SV RAID:%s Adapter error (BBU failed) vendor-id=%s device-id=%s revision=%s"
   --#ARGUMENTS		{ 0, 1, 2, 3, 4, 5, 6, 7, 8 }
   --#SEVERITY		MAJOR
   ::= 28506

svraidWinEvent7 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU fast charging failed)"
   --#TYPE			"Svraid Win Event 7"
   --#SUMMARY		"%s(PID=%d) %s %d %s SV RAID:%s Adapter error (BBU fast charging failed) vendor-id=%s device-id=%s revision=%s"
   --#ARGUMENTS		{ 0, 1, 2, 3, 4, 5, 6, 7, 8 }
   --#SEVERITY		MAJOR
   ::= 28507

svraidWinEvent8 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU charge count exceeded)"
   --#TYPE			"Svraid Win Event 8"
   --#SUMMARY		"%s(PID=%d) %s %d %s SV RAID:%s Adapter error (BBU charge count exceeded) vendor-id=%s device-id=%s revision=%s"
   --#ARGUMENTS		{ 0, 1, 2, 3, 4, 5, 6, 7, 8 }
   --#SEVERITY		MINOR
   ::= 28508

svraidWinEvent9 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Rebuild on disk failed)"
   --#TYPE			"Svraid Win Event 9"
   --#SUMMARY		"%s(PID=%d) %s %d %s SV RAID:%s Device error (Rebuild on disk failed)"
   --#ARGUMENTS		{ 0, 1, 2, 3, 4, 5 }
   --#SEVERITY		MAJOR
   ::= 28509

svraidWinEvent10 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Rebuild failed on logical drive)"
   --#TYPE			"Svraid Win Event 10"
   --#SUMMARY		"%s(PID=%d) %s %d %s SV RAID:%s Device error (Rebuild failed on logical drive)"
   --#ARGUMENTS		{ 0, 1, 2, 3, 4, 5 }
   --#SEVERITY		MAJOR
   ::= 28510

svraidWinEvent11 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Migration failed on logical drive)"
   --#TYPE			"Svraid Win Event 11"
   --#SUMMARY		"%s(PID=%d) %s %d %s SV RAID:%s Device error (Migration failed on logical drive)"
   --#ARGUMENTS		{ 0, 1, 2, 3, 4, 5 }
   --#SEVERITY		MAJOR
   ::= 28511

svraidWinEvent12 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Migration aborted on logical drive)"
   --#TYPE			"Svraid Win Event 12"
   --#SUMMARY		"%s(PID=%d) %s %d %s SV RAID:%s Device error (Migration aborted on logical drive)"
   --#ARGUMENTS		{ 0, 1, 2, 3, 4, 5 }
   --#SEVERITY		MINOR
   ::= 28512

svraidWinEvent13 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Logical drive degraded)"
   --#TYPE			"Svraid Win Event 13"
   --#SUMMARY		"%s(PID=%d) %s %d %s SV RAID:%s Device error (Logical drive degraded)"
   --#ARGUMENTS		{ 0, 1, 2, 3, 4, 5 }
   --#SEVERITY		MAJOR
   ::= 28513

svraidWinEvent14 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Logical drive failed)"
   --#TYPE			"Svraid Win Event 14"
   --#SUMMARY		"%s(PID=%d) %s %d %s SV RAID:%s Device error (Logical drive failed)"
   --#ARGUMENTS		{ 0, 1, 2, 3, 4, 5 }
   --#SEVERITY		MAJOR
   ::= 28514

svraidWinEvent15 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU voltage problem detected)"
   --#TYPE			"Svraid Win Event 15"
   --#SUMMARY		"%s(PID=%d) %s %d %s SV RAID:%s Adapter error (BBU voltage problem detected) vendor-id=%s device-id=%s revision=%s"
   --#ARGUMENTS		{ 0, 1, 2, 3, 4, 5, 6, 7, 8 }
   --#SEVERITY		MAJOR
   ::= 28515

svraidWinEvent16 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU temperature problem detected)"
   --#TYPE			"Svraid Win Event 16"
   --#SUMMARY		"%s(PID=%d) %s %d %s SV RAID:%s Adapter error (BBU temperature problem detected) vendor-id=%s device-id=%s revision=%s"
   --#ARGUMENTS		{ 0, 1, 2, 3, 4, 5, 6, 7, 8 }
   --#SEVERITY		MAJOR
   ::= 28516

svraidWinEvent17 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU failed)"
   --#TYPE			"Svraid Win Event 17"
   --#SUMMARY		"%s(PID=%d) %s %d %s SV RAID:%s Adapter error (BBU failed) vendor-id=%s device-id=%s revision=%s"
   --#ARGUMENTS		{ 0, 1, 2, 3, 4, 5, 6, 7, 8 }
   --#SEVERITY		MAJOR
   ::= 28517

svraidWinEvent18 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Fatal firmware error)"
   --#TYPE			"Svraid Win Event 18"
   --#SUMMARY		"%s(PID=%d) %s %d %s SV RAID:%s Adapter error (Fatal firmware error) vendor-id=%s device-id=%s revision=%s"
   --#ARGUMENTS		{ 0, 1, 2, 3, 4, 5, 6, 7, 8 }
   --#SEVERITY		MAJOR
   ::= 28518

svraidWinEvent19 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Multi-bit ECC error)"
   --#TYPE			"Svraid Win Event 19"
   --#SUMMARY		"%s(PID=%d) %s %d %s SV RAID:%s Adapter error (Multi-bit ECC error) vendor-id=%s device-id=%s revision=%s"
   --#ARGUMENTS		{ 0, 1, 2, 3, 4, 5, 6, 7, 8 }
   --#SEVERITY		MAJOR
   ::= 28519

svraidWinEvent20 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Single-bit ECC error)"
   --#TYPE			"Svraid Win Event 20"
   --#SUMMARY		"%s(PID=%d) %s %d %s SV RAID:%s Adapter error (Single-bit ECC error) vendor-id=%s device-id=%s revision=%s"
   --#ARGUMENTS		{ 0, 1, 2, 3, 4, 5, 6, 7, 8 }
   --#SEVERITY		MAJOR
   ::= 28520

svraidWinEvent21 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Not enough adapter memory)"
   --#TYPE			"Svraid Win Event 21"
   --#SUMMARY		"%s(PID=%d) %s %d %s SV RAID:%s Adapter error (Not enough adapter memory) vendor-id=%s device-id=%s revision=%s"
   --#ARGUMENTS		{ 0, 1, 2, 3, 4, 5, 6, 7, 8 }
   --#SEVERITY		MAJOR
   ::= 28521

svraidWinEvent22 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Resume migration of logical drive failed due to Configuration Mismatch)"
   --#TYPE			"Svraid Win Event 22"
   --#SUMMARY		"%s(PID=%d) %s %d %s SV RAID:%s Device error (Resume migration of logical drive failed due to Configuration Mismatch)"
   --#ARGUMENTS		{ 0, 1, 2, 3, 4, 5 }
   --#SEVERITY		MAJOR
   ::= 28522

svraidWinEvent23 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Hot spare S.M.A.R.T. polling failed on disk)"
   --#TYPE			"Svraid Win Event 23"
   --#SUMMARY		"%s(PID=%d) %s %d %s SV RAID:%s Device error (Hot spare S.M.A.R.T. polling failed on disk)"
   --#ARGUMENTS		{ 0, 1, 2, 3, 4, 5 }
   --#SEVERITY		MAJOR
   ::= 28523

svraidWinEvent24 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Predictive failure)"
   --#TYPE			"Svraid Win Event 24"
   --#SUMMARY		"%s(PID=%d) %s %d %s SV RAID:%s Device error (Predictive failure)"
   --#ARGUMENTS		{ 0, 1, 2, 3, 4, 5 }
   --#SEVERITY		MAJOR
   ::= 28524

svraidWinEvent25 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU needs to be replaced - SOH bad)"
   --#TYPE			"Svraid Win Event 25"
   --#SUMMARY		"%s(PID=%d) %s %d %s SV RAID:%s Adapter error (BBU needs to be replaced - SOH bad) vendor-id=%s device-id=%s revision=%s"
   --#ARGUMENTS		{ 0, 1, 2, 3, 4, 5, 6, 7, 8 }
   --#SEVERITY		MAJOR
   ::= 28525

svraidWinEvent26 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU removed)"
   --#TYPE			"Svraid Win Event 26"
   --#SUMMARY		"%s(PID=%d) %s %d %s SV RAID:%s Adapter error (BBU removed) vendor-id=%s device-id=%s revision=%s"
   --#ARGUMENTS		{ 0, 1, 2, 3, 4, 5, 6, 7, 8 }
   --#SEVERITY		MINOR
   ::= 28526

svraidWinEvent27 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure communication lost)"
   --#TYPE			"Svraid Win Event 27"
   --#SUMMARY		"%s(PID=%d) %s %d %s SV RAID:%s Adapter error (Enclosure communication lost) vendor-id=%s device-id=%s revision=%s"
   --#ARGUMENTS		{ 0, 1, 2, 3, 4, 5, 6, 7, 8 }
   --#SEVERITY		MINOR
   ::= 28527

svraidWinEvent28 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure not responding)"
   --#TYPE			"Svraid Win Event 28"
   --#SUMMARY		"%s(PID=%d) %s %d %s SV RAID:%s Adapter error (Enclosure not responding) vendor-id=%s device-id=%s revision=%s"
   --#ARGUMENTS		{ 0, 1, 2, 3, 4, 5, 6, 7, 8 }
   --#SEVERITY		MINOR
   ::= 28528

svraidWinEvent29 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (SAS/SATA mixing not supported in enclosure)"
   --#TYPE			"Svraid Win Event 29"
   --#SUMMARY		"%s(PID=%d) %s %d %s SV RAID:%s Adapter error (SAS/SATA mixing not supported in enclosure) vendor-id=%s device-id=%s revision=%s"
   --#ARGUMENTS		{ 0, 1, 2, 3, 4, 5, 6, 7, 8 }
   --#SEVERITY		MINOR
   ::= 28529

svraidWinEvent30 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Bad block table on disk is 80 percent full)"
   --#TYPE			"Svraid Win Event 30"
   --#SUMMARY		"%s(PID=%d) %s %d %s SV RAID:%s Device error (Bad block table on disk is 80 percent full)"
   --#ARGUMENTS		{ 0, 1, 2, 3, 4, 5 }
   --#SEVERITY		INFORMATIONAL
   ::= 28530

svraidWinEvent31 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Bad block table on disk is full; unable to log Block)"
   --#TYPE			"Svraid Win Event 31"
   --#SUMMARY		"%s(PID=%d) %s %d %s SV RAID:%s Device error (Bad block table on disk is full; unable to log Block)"
   --#ARGUMENTS		{ 0, 1, 2, 3, 4, 5 }
   --#SEVERITY		MAJOR
   ::= 28531

svraidWinEvent32 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU/charger problems detected; SOH bad)"
   --#TYPE			"Svraid Win Event 32"
   --#SUMMARY		"%s(PID=%d) %s %d %s SV RAID:%s Adapter error (BBU/charger problems detected; SOH bad) vendor-id=%s device-id=%s revision=%s"
   --#ARGUMENTS		{ 0, 1, 2, 3, 4, 5, 6, 7, 8 }
   --#SEVERITY		MINOR
   ::= 28532

svraidWinEvent33 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Single-bit ECC error; warning threshold exceeded)"
   --#TYPE			"Svraid Win Event 33"
   --#SUMMARY		"%s(PID=%d) %s %d %s SV RAID:%s Adapter error (Single-bit ECC error; warning threshold exceeded) vendor-id=%s device-id=%s revision=%s"
   --#ARGUMENTS		{ 0, 1, 2, 3, 4, 5, 6, 7, 8 }
   --#SEVERITY		MINOR
   ::= 28533

svraidWinEvent34 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Single-bit ECC error; critical threshold exceeded)"
   --#TYPE			"Svraid Win Event 34"
   --#SUMMARY		"%s(PID=%d) %s %d %s SV RAID:%s Adapter error (Single-bit ECC error; critical threshold exceeded) vendor-id=%s device-id=%s revision=%s"
   --#ARGUMENTS		{ 0, 1, 2, 3, 4, 5, 6, 7, 8 }
   --#SEVERITY		MINOR
   ::= 28534

svraidWinEvent35 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Single-bit ECC error; further reporting disabled)"
   --#TYPE			"Svraid Win Event 35"
   --#SUMMARY		"%s(PID=%d) %s %d %s SV RAID:%s Adapter error (Single-bit ECC error; further reporting disabled) vendor-id=%s device-id=%s revision=%s"
   --#ARGUMENTS		{ 0, 1, 2, 3, 4, 5, 6, 7, 8 }
   --#SEVERITY		INFORMATIONAL
   ::= 28535

svraidWinEvent36 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Previous configuration completely missing at boot)"
   --#TYPE			"Svraid Win Event 36"
   --#SUMMARY		"%s(PID=%d) %s %d %s SV RAID:%s Adapter error (Previous configuration completely missing at boot) vendor-id=%s device-id=%s revision=%s"
   --#ARGUMENTS		{ 0, 1, 2, 3, 4, 5, 6, 7, 8 }
   --#SEVERITY		MINOR
   ::= 28536

svraidWinEvent37 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Logical drive partially degraded)"
   --#TYPE			"Svraid Win Event 37"
   --#SUMMARY		"%s(PID=%d) %s %d %s SV RAID:%s Device error (Logical drive partially degraded)"
   --#ARGUMENTS		{ 0, 1, 2, 3, 4, 5 }
   --#SEVERITY		MAJOR
   ::= 28537

svraidWinEvent38 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Disks missing)"
   --#TYPE			"Svraid Win Event 38"
   --#SUMMARY		"%s(PID=%d) %s %d %s SV RAID:%s Device error (Disks missing)"
   --#ARGUMENTS		{ 0, 1, 2, 3, 4, 5 }
   --#SEVERITY		MINOR
   ::= 28538

svraidWinEvent39 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from operational to degraded)"
   --#TYPE			"Svraid Win Event 39"
   --#SUMMARY		"%s(PID=%d) %s %d %s SV RAID:%s Device error (State change on logical drive from operational to degraded)"
   --#ARGUMENTS		{ 0, 1, 2, 3, 4, 5 }
   --#SEVERITY		MAJOR
   ::= 28539

svraidWinEvent40 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from operational to partially degraded)"
   --#TYPE			"Svraid Win Event 40"
   --#SUMMARY		"%s(PID=%d) %s %d %s SV RAID:%s Device error (State change on logical drive from operational to partially degraded)"
   --#ARGUMENTS		{ 0, 1, 2, 3, 4, 5 }
   --#SEVERITY		MAJOR
   ::= 28540

svraidWinEvent41 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from operational to failed)"
   --#TYPE			"Svraid Win Event 41"
   --#SUMMARY		"%s(PID=%d) %s %d %s SV RAID:%s Device error (State change on logical drive from operational to failed)"
   --#ARGUMENTS		{ 0, 1, 2, 3, 4, 5 }
   --#SEVERITY		MAJOR
   ::= 28541

svraidWinEvent42 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from degraded to degraded)"
   --#TYPE			"Svraid Win Event 42"
   --#SUMMARY		"%s(PID=%d) %s %d %s SV RAID:%s Device error (State change on logical drive from degraded to degraded)"
   --#ARGUMENTS		{ 0, 1, 2, 3, 4, 5 }
   --#SEVERITY		MAJOR
   ::= 28542

svraidWinEvent43 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from degraded to partially degraded)"
   --#TYPE			"Svraid Win Event 43"
   --#SUMMARY		"%s(PID=%d) %s %d %s SV RAID:%s Device error (State change on logical drive from degraded to partially degraded)"
   --#ARGUMENTS		{ 0, 1, 2, 3, 4, 5 }
   --#SEVERITY		MAJOR
   ::= 28543

svraidWinEvent44 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from degraded to failed)"
   --#TYPE			"Svraid Win Event 44"
   --#SUMMARY		"%s(PID=%d) %s %d %s SV RAID:%s Device error (State change on logical drive from degraded to failed)"
   --#ARGUMENTS		{ 0, 1, 2, 3, 4, 5 }
   --#SEVERITY		MAJOR
   ::= 28544

svraidWinEvent45 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from partially degraded to degraded)"
   --#TYPE			"Svraid Win Event 45"
   --#SUMMARY		"%s(PID=%d) %s %d %s SV RAID:%s Device error (State change on logical drive from partially degraded to degraded)"
   --#ARGUMENTS		{ 0, 1, 2, 3, 4, 5 }
   --#SEVERITY		MAJOR
   ::= 28545

svraidWinEvent46 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from partially degraded to partially degraded)"
   --#TYPE			"Svraid Win Event 46"
   --#SUMMARY		"%s(PID=%d) %s %d %s SV RAID:%s Device error (State change on logical drive from partially degraded to partially degraded)"
   --#ARGUMENTS		{ 0, 1, 2, 3, 4, 5 }
   --#SEVERITY		MAJOR
   ::= 28546

svraidWinEvent47 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from partially degraded to failed)"
   --#TYPE			"Svraid Win Event 47"
   --#SUMMARY		"%s(PID=%d) %s %d %s SV RAID:%s Device error (State change on logical drive from partially degraded to failed)"
   --#ARGUMENTS		{ 0, 1, 2, 3, 4, 5 }
   --#SEVERITY		MAJOR
   ::= 28547

svraidWinEvent48 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on logical drive from failed to failed)"
   --#TYPE			"Svraid Win Event 48"
   --#SUMMARY		"%s(PID=%d) %s %d %s SV RAID:%s Device error (State change on logical drive from failed to failed)"
   --#ARGUMENTS		{ 0, 1, 2, 3, 4, 5 }
   --#SEVERITY		MAJOR
   ::= 28548

svraidWinEvent49 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from failed to failed)"
   --#TYPE			"Svraid Win Event 49"
   --#SUMMARY		"%s(PID=%d) %s %d %s SV RAID:%s Device error (State change by user on disk from failed to failed)"
   --#ARGUMENTS		{ 0, 1, 2, 3, 4, 5 }
   --#SEVERITY		MAJOR
   ::= 28549

svraidWinEvent50 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from hotspare to failed)"
   --#TYPE			"Svraid Win Event 50"
   --#SUMMARY		"%s(PID=%d) %s %d %s SV RAID:%s Device error (State change by user on disk from hotspare to failed)"
   --#ARGUMENTS		{ 0, 1, 2, 3, 4, 5 }
   --#SEVERITY		MAJOR
   ::= 28550

svraidWinEvent51 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from rebuilding to failed)"
   --#TYPE			"Svraid Win Event 51"
   --#SUMMARY		"%s(PID=%d) %s %d %s SV RAID:%s Device error (State change by user on disk from rebuilding to failed)"
   --#ARGUMENTS		{ 0, 1, 2, 3, 4, 5 }
   --#SEVERITY		MAJOR
   ::= 28551

svraidWinEvent52 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from operational to failed)"
   --#TYPE			"Svraid Win Event 52"
   --#SUMMARY		"%s(PID=%d) %s %d %s SV RAID:%s Device error (State change by user on disk from operational to failed)"
   --#ARGUMENTS		{ 0, 1, 2, 3, 4, 5 }
   --#SEVERITY		MAJOR
   ::= 28552

svraidWinEvent53 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from failed to failed)"
   --#TYPE			"Svraid Win Event 53"
   --#SUMMARY		"%s(PID=%d) %s %d %s SV RAID:%s Device error (State change on disk from failed to failed)"
   --#ARGUMENTS		{ 0, 1, 2, 3, 4, 5 }
   --#SEVERITY		MAJOR
   ::= 28553

svraidWinEvent54 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from hot spare to failed)"
   --#TYPE			"Svraid Win Event 54"
   --#SUMMARY		"%s(PID=%d) %s %d %s SV RAID:%s Device error (State change on disk from hot spare to failed)"
   --#ARGUMENTS		{ 0, 1, 2, 3, 4, 5 }
   --#SEVERITY		MAJOR
   ::= 28554

svraidWinEvent55 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID:%s Device error (State change on disk from rebuilding to failed)"
   --#TYPE			"Svraid Win Event 55"
   --#SUMMARY		"%s(PID=%d) %s %d %s SV RAID:%s Device error (State change on disk from rebuilding to failed)"
   --#ARGUMENTS		{ 0, 1, 2, 3, 4, 5 }
   --#SEVERITY		MAJOR
   ::= 28555

svraidWinEvent56 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID:%s Device error (State change on disk from operational to failed)"
   --#TYPE			"Svraid Win Event 56"
   --#SUMMARY		"%s(PID=%d) %s %d %s SV RAID:%s Device error (State change on disk from operational to failed)"
   --#ARGUMENTS		{ 0, 1, 2, 3, 4, 5 }
   --#SEVERITY		MAJOR
   ::= 28556

svraidWinEvent57 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Disk missing after reboot)"
   --#TYPE			"Svraid Win Event 57"
   --#SUMMARY		"%s(PID=%d) %s %d %s SV RAID:%s Device error (Disk missing after reboot)"
   --#ARGUMENTS		{ 0, 1, 2, 3, 4, 5 }
   --#SEVERITY		MAJOR
   ::= 28557

svraidWinEvent58 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Logical drive missing after reboot)"
   --#TYPE			"Svraid Win Event 58"
   --#SUMMARY		"%s(PID=%d) %s %d %s SV RAID:%s Adapter error (Logical drive missing after reboot) vendor-id=%s device-id=%s revision=%s"
   --#ARGUMENTS		{ 0, 1, 2, 3, 4, 5, 6, 7, 8 }
   --#SEVERITY		MAJOR
   ::= 28558

svraidWinEvent59 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from hot spare to offline)"
   --#TYPE			"Svraid Win Event 59"
   --#SUMMARY		"%s(PID=%d) %s %d %s SV RAID:%s Device error (State change by user on disk from hot spare to offline)"
   --#ARGUMENTS		{ 0, 1, 2, 3, 4, 5 }
   --#SEVERITY		MAJOR
   ::= 28559

svraidWinEvent60 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from offline to failed)"
   --#TYPE			"Svraid Win Event 60"
   --#SUMMARY		"%s(PID=%d) %s %d %s SV RAID:%s Device error (State change by user on disk from offline to failed)"
   --#ARGUMENTS		{ 0, 1, 2, 3, 4, 5 }
   --#SEVERITY		MAJOR
   ::= 28560

svraidWinEvent61 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from operational to offline)"
   --#TYPE			"Svraid Win Event 61"
   --#SUMMARY		"%s(PID=%d) %s %d %s SV RAID:%s Device error (State change by user on disk from operational to offline)"
   --#ARGUMENTS		{ 0, 1, 2, 3, 4, 5 }
   --#SEVERITY		MINOR
   ::= 28561

svraidWinEvent62 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from rebuilding to offline)"
   --#TYPE			"Svraid Win Event 62"
   --#SUMMARY		"%s(PID=%d) %s %d %s SV RAID:%s Device error (State change by user on disk from rebuilding to offline)"
   --#ARGUMENTS		{ 0, 1, 2, 3, 4, 5 }
   --#SEVERITY		MINOR
   ::= 28562

svraidWinEvent63 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from hot spare to offline)"
   --#TYPE			"Svraid Win Event 63"
   --#SUMMARY		"%s(PID=%d) %s %d %s SV RAID:%s Device error (State change on disk from hot spare to offline)"
   --#ARGUMENTS		{ 0, 1, 2, 3, 4, 5 }
   --#SEVERITY		MINOR
   ::= 28563

svraidWinEvent64 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from offline to failed)"
   --#TYPE			"Svraid Win Event 64"
   --#SUMMARY		"%s(PID=%d) %s %d %s SV RAID:%s Device error (State change on disk from offline to failed)"
   --#ARGUMENTS		{ 0, 1, 2, 3, 4, 5 }
   --#SEVERITY		MAJOR
   ::= 28564

svraidWinEvent65 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from operational to offline)"
   --#TYPE			"Svraid Win Event 65"
   --#SUMMARY		"%s(PID=%d) %s %d %s SV RAID:%s Device error (State change on disk from operational to offline)"
   --#ARGUMENTS		{ 0, 1, 2, 3, 4, 5 }
   --#SEVERITY		MAJOR
   ::= 28565

svraidWinEvent66 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from rebuilding to offline)"
   --#TYPE			"Svraid Win Event 66"
   --#SUMMARY		"%s(PID=%d) %s %d %s SV RAID:%s Device error (State change on disk from rebuilding to offline)"
   --#ARGUMENTS		{ 0, 1, 2, 3, 4, 5 }
   --#SEVERITY		MINOR
   ::= 28566

svraidWinEvent67 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (SAS port lost link)"
   --#TYPE			"Svraid Win Event 67"
   --#SUMMARY		"%s(PID=%d) %s %d %s SV RAID:%s Adapter error (SAS port lost link) vendor-id=%s device-id=%s revision=%s"
   --#ARGUMENTS		{ 0, 1, 2, 3, 4, 5, 6, 7, 8 }
   --#SEVERITY		MAJOR
   ::= 28567

svraidWinEvent68 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Adapter missing after reboot)"
   --#TYPE			"Svraid Win Event 68"
   --#SUMMARY		"%s(PID=%d) %s %d %s SV RAID:%s Adapter error (Adapter missing after reboot) vendor-id=%s device-id=%s revision=%s"
   --#ARGUMENTS		{ 0, 1, 2, 3, 4, 5, 6, 7, 8 }
   --#SEVERITY		MAJOR
   ::= 28568

svraidWinEvent69 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Adapter needs replacement; faulty IOP detected)"
   --#TYPE			"Svraid Win Event 69"
   --#SUMMARY		"%s(PID=%d) %s %d %s SV RAID:%s Adapter error (Adapter needs replacement; faulty IOP detected) vendor-id=%s device-id=%s revision=%s"
   --#ARGUMENTS		{ 0, 1, 2, 3, 4, 5, 6, 7, 8 }
   --#SEVERITY		MAJOR
   ::= 28569

svraidWinEvent70 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Microcode update timeout on disk)"
   --#TYPE			"Svraid Win Event 70"
   --#SUMMARY		"%s(PID=%d) %s %d %s SV RAID:%s Device error (Microcode update timeout on disk)"
   --#ARGUMENTS		{ 0, 1, 2, 3, 4, 5 }
   --#SEVERITY		MINOR
   ::= 28570

svraidWinEvent71 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Microcode update failed on disk)"
   --#TYPE			"Svraid Win Event 71"
   --#SUMMARY		"%s(PID=%d) %s %d %s SV RAID:%s Device error (Microcode update failed on disk)"
   --#ARGUMENTS		{ 0, 1, 2, 3, 4, 5 }
   --#SEVERITY		MINOR
   ::= 28571

svraidWinEvent72 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Adapter cache pinned for missing or offline logical drive)"
   --#TYPE			"Svraid Win Event 72"
   --#SUMMARY		"%s(PID=%d) %s %d %s SV RAID:%s Device error (Adapter cache pinned for missing or offline logical drive)"
   --#ARGUMENTS		{ 0, 1, 2, 3, 4, 5 }
   --#SEVERITY		MAJOR
   ::= 28572

svraidWinEvent73 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Adapter cache pinned for missing or offline logical drives)"
   --#TYPE			"Svraid Win Event 73"
   --#SUMMARY		"%s(PID=%d) %s %d %s SV RAID:%s Device error (Adapter cache pinned for missing or offline logical drives)"
   --#ARGUMENTS		{ 0, 1, 2, 3, 4, 5 }
   --#SEVERITY		MAJOR
   ::= 28573

svraidWinEvent74 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Adapter cache discarded by user for missing logical drives)"
   --#TYPE			"Svraid Win Event 74"
   --#SUMMARY		"%s(PID=%d) %s %d %s SV RAID:%s Device error (Adapter cache discarded by user for missing logical drives)"
   --#ARGUMENTS		{ 0, 1, 2, 3, 4, 5 }
   --#SEVERITY		INFORMATIONAL
   ::= 28574

svraidWinEvent75 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Adapter cache destaged for logical drive)"
   --#TYPE			"Svraid Win Event 75"
   --#SUMMARY		"%s(PID=%d) %s %d %s SV RAID:%s Device error (Adapter cache destaged for logical drive)"
   --#ARGUMENTS		{ 0, 1, 2, 3, 4, 5 }
   --#SEVERITY		INFORMATIONAL
   ::= 28575

svraidWinEvent76 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Internal hardware error)"
   --#TYPE			"Svraid Win Event 76"
   --#SUMMARY		"%s(PID=%d) %s %d %s SV RAID:%s Adapter error (Internal hardware error) vendor-id=%s device-id=%s revision=%s"
   --#ARGUMENTS		{ 0, 1, 2, 3, 4, 5, 6, 7, 8 }
   --#SEVERITY		MAJOR
   ::= 28576

svraidWinEvent77 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Internal hardware error during POST)"
   --#TYPE			"Svraid Win Event 77"
   --#SUMMARY		"%s(PID=%d) %s %d %s SV RAID:%s Adapter error (Internal hardware error during POST) vendor-id=%s device-id=%s revision=%s"
   --#ARGUMENTS		{ 0, 1, 2, 3, 4, 5, 6, 7, 8 }
   --#SEVERITY		MAJOR
   ::= 28577

svraidWinEvent78 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Bad block table of disk threshold exceeded; table is about to overflow)"
   --#TYPE			"Svraid Win Event 78"
   --#SUMMARY		"%s(PID=%d) %s %d %s SV RAID:%s Device error (Bad block table of disk threshold exceeded; table is about to overflow)"
   --#ARGUMENTS		{ 0, 1, 2, 3, 4, 5 }
   --#SEVERITY		INFORMATIONAL
   ::= 28578

svraidWinEvent79 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Disk failed due to bad block table overflow)"
   --#TYPE			"Svraid Win Event 79"
   --#SUMMARY		"%s(PID=%d) %s %d %s SV RAID:%s Device error (Disk failed due to bad block table overflow)"
   --#ARGUMENTS		{ 0, 1, 2, 3, 4, 5 }
   --#SEVERITY		MAJOR
   ::= 28579

svraidWinEvent80 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Disk failure detected during POST)"
   --#TYPE			"Svraid Win Event 80"
   --#SUMMARY		"%s(PID=%d) %s %d %s SV RAID:%s Device error (Disk failure detected during POST)"
   --#ARGUMENTS		{ 0, 1, 2, 3, 4, 5 }
   --#SEVERITY		MAJOR
   ::= 28580

svraidWinEvent81 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Failure detected during POST)"
   --#TYPE			"Svraid Win Event 81"
   --#SUMMARY		"%s(PID=%d) %s %d %s SV RAID:%s Adapter error (Failure detected during POST) vendor-id=%s device-id=%s revision=%s"
   --#ARGUMENTS		{ 0, 1, 2, 3, 4, 5, 6, 7, 8 }
   --#SEVERITY		MAJOR
   ::= 28581

svraidWinEvent82 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Multiple failure on disk detected)"
   --#TYPE			"Svraid Win Event 82"
   --#SUMMARY		"%s(PID=%d) %s %d %s SV RAID:%s Device error (Multiple failure on disk detected)"
   --#ARGUMENTS		{ 0, 1, 2, 3, 4, 5 }
   --#SEVERITY		MAJOR
   ::= 28582

svraidWinEvent83 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Disk failed since it never entered ready state)"
   --#TYPE			"Svraid Win Event 83"
   --#SUMMARY		"%s(PID=%d) %s %d %s SV RAID:%s Device error (Disk failed since it never entered ready state)"
   --#ARGUMENTS		{ 0, 1, 2, 3, 4, 5 }
   --#SEVERITY		MAJOR
   ::= 28583

svraidWinEvent84 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Internal software interface error)"
   --#TYPE			"Svraid Win Event 84"
   --#SUMMARY		"%s(PID=%d) %s %d %s SV RAID:%s Adapter error (Internal software interface error) vendor-id=%s device-id=%s revision=%s"
   --#ARGUMENTS		{ 0, 1, 2, 3, 4, 5, 6, 7, 8 }
   --#SEVERITY		MINOR
   ::= 28584

svraidWinEvent85 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Device open error)"
   --#TYPE			"Svraid Win Event 85"
   --#SUMMARY		"%s(PID=%d) %s %d %s SV RAID:%s Adapter error (Device open error) vendor-id=%s device-id=%s revision=%s"
   --#ARGUMENTS		{ 0, 1, 2, 3, 4, 5, 6, 7, 8 }
   --#SEVERITY		MINOR
   ::= 28585

svraidWinEvent86 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Ioctl send error)"
   --#TYPE			"Svraid Win Event 86"
   --#SUMMARY		"%s(PID=%d) %s %d %s SV RAID:%s Adapter error (Ioctl send error) vendor-id=%s device-id=%s revision=%s"
   --#ARGUMENTS		{ 0, 1, 2, 3, 4, 5, 6, 7, 8 }
   --#SEVERITY		MINOR
   ::= 28586

svraidWinEvent87 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Insufficient application memory)"
   --#TYPE			"Svraid Win Event 87"
   --#SUMMARY		"%s(PID=%d) %s %d %s SV RAID:%s Adapter error (Insufficient application memory) vendor-id=%s device-id=%s revision=%s"
   --#ARGUMENTS		{ 0, 1, 2, 3, 4, 5, 6, 7, 8 }
   --#SEVERITY		MINOR
   ::= 28587

svraidWinEvent88 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (System API error)"
   --#TYPE			"Svraid Win Event 88"
   --#SUMMARY		"%s(PID=%d) %s %d %s SV RAID:%s Adapter error (System API error) vendor-id=%s device-id=%s revision=%s"
   --#ARGUMENTS		{ 0, 1, 2, 3, 4, 5, 6, 7, 8 }
   --#SEVERITY		MINOR
   ::= 28588

svraidWinEvent89 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Firmware initialization failed)"
   --#TYPE			"Svraid Win Event 89"
   --#SUMMARY		"%s(PID=%d) %s %d %s SV RAID:%s Adapter error (Firmware initialization failed) vendor-id=%s device-id=%s revision=%s"
   --#ARGUMENTS		{ 0, 1, 2, 3, 4, 5, 6, 7, 8 }
   --#SEVERITY		MAJOR
   ::= 28589

svraidWinEvent90 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Firmware recovery failed)"
   --#TYPE			"Svraid Win Event 90"
   --#SUMMARY		"%s(PID=%d) %s %d %s SV RAID:%s Adapter error (Firmware recovery failed) vendor-id=%s device-id=%s revision=%s"
   --#ARGUMENTS		{ 0, 1, 2, 3, 4, 5, 6, 7, 8 }
   --#SEVERITY		MAJOR
   ::= 28590

svraidWinEvent91 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (BBU requires reconditioning; please initiate recalibration)"
   --#TYPE			"Svraid Win Event 91"
   --#SUMMARY		"%s(PID=%d) %s %d %s SV RAID:%s Adapter error (BBU requires reconditioning; please initiate recalibration) vendor-id=%s device-id=%s revision=%s"
   --#ARGUMENTS		{ 0, 1, 2, 3, 4, 5, 6, 7, 8 }
   --#SEVERITY		MINOR
   ::= 28591

svraidWinEvent92 TRAP-TYPE
   ENTERPRISE   psaWinSvsRaidTrap
   VARIABLES {
      trapPartitionName,
      trapPartitionId,
      trapEventLevel,
      trapEventId,
      trapUnitName,
      trapMmbVip
   }
   DESCRIPTION "SV RAID: Software error (Task for object cannot be started. The scheduler has disabled the task)"
   --#TYPE			"Svraid Win Event 92"
   --#SUMMARY		"%s(PID=%d) %s %d %s SV RAID: Software error (Task for object cannot be started. The scheduler has disabled the task)"
   --#ARGUMENTS		{ 0, 1, 2, 3, 4 }
   --#SEVERITY		MAJOR
   ::= 28592

svraidWinEvent93 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (SAS topology error)"
   --#TYPE			"Svraid Win Event 92"
   --#SUMMARY		"%s(PID=%d) %s %d %s SV RAID:%s Adapter error (SAS topology error) vendor-id=%s device-id=%s revision=%s"
   --#ARGUMENTS		{ 0, 1, 2, 3, 4, 5, 6, 7, 8 }
   --#SEVERITY		MAJOR
   ::= 28593

svraidWinEvent94 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from copyback to failed)"
   --#TYPE			"Svraid Win Event 94"
   --#SUMMARY		"%s(PID=%d) %s %d %s SV RAID:%s Device error (State change on disk from copyback to failed)"
   --#ARGUMENTS		{ 0, 1, 2, 3, 4, 5 }
   --#SEVERITY		MAJOR
   ::= 28594

svraidWinEvent95 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from copyback to offline)"
   --#TYPE			"Svraid Win Event 95"
   --#SUMMARY		"%s(PID=%d) %s %d %s SV RAID:%s Device error (State change on disk from copyback to offline)"
   --#ARGUMENTS		{ 0, 1, 2, 3, 4, 5 }
   --#SEVERITY		MINOR
   ::= 28595

svraidWinEvent96 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from JBOD to failed)"
   --#TYPE			"Svraid Win Event 96"
   --#SUMMARY		"%s(PID=%d) %s %d %s SV RAID:%s Device error (State change on disk from JBOD to failed)"
   --#ARGUMENTS		{ 0, 1, 2, 3, 4, 5 }
   --#SEVERITY		MAJOR
   ::= 28596

svraidWinEvent97 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change on disk from JBOD to offline)"
   --#TYPE			"Svraid Win Event 97"
   --#SUMMARY		"%s(PID=%d) %s %d %s SV RAID:%s Device error (State change on disk from JBOD to offline)"
   --#ARGUMENTS		{ 0, 1, 2, 3, 4, 5 }
   --#SEVERITY		MINOR
   ::= 28597

svraidWinEvent98 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from copyback to failed)"
   --#TYPE			"Svraid Win Event 98"
   --#SUMMARY		"%s(PID=%d) %s %d %s SV RAID:%s Device error (State change by user on disk from copyback to failed)"
   --#ARGUMENTS		{ 0, 1, 2, 3, 4, 5 }
   --#SEVERITY		MAJOR
   ::= 28598

svraidWinEvent99 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from copyback to offline)"
   --#TYPE			"Svraid Win Event 99"
   --#SUMMARY		"%s(PID=%d) %s %d %s SV RAID:%s Device error (State change by user on disk from copyback to offline)"
   --#ARGUMENTS		{ 0, 1, 2, 3, 4, 5 }
   --#SEVERITY		MINOR
   ::= 28599

svraidWinEvent100 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (State change by user on disk from JBOD to failed)"
   --#TYPE			"Svraid Win Event 100"
   --#SUMMARY		"%s(PID=%d) %s %d %s SV RAID:%s Device error (State change by user on disk from JBOD to failed)"
   --#ARGUMENTS		{ 0, 1, 2, 3, 4, 5 }
   --#SEVERITY		MAJOR
   ::= 28600

svraidWinEvent101 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Disk security failed to communicate with EKMS)"
   --#TYPE			"Svraid Win Event 101"
   --#SUMMARY		"%s(PID=%d) %s %d %s SV RAID:%s Adapter error (Disk security failed to communicate with EKMS) vendor-id=%s device-id=%s revision=%s"
   --#ARGUMENTS		{ 0, 1, 2, 3, 4, 5, 6, 7, 8 }
   --#SEVERITY		MINOR
   ::= 28601

svraidWinEvent102 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Logical drive secure failed)"
   --#TYPE			"Svraid Win Event 102"
   --#SUMMARY		"%s(PID=%d) %s %d %s SV RAID:%s Adapter error (Logical drive secure failed) vendor-id=%s device-id=%s revision=%s"
   --#ARGUMENTS		{ 0, 1, 2, 3, 4, 5, 6, 7, 8 }
   --#SEVERITY		MINOR
   ::= 28602

svraidWinEvent103 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Controller encountered a fatal error and was reset)"
   --#TYPE			"Svraid Win Event 103"
   --#SUMMARY		"%s(PID=%d) %s %d %s SV RAID:%s Adapter error (Controller encountered a fatal error and was reset) vendor-id=%s device-id=%s revision=%s"
   --#ARGUMENTS		{ 0, 1, 2, 3, 4, 5, 6, 7, 8 }
   --#SEVERITY		MAJOR
   ::= 28603

svraidWinEvent104 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Configuration command could not be committed to disk)"
   --#TYPE			"Svraid Win Event 104"
   --#SUMMARY		"%s(PID=%d) %s %d %s SV RAID:%s Device error (Configuration command could not be committed to disk)"
   --#ARGUMENTS		{ 0, 1, 2, 3, 4, 5 }
   --#SEVERITY		MAJOR
   ::= 28604

svraidWinEvent105 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk)"
   --#TYPE			"Svraid Win Event 105"
   --#SUMMARY		"%s(PID=%d) %s %d %s SV RAID:%s Device error (Power state change failed on disk)"
   --#ARGUMENTS		{ 0, 1, 2, 3, 4, 5 }
   --#SEVERITY		MINOR
   ::= 28605

svraidWinEvent106 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk (from stopped to active))"
   --#TYPE			"Svraid Win Event 106"
   --#SUMMARY		"%s(PID=%d) %s %d %s SV RAID:%s Device error (Power state change failed on disk (from stopped to active))"
   --#ARGUMENTS		{ 0, 1, 2, 3, 4, 5 }
   --#SEVERITY		MINOR
   ::= 28606

svraidWinEvent107 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Logical drive is not ready)"
   --#TYPE			"Svraid Win Event 107"
   --#SUMMARY		"%s(PID=%d) %s %d %s SV RAID:%s Device error (Logical drive is not ready)"
   --#ARGUMENTS		{ 0, 1, 2, 3, 4, 5 }
   --#SEVERITY		MINOR
   ::= 28607

svraidWinEvent108 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Adapter has been replaced during reboot)"
   --#TYPE			"Svraid Win Event 108"
   --#SUMMARY		"%s(PID=%d) %s %d %s SV RAID:%s Adapter error (Adapter has been replaced during reboot) vendor-id=%s device-id=%s revision=%s"
   --#ARGUMENTS		{ 0, 1, 2, 3, 4, 5, 6, 7, 8 }
   --#SEVERITY		MINOR
   ::= 28608

svraidWinEvent109 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure power supply removed)"
   --#TYPE			"Svraid Win Event 109"
   --#SUMMARY		"%s(PID=%d) %s %d %s SV RAID:%s Adapter error (Enclosure power supply removed) vendor-id=%s device-id=%s revision=%s"
   --#ARGUMENTS		{ 0, 1, 2, 3, 4, 5, 6, 7, 8 }
   --#SEVERITY		MINOR
   ::= 28609

svraidWinEvent110 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure power supply turned off)"
   --#TYPE			"Svraid Win Event 110"
   --#SUMMARY		"%s(PID=%d) %s %d %s SV RAID:%s Adapter error (Enclosure power supply turned off) vendor-id=%s device-id=%s revision=%s"
   --#ARGUMENTS		{ 0, 1, 2, 3, 4, 5, 6, 7, 8 }
   --#SEVERITY		MINOR
   ::= 28610

svraidWinEvent111 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure temperature sensor below warning threshold)"
   --#TYPE			"Svraid Win Event 111"
   --#SUMMARY		"%s(PID=%d) %s %d %s SV RAID:%s Adapter error (Enclosure temperature sensor below warning threshold) vendor-id=%s device-id=%s revision=%s"
   --#ARGUMENTS		{ 0, 1, 2, 3, 4, 5, 6, 7, 8 }
   --#SEVERITY		MINOR
   ::= 28611

svraidWinEvent112 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure temperature sensor below error threshold)"
   --#TYPE			"Svraid Win Event 112"
   --#SUMMARY		"%s(PID=%d) %s %d %s SV RAID:%s Adapter error (Enclosure temperature sensor below error threshold) vendor-id=%s device-id=%s revision=%s"
   --#ARGUMENTS		{ 0, 1, 2, 3, 4, 5, 6, 7, 8 }
   --#SEVERITY		MAJOR
   ::= 28612

svraidWinEvent113 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure temperature sensor above warning threshold)"
   --#TYPE			"Svraid Win Event 113"
   --#SUMMARY		"%s(PID=%d) %s %d %s SV RAID:%s Adapter error (Enclosure temperature sensor above warning threshold) vendor-id=%s device-id=%s revision=%s"
   --#ARGUMENTS		{ 0, 1, 2, 3, 4, 5, 6, 7, 8 }
   --#SEVERITY		MINOR
   ::= 28613

svraidWinEvent114 TRAP-TYPE
   ENTERPRISE   psaWinSvsRaidTrap
   VARIABLES {
      trapPartitionName,
      trapPartitionId,
      trapEventLevel,
      trapEventId,
      trapUnitName,
      trapSuspect,
      trapVendorId,
      trapDeviceId,
      trapRevision,
      trapMmbVip
   }
   DESCRIPTION "SV RAID: Adapter error (Enclosure temperature sensor above error threshold)"
   --#TYPE			"Svraid Win Event 114"
   --#SUMMARY		"%s(PID=%d) %s %d %s SV RAID:%s Adapter error (Enclosure temperature sensor above error threshold) vendor-id=%s device-id=%s revision=%s"
   --#ARGUMENTS		{ 0, 1, 2, 3, 4, 5, 6, 7, 8 }
   --#SEVERITY		MAJOR
   ::= 28614

svraidWinEvent115 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk (from active to transition))"
   --#TYPE			"Svraid Win Event 115"
   --#SUMMARY		"%s(PID=%d) %s %d %s SV RAID:%s Device error (Power state change failed on disk (from active to transition))"
   --#ARGUMENTS		{ 0, 1, 2, 3, 4, 5 }
   --#SEVERITY		MINOR
   ::= 28615

svraidWinEvent116 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk (from stopped to transition))"
   --#TYPE			"Svraid Win Event 116"
   --#SUMMARY		"%s(PID=%d) %s %d %s SV RAID:%s Device error (Power state change failed on disk (from stopped to transition))"
   --#ARGUMENTS		{ 0, 1, 2, 3, 4, 5 }
   --#SEVERITY		MINOR
   ::= 28616

svraidWinEvent117 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk (from transition to active))"
   --#TYPE			"Svraid Win Event 117"
   --#SUMMARY		"%s(PID=%d) %s %d %s SV RAID:%s Device error (Power state change failed on disk (from transition to active))"
   --#ARGUMENTS		{ 0, 1, 2, 3, 4, 5 }
   --#SEVERITY		MINOR
   ::= 28617

svraidWinEvent118 TRAP-TYPE
   ENTERPRISE   psaWinSvsRaidTrap
   VARIABLES {
      trapPartitionName,
      trapPartitionId,
      trapEventLevel,
      trapEventId,
      trapUnitName,
      trapSuspect,
      trapMmbVip
   }
   DESCRIPTION "SV RAID: Device error (Power state change failed on disk (from transition to stopped))"
   --#TYPE			"Svraid Win Event 118"
   --#SUMMARY		"%s(PID=%d) %s %d %s SV RAID:%s Device error (Power state change failed on disk (from transition to stopped))"
   --#ARGUMENTS		{ 0, 1, 2, 3, 4, 5 }
   --#SEVERITY		MINOR
   ::= 28618

END
