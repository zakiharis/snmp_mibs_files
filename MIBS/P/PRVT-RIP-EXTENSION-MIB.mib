-- *********************************************************************
-- *********************************************************************
-- ** Filename: PRVT-RIP-EXTENSION-MIB
-- ** Project: T - Ethernet and Fast Ethernet IP Switches.
-- ** Purpose: Private MIB
-- *********************************************************************
-- (c) Copyright,  2001,  BATM Advanced Communications. All rights reserved.
-- WARNING:
--
-- BY UTILIZING THIS FILE,  YOU AGREE TO THE FOLLOWING:
--
-- This file is the property of BATM Advanced Communications.
-- BATM Advanced Communications retains all title and
-- ownership in the Specification,  including any revisions.

-- BATM Advanced Communications grants all interested parties a non-exclusive
-- license to use and distribute an unmodified copy of this
-- Specification in connection with management of BATM Advanced Communications 
-- and Telco Systems products,  and without fee,  provided that the following
-- conditions are met:
-- 1. Redistributions of this specification must retain the above copyright
-- notice,  this list of conditions and the following disclaimer.
-- 2. Redistributions in binary form must reproduce the above copyright
-- notice,  this list of conditions and the following disclaimer in the
-- documentation and/or other materials provided with the distribution.
-- 3. The name of the BATM Advanced Communications MAY NOT be used to endorse
-- or promote products derived from this specification without specific prior written
-- permission.
--
-- EXCEPT AS RESTRICTED BY LAW,  OR AS PROVIDED IN BATM'S LIMITED
-- WARRANTY,  THE SPECIFICATIONS CONTAINED IN THIS FILE ARE
-- PROVIDED "AS IS" WITHOUT WARRANTY OF ANY KIND,  EITHER EXPRESSED
-- OR IMPLIED,  INCLUDING BUT NOT LIMITED TO,  ANY IMPLIED WARRANTIES
-- OF MERCHANTABILITY OR FITNESS FOR A PARTICULAR PURPOSE.
-- IN NO EVENT SHALL BATM BE LIABLE FOR ANY DAMAGES WHATSOEVER
-- INCLUDING,  WITHOUT LIMITATION,  DAMAGES FOR LOSS OF BUSINESS
-- PROFITS,  BUSINESS INTERRUPTION,  LOSS OF BUSINESS INFORMATION OR
-- OTHER CONSEQUENTIAL DAMAGES ARISING OUT OF THE USE,  OR INABILITY
-- TO USE,  THE SPECIFICATION CONTAINED IN THIS FILE.
-- *********************************************************************
-- (c) Copyright,  2001,  BATM Advanced Communications. All rights reserved.
-- WARNING:
--
-- BY UTILIZING THIS FILE,  YOU AGREE TO THE FOLLOWING:
--
-- This file is the property of BATM Advanced Communications.
-- BATM Advanced Communications retains all title and
-- ownership in the Specification,  including any revisions.

-- BATM Advanced Communications grants all interested parties a non-exclusive
-- license to use and distribute an unmodified copy of this
-- Specification in connection with management of BATM Advanced Communications 
-- and Telco Systems products,  and without fee,  provided that the following
-- conditions are met:
-- 1. Redistributions of this specification must retain the above copyright
-- notice,  this list of conditions and the following disclaimer.
-- 2. Redistributions in binary form must reproduce the above copyright
-- notice,  this list of conditions and the following disclaimer in the
-- documentation and/or other materials provided with the distribution.
-- 3. The name of the BATM Advanced Communications MAY NOT be used to endorse
-- or promote products derived from this specification without specific prior written
-- permission.
--
-- EXCEPT AS RESTRICTED BY LAW,  OR AS PROVIDED IN BATM'S LIMITED
-- WARRANTY,  THE SPECIFICATIONS CONTAINED IN THIS FILE ARE
-- PROVIDED "AS IS" WITHOUT WARRANTY OF ANY KIND,  EITHER EXPRESSED
-- OR IMPLIED,  INCLUDING BUT NOT LIMITED TO,  ANY IMPLIED WARRANTIES
-- OF MERCHANTABILITY OR FITNESS FOR A PARTICULAR PURPOSE.
-- IN NO EVENT SHALL BATM BE LIABLE FOR ANY DAMAGES WHATSOEVER
-- INCLUDING,  WITHOUT LIMITATION,  DAMAGES FOR LOSS OF BUSINESS
-- PROFITS,  BUSINESS INTERRUPTION,  LOSS OF BUSINESS INFORMATION OR
-- OTHER CONSEQUENTIAL DAMAGES ARISING OUT OF THE USE,  OR INABILITY
-- TO USE,  THE SPECIFICATION CONTAINED IN THIS FILE.

PRVT-RIP-EXTENSION-MIB DEFINITIONS ::= BEGIN
IMPORTS
    MODULE-IDENTITY,  OBJECT-TYPE
        FROM SNMPv2-SMI
    TruthValue,  RowStatus
        FROM SNMPv2-TC

        ipSwitch   
	                                     FROM PRVT-SWITCH-MIB;          



    prvtRIPExtensionMib MODULE-IDENTITY
    LAST-UPDATED "200801010000Z"
    ORGANIZATION "BATM Advanced Communication"
    CONTACT-INFO
        "BATM/Telco Systems Support team
				Email: 
				For North America: techsupport@telco.com
				For North Europe: support@batm.de,  info@batm.de
				For the rest of the world: techsupport@telco.com"

    DESCRIPTION
        "The RIP extension MIB module contains additional information,  needed to
         control the RIP protocol,  that is not found in the standard RFC"

    -- revision history   
         REVISION     "200801010000Z"
     	 DESCRIPTION
		"Removed redefined OIDs in private vendor extension definitions." 
     REVISION     "200502160000Z"
     	 DESCRIPTION
		"Fixed spelling errors and changed the contact info." 

	REVISION     "200305060000Z"
	DESCRIPTION
					"Move to SMI-V2."
    REVISION     "200211110000Z"
    DESCRIPTION
        "Initial version."


    ::= { routingProtocols 1 }
    -------------------------------------------------------------------------------
    --     PRIVATE BRANCH  PRODUCTS
    -------------------------------------------------------------------------------
    routingProtocols   OBJECT IDENTIFIER ::= { ipSwitch 4 }


    ripExtension OBJECT IDENTIFIER ::= { prvtRIPExtensionMib 1 }

    ripEnable OBJECT-TYPE
    SYNTAX TruthValue
    MAX-ACCESS read-write
    STATUS current
    DESCRIPTION
        "This object enables/disables the RIP process in the switch"
    ::= { ripExtension 1 }
    
    ripRedistributeTable OBJECT-TYPE
    SYNTAX SEQUENCE OF RipRedistributeEntry
    MAX-ACCESS not-accessible
    STATUS current
    DESCRIPTION
    "The table represents the routing protocols,  redistributed into the RIP 
    routing domain. 
    
    Creation of conceptual row in the table starts the redistribution of 
    the specified protocol,  which would lead to the injection of routing information 
    from that protocol into RIP. 
    
    Deletion of conceptual row would stop the redistribution of that protocol into RIP."
    ::= { ripExtension 2 }

    ripRedistributeEntry OBJECT-TYPE
    SYNTAX RipRedistributeEntry
    MAX-ACCESS not-accessible
    STATUS current
    DESCRIPTION
               "The conceptual row represents a routing protocol,  redistributed into RIP"
    INDEX {ripRedistributeProtocol}
    ::= {ripRedistributeTable 1}

    RipRedistributeEntry ::= SEQUENCE {
        ripRedistributeProtocol       INTEGER, 
        ripRedistributeMetric         INTEGER, 
        ripRedistributeRouteMap       OCTET STRING, 
        ripRedistributeRowStatus      RowStatus
    }


    ripRedistributeProtocol OBJECT-TYPE
    SYNTAX INTEGER {
           kernel(1), 
           connected(2), 
           static(3), 
           ospf(4), 
           bgp(5)
           }
    MAX-ACCESS read-only
    STATUS current
    DESCRIPTION
		"The specific routes redistributed into RIP. For T4R models the valid values 
		are connected,  static and OSPF. For T5 the valid values are kernel,  connected,  
		static and OSPF. For T5RN,  T5Pro,  T6,  and E-series and G-series all of the above 
		routes can be redistributed"
        ::= { ripRedistributeEntry 1}

    ripRedistributeMetric OBJECT-TYPE
    SYNTAX INTEGER (1..16)
    MAX-ACCESS read-create
    STATUS current
    DESCRIPTION
		"The metric,  with which the external routes will be redistributed in the RIP"
        ::= {ripRedistributeEntry 2}

    ripRedistributeRouteMap OBJECT-TYPE
    SYNTAX OCTET STRING
    MAX-ACCESS read-create
    STATUS current
    DESCRIPTION
               "The route map that would filter the redistributed routing information"
    ::= {ripRedistributeEntry 3}

    ripRedistributeRowStatus OBJECT-TYPE
    SYNTAX RowStatus
    MAX-ACCESS read-create
    STATUS current
    DESCRIPTION
        "Indicates the status of the row. Setting of this field to active enables the 
        redistribution of the protocol. Setting this field to destroy disables the 
        redistribution of the protocol"
    ::= {ripRedistributeEntry 4}

END
