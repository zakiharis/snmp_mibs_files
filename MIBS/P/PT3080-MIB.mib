PT3080-MIB DEFINITIONS ::= BEGIN

IMPORTS
    pt FROM PT-MIB
    MODULE-IDENTITY, OBJECT-TYPE, NOTIFICATION-TYPE, Integer32, IpAddress FROM SNMPv2-SMI
    MODULE-COMPLIANCE, OBJECT-GROUP, NOTIFICATION-GROUP, AGENT-CAPABILITIES FROM SNMPv2-CONF
    DateAndTime, DisplayString FROM SNMPv2-TC;

pt3080 MODULE-IDENTITY
    LAST-UPDATED "201506220940Z"
    ORGANIZATION "ProTelevision Technologies A/S, Denmark"
    CONTACT-INFO
      "Contact: 

       Web: http://www.protelevision.com

       Address: Valhoejs Alle 176, DK-2610 Roedovre, Denmark
       Telephone: +45 44700000
       Fax:       +45 44700001"

    DESCRIPTION
      "This is the MIB file of PT3080 DVB-T/H Modulator.

       Copyright (c) 2008-2015 Protelevision Technologies A/S.
       All rights reserved.
       Reproduction of this document is authorized on the condition
       that the foregoing copyright notice is included."

    REVISION
      "201506220940Z"

    DESCRIPTION
      "SWPROTELEVISION_P3_1_02_157 build 1441106393"

::=  { pt 3080 }

pt3080System           OBJECT IDENTIFIER ::= { pt3080  1 }
pt3080Mode             OBJECT IDENTIFIER ::= { pt3080  2 }
pt3080Input            OBJECT IDENTIFIER ::= { pt3080  3 }
pt3080Output           OBJECT IDENTIFIER ::= { pt3080  4 }
pt3080Gps              OBJECT IDENTIFIER ::= { pt3080  7 }
pt3080TSoIP            OBJECT IDENTIFIER ::= { pt3080  10 }
pt3080Monitor          OBJECT IDENTIFIER ::= { pt3080  12 }
pt3080Test             OBJECT IDENTIFIER ::= { pt3080  13 }
pt3080Alarm            OBJECT IDENTIFIER ::= { pt3080  14 }
pt3080Preset           OBJECT IDENTIFIER ::= { pt3080  15 }
pt3080Eventlog         OBJECT IDENTIFIER ::= { pt3080  16 }
pt3080Comms            OBJECT IDENTIFIER ::= { pt3080  17 }
pt3080Demodulator      OBJECT IDENTIFIER ::= { pt3080  24 }

pt3080Precorrector     OBJECT IDENTIFIER ::= { pt3080  25 }

pt3080ASI              OBJECT IDENTIFIER ::= { pt3080  30 }

pt3080Reception        OBJECT IDENTIFIER ::= { pt3080  26 }

pt3080Backplane        OBJECT IDENTIFIER ::= { pt3080  27 }


pt3080Notifs           OBJECT IDENTIFIER ::= { pt3080  64 }

pt3080Conformance      OBJECT IDENTIFIER ::= { pt3080 100 }
pt3080Compliances      OBJECT IDENTIFIER ::= { pt3080Conformance 1 }

--

--
-- pt3080 System sub-tree
--  

pt3080SystemInstrumentFW1Rev    OBJECT-TYPE
    SYNTAX                      DisplayString
    MAX-ACCESS                  read-only
    STATUS                      current
    DESCRIPTION
        "The instrument FW1 revision"
    ::= { pt3080System 7 }

pt3080SystemInstrumentFW1RevBL  OBJECT-TYPE
    SYNTAX                      DisplayString
    MAX-ACCESS                  read-only
    STATUS                      current
    DESCRIPTION
        "The instrument FW1 BL revision"
    ::= { pt3080System 8 }

pt3080SystemInstrumentFW2Rev    OBJECT-TYPE
    SYNTAX                      DisplayString
    MAX-ACCESS                  read-only
    STATUS                      current
    DESCRIPTION
        "The instrument FW2 revision"
    ::= { pt3080System 9 }

pt3080SystemInstrumentFW2RevBL  OBJECT-TYPE
    SYNTAX                      DisplayString
    MAX-ACCESS                  read-only
    STATUS                      current
    DESCRIPTION
        "The instrument FW2 BL revision"
    ::= { pt3080System 10 }

pt3080SystemInstrumentFW3Rev    OBJECT-TYPE
    SYNTAX                      DisplayString
    MAX-ACCESS                  read-only
    STATUS                      current
    DESCRIPTION
        "The instrument FW3 revision"
    ::= { pt3080System 11 }

pt3080SystemInstrumentFW4Rev    OBJECT-TYPE
    SYNTAX                      DisplayString
    MAX-ACCESS                  read-only
    STATUS                      current
    DESCRIPTION
        "The instrument FW4 revision"
    ::= { pt3080System 12 }

pt3080SystemInstrumentPCBRev    OBJECT-TYPE
    SYNTAX                      DisplayString
    MAX-ACCESS                  read-only
    STATUS                      current
    DESCRIPTION
        "The instrument PCB revision"
    ::= { pt3080System 13 }

pt3080SystemInstrumentCalibrationRev OBJECT-TYPE
    SYNTAX                      DisplayString
    MAX-ACCESS                  read-only
    STATUS                      current
    DESCRIPTION
        "The instrument Calibration revision"
    ::= { pt3080System 14 }

pt3080SystemInstrumentCalibrationDate OBJECT-TYPE
    SYNTAX                      DisplayString
    MAX-ACCESS                  read-only
    STATUS                      current
    DESCRIPTION
        "The instrument Calibration date"
    ::= { pt3080System 15 }

pt3080SystemReboot              OBJECT-TYPE
    SYNTAX                      INTEGER { keeprunning(0), sameimage(1), otherimage(2), image0(3), image1(4) }
    MAX-ACCESS                  read-write
    STATUS                      current
    DESCRIPTION
        "Force a reboot of the device on the designated image now."
    ::= { pt3080System 16 }

pt3080SystemRebootDefaultConfig OBJECT-TYPE
    SYNTAX                      INTEGER { keeprunning(0), reboot(1) }
    MAX-ACCESS                  read-write
    STATUS                      current
    DESCRIPTION
        "Restore all parameters to factory default and reboot the device on the same image."
    ::= { pt3080System 19 }

pt3080SystemDateTime            OBJECT-TYPE
    SYNTAX                      DisplayString
    MAX-ACCESS                  read-write
    STATUS                      current
    DESCRIPTION
        "The current date/time in local timezone of the device.
         Format is YYYY MM DD HH MM SS."
    ::= { pt3080System 22 }

pt3080SystemImage0Version       OBJECT-TYPE
    SYNTAX                      DisplayString
    MAX-ACCESS                  read-only
    STATUS                      current
    DESCRIPTION
        "The image 0 version string."
    ::= { pt3080System 24 }

pt3080SystemImage0InstalledDate OBJECT-TYPE
    SYNTAX                      DateAndTime
    MAX-ACCESS                  read-only
    STATUS                      current
    DESCRIPTION
        "The date and time image 0 was installed."
    ::= { pt3080System 25 }

pt3080SystemImage1version       OBJECT-TYPE
    SYNTAX                      DisplayString
    MAX-ACCESS                  read-only
    STATUS                      current
    DESCRIPTION
        "The image 1 version string."
    ::= { pt3080System 26 }

pt3080SystemImage1InstalledDate OBJECT-TYPE
    SYNTAX                      DateAndTime
    MAX-ACCESS                  read-only
    STATUS                      current
    DESCRIPTION
        "The date and time image 0 was installed."
    ::= { pt3080System 27 }

pt3080SystemServiceLED OBJECT-TYPE
    SYNTAX      INTEGER { off(0), on(1) }
    MAX-ACCESS  read-write
    STATUS      current
    DESCRIPTION
        "Control the Service LED on frontpanel."
    ::= { pt3080System  28 }

pt3080SystemLanguage OBJECT-TYPE
    SYNTAX      INTEGER { c(0), da-dk(1), ru-ru(2), es-es(3), pt-br(4), it-it(5), de-de(6), fr-fr(7) }
    MAX-ACCESS  read-write
    STATUS      current
    DESCRIPTION
        "Controls which language is used on web and facia. Change requires
         reboot."
    ::= { pt3080System  33 }

pt3080SystemType OBJECT-TYPE
    SYNTAX      INTEGER { modulator(0), repeater(1) }
    MAX-ACCESS  read-write
    STATUS      current
    DESCRIPTION
        "The system type to start in on next reboot."
    ::= { pt3080System  30 }

pt3080SystemModulationStandard OBJECT-TYPE
    SYNTAX      INTEGER { dvbt(0), dvbt2(1), atsc(2), isdbt(3), iboc(4) }
    MAX-ACCESS  read-write
    STATUS      current
    DESCRIPTION
        "The Modulation Standard to start in on next reboot."
    ::= { pt3080System  32 }

pt3080SystemCurrentImage OBJECT-TYPE
    SYNTAX      Integer32
    MAX-ACCESS  read-only
    STATUS      current
    DESCRIPTION
        "The flash Image the device is currently booted from."
    ::= { pt3080System  23 }

pt3080SystemInstrumentKU OBJECT-TYPE
    SYNTAX      DisplayString
    MAX-ACCESS  read-only
    STATUS      current
    DESCRIPTION
        "The instrument serial number."
    ::= { pt3080System  1 }

pt3080SystemInstrumentType OBJECT-TYPE
    SYNTAX      DisplayString
    MAX-ACCESS  read-only
    STATUS      current
    DESCRIPTION
        "The product type designation."
    ::= { pt3080System  2 }

pt3080SystemInstrumentOptions OBJECT-TYPE
    SYNTAX      DisplayString
    MAX-ACCESS  read-only
    STATUS      current
    DESCRIPTION
        "The options installed on this instrument."
    ::= { pt3080System  6 }

pt3080SystemDateTimeSync OBJECT-TYPE
    SYNTAX      INTEGER { manual(0), auto(1), gps(2), ntp(3) }
    MAX-ACCESS  read-write
    STATUS      current
    DESCRIPTION
        "The method used to synchronize system RTC. Mode auto means use
         gps if available else ntp else manual."
    ::= { pt3080System  20 }

pt3080SystemDateTimeSyncActual OBJECT-TYPE
    SYNTAX      INTEGER { manual(0), auto(1), gps(2), ntp(3) }
    MAX-ACCESS  read-only
    STATUS      current
    DESCRIPTION
        "The actual method used to synchronize system RTC."
    ::= { pt3080System  31 }

pt3080SystemTimezone OBJECT-TYPE
    SYNTAX      DisplayString
    MAX-ACCESS  read-write
    STATUS      current
    DESCRIPTION
        "The Time Zone used for displaying Data and Time."
    ::= { pt3080System  21 }

pt3080SystemInstrumentSWRev OBJECT-TYPE
    SYNTAX      DisplayString
    MAX-ACCESS  read-only
    STATUS      current
    DESCRIPTION
        "The instrument Software Revision currently running."
    ::= { pt3080System  3 }

pt3080SystemInstrumentBootLoaderRev OBJECT-TYPE
    SYNTAX      DisplayString
    MAX-ACCESS  read-only
    STATUS      current
    DESCRIPTION
        "The instrument Bootloader Software Revision."
    ::= { pt3080System  4 }

pt3080SystemInstrumentKernelRev OBJECT-TYPE
    SYNTAX      DisplayString
    MAX-ACCESS  read-only
    STATUS      current
    DESCRIPTION
        "The instrument O/S Kernel Version."
    ::= { pt3080System  5 }

pt3080SystemOperationOnTime OBJECT-TYPE
    SYNTAX      Integer32
    UNITS       "1 secs"
    MAX-ACCESS  read-only
    STATUS      current
    DESCRIPTION
        "Number of seconds this unit has been turned on since production."
    ::= { pt3080System  34 }

pt3080SystemOperationOnAirTime OBJECT-TYPE
    SYNTAX      Integer32
    UNITS       "1 secs"
    MAX-ACCESS  read-only
    STATUS      current
    DESCRIPTION
        "Number of seconds this unit has been unmuted since production."
    ::= { pt3080System  35 }

pt3080SystemOperationNumberOfBoots OBJECT-TYPE
    SYNTAX      Integer32
    MAX-ACCESS  read-only
    STATUS      current
    DESCRIPTION
        "Number of times this unit has been booted since last factory
         default restore."
    ::= { pt3080System  36 }

pt3080SystemBackplaneid OBJECT-TYPE
    SYNTAX      Integer32
    MAX-ACCESS  read-only
    STATUS      current
    DESCRIPTION
        "ID of the backplane the device is plugged into"
    ::= { pt3080System  40 }

pt3080SystemBackplaneIdRaw OBJECT-TYPE
    SYNTAX      Integer32
    MAX-ACCESS  read-only
    STATUS      current
    DESCRIPTION
        "Raw ID of the backplane the device is plugged into"
    ::= { pt3080System  41 }

pt3080SystemBackplaneIdPcb OBJECT-TYPE
    SYNTAX      Integer32
    MAX-ACCESS  read-only
    STATUS      current
    DESCRIPTION
        "PCB version of the backplane the device is plugged into"
    ::= { pt3080System  42 }

pt3080SystemBackplaneIdCableOptions OBJECT-TYPE
    SYNTAX      Integer32
    MAX-ACCESS  read-only
    STATUS      current
    DESCRIPTION
        "Cable options of the backplane the device is plugged into"
    ::= { pt3080System  43 }

pt3080SystemBackplaneIdMAnuf OBJECT-TYPE
    SYNTAX      DisplayString
    MAX-ACCESS  read-only
    STATUS      current
    DESCRIPTION
        "Manufacture ID of the backplane the device is plugged into"
    ::= { pt3080System  44 }

pt3080SystemBackplaneCalibrationDate OBJECT-TYPE
    SYNTAX      DisplayString
    MAX-ACCESS  read-only
    STATUS      current
    DESCRIPTION
        "Calibration date of the backplane the device is plugged into"
    ::= { pt3080System  45 }

pt3080SystemBackplaneCalibrationSw OBJECT-TYPE
    SYNTAX      Integer32
    MAX-ACCESS  read-only
    STATUS      current
    DESCRIPTION
        "Calibration SW version of the backplane the device is plugged
         into"
    ::= { pt3080System  46 }

pt3080SystemBackplaneIdPartlist OBJECT-TYPE
    SYNTAX      Integer32
    MAX-ACCESS  read-only
    STATUS      current
    DESCRIPTION
        "Partlist version of the backplane the device is plugged into"
    ::= { pt3080System  47 }


-- Scheduled Action table --

pt3080SystemScheduledActionTable OBJECT-TYPE
    SYNTAX                      SEQUENCE OF Pt3080SystemScheduledActionEntry
    MAX-ACCESS                  not-accessible
    STATUS                      current
    DESCRIPTION
        "This table contains the scheduled actions"
    ::= { pt3080System 50 }

pt3080SystemScheduledActionEntry OBJECT-TYPE
    SYNTAX                      Pt3080SystemScheduledActionEntry
    MAX-ACCESS                  not-accessible
    STATUS                      current
    DESCRIPTION
        "An entry for the scheduled action"
    INDEX                       { pt3080SystemScheduledActionID }
    ::= { pt3080SystemScheduledActionTable 1 }

Pt3080SystemScheduledActionEntry ::= SEQUENCE {
    pt3080SystemScheduledActionID           Integer32,
    pt3080SystemScheduledActionRecurrence   INTEGER,
    pt3080SystemScheduledActionHour         Integer32,
    pt3080SystemScheduledActionMinute       Integer32,
    pt3080SystemScheduledActionWeekday      INTEGER,
    pt3080SystemScheduledActionMonthDay     Integer32,
    pt3080SystemScheduledActionDate         DisplayString,
    pt3080SystemScheduledActionRandomDelay  Integer32,
    pt3080SystemScheduledActionAction       INTEGER,
    pt3080SystemScheduledActionRepeaterMode INTEGER,
    pt3080SystemScheduledActionPresetNo     INTEGER,
    pt3080SystemScheduledActionRebootImage  INTEGER,
    pt3080SystemScheduledActionRebootSystemType  INTEGER,
    pt3080SystemScheduledActionMute         INTEGER,
    pt3080SystemScheduledActionSWUpgradeProtocol INTEGER,
    pt3080SystemScheduledActionSWUpgradeUsername DisplayString,
    pt3080SystemScheduledActionSWUpgradePassword DisplayString,
    pt3080SystemScheduledActionSWUpgradeImageServer DisplayString,
    pt3080SystemScheduledActionSWUpgradeImagePath DisplayString
}

pt3080SystemScheduledActionID   OBJECT-TYPE
    SYNTAX                      Integer32 ( 1 .. 10 )
    MAX-ACCESS                  not-accessible
    STATUS                      current
    DESCRIPTION
        "Unique ID for this scheduled action entry"
    ::= { pt3080SystemScheduledActionEntry 1 }

pt3080SystemScheduledActionRecurrence OBJECT-TYPE
    SYNTAX                      INTEGER { never(0), immediate(1), once(2), hourly(3), daily(4), weekly(5), monthly(6) }
    MAX-ACCESS                  read-write
    STATUS                      current
    DESCRIPTION
        "The interval at which this scheduled action entry will be executed"
    ::= { pt3080SystemScheduledActionEntry 2 }

pt3080SystemScheduledActionHour OBJECT-TYPE
    SYNTAX                      Integer32 ( 0 .. 23 )
    MAX-ACCESS                  read-write
    STATUS                      current
    DESCRIPTION
        "The recurrence hour used when pt3080SystemScheduledActionRecurrence is once, hourly, dayly, weekly and monthly."
    ::= { pt3080SystemScheduledActionEntry 3 }

pt3080SystemScheduledActionMinute OBJECT-TYPE
    SYNTAX                      Integer32 ( 0 .. 59 )
    MAX-ACCESS                  read-write
    STATUS                      current
    DESCRIPTION
        "The recurrence minute used when pt3080SystemScheduledActionRecurrence is once, hourly, dayly, weekly and monthly."
    ::= { pt3080SystemScheduledActionEntry 4 }

pt3080SystemScheduledActionWeekday OBJECT-TYPE
    SYNTAX                      INTEGER { monday(0), tuesday(1), wednesday(2), thursday(3), friday(4), saturday(5), sunday(6) }
    MAX-ACCESS                  read-write
    STATUS                      current
    DESCRIPTION
        "The recurrence weekday used when pt3080SystemScheduledActionRecurrence is weekly."
    ::= { pt3080SystemScheduledActionEntry 5 }

pt3080SystemScheduledActionMonthDay OBJECT-TYPE
    SYNTAX                      Integer32 ( 1 .. 31 )
    MAX-ACCESS                  read-write
    STATUS                      current
    DESCRIPTION
        "The recurrence day of the monthe used when pt3080SystemScheduledActionRecurrence is monthly."
    ::= { pt3080SystemScheduledActionEntry 6 }

pt3080SystemScheduledActionDate OBJECT-TYPE
    SYNTAX                      DisplayString
    MAX-ACCESS                  read-write
    STATUS                      current
    DESCRIPTION
        "The recurrence date used when pt3080SystemScheduledActionRecurrence is once.
         The format is dd/mm/yyyy."
    ::= { pt3080SystemScheduledActionEntry 7 }

pt3080SystemScheduledActionRandomDelay OBJECT-TYPE
    SYNTAX                      Integer32 ( 0 .. 600 )
    UNITS                       "secs"
    MAX-ACCESS                  read-write
    STATUS                      current
    DESCRIPTION
        "An extra random delay added before the action for this entry is executed.
         A setting of x means that a random delay between 0 and x seconds are added."
    ::= { pt3080SystemScheduledActionEntry 8 }

pt3080SystemScheduledActionAction OBJECT-TYPE
    SYNTAX                      INTEGER { none(0), repeatermode(1), preset(2), swupgrade(3), reboot(4), mute(5) }
    MAX-ACCESS                  read-write
    STATUS                      current
    DESCRIPTION
        "The action for this entry is executed"
    ::= { pt3080SystemScheduledActionEntry 9 }

pt3080SystemScheduledActionRepeaterMode OBJECT-TYPE
    SYNTAX			INTEGER { auto(0), 
                                          digital-iso-repeater(1),
                                          digital-transposer(2),
                                          analog-iso-repeater(3),
                                          analog-transposer(4) }
    MAX-ACCESS                  read-write
    STATUS                      current
    DESCRIPTION
        "The new repeater mode to change to when pt3080SystemScheduledActionAction
         of type repeatermode is executed"
    ::= { pt3080SystemScheduledActionEntry 10 }

pt3080SystemScheduledActionPresetNo OBJECT-TYPE
    SYNTAX			INTEGER { auto(0), 
                                          digital-iso-repeater(1),
                                          digital-transposer(2),
                                          analog-iso-repeater(3),
                                          analog-transposer(4) }
    MAX-ACCESS                  read-write
    STATUS                      current
    DESCRIPTION
        "The preset to load when pt3080SystemScheduledActionAction
         of type preset is executed"
    ::= { pt3080SystemScheduledActionEntry 11 }

pt3080SystemScheduledActionRebootImage OBJECT-TYPE
    SYNTAX                      INTEGER { sameimage(0), otherimage(1), image0(2), image1(3) }
    MAX-ACCESS                  read-write
    STATUS                      current
    DESCRIPTION
        "The image to reboot to when pt3080SystemScheduledActionAction
         of type reboot is executed"
    ::= { pt3080SystemScheduledActionEntry 12 }

pt3080SystemScheduledActionRebootSystemType OBJECT-TYPE
    SYNTAX                      INTEGER { modulator(0), repeater(1), same(2) }
    MAX-ACCESS                  read-write
    STATUS                      current
    DESCRIPTION
        "The system type to reboot to when pt3080SystemScheduledActionAction
         of type reboot is executed"
    ::= { pt3080SystemScheduledActionEntry 13 }

pt3080SystemScheduledActionMute OBJECT-TYPE
    SYNTAX                      INTEGER { off(0), on(1) }
    MAX-ACCESS                  read-write
    STATUS                      current
    DESCRIPTION
        "The mute mode to change into when pt3080SystemScheduledActionAction
         of type mute is executed"
    ::= { pt3080SystemScheduledActionEntry 14 }

pt3080SystemScheduledActionSWUpgradeProtocol OBJECT-TYPE
    SYNTAX                      INTEGER { http(0), ftp(1) }
    MAX-ACCESS                  read-write
    STATUS                      current
    DESCRIPTION
        "The protocol to use into when pt3080SystemScheduledActionAction
         of type swupgrade(3) is executed"
    ::= { pt3080SystemScheduledActionEntry 15 }

pt3080SystemScheduledActionSWUpgradeUsername OBJECT-TYPE
    SYNTAX                      DisplayString
    MAX-ACCESS                  read-write
    STATUS                      current
    DESCRIPTION
        "The username to use into when pt3080SystemScheduledActionAction
         of type swupgrade(3) is executed"
    ::= { pt3080SystemScheduledActionEntry 16 }

pt3080SystemScheduledActionSWUpgradePassword OBJECT-TYPE
    SYNTAX                      DisplayString
    MAX-ACCESS                  read-write
    STATUS                      current
    DESCRIPTION
        "The password to use into when pt3080SystemScheduledActionAction
         of type swupgrade(3) is executed"
    ::= { pt3080SystemScheduledActionEntry 17 }

pt3080SystemScheduledActionSWUpgradeImageServer OBJECT-TYPE
    SYNTAX                      DisplayString
    MAX-ACCESS                  read-write
    STATUS                      current
    DESCRIPTION
        "The server name to use into when pt3080SystemScheduledActionAction
         of type swupgrade(3) is executed"
    ::= { pt3080SystemScheduledActionEntry 18 }

pt3080SystemScheduledActionSWUpgradeImagePath OBJECT-TYPE
    SYNTAX                      DisplayString
    MAX-ACCESS                  read-write
    STATUS                      current
    DESCRIPTION
        "The image path name to use into when pt3080SystemScheduledActionAction
         of type swupgrade(3) is executed"
    ::= { pt3080SystemScheduledActionEntry 19 }

--
-- pt3080 Mode sub-tree
--
pt3080ModeListenBroadcast OBJECT-TYPE
    SYNTAX      INTEGER { off(0), on(1) }
    MAX-ACCESS  read-write
    STATUS      current
    DESCRIPTION
        "Control wheter to react on broadcast tx id."
    ::= { pt3080Mode  40 }


pt3080ModeNetwork               OBJECT-TYPE
    SYNTAX                      INTEGER { network-mode-mfn(0), network-mode-sfn(1) }
    MAX-ACCESS                  read-write
    STATUS                      current
    DESCRIPTION
        "Network mode multi-frequency-network or single-frequency-network"
    ::= { pt3080Mode 1 }

pt3080ModeHierarchy             OBJECT-TYPE
    SYNTAX                      INTEGER { network-hierarchy-none(0), network-hierarchy-h1(1), network-hierarchy-h2(2), network-hierarchy-h4(3) }
    MAX-ACCESS                  read-write
    STATUS                      current
    DESCRIPTION
        "Hierarchy mode. Cannot be set if pt3080ModeMipControl is on(1)."
    ::= { pt3080Mode 2 }

pt3080Modeifft                  OBJECT-TYPE
    SYNTAX                      INTEGER { ifft-mode-2k(0), ifft-mode-4k(1), ifft-mode-8k(2) }
    MAX-ACCESS                  read-write
    STATUS                      current
    DESCRIPTION
        "IFFT 2k, 4k or 8k mode. Cannot be set if pt3080ModeMipControl is on(1)."
    ::= { pt3080Mode 3 }

pt3080ModeCodeRateHighPrio      OBJECT-TYPE
    SYNTAX                      INTEGER {
                                        code-rate-1-2(0),
                                        code-rate-2-3(1),
                                        code-rate-3-4(2),
                                        code-rate-5-6(3),
                                        code-rate-7-8(4)
                               }
    MAX-ACCESS                  read-write
    STATUS                      current
    DESCRIPTION
        "High Priority Code Rate. Cannot be set if pt3080ModeMipControl is on(1)."
    ::= { pt3080Mode 4 }

pt3080ModeCodeRateLowPrio       OBJECT-TYPE
    SYNTAX                      INTEGER {
                                        code-rate-1-2(0), 
                                        code-rate-2-3(1), 
                                        code-rate-3-4(2), 
                                        code-rate-5-6(3), 
                                        code-rate-7-8(4)}
    MAX-ACCESS                  read-write
    STATUS                      current
    DESCRIPTION
        "Low Priority Code Rate. Cannot be set if pt3080ModeMipControl is on(1)."
    ::= { pt3080Mode 5 }

pt3080ModeConstellation         OBJECT-TYPE
    SYNTAX                      INTEGER {
                                        qpsk(0), 
                                        qam16(1),
                                        qam64(2)
                               }
    MAX-ACCESS                  read-write
    STATUS                      current
    DESCRIPTION
        "If QPSK is selected and Hierarchical is <> NONE, 
        then Hierarchical will be forced to NONE. Cannot be set if pt3080ModeMipControl is on(1)."
    ::= { pt3080Mode 6 }

pt3080ModeGuardInterval         OBJECT-TYPE
    SYNTAX                      INTEGER {
                                        guard-1-32(0), 
                                        guard-1-16(1),
                                        guard-1-8(2),
                                        guard-1-4(3)
                                }
    MAX-ACCESS                  read-write
    STATUS                      current
    DESCRIPTION
        "Guard Interval. Cannot be set if pt3080ModeMipControl is on(1)."
    ::= { pt3080Mode 7 }

pt3080ModeCellID        OBJECT-TYPE
    SYNTAX              Integer32 ( 0 .. 65535 )
    MAX-ACCESS          read-write
    STATUS              current
    DESCRIPTION
        "Sets the Cell ID value. Cannot be set if pt3080ModeMipControl is on(1)."
    ::= { pt3080Mode 8 }

pt3080ModeEnableCellID  OBJECT-TYPE
    SYNTAX              INTEGER {off(0), on(1)}
    MAX-ACCESS          read-write
    STATUS              current
    DESCRIPTION
        "Enables Cell ID in the TPS information. Cannot be set if pt3080ModeMipControl is on(1).
         Cannot be set to off(0) if pt3080ModeEnableDVBH is on(1)"
    ::= { pt3080Mode 9 }

pt3080ModeDeepInterleaver OBJECT-TYPE
    SYNTAX              INTEGER {off(0), on(1)}
    MAX-ACCESS          read-write
    STATUS              current
    DESCRIPTION
        "Enables Deep Interleaver. Cannot be set if pt3080ModeMipControl is on(1)."
    ::= { pt3080Mode 10 }

pt3080ModeEnableDVBH    OBJECT-TYPE
    SYNTAX              INTEGER {off(0), on(1)}
    MAX-ACCESS          read-write
    STATUS              current
    DESCRIPTION
        "Enables DVB-H mode"
    ::= { pt3080Mode 11 }

pt3080ModeMpeFecLowPrio OBJECT-TYPE
    SYNTAX              INTEGER {off(0), on(1)}
    MAX-ACCESS          read-write
    STATUS              current
    DESCRIPTION
        "Enables MPE Fec Low Priority. Cannot be set if pt3080ModeMipControl is on(1)."
    ::= { pt3080Mode 12 }

pt3080ModeMpeFecHighPrio OBJECT-TYPE
    SYNTAX              INTEGER {off(0), on(1)}
    MAX-ACCESS          read-write
    STATUS              current
    DESCRIPTION
        "Enables MPE Fec High Priority. Cannot be set if pt3080ModeMipControl is on(1)."
    ::= { pt3080Mode 13 }

pt3080ModeTimeSlicingLowPrio OBJECT-TYPE
    SYNTAX              INTEGER {off(0), on(1)}
    MAX-ACCESS          read-write
    STATUS              current
    DESCRIPTION
        "Enables timeslicing High Priority. Cannot be set if pt3080ModeMipControl is on(1)."
    ::= { pt3080Mode 14 }

pt3080ModeTimeSlicingHighPrio OBJECT-TYPE  
    SYNTAX              INTEGER {off(0), on(1)}
    MAX-ACCESS          read-write
    STATUS              current
    DESCRIPTION
        "Enables timeslicing High Priority. Cannot be set if pt3080ModeMipControl is on(1)."
    ::= { pt3080Mode 15 }


pt3080ModeSfnDelayOffset OBJECT-TYPE
    SYNTAX              Integer32 ( -9999999 .. 9999999 )
    MAX-ACCESS          read-write
    STATUS              current
    DESCRIPTION
        "SFN delay offset"
    ::= { pt3080Mode 16 }


pt3080ModeTxIdent       OBJECT-TYPE
    SYNTAX              Integer32 ( 0..65535 )
    MAX-ACCESS          read-write
    STATUS              current
    DESCRIPTION
        "The transport stream control identifier"
    ::= { pt3080Mode 17 }

pt3080ModeMipControl    OBJECT-TYPE
    SYNTAX              INTEGER { off(0), on(1) }
    MAX-ACCESS          read-write
    STATUS              current
    DESCRIPTION
        "Enables transport stream control of modulator"
    ::= { pt3080Mode 18 }

pt3080ModeMfnKeepNullPackets    OBJECT-TYPE
    SYNTAX                      INTEGER { off(0), on(1) }
    MAX-ACCESS                  read-write
    STATUS                      current
    DESCRIPTION
        "Enables MFN mode keep null packets option"
    ::= { pt3080Mode 19 }

pt3080ModeNetworkDelayHP  OBJECT-TYPE
    SYNTAX              Integer32
    UNITS               "100ns"
    MAX-ACCESS          read-only
    STATUS              current
    DESCRIPTION
        "Current network delay of HP TS"
    ::= { pt3080Mode 20 }
    
pt3080ModeNetworkDelayMinHP OBJECT-TYPE
    SYNTAX              Integer32
    UNITS               "100ns"
    MAX-ACCESS          read-only
    STATUS              current
    DESCRIPTION
        "Minimum network delay  of HP TS seen since last reset"
    ::= { pt3080Mode 21 }
    
pt3080ModeNetworkDelayMaxHP OBJECT-TYPE
    SYNTAX              Integer32
    UNITS               "100ns"
    MAX-ACCESS          read-only
    STATUS              current
    DESCRIPTION
        "Maximum network delay  of HP TS seen since last reset"
    ::= { pt3080Mode 22 }
    
pt3080ModeMaxNetworkDelayHP OBJECT-TYPE
    SYNTAX              Integer32
    UNITS               "100ns"
    MAX-ACCESS          read-only
    STATUS              current
    DESCRIPTION
        "Maximum allowed network delay, as received from MIP"
    ::= { pt3080Mode 23 }
    
pt3080ModeNetworkDelayMarginHP OBJECT-TYPE
    SYNTAX              Integer32
    UNITS               "100ns"
    MAX-ACCESS          read-only
    STATUS              current
    DESCRIPTION
        "Difference between Actual Network Delay and Max. Allowed Network Delay"
    ::= { pt3080Mode 24 }

pt3080ModeNetworkDelayLP  OBJECT-TYPE
    SYNTAX              Integer32
    UNITS               "100ns"
    MAX-ACCESS          read-only
    STATUS              current
    DESCRIPTION
        "Current network delay of LP TS"
    ::= { pt3080Mode 25 }
    
pt3080ModeNetworkDelayMinLP OBJECT-TYPE
    SYNTAX              Integer32
    UNITS               "100ns"
    MAX-ACCESS          read-only
    STATUS              current
    DESCRIPTION
        "Minimum network delay  of LP TS seen since last reset"
    ::= { pt3080Mode 26 }
    
pt3080ModeNetworkDelayMaxLP OBJECT-TYPE
    SYNTAX              Integer32
    UNITS               "100ns"
    MAX-ACCESS          read-only
    STATUS              current
    DESCRIPTION
        "Maximum network delay  of LP TS seen since last reset"
    ::= { pt3080Mode 27 }
    
pt3080ModeMaxNetworkDelayLP OBJECT-TYPE
    SYNTAX              Integer32
    UNITS               "100ns"
    MAX-ACCESS          read-only
    STATUS              current
    DESCRIPTION
        "Maximum allowed network delay, as received from MIP"
    ::= { pt3080Mode 28 }
    
pt3080ModeNetworkDelayMarginLP OBJECT-TYPE
    SYNTAX              Integer32
    UNITS               "100ns"
    MAX-ACCESS          read-only
    STATUS              current
    DESCRIPTION
        "Difference between Actual Network Delay and Max. Allowed Network Delay"
    ::= { pt3080Mode 29 }

pt3080ModeNetworkDelayReset OBJECT-TYPE
    SYNTAX              INTEGER { noop(0), reset(1) }
    MAX-ACCESS          read-write
    STATUS              current
    DESCRIPTION
        "Reset network delay. Always reads back as noop(0)"
    ::= { pt3080Mode 30 }
    
pt3080ModeDefaultMIPOutputPower     OBJECT-TYPE
    SYNTAX              Integer32 ( 0 .. 1000 )
    UNITS               "0.1 dBm"
    MAX-ACCESS          read-write
    STATUS              current
    DESCRIPTION
        "Default MIP value for Output Power Level. Cannot be set if  pt3080ModeMipControlOutputPower is on(1)"
    ::= { pt3080Mode 31 }

pt3080ModeDefaultMIPOutputTimeOffset     OBJECT-TYPE
    SYNTAX              Integer32 ( -9999999 .. 9999999 )
    UNITS               "x100ns"
    MAX-ACCESS          read-write
    STATUS              current
    DESCRIPTION
        "Default MIP value for Output SFN Time Offset. Cannot be set if  pt3080ModeMipControlOutputTimeOffset is on(1)"
    ::= { pt3080Mode 32 }

pt3080ModeDefaultMIPOutputCellID     OBJECT-TYPE
    SYNTAX              Integer32 ( 0 .. 65535 )
    MAX-ACCESS          read-write
    STATUS              current
    DESCRIPTION
        "Default MIP value for Output Cell ID. Cannot be set if  pt3080ModeMipControlOutputCellId is on(1)"
    ::= { pt3080Mode 33 }

pt3080ModeDefaultMIPOutputFreqOffset     OBJECT-TYPE
    SYNTAX              Integer32 ( -8388608 .. 8388607 )
    UNITS               "Hz"
    MAX-ACCESS          read-write
    STATUS              current
    DESCRIPTION
        "Default MIP value for Output frequency Offset. Cannot be set if  pt3080ModeMipControlOutputFreqOffset is on(1)"
    ::= { pt3080Mode 34 }

pt3080ModeMIPMaxSFNDelay         OBJECT-TYPE
    SYNTAX              Integer32
    UNITS               "x100ns"
    MAX-ACCESS          read-only
    STATUS              current
    DESCRIPTION
        "The MIP value for SFN maximum delay"
    ::= { pt3080Mode 35 }

pt3080ModeMipControlOutputPower    OBJECT-TYPE
    SYNTAX              INTEGER { off(0), on(1) }
    MAX-ACCESS          read-write
    STATUS              current
    DESCRIPTION
        "Enables transport stream control of ModeDefaultMIPOutputPower"
    ::= { pt3080Mode 36 }

pt3080ModeMipControlOutputTimeOffset    OBJECT-TYPE
    SYNTAX              INTEGER { off(0), on(1) }
    MAX-ACCESS          read-write
    STATUS              current
    DESCRIPTION
        "Enables transport stream control of ModeDefaultMIPOutputTimeOffset"
    ::= { pt3080Mode 37 }

pt3080ModeMipControlOutputCellId    OBJECT-TYPE
    SYNTAX              INTEGER { off(0), on(1) }
    MAX-ACCESS          read-write
    STATUS              current
    DESCRIPTION
        "Enables transport stream control of ModeDefaultMIPOutputCellId"
    ::= { pt3080Mode 38 }

pt3080ModeMipControlOutputFreqOffset    OBJECT-TYPE
    SYNTAX              INTEGER { off(0), on(1) }
    MAX-ACCESS          read-write
    STATUS              current
    DESCRIPTION
        "Enables transport stream control of ModeDefaultMIPOutputFreqOffset"
    ::= { pt3080Mode 39 }





pt3080ReceptionGainControl OBJECT-TYPE
    SYNTAX      INTEGER { auto(0), freeze(1), manual(2) }
    MAX-ACCESS  read-write
    STATUS      current
    DESCRIPTION
        "Controls the gain function mode."
    ::= { pt3080Reception  9 }

pt3080ReceptionGainManualValue OBJECT-TYPE
    SYNTAX      Integer32 ( 0 .. 700 )
    UNITS       "0.1 dB"
    MAX-ACCESS  read-write
    STATUS      current
    DESCRIPTION
        "Defines manual gain value."
    ::= { pt3080Reception  10 }

pt3080ReceptionGainLimitEnable OBJECT-TYPE
    SYNTAX      INTEGER { off(0), on(1) }
    MAX-ACCESS  read-write
    STATUS      current
    DESCRIPTION
        "Controls the Reception RF Gain limit function."
    ::= { pt3080Reception  11 }

pt3080ReceptionGainLimit OBJECT-TYPE
    SYNTAX      Integer32 ( 200 .. 700 )
    UNITS       "0.1 db"
    MAX-ACCESS  read-write
    STATUS      current
    DESCRIPTION
        "Defines gain limit value."
    ::= { pt3080Reception  12 }

pt3080ReceptionGainCurrent OBJECT-TYPE
    SYNTAX      Integer32
    UNITS       "0.01 db"
    MAX-ACCESS  read-only
    STATUS      current
    DESCRIPTION
        "The current total gain."
    ::= { pt3080Reception  13 }

pt3080ReceptionAGCMode OBJECT-TYPE
    SYNTAX      INTEGER { slow(0), fast(1) }
    MAX-ACCESS  read-write
    STATUS      current
    DESCRIPTION
        "Controls the AGC function mode."
    ::= { pt3080Reception  30 }

pt3080ReceptionAGCHysteresis OBJECT-TYPE
    SYNTAX      Integer32 ( 0 .. 200 )
    UNITS       "0.01 dB"
    MAX-ACCESS  read-write
    STATUS      current
    DESCRIPTION
        "Defines the AGC function Hysteresis."
    ::= { pt3080Reception  31 }

pt3080ReceptionBandwidth OBJECT-TYPE
    SYNTAX      INTEGER { r5(0), r6(1), r7(2), r8(3) }
    MAX-ACCESS  read-write
    STATUS      current
    DESCRIPTION
        "Controls reception bandwidth"
    ::= { pt3080Reception  23 }

pt3080ReceptionRFFrequency OBJECT-TYPE
    SYNTAX      Integer32 ( 30000000 .. 954000000 )
    UNITS       "1 hz"
    MAX-ACCESS  read-write
    STATUS      current
    DESCRIPTION
        "Defines the reception frequency for the tuner."
    ::= { pt3080Reception  1 }

pt3080ReceptionRFFrequencyOffset OBJECT-TYPE
    SYNTAX      Integer32 ( -500000 .. 500000 )
    UNITS       "1 hz"
    MAX-ACCESS  read-write
    STATUS      current
    DESCRIPTION
        "Defines the offset to be added to the reception frequency for
         the tuner."
    ::= { pt3080Reception  2 }

pt3080ReceptionRFPolarity OBJECT-TYPE
    SYNTAX      INTEGER { norm(0), inv(1) }
    MAX-ACCESS  read-write
    STATUS      current
    DESCRIPTION
        "Controls RF reception Polarity"
    ::= { pt3080Reception  24 }

pt3080ReceptionRFSquelchEnable OBJECT-TYPE
    SYNTAX      INTEGER { off(0), on(1) }
    MAX-ACCESS  read-write
    STATUS      current
    DESCRIPTION
        "Controls the squelch function."
    ::= { pt3080Reception  6 }

pt3080ReceptionRFSquelchThreshold OBJECT-TYPE
    SYNTAX      Integer32 ( -800 .. -70 )
    UNITS       "0.1 dBm"
    MAX-ACCESS  read-write
    STATUS      current
    DESCRIPTION
        "Defines the Squelch function threshold."
    ::= { pt3080Reception  7 }

pt3080ReceptionRFSquelchHysteresis OBJECT-TYPE
    SYNTAX      Integer32 ( 10 .. 500 )
    UNITS       "0.01 dB"
    MAX-ACCESS  read-write
    STATUS      current
    DESCRIPTION
        "Defines the Squelch function Hysteresis."
    ::= { pt3080Reception  8 }

pt3080ReceptionRFTrackingFilterEnable OBJECT-TYPE
    SYNTAX      INTEGER { off(0), on(1) }
    MAX-ACCESS  read-write
    STATUS      current
    DESCRIPTION
        "Controls the Reception RF Tracking Filter."
    ::= { pt3080Reception  35 }

pt3080ReceptionRFifLevel OBJECT-TYPE
    SYNTAX      Integer32
    UNITS       "0.1 dB"
    MAX-ACCESS  read-only
    STATUS      current
    DESCRIPTION
        "The current if level from the tuner."
    ::= { pt3080Reception  36 }

pt3080ReceptionRFNominalInputLevel OBJECT-TYPE
    SYNTAX      Integer32 ( -400 .. 100 )
    UNITS       "0.1 dBm"
    MAX-ACCESS  read-write
    STATUS      current
    DESCRIPTION
        "The nominal input level on the tuner. The dynamic range of the
         tuner is from 20dB below nominal level to nominal level"
    ::= { pt3080Reception  37 }

pt3080ReceptionRFInputLevel OBJECT-TYPE
    SYNTAX      Integer32
    UNITS       "0.1 dBm"
    MAX-ACCESS  read-only
    STATUS      current
    DESCRIPTION
        "The current RF input level on the tuner."
    ::= { pt3080Reception  21 }

pt3080ReceptionRFInputLevelThreshold OBJECT-TYPE
    SYNTAX      Integer32 ( -8000 .. -700 )
    UNITS       "0.01 dBm"
    MAX-ACCESS  read-write
    STATUS      current
    DESCRIPTION
        "Defines the Input level threshold."
    ::= { pt3080Reception  26 }

pt3080ReceptionRFInputLevelHysteresis OBJECT-TYPE
    SYNTAX      Integer32 ( 10 .. 500 )
    UNITS       "0.01 dB"
    MAX-ACCESS  read-write
    STATUS      current
    DESCRIPTION
        "Defines the Input Level Hysteresis."
    ::= { pt3080Reception  25 }

pt3080ReceptionIFFrequency OBJECT-TYPE
    SYNTAX      INTEGER { if36mhz(0), if36p15mhz(1), if40mhz(2) }
    MAX-ACCESS  read-write
    STATUS      current
    DESCRIPTION
        "Defines the reception frequency for the tuner."
    ::= { pt3080Reception  4 }

pt3080ReceptionIFPolarity OBJECT-TYPE
    SYNTAX      INTEGER { norm(0), inv(1) }
    MAX-ACCESS  read-write
    STATUS      current
    DESCRIPTION
        "Controls IF reception Polarity"
    ::= { pt3080Reception  5 }

pt3080ReceptionIFInputLevel OBJECT-TYPE
    SYNTAX      Integer32
    UNITS       "0.01 dBm"
    MAX-ACCESS  read-only
    STATUS      current
    DESCRIPTION
        "Shows the current IF input level"
    ::= { pt3080Reception  22 }

pt3080ReceptionIFInputPolicy OBJECT-TYPE
    SYNTAX      INTEGER { rf(0), if(1), rfav(2), ifav(3) }
    MAX-ACCESS  read-write
    STATUS      current
    DESCRIPTION
        "Controls RF/IF reception Policy"
    ::= { pt3080Reception  3 }

pt3080ReceptionIFInput OBJECT-TYPE
    SYNTAX      INTEGER { if(0), rf(1) }
    MAX-ACCESS  read-only
    STATUS      current
    DESCRIPTION
        "Shows the current RF/IF input selected"
    ::= { pt3080Reception  20 }

pt3080ReceptionIFRFtoIFHoldoverDelay OBJECT-TYPE
    SYNTAX      Integer32 ( 0 .. 300 )
    UNITS       "1 secs"
    MAX-ACCESS  read-write
    STATUS      current
    DESCRIPTION
        "The holdover delay for switching reception from RF to IF input."
    ::= { pt3080Reception  18 }

pt3080ReceptionIFIFtoRFHoldoverDelay OBJECT-TYPE
    SYNTAX      Integer32 ( 0 .. 300 )
    UNITS       "1 secs"
    MAX-ACCESS  read-write
    STATUS      current
    DESCRIPTION
        "The holdover delay for switching reception from IF to RF input."
    ::= { pt3080Reception  19 }

pt3080ReceptionTunerHWVersion OBJECT-TYPE
    SYNTAX      DisplayString
    MAX-ACCESS  read-only
    STATUS      current
    DESCRIPTION
        "The tuner HW version."
    ::= { pt3080Reception  40 }

pt3080ReceptionTunerHWType OBJECT-TYPE
    SYNTAX      DisplayString
    MAX-ACCESS  read-only
    STATUS      current
    DESCRIPTION
        "The tuner HW type."
    ::= { pt3080Reception  41 }

pt3080ReceptionTunerHWID OBJECT-TYPE
    SYNTAX      DisplayString
    MAX-ACCESS  read-only
    STATUS      current
    DESCRIPTION
        "The tuner HW ID."
    ::= { pt3080Reception  42 }

pt3080ReceptionTunerHWSerialNumber OBJECT-TYPE
    SYNTAX      DisplayString
    MAX-ACCESS  read-only
    STATUS      current
    DESCRIPTION
        "The tuner HW Serial Number."
    ::= { pt3080Reception  43 }

pt3080ReceptionTunerHWCalibrationDate OBJECT-TYPE
    SYNTAX      DisplayString
    MAX-ACCESS  read-only
    STATUS      current
    DESCRIPTION
        "The tuner HW Calibration Date."
    ::= { pt3080Reception  44 }

pt3080ReceptionTunerHWCalibrationDataVersion OBJECT-TYPE
    SYNTAX      DisplayString
    MAX-ACCESS  read-only
    STATUS      current
    DESCRIPTION
        "The tuner HW Calibration Data Version."
    ::= { pt3080Reception  45 }

pt3080ReceptionTunerHWCalibrationSWVersion OBJECT-TYPE
    SYNTAX      DisplayString
    MAX-ACCESS  read-only
    STATUS      current
    DESCRIPTION
        "The tuner HW Calibration SW Version."
    ::= { pt3080Reception  46 }


--
-- pt3080 ASI sub-tree
--

pt3080ASIInput1SyncTimeout OBJECT-TYPE
    SYNTAX      Integer32 ( 1 .. 250 )
    UNITS       "1 ms"
    MAX-ACCESS  read-write
    STATUS      current
    DESCRIPTION
        "Specifies the maximum time accepted between received TS packages."
    ::= { pt3080ASI  1 }

pt3080ASIInput2SyncTimeout OBJECT-TYPE
    SYNTAX      Integer32 ( 1 .. 250 )
    UNITS       "1 ms"
    MAX-ACCESS  read-write
    STATUS      current
    DESCRIPTION
        "Specifies the maximum time accepted between received TS packages."
    ::= { pt3080ASI  51 }

pt3080ASIInput1DataErrorLimit OBJECT-TYPE
    SYNTAX      Integer32 ( 0 .. 20000 )
    UNITS       "0.1 bits/s"
    MAX-ACCESS  read-write
    STATUS      current
    DESCRIPTION
        "Specifies the alarm limit for date error rate."
    ::= { pt3080ASI  2 }

pt3080ASIInput2DataErrorLimit OBJECT-TYPE
    SYNTAX      Integer32 ( 0 .. 20000 )
    UNITS       "0.1 bits/s"
    MAX-ACCESS  read-write
    STATUS      current
    DESCRIPTION
        "Specifies the alarm limit for date error rate."
    ::= { pt3080ASI  52 }

pt3080ASIInput1SyncStatus OBJECT-TYPE
    SYNTAX      INTEGER { locked(0), unlocked(1) }
    MAX-ACCESS  read-only
    STATUS      current
    DESCRIPTION
        "Current state of the sync detector"
    ::= { pt3080ASI  3 }

pt3080ASIInput2SyncStatus OBJECT-TYPE
    SYNTAX      INTEGER { locked(0), unlocked(1) }
    MAX-ACCESS  read-only
    STATUS      current
    DESCRIPTION
        "Current state of the sync detector"
    ::= { pt3080ASI  53 }

pt3080ASIInput1SyncSignal OBJECT-TYPE
    SYNTAX      INTEGER { undefined(0), norm(1), inv(2) }
    MAX-ACCESS  read-only
    STATUS      current
    DESCRIPTION
        "Current state of the sync detector signal type"
    ::= { pt3080ASI  4 }

pt3080ASIInput2SyncSignal OBJECT-TYPE
    SYNTAX      INTEGER { undefined(0), norm(1), inv(2) }
    MAX-ACCESS  read-only
    STATUS      current
    DESCRIPTION
        "Current state of the sync detector signal type"
    ::= { pt3080ASI  54 }

pt3080ASIInput1SyncTSSize OBJECT-TYPE
    SYNTAX      INTEGER { undefined(0), ts188(1), ts204(2) }
    MAX-ACCESS  read-only
    STATUS      current
    DESCRIPTION
        "Current TS packet size determined by the sync detector"
    ::= { pt3080ASI  5 }

pt3080ASIInput2SyncTSSize OBJECT-TYPE
    SYNTAX      INTEGER { undefined(0), ts188(1), ts204(2) }
    MAX-ACCESS  read-only
    STATUS      current
    DESCRIPTION
        "Current TS packet size determined by the sync detector"
    ::= { pt3080ASI  55 }

pt3080ASIInput1LineErrors OBJECT-TYPE
    SYNTAX      Integer32
    UNITS       "1 bits"
    MAX-ACCESS  read-only
    STATUS      current
    DESCRIPTION
        "Counts the number of line errors including IDLE stuffing."
    ::= { pt3080ASI  6 }

pt3080ASIInput2LineErrors OBJECT-TYPE
    SYNTAX      Integer32
    UNITS       "1 bits"
    MAX-ACCESS  read-only
    STATUS      current
    DESCRIPTION
        "Counts the number of line errors including IDLE stuffing."
    ::= { pt3080ASI  56 }

pt3080ASIInput1LineRate OBJECT-TYPE
    SYNTAX      Integer32
    UNITS       "0.1 Mbps"
    MAX-ACCESS  read-only
    STATUS      current
    DESCRIPTION
        "Current line rate"
    ::= { pt3080ASI  7 }

pt3080ASIInput2LineRate OBJECT-TYPE
    SYNTAX      Integer32
    UNITS       "0.1 Mbps"
    MAX-ACCESS  read-only
    STATUS      current
    DESCRIPTION
        "Current line rate"
    ::= { pt3080ASI  57 }

pt3080ASIInput1LineErrorRate OBJECT-TYPE
    SYNTAX      Integer32
    UNITS       "0.1 bits/s"
    MAX-ACCESS  read-only
    STATUS      current
    DESCRIPTION
        "Current line error rate"
    ::= { pt3080ASI  8 }

pt3080ASIInput2LineErrorRate OBJECT-TYPE
    SYNTAX      Integer32
    UNITS       "0.1 bits/s"
    MAX-ACCESS  read-only
    STATUS      current
    DESCRIPTION
        "Current line error rate"
    ::= { pt3080ASI  58 }

pt3080ASIInput1DataErrors OBJECT-TYPE
    SYNTAX      Integer32
    UNITS       "1 bits"
    MAX-ACCESS  read-only
    STATUS      current
    DESCRIPTION
        "Counts the number of data errors excluding IDLE stuffing."
    ::= { pt3080ASI  9 }

pt3080ASIInput2DataErrors OBJECT-TYPE
    SYNTAX      Integer32
    UNITS       "1 bits"
    MAX-ACCESS  read-only
    STATUS      current
    DESCRIPTION
        "Counts the number of data errors excluding IDLE stuffing."
    ::= { pt3080ASI  59 }

pt3080ASIInput1DataRate OBJECT-TYPE
    SYNTAX      Integer32
    UNITS       "0.1 Mbps/s"
    MAX-ACCESS  read-only
    STATUS      current
    DESCRIPTION
        "Current data rate"
    ::= { pt3080ASI  10 }

pt3080ASIInput2DataRate OBJECT-TYPE
    SYNTAX      Integer32
    UNITS       "0.1 Mbps/s"
    MAX-ACCESS  read-only
    STATUS      current
    DESCRIPTION
        "Current data rate"
    ::= { pt3080ASI  60 }

pt3080ASIInput1DataErrorRate OBJECT-TYPE
    SYNTAX      Integer32
    UNITS       "0.1 bits/s"
    MAX-ACCESS  read-only
    STATUS      current
    DESCRIPTION
        "Current data error rate"
    ::= { pt3080ASI  11 }

pt3080ASIInput2DataErrorRate OBJECT-TYPE
    SYNTAX      Integer32
    UNITS       "0.1 bits/s"
    MAX-ACCESS  read-only
    STATUS      current
    DESCRIPTION
        "Current data error rate"
    ::= { pt3080ASI  61 }

pt3080ASIInput1ClearErrorCounters OBJECT-TYPE
    SYNTAX      INTEGER { noop(0), activate(1) }
    MAX-ACCESS  read-write
    STATUS      current
    DESCRIPTION
        "Clear all error counters and reset all rates"
    ::= { pt3080ASI  12 }

pt3080ASIInput2ClearErrorCounters OBJECT-TYPE
    SYNTAX      INTEGER { noop(0), activate(1) }
    MAX-ACCESS  read-write
    STATUS      current
    DESCRIPTION
        "Clear all error counters and reset all rates"
    ::= { pt3080ASI  62 }


--
-- pt3080 Input sub-tree
--

pt3080InputRefDevType OBJECT-TYPE
    SYNTAX      INTEGER { tcxo-int(0), ocxo-pt3710-10(1), ocxo-pt3710-20(2) }
    MAX-ACCESS  read-only
    STATUS      current
    DESCRIPTION
        "Type of TCXO/OCXO"
    ::= { pt3080Input  90 }

pt3080InputRefCalDate OBJECT-TYPE
    SYNTAX      DisplayString
    MAX-ACCESS  read-only
    STATUS      current
    DESCRIPTION
        "Calibration Date"
    ::= { pt3080Input  91 }

pt3080InputRefCalVer OBJECT-TYPE
    SYNTAX      Integer32
    MAX-ACCESS  read-only
    STATUS      current
    DESCRIPTION
        "Calibration SW Version"
    ::= { pt3080Input  92 }

pt3080InputRefDirection OBJECT-TYPE
    SYNTAX      INTEGER { input(0), output(1) }
    MAX-ACCESS  read-write
    STATUS      current
    DESCRIPTION
        "monitors the Reference signal direction. state: - inputOutput[inputOutput_INPUT]
         - inputOutput[inputOutput_OUTPUT]"
    ::= { pt3080Input  1 }

pt3080InputRefSource OBJECT-TYPE
    SYNTAX      INTEGER { auto(0), ext(1), int(2), gps(3) }
    MAX-ACCESS  read-write
    STATUS      current
    DESCRIPTION
        "Defines the input reference synchronisation source. If the value
         AUTO is chosen, the source is chosen automatically between 
        available sources. The order of choice is GPS->EXT10MHz->INT.
         If the value EXT is chosen, the external clock is chosen as
         source If the value INT is chosen, the internal clock is chosen
         as source. If the value GPS is chosen, the GNSS 1PPS clock 
        is chosen as source."
    ::= { pt3080Input  2 }

pt3080InputRefStatus OBJECT-TYPE
    SYNTAX      INTEGER { external(0), external-10mhz(1), external-1pps(2), internal(3), gnss(4), asi1(5), asi2(6), ndel(7) }
    MAX-ACCESS  read-only
    STATUS      current
    DESCRIPTION
        "returns the current input reference synchronisation source."
    ::= { pt3080Input  11 }

pt3080InputRef10MhzImpedance OBJECT-TYPE
    SYNTAX      INTEGER { o-50(0), himp(1) }
    MAX-ACCESS  read-write
    STATUS      current
    DESCRIPTION
        "Defines the external 10 MHz input reference synchronisation 
        source impedance. The value is either 50O or high impedance."
    ::= { pt3080Input  3 }

pt3080InputRef10MhzHoldoverDelay OBJECT-TYPE
    SYNTAX      Integer32 ( 0 .. 172800 )
    MAX-ACCESS  read-write
    STATUS      current
    DESCRIPTION
        "Defines the external 10 MHz input reference synchronisation 
        source impedance. The value is either 50O or high impedance."
    ::= { pt3080Input  7 }

pt3080InputRef10MhzHoldoverForever OBJECT-TYPE
    SYNTAX      INTEGER { no(0), yes(1) }
    MAX-ACCESS  read-write
    STATUS      current
    DESCRIPTION
        "The holdover delay for input reference source 10MHz failure 
        is forever"
    ::= { pt3080Input  8 }

pt3080InputRef1PPSImpedance OBJECT-TYPE
    SYNTAX      INTEGER { o-50(0), himp(1) }
    MAX-ACCESS  read-write
    STATUS      current
    DESCRIPTION
        "Defines the external 1 PPS input reference synchronisation source
         impedance. The value is either 50ohm or high impedance."
    ::= { pt3080Input  4 }

pt3080InputRef1PPSHoldoverDelay OBJECT-TYPE
    SYNTAX      Integer32 ( 0 .. 172800 )
    MAX-ACCESS  read-write
    STATUS      current
    DESCRIPTION
        "Defines the external 1 PPS input reference synchronisation source
         impedance. The value is either 50ohm or high impedance."
    ::= { pt3080Input  9 }

pt3080InputRef1PPSHoldoverForever OBJECT-TYPE
    SYNTAX      INTEGER { no(0), yes(1) }
    MAX-ACCESS  read-write
    STATUS      current
    DESCRIPTION
        "The holdover delay for input reference source 1 pps failure 
        is forever"
    ::= { pt3080Input  10 }

pt3080InputRef1PPSTrigSlope OBJECT-TYPE
    SYNTAX      INTEGER { rising(0), falling(1) }
    MAX-ACCESS  read-write
    STATUS      current
    DESCRIPTION
        "Defines the trigger edge of the external 1PPS input reference
         clock. The value is either RISING or FALLING."
    ::= { pt3080Input  5 }

pt3080InputRef1PPSTrigLevel OBJECT-TYPE
    SYNTAX      Integer32 ( 10 .. 16 )
    UNITS       "0.1 v"
    MAX-ACCESS  read-write
    STATUS      current
    DESCRIPTION
        "Defines the trigger level of the external 1PPS input reference
         clock"
    ::= { pt3080Input  6 }

pt3080InputASIAutoRoutingDelayHp2Lp OBJECT-TYPE
    SYNTAX      Integer32 ( 0 .. 300 )
    UNITS       "1 secs"
    MAX-ACCESS  read-write
    STATUS      current
    DESCRIPTION
        "The delay before performing the actual substitution where TS-Primary
         -> TS-LP and TS-Secondary -> TS-HP"
    ::= { pt3080Input  15 }

pt3080InputASIAutoRoutingDelayLp2Hp OBJECT-TYPE
    SYNTAX      Integer32 ( 0 .. 300 )
    UNITS       "1 secs"
    MAX-ACCESS  read-write
    STATUS      current
    DESCRIPTION
        "The delay before performing the actual substitution where TS-Primary
         -> TS-HP and TS-Secondary -> TS-LP"
    ::= { pt3080Input  16 }

pt3080InputASIHoldoverTimeout OBJECT-TYPE
    SYNTAX      Integer32 ( 0 .. 3600 )
    UNITS       "1 secs"
    MAX-ACCESS  read-write
    STATUS      current
    DESCRIPTION
        "The time ASI Holdover will be active, if seamless ASI switching
         is not possible"
    ::= { pt3080Input  17 }


pt3080InputASITSPrimarySource   OBJECT-TYPE
    SYNTAX                      INTEGER {
                                          asi-in-1(0), asi-in-2(1),
                                          demodulator-1(2), demodulator-2(3),
                                          tsoip-rx1(4), tsoip-rx2(5),
                                          satRecv(6)
                                        }
    MAX-ACCESS                  read-write
    STATUS                      current
    DESCRIPTION
        "The TS-Primary input source connector selected"
    ::= { pt3080Input 12 }

pt3080InputASITSSecondarySource OBJECT-TYPE
    SYNTAX                      INTEGER {
                                          asi-in-1(0), asi-in-2(1),
                                          demodulator-1(2), demodulator-2(3),
                                          tsoip-rx1(4), tsoip-rx2(5),
                                          satRecv(6)
                                        }
    MAX-ACCESS                  read-write
    STATUS                      current
    DESCRIPTION
        "The TS-Secondary input source connector selected"
    ::= { pt3080Input 13 }

pt3080InputASIAutoRoutingPolicy OBJECT-TYPE
    SYNTAX                      INTEGER { only-use-primary(0), only-use-secondary(1),
                                          use-primary-if-available(2), use-any-available(3) }
    MAX-ACCESS                  read-write
    STATUS                      current
    DESCRIPTION
        "The policy to use for TS auto routing"
    ::= { pt3080Input 14 }

pt3080InputTSPrimaryMaxPATDelay OBJECT-TYPE
    SYNTAX      Integer32 ( 10 .. 10000 )
    UNITS       "1 ms"
    MAX-ACCESS  read-write
    STATUS      current
    DESCRIPTION
        "The Max delay between the Program Association Table (PAT) on
         the incomming transport stream."
    ::= { pt3080Input  18 }

pt3080InputTSPrimaryMaxPATDelayEnable OBJECT-TYPE
    SYNTAX      INTEGER { off(0), on(1) }
    MAX-ACCESS  read-write
    STATUS      current
    DESCRIPTION
        "Enables TS switching if the Max delay between PAT table updates
         has been exceeded."
    ::= { pt3080Input  19 }

pt3080InputTSPrimaryExpectedTSID OBJECT-TYPE
    SYNTAX      Integer32 ( 0 .. 65535 )
    MAX-ACCESS  read-write
    STATUS      current
    DESCRIPTION
        "The TS-ID value expected on the incoming TS stream."
    ::= { pt3080Input  20 }

pt3080InputTSPrimaryExpectedTSIDEnable OBJECT-TYPE
    SYNTAX      INTEGER { off(0), on(1) }
    MAX-ACCESS  read-write
    STATUS      current
    DESCRIPTION
        "Enables TS switching if the TS-ID is not the expected value."
    ::= { pt3080Input  21 }

pt3080InputTSPrimaryExpectedNWID OBJECT-TYPE
    SYNTAX      Integer32 ( 0 .. 65535 )
    MAX-ACCESS  read-write
    STATUS      current
    DESCRIPTION
        "The NW-ID value expected on the incoming TS stream."
    ::= { pt3080Input  22 }

pt3080InputTSPrimaryExpectedNWIDEnable OBJECT-TYPE
    SYNTAX      INTEGER { off(0), on(1) }
    MAX-ACCESS  read-write
    STATUS      current
    DESCRIPTION
        "Enables TS switching if the NW-ID is not the expected value."
    ::= { pt3080Input  23 }

pt3080InputTSPrimaryMaxStuffingrate OBJECT-TYPE
    SYNTAX      Integer32 ( 0 .. 100 )
    UNITS       "1 %"
    MAX-ACCESS  read-write
    STATUS      current
    DESCRIPTION
        "The expected stuffing rate on the incoming TS stream."
    ::= { pt3080Input  24 }

pt3080InputTSPrimaryMaxStuffingrateEnable OBJECT-TYPE
    SYNTAX      INTEGER { off(0), on(1) }
    MAX-ACCESS  read-write
    STATUS      current
    DESCRIPTION
        "Enables TS switching if the Stuffing rate is over the expected
         value."
    ::= { pt3080Input  25 }

pt3080InputTSPrimaryMinDelaymargin OBJECT-TYPE
    SYNTAX      Integer32 ( 0 .. 1000 )
    UNITS       "1 ms"
    MAX-ACCESS  read-write
    STATUS      current
    DESCRIPTION
        "The minimum delay margin of the incoming TS stream."
    ::= { pt3080Input  64 }

pt3080InputTSPrimaryMinDelaymarginEnable OBJECT-TYPE
    SYNTAX      INTEGER { off(0), on(1) }
    MAX-ACCESS  read-write
    STATUS      current
    DESCRIPTION
        "Enables TS switching if the Minimum Delay margin is not according
         to the expected value."
    ::= { pt3080Input  65 }

pt3080InputTSPrimaryMaxMissingmip OBJECT-TYPE
    SYNTAX      Integer32 ( 1 .. 255 )
    UNITS       "1 secs"
    MAX-ACCESS  read-write
    STATUS      current
    DESCRIPTION
        "The maximum seconds of missing mip information from the incoming
         TS stream."
    ::= { pt3080Input  68 }

pt3080InputTSPrimaryMaxMissingmipEnable OBJECT-TYPE
    SYNTAX      INTEGER { off(0), on(1) }
    MAX-ACCESS  read-write
    STATUS      current
    DESCRIPTION
        "Enables TS switching if the Maximum missing mip is not according
         to the expected value."
    ::= { pt3080Input  69 }

pt3080InputTSSecondaryMaxPATDelay OBJECT-TYPE
    SYNTAX      Integer32 ( 10 .. 10000 )
    UNITS       "1 ms"
    MAX-ACCESS  read-write
    STATUS      current
    DESCRIPTION
        "The Max delay between the Program Association Table (PAT) on
         the incomming transport stream."
    ::= { pt3080Input  27 }

pt3080InputTSSecondaryMaxPATDelayEnable OBJECT-TYPE
    SYNTAX      INTEGER { off(0), on(1) }
    MAX-ACCESS  read-write
    STATUS      current
    DESCRIPTION
        "Enables TS switching if the Max delay between PAT table updates
         has been exceeded."
    ::= { pt3080Input  28 }

pt3080InputTSSecondaryExpectedTSID OBJECT-TYPE
    SYNTAX      Integer32 ( 0 .. 65535 )
    MAX-ACCESS  read-write
    STATUS      current
    DESCRIPTION
        "The TS-ID value expected on the incoming TS stream."
    ::= { pt3080Input  29 }

pt3080InputTSSecondaryExpectedTSIDEnable OBJECT-TYPE
    SYNTAX      INTEGER { off(0), on(1) }
    MAX-ACCESS  read-write
    STATUS      current
    DESCRIPTION
        "Enables TS switching if the TS-ID is not the expected value."
    ::= { pt3080Input  30 }

pt3080InputTSSecondaryExpectedNWID OBJECT-TYPE
    SYNTAX      Integer32 ( 0 .. 65535 )
    MAX-ACCESS  read-write
    STATUS      current
    DESCRIPTION
        "The NW-ID value expected on the incoming TS stream."
    ::= { pt3080Input  31 }

pt3080InputTSSecondaryExpectedNWIDEnable OBJECT-TYPE
    SYNTAX      INTEGER { off(0), on(1) }
    MAX-ACCESS  read-write
    STATUS      current
    DESCRIPTION
        "Enables TS switching if the NW-ID is not the expected value."
    ::= { pt3080Input  32 }

pt3080InputTSSecondaryMaxStuffingrate OBJECT-TYPE
    SYNTAX      Integer32 ( 0 .. 100 )
    UNITS       "1 %"
    MAX-ACCESS  read-write
    STATUS      current
    DESCRIPTION
        "The expected stuffing rate on the incoming TS stream."
    ::= { pt3080Input  33 }

pt3080InputTSSecondaryMaxStuffingrateEnable OBJECT-TYPE
    SYNTAX      INTEGER { off(0), on(1) }
    MAX-ACCESS  read-write
    STATUS      current
    DESCRIPTION
        "Enables TS switching if the Stuffing rate is over the expected
         value."
    ::= { pt3080Input  34 }

pt3080InputTSSecondaryMinDelaymargin OBJECT-TYPE
    SYNTAX      Integer32 ( 0 .. 1000 )
    UNITS       "1 ms"
    MAX-ACCESS  read-write
    STATUS      current
    DESCRIPTION
        "The minimum delay margin of the incoming TS stream."
    ::= { pt3080Input  66 }

pt3080InputTSSecondaryMinDelaymarginEnable OBJECT-TYPE
    SYNTAX      INTEGER { off(0), on(1) }
    MAX-ACCESS  read-write
    STATUS      current
    DESCRIPTION
        "Enables TS switching if the Minimum Delay margin is not according
         to the expected value."
    ::= { pt3080Input  67 }

pt3080InputTSSecondaryMaxMissingmip OBJECT-TYPE
    SYNTAX      Integer32 ( 1 .. 255 )
    UNITS       "1 secs"
    MAX-ACCESS  read-write
    STATUS      current
    DESCRIPTION
        "The maximum seconds of missing mip information from the incoming
         TS stream."
    ::= { pt3080Input  73 }

pt3080InputTSSecondaryMaxMissingmipEnable OBJECT-TYPE
    SYNTAX      INTEGER { off(0), on(1) }
    MAX-ACCESS  read-write
    STATUS      current
    DESCRIPTION
        "Enables TS switching if the Maximum missing mip is not according
         to the expected value."
    ::= { pt3080Input  74 }


pt3080InputTSPrimaryMaxStsJitter OBJECT-TYPE
    SYNTAX                      Integer32 ( 0 .. 500 )
    UNITS                       "100ns"
    MAX-ACCESS                  read-write
    STATUS                      current
    DESCRIPTION
        "The Max STS jitter on the TS-Primary"
    ::= { pt3080Input 26 }


pt3080InputTSSecondaryMaxStsJitter OBJECT-TYPE
    SYNTAX                      Integer32 ( 0 .. 500 )
    UNITS                       "100ns"
    MAX-ACCESS                  read-write
    STATUS                      current
    DESCRIPTION
        "The Max STS jitter on the TS-Secondary"
    ::= { pt3080Input 35 }

pt3080InputTSPrimaryStatus      OBJECT-TYPE
    SYNTAX                      INTEGER { available(0), unavailable(1), nosync(2) }
    MAX-ACCESS                  read-only
    STATUS                      current
    DESCRIPTION
        "The current state for TS-Primary. Unavailable means violation of alarms."
    ::= { pt3080Input 36 }

pt3080InputTSSecondaryStatus    OBJECT-TYPE
    SYNTAX                      INTEGER { available(0), unavailable(1), nosync(2) }
    MAX-ACCESS                  read-only
    STATUS                      current
    DESCRIPTION
        "The current state for TS-Secondary. Unavailable means violation of alarms."
    ::= { pt3080Input 37 }

pt3080InputTSHp                 OBJECT-TYPE
    SYNTAX                      INTEGER {
                                          asi-in-1(0), asi-in-2(1),
                                          demodulator-1(2), demodulator-2(3),
                                          tsoip-rx1(4), tsoip-rx2(5),
                                          satRecv(6)
                                        }
    MAX-ACCESS                  read-only
    STATUS                      current
    DESCRIPTION
        "The input source currently On Air. (TS-HP)"
    ::= { pt3080Input 38 }

pt3080InputTSLp                 OBJECT-TYPE
    SYNTAX                      INTEGER {
                                          asi-in-1(0), asi-in-2(1),
                                          demodulator-1(2), demodulator-2(3),
                                          tsoip-rx1(4), tsoip-rx2(5),
                                          satRecv(6)
                                        }
    MAX-ACCESS                  read-only
    STATUS                      current
    DESCRIPTION
        "The input source currently used as backup. (TS-LP)"
    ::= { pt3080Input 39 }

pt3080InputEffectiveAutoroutingPolicy  OBJECT-TYPE
    SYNTAX                             INTEGER { only-primary(0), only-secondary(1), prefer-primary(2), any-available(3), seamless(4) }
    MAX-ACCESS                         read-only
    STATUS                             current
    DESCRIPTION
        "Reflects the effective ASI Autorouting Policy"
    ::= { pt3080Input 40 }

pt3080InputTSHpBitrate          OBJECT-TYPE
    SYNTAX                      Integer32
    UNITS                       "Kb/s"
    MAX-ACCESS                  read-only
    STATUS                      current
    DESCRIPTION
        "Current bitrate for On Air TS. (TS-HP)"
    ::= { pt3080Input 41 }

pt3080InputTSHpPacketsBuffered  OBJECT-TYPE
    SYNTAX                      Integer32
    UNITS                       "packets"
    MAX-ACCESS                  read-only
    STATUS                      current
    DESCRIPTION
        "Current number of packets buffered for On Air TS (TS-HP)"
    ::= { pt3080Input 42 }

pt3080InputTSHpPacketSize       OBJECT-TYPE
    SYNTAX                      Integer32
    UNITS                       "bytes"
    MAX-ACCESS                  read-only
    STATUS                      current
    DESCRIPTION
        "Current size of packets for On Air TS (TS-HP)"
    ::= { pt3080Input 43 }

pt3080InputTSHpStuffingrate     OBJECT-TYPE
    SYNTAX                      Integer32
    UNITS                       "Kb/s"
    MAX-ACCESS                  read-only
    STATUS                      current
    DESCRIPTION
        "Current NULL stuffing as a percentage of the
         current bitrate for On Air TS (TS-HP)"
    ::= { pt3080Input 44 }

pt3080InputTSHpTSID             OBJECT-TYPE
    SYNTAX                      Integer32
    MAX-ACCESS                  read-only
    STATUS                      current
    DESCRIPTION
        "Current Transport Stream ID for On Air TS. (TS-HP)"
    ::= { pt3080Input 45 }

pt3080InputTSHpNWID             OBJECT-TYPE
    SYNTAX                      Integer32
    MAX-ACCESS                  read-only
    STATUS                      current
    DESCRIPTION
        "Current Network ID for On Air TS. (TS-HP)"
    ::= { pt3080Input 46 }

pt3080InputTSLpBitrate          OBJECT-TYPE
    SYNTAX                      Integer32
    UNITS                       "Kb/s"
    MAX-ACCESS                  read-only
    STATUS                      current
    DESCRIPTION
        "Current bitrate for Backup TS. (TS-LP)"
    ::= { pt3080Input 47 }

pt3080InputTSLpPacketsBuffered  OBJECT-TYPE
    SYNTAX                      Integer32
    UNITS                       "packets"
    MAX-ACCESS                  read-only
    STATUS                      current
    DESCRIPTION
        "Current number of packets buffered for Backup TS. (TS-LP)"
    ::= { pt3080Input 48 }

pt3080InputTSLpPacketSize       OBJECT-TYPE
    SYNTAX                      Integer32
    UNITS                       "bytes"
    MAX-ACCESS                  read-only
    STATUS                      current
    DESCRIPTION
        "Current size of packets for Backup TS. (TS-LP)"
    ::= { pt3080Input 49 }

pt3080InputTSLpStuffingrate     OBJECT-TYPE
    SYNTAX                      Integer32
    UNITS                       "Permille"
    MAX-ACCESS                  read-only
    STATUS                      current
    DESCRIPTION
        "Current NULL stuffing as a percentage of the
         current bitrate for  Backup TS. (TS-LP)"
    ::= { pt3080Input 50 }

pt3080InputTSLpTSID             OBJECT-TYPE
    SYNTAX                      Integer32
    MAX-ACCESS                  read-only
    STATUS                      current
    DESCRIPTION
        "Current Transport Stream ID for Backup TS. (TS-LP)"
    ::= { pt3080Input 51 }

pt3080InputTSLpNWID             OBJECT-TYPE
    SYNTAX                      Integer32
    MAX-ACCESS                  read-only
    STATUS                      current
    DESCRIPTION
        "Current Network ID for Backup TS. (TS-LP)"
    ::= { pt3080Input 52 }

pt3080InputTSPrimaryStsJitter   OBJECT-TYPE
    SYNTAX                      Integer32
    UNITS                       "100ns"
    MAX-ACCESS                  read-only
    STATUS                      current
    DESCRIPTION
        "Current STS jitter on the TS-Primary."
    ::= { pt3080Input 53 }

pt3080InputTSPrimaryStsJitterMax OBJECT-TYPE
    SYNTAX                      Integer32
    UNITS                       "100ns"
    MAX-ACCESS                  read-only
    STATUS                      current
    DESCRIPTION
        "The Maximum STS jitter value seen on the TS-Primary"
    ::= { pt3080Input 54 }

pt3080InputTSPrimaryStsJitterMin OBJECT-TYPE
    SYNTAX                      Integer32
    UNITS                       "100ns"
    MAX-ACCESS                  read-only
    STATUS                      current
    DESCRIPTION
        "The minimum STS jitter value seen on the TS-Primary"
    ::= { pt3080Input 55 }

pt3080InputTSPrimaryStsJitterReset OBJECT-TYPE
    SYNTAX                      INTEGER { noop(0), reset-min-max(1) }
    MAX-ACCESS                  read-write
    STATUS                      current
    DESCRIPTION
        "Reset the pt3080InputTSPrimaryStsJitterMax and pt3080InputTSPrimaryStsJitterMin values"
    ::= { pt3080Input 56 }

pt3080InputTSSecondaryStsJitter OBJECT-TYPE
    SYNTAX                      Integer32
    UNITS                       "100ns"
    MAX-ACCESS                  read-only
    STATUS                      current
    DESCRIPTION
        "Current STS jitter on the TS-Secondary"
    ::= { pt3080Input 57 }

pt3080InputTSSecondaryStsJitterMax OBJECT-TYPE
    SYNTAX                      Integer32
    UNITS                       "100ns"
    MAX-ACCESS                  read-only
    STATUS                      current
    DESCRIPTION
        "The Maximum STS jitter value seen on the TS-Secondary"
    ::= { pt3080Input 58 }

pt3080InputTSSecondaryStsJitterMin OBJECT-TYPE
    SYNTAX                      Integer32
    UNITS                       "100ns"
    MAX-ACCESS                  read-only
    STATUS                      current
    DESCRIPTION
        "The minimum STS jitter value seen on the TS-Secondary"
    ::= { pt3080Input 59 }

pt3080InputTSSecondaryStsJitterReset OBJECT-TYPE
    SYNTAX                      INTEGER { noop(0), reset-min-max(1) }
    MAX-ACCESS                  read-write
    STATUS                      current
    DESCRIPTION
        "Reset the pt3080InputTSSecondaryStsJitterMax and
         pt3080InputTSSecondaryStsJitterMin values"
    ::= { pt3080Input 60 }

--
-- pt3080 Output sub-tree
--

pt3080OutputBandwidth           OBJECT-TYPE
    SYNTAX                      Integer32 ( 5 .. 8 )
    UNITS                       "MHz"
    MAX-ACCESS                  read-write
    STATUS                      current
    DESCRIPTION
        "Output Bandwidth"
    ::= { pt3080Output 4 }

pt3080OutputChannel             OBJECT-TYPE
    SYNTAX                      Integer32 ( 21 .. 69 )
    MAX-ACCESS                  read-write
    STATUS                      current
    DESCRIPTION
        "Channel settings"
    ::= { pt3080Output 5 }

pt3080OutputSynchronized        OBJECT-TYPE
    SYNTAX                      INTEGER { not-synchronized(0), synchronized(1) }
    MAX-ACCESS                  read-only
    STATUS                      current
    DESCRIPTION
        "The values of pt3080OutputRfFrequency, pt3080OutputBandwidth and
         pt3080OutputChannel are synchronized aaccording to
         freq = (bw * channel) + 306000000."
    ::= { pt3080Output 6 }

pt3080OutputMute                OBJECT-TYPE
    SYNTAX                      INTEGER { off(0), on(1) }
    MAX-ACCESS                  read-write
    STATUS                      current
    DESCRIPTION
        "Output mute. When set the mute reason UserRequest is ORed into the mute reason set.
         When read it is the logical OR of all mute reasons"
    ::= { pt3080Output 7 }

pt3080OutputPowerLevel          OBJECT-TYPE
    SYNTAX                      Integer32 ( 280 .. 490 )
    UNITS                       "0.1 dBm"
    MAX-ACCESS                  read-write
    STATUS                      current
    DESCRIPTION
        "The desired output power level."
    ::= { pt3080Output 9 }


pt3080OutputIfEnable OBJECT-TYPE
    SYNTAX      INTEGER { no(0), yes(1) }
    MAX-ACCESS  read-write
    STATUS      current
    DESCRIPTION
        "Control IF output"
    ::= { pt3080Output  13 }

pt3080OutputIfFrequency OBJECT-TYPE
    SYNTAX      Integer32 ( 35150000 .. 37150000 )
    UNITS       "1 Hz"
    MAX-ACCESS  read-write
    STATUS      current
    DESCRIPTION
        "Output Frequency for I/F"
    ::= { pt3080Output  14 }

pt3080OutputIfPolarity OBJECT-TYPE
    SYNTAX      INTEGER { norm(0), inv(1) }
    MAX-ACCESS  read-write
    STATUS      current
    DESCRIPTION
        "Control IF output polarity"
    ::= { pt3080Output  15 }

pt3080OutputIfLevel OBJECT-TYPE
    SYNTAX      Integer32 ( -1000 .. 0 )
    UNITS       "0.01 dBm"
    MAX-ACCESS  read-write
    STATUS      current
    DESCRIPTION
        "Output Level for I/F"
    ::= { pt3080Output  16 }

pt3080OutputMode OBJECT-TYPE
    SYNTAX      INTEGER { normal(0), standby(1) }
    MAX-ACCESS  read-write
    STATUS      current
    DESCRIPTION
        "Control RF output mode"
    ::= { pt3080Output  1 }

pt3080OutputEffectiveLevel OBJECT-TYPE
    SYNTAX      Integer32
    UNITS       "0.01 dBm"
    MAX-ACCESS  read-only
    STATUS      current
    DESCRIPTION
        "Effective RF Output Level"
    ::= { pt3080Output  17 }

pt3080OutputActualLevel OBJECT-TYPE
    SYNTAX      Integer32
    UNITS       "0.01 dBm"
    MAX-ACCESS  read-only
    STATUS      current
    DESCRIPTION
        "Actual RF Output Level"
    ::= { pt3080Output  18 }

pt3080OutputPolarity OBJECT-TYPE
    SYNTAX      INTEGER { norm(0), inv(1) }
    MAX-ACCESS  read-write
    STATUS      current
    DESCRIPTION
        "Control RF output polarity"
    ::= { pt3080Output  8 }

pt3080OutputRfFrequency OBJECT-TYPE
    SYNTAX      Integer32 ( 30000000 .. 860000000 )
    UNITS       "1 Hz"
    MAX-ACCESS  read-write
    STATUS      current
    DESCRIPTION
        "Output RF frequency"
    ::= { pt3080Output  2 }

pt3080OutputRfFrequencyOffset OBJECT-TYPE
    SYNTAX      Integer32 ( -8388608 .. 8388607 )
    UNITS       "1 Hz"
    MAX-ACCESS  read-write
    STATUS      current
    DESCRIPTION
        "Output RF frequency offset"
    ::= { pt3080Output  10 }

pt3080OutputRfLevel OBJECT-TYPE
    SYNTAX      Integer32 ( -1000 .. 1000 )
    UNITS       "0.01 dBm"
    MAX-ACCESS  read-write
    STATUS      current
    DESCRIPTION
        "Sets the output level in 0.01dB steps, 0dB is +6dBm on IF, 0dBm
         on RF"
    ::= { pt3080Output  3 }

pt3080OutputRfCableMode OBJECT-TYPE
    SYNTAX      INTEGER { none(0), const(1), auto(2) }
    MAX-ACCESS  read-write
    STATUS      current
    DESCRIPTION
        "Control whether Cable Level loss compensation should be enabled"
    ::= { pt3080Output  50 }

pt3080OutputRfCableConstantLevelOffset OBJECT-TYPE
    SYNTAX      Integer32 ( -10000 .. 10000 )
    UNITS       "0.001 dBm"
    MAX-ACCESS  read-write
    STATUS      current
    DESCRIPTION
        "Constant level offset to add to RF Output level. Only used if
         mode is Constant."
    ::= { pt3080Output  51 }

pt3080OutputRfCableFrequencyLevelOffset0 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  52 }

pt3080OutputRfCableFrequencyLevelOffset1 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  53 }

pt3080OutputRfCableFrequencyLevelOffset2 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  54 }

pt3080OutputRfCableFrequencyLevelOffset3 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  55 }

pt3080OutputRfCableFrequencyLevelOffset4 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  56 }

pt3080OutputRfCableFrequencyLevelOffset5 OBJECT-TYPE
    SYNTAX      Integer32 ( -10000 .. 10000 )
    UNITS       "0.001 dBm"
    MAX-ACCESS  read-write
    STATUS      current
    DESCRIPTION
        "Frequency depedent level offset to add to RF Output level. Only
         used if mode is Automatic."
    ::= { pt3080Output  57 }

pt3080OutputRfDetectedActualLevel OBJECT-TYPE
    SYNTAX      Integer32
    UNITS       "0.01 dBm"
    MAX-ACCESS  read-only
    STATUS      current
    DESCRIPTION
        "Detected Output Level for RF"
    ::= { pt3080Output  19 }

pt3080OutputRfDetectedLowerLevelLimit OBJECT-TYPE
    SYNTAX      Integer32 ( 2 .. 50 )
    UNITS       "0.1 dB"
    MAX-ACCESS  read-write
    STATUS      current
    DESCRIPTION
        "Limit to how much lower the detected RF output level can be 
        than the configured level."
    ::= { pt3080Output  20 }

pt3080OutputRfDetectedLowerLevelcontrol OBJECT-TYPE
    SYNTAX      INTEGER { disable(0), enable(1) }
    MAX-ACCESS  read-write
    STATUS      current
    DESCRIPTION
        "Controls whether the lower limit for RF output level is enforced."
    ::= { pt3080Output  21 }

pt3080OutputRfDetectedHigherLevelLimit OBJECT-TYPE
    SYNTAX      Integer32 ( 2 .. 50 )
    UNITS       "0.1 dB"
    MAX-ACCESS  read-write
    STATUS      current
    DESCRIPTION
        "Limit to how much higher the detected RF output level can be
         than the configured level."
    ::= { pt3080Output  22 }

pt3080OutputRfDetectedHigherLevelcontrol OBJECT-TYPE
    SYNTAX      INTEGER { disable(0), enable(1) }
    MAX-ACCESS  read-write
    STATUS      current
    DESCRIPTION
        "Controls whether the higher limit for RF output level is enforced."
    ::= { pt3080Output  23 }

pt3080OutputRfAlcControl OBJECT-TYPE
    SYNTAX      INTEGER { disable(0), enable(1) }
    MAX-ACCESS  read-write
    STATUS      current
    DESCRIPTION
        "Controls whether the ALC system is enabled or disabled."
    ::= { pt3080Output  30 }

pt3080OutputRfAlcSense OBJECT-TYPE
    SYNTAX      INTEGER { rfsense1(0), rfsense2(1) }
    MAX-ACCESS  read-write
    STATUS      current
    DESCRIPTION
        "Controls which sense port is used by the ALC system if the ALC
         is enabled."
    ::= { pt3080Output  31 }

pt3080OutputRfAlcSetpointPort1 OBJECT-TYPE
    SYNTAX      Integer32 ( -11000 .. 11000 )
    UNITS       "0.01 dB"
    MAX-ACCESS  read-write
    STATUS      current
    DESCRIPTION
        "ALC setpoint for RF Sense Port 1"
    ::= { pt3080Output  32 }

pt3080OutputRfAlcSetpointPort2 OBJECT-TYPE
    SYNTAX      Integer32 ( -11000 .. 11000 )
    UNITS       "0.01 dB"
    MAX-ACCESS  read-write
    STATUS      current
    DESCRIPTION
        "ALC setpoint for RF Sense Port 2"
    ::= { pt3080Output  33 }

pt3080OutputRfAlcStatus OBJECT-TYPE
    SYNTAX      INTEGER { disable(0), enable(1) }
    MAX-ACCESS  read-only
    STATUS      current
    DESCRIPTION
        "Status for whether the ALC system is enabled or disabled."
    ::= { pt3080Output  34 }

pt3080OutputRfAlcStatusInformation OBJECT-TYPE
    SYNTAX      DisplayString
    MAX-ACCESS  read-only
    STATUS      current
    DESCRIPTION
        "Information on the state of the ALC system."
    ::= { pt3080Output  35 }


--
-- pt3080 GPS sub-tree
--

pt3080GpsBias OBJECT-TYPE
    SYNTAX      INTEGER { off(0), on(1) }
    MAX-ACCESS  read-write
    STATUS      current
    DESCRIPTION
        "Defines the bias to be either on or off for the GPS antenna 
        DC supply (5V or 3V DC). An active GPS antenna requires a power
         supply i.e. requires this parameter to set to ON."
    ::= { pt3080Gps  4 }

pt3080GpsbiasVoltage OBJECT-TYPE
    SYNTAX      INTEGER { gpsant-5v(0), gpsant-33v(1) }
    MAX-ACCESS  read-write
    STATUS      current
    DESCRIPTION
        "Defines the gps antenna bias voltage. An active GPS antenna 
        requires a power supply of either 3V or 5V."
    ::= { pt3080Gps  15 }

pt3080GpsCableDelay OBJECT-TYPE
    SYNTAX      Integer32 ( -18125 .. 13750 )
    UNITS       "0.1 ns"
    MAX-ACCESS  read-write
    STATUS      current
    DESCRIPTION
        "Defines the antenna cable compensation delay. If the GPS antenna
         is situated far away from the receiver itself the signal will
         be delayed and must be compensated."
    ::= { pt3080Gps  12 }

pt3080GpsHoldoverForever OBJECT-TYPE
    SYNTAX      INTEGER { no(0), yes(1) }
    MAX-ACCESS  read-write
    STATUS      current
    DESCRIPTION
        "Defines whether the GPS system is allowed to operate infinitely
         (YES) following loss of GPS locking using the internal GPS 
        chip oscillator or not (NO).In case NO is chosen the GPS holdover
         time applies."
    ::= { pt3080Gps  11 }

pt3080GpsHoldoverTime OBJECT-TYPE
    SYNTAX      Integer32 ( 0 .. 172800 )
    MAX-ACCESS  read-write
    STATUS      current
    DESCRIPTION
        "Defines the GPS holdover time. This value is ignored if the 
        holdover forever (see below) is set to YES If the GPS locking
         is lost the system is allowed to continue operating for holdover
         time seconds using the internal GPS chip oscillator. If - when
         the holdover time interval expires - the GPS locking it still
         lost, the GPS operation will be maintained using external timing
         if present. If external timing is not present the GPS operation
         will be maintained using the internal motherboard oscillator."
    ::= { pt3080Gps  10 }

pt3080GpsSatelliteSystemGPS OBJECT-TYPE
    SYNTAX      INTEGER { disable(0), enable(1) }
    MAX-ACCESS  read-write
    STATUS      current
    DESCRIPTION
        "Controls whether GPS satellites are used to obtain position 
        and timing information."
    ::= { pt3080Gps  16 }

pt3080GpsSatelliteSystemGLONASS OBJECT-TYPE
    SYNTAX      INTEGER { disable(0), enable(1) }
    MAX-ACCESS  read-write
    STATUS      current
    DESCRIPTION
        "Controls whether GLONASS satellites are used to obtain position
         and timing information."
    ::= { pt3080Gps  17 }

pt3080GpsSatelliteSystemGALILEO OBJECT-TYPE
    SYNTAX      INTEGER { disable(0), enable(1) }
    MAX-ACCESS  read-write
    STATUS      current
    DESCRIPTION
        "Controls whether GALILEO satellites are used to obtain position
         and timing information."
    ::= { pt3080Gps  18 }

pt3080GpsSatelliteSystemCOMPASS OBJECT-TYPE
    SYNTAX      INTEGER { disable(0), enable(1) }
    MAX-ACCESS  read-write
    STATUS      current
    DESCRIPTION
        "Controls whether COMPASS satellites are used to obtain position
         and timing information."
    ::= { pt3080Gps  19 }

pt3080GpsVersion OBJECT-TYPE
    SYNTAX      DisplayString
    MAX-ACCESS  read-only
    STATUS      current
    DESCRIPTION
        "Returns the GPS chip firmware version as a string."
    ::= { pt3080Gps  9 }

pt3080Gps1PPSStatus OBJECT-TYPE
    SYNTAX      INTEGER { locked(0), unlocked(1) }
    MAX-ACCESS  read-only
    STATUS      current
    DESCRIPTION
        "Returns the current locking state of the GPS system. The value
         LOCKED indicates that the GPS system is locked to a sufficient
         number of satellites to perform well. UNLOCKED indicates that
         it is not. For the GPS system to perform well at least 4 satellites
         must be visible with a proper signal to noise ratio."
    ::= { pt3080Gps  1 }

pt3080GpsState OBJECT-TYPE
    SYNTAX      DisplayString
    MAX-ACCESS  read-only
    STATUS      current
    DESCRIPTION
        "Returns a string describing the GPS state. For informational
         purposes."
    ::= { pt3080Gps  13 }

pt3080GpsVisibleSatellitesSnr OBJECT-TYPE
    SYNTAX      Integer32
    UNITS       "0.1 dBHz"
    MAX-ACCESS  read-only
    STATUS      current
    DESCRIPTION
        "Returns the average signal to noise ratio of all visible satellites
         via the built-in GPS receiver"
    ::= { pt3080Gps  14 }

pt3080GpsVisibleSatellites OBJECT-TYPE
    SYNTAX      Integer32
    MAX-ACCESS  read-only
    STATUS      current
    DESCRIPTION
        "Returns the number of currently visible satellites via the built-in
         GPS receiver. A satellite is visible if at all detectable by
         the GPS system i.e. regardless of signal to noise ratio. Note
         that the upper value N can change with the launch of new satellites.
         For some time, however, the GPS system has had a total of 24
         satellites."
    ::= { pt3080Gps  2 }

pt3080GpsTrackedSatellites OBJECT-TYPE
    SYNTAX      Integer32
    MAX-ACCESS  read-only
    STATUS      current
    DESCRIPTION
        "Returns the number of currently tracked satellites via the GPS
         receiver."
    ::= { pt3080Gps  3 }

pt3080GpsLongtitude OBJECT-TYPE
    SYNTAX      DisplayString
    MAX-ACCESS  read-only
    STATUS      current
    DESCRIPTION
        "Returns - as a string - the current longtitude derived from 
        the received GPS signal(s). The string format is DDD MM SS C.
         according to the following: - DD denotes degrees in the intervals
         [0 .. 180]. MM and SS denote minutes/seconds in the interval
         [0 .. 59]. C denotes E, W (East, West)."
    ::= { pt3080Gps  6 }

pt3080GpsLatitude OBJECT-TYPE
    SYNTAX      DisplayString
    MAX-ACCESS  read-only
    STATUS      current
    DESCRIPTION
        "Returns - as a string - the current latitude derived from the
         received GPS signal(s). The string format is DD MM SS C. according
         to the following: - DD denotes degrees in the intervals [0 
        .. 90]. MM and SS denote minutes/seconds in the interval [0 
        .. 59]. C denotes N, S (North, South)."
    ::= { pt3080Gps  7 }

pt3080GpsAltitude OBJECT-TYPE
    SYNTAX      DisplayString
    MAX-ACCESS  read-only
    STATUS      current
    DESCRIPTION
        "Returns - as a string - the current altitude derived from the
         received GPS signal(s). The string format is HHHH.c;. according
         to the following: HHHH.c denotes the altitude in metres with
         one digit after the comma. The altitude can be negative."
    ::= { pt3080Gps  8 }


--
-- pt3080 ChannelFilters sub-tree
--




--
-- Pt3080 TSoIP sub-tree
--

pt3080TSoIPRx1ReceiverEnable OBJECT-TYPE
    SYNTAX      INTEGER { disable(0), enable(1) }
    MAX-ACCESS  read-write
    STATUS      current
    DESCRIPTION
        "Enables the reception of IP/UDP packets with transport stream
         data to be forward into the modulator."
    ::= { pt3080TSoIP  15 }

pt3080TSoIPRx2ReceiverEnable OBJECT-TYPE
    SYNTAX      INTEGER { disable(0), enable(1) }
    MAX-ACCESS  read-write
    STATUS      current
    DESCRIPTION
        "Enables the reception of IP/UDP packets with transport stream
         data to be forward into the modulator."
    ::= { pt3080TSoIP  45 }

pt3080TSoIPRx1LanSelect OBJECT-TYPE
    SYNTAX      INTEGER { flan(0), alan(1), tlan(2), blan(3), plan(4) }
    MAX-ACCESS  read-write
    STATUS      current
    DESCRIPTION
        "Specifies which virtual LAN interface to receive IP/UDP packets
         from."
    ::= { pt3080TSoIP  11 }

pt3080TSoIPRx2LanSelect OBJECT-TYPE
    SYNTAX      INTEGER { flan(0), alan(1), tlan(2), blan(3), plan(4) }
    MAX-ACCESS  read-write
    STATUS      current
    DESCRIPTION
        "Specifies which virtual LAN interface to receive IP/UDP packets
         from."
    ::= { pt3080TSoIP  41 }

pt3080TSoIPRx1Multicast OBJECT-TYPE
    SYNTAX      INTEGER { off(0), on(1) }
    MAX-ACCESS  read-write
    STATUS      current
    DESCRIPTION
        "Enables the reception of Multicast IP/UDP packets with transport
         stream data to be forward into the modulator. If disabled, 
        only unicast IP/UDP packets are considdered."
    ::= { pt3080TSoIP  12 }

pt3080TSoIPRx2Multicast OBJECT-TYPE
    SYNTAX      INTEGER { off(0), on(1) }
    MAX-ACCESS  read-write
    STATUS      current
    DESCRIPTION
        "Enables the reception of Multicast IP/UDP packets with transport
         stream data to be forward into the modulator. If disabled, 
        only unicast IP/UDP packets are considdered."
    ::= { pt3080TSoIP  42 }

pt3080TSoIPRx1Protocol OBJECT-TYPE
    SYNTAX      INTEGER { udp(0), rtp(1), auto(2) }
    MAX-ACCESS  read-write
    STATUS      current
    DESCRIPTION
        "Selects which protocol to expect incoming packets to have."
    ::= { pt3080TSoIP  13 }

pt3080TSoIPRx2Protocol OBJECT-TYPE
    SYNTAX      INTEGER { udp(0), rtp(1), auto(2) }
    MAX-ACCESS  read-write
    STATUS      current
    DESCRIPTION
        "Selects which protocol to expect incoming packets to have."
    ::= { pt3080TSoIP  43 }

pt3080TSoIPRx1Portnumber OBJECT-TYPE
    SYNTAX      Integer32 ( 1 .. 65535 )
    MAX-ACCESS  read-write
    STATUS      current
    DESCRIPTION
        "Specifies which UDP port number to receive IP/UDP packets from."
    ::= { pt3080TSoIP  14 }

pt3080TSoIPRx2Portnumber OBJECT-TYPE
    SYNTAX      Integer32 ( 1 .. 65535 )
    MAX-ACCESS  read-write
    STATUS      current
    DESCRIPTION
        "Specifies which UDP port number to receive IP/UDP packets from."
    ::= { pt3080TSoIP  44 }

pt3080TSoIPRx1PacketErrorRatioLimit OBJECT-TYPE
    SYNTAX      Integer32 ( 0 .. 500 )
    UNITS       "0.1 %"
    MAX-ACCESS  read-write
    STATUS      current
    DESCRIPTION
        "Specifies limit for the Packet Error Ratio. If the limit is 
        exceeded and alarm is raised."
    ::= { pt3080TSoIP  16 }

pt3080TSoIPRx2PacketErrorRatioLimit OBJECT-TYPE
    SYNTAX      Integer32 ( 0 .. 500 )
    UNITS       "0.1 %"
    MAX-ACCESS  read-write
    STATUS      current
    DESCRIPTION
        "Specifies limit for the Packet Error Ratio. If the limit is 
        exceeded and alarm is raised."
    ::= { pt3080TSoIP  46 }

pt3080TSoIPRx1MinumimLatency OBJECT-TYPE
    SYNTAX      Integer32 ( 0 .. 5000 )
    UNITS       "0.1 ms"
    MAX-ACCESS  read-write
    STATUS      current
    DESCRIPTION
        "Specifies the minimum time incoming data is buffered. The value
         configured might be modified by FEC row/column sized on the
         incoming data."
    ::= { pt3080TSoIP  10 }

pt3080TSoIPRx2MinumimLatency OBJECT-TYPE
    SYNTAX      Integer32 ( 0 .. 5000 )
    UNITS       "0.1 ms"
    MAX-ACCESS  read-write
    STATUS      current
    DESCRIPTION
        "Specifies the minimum time incoming data is buffered. The value
         configured might be modified by FEC row/column sized on the
         incoming data."
    ::= { pt3080TSoIP  40 }

pt3080TSoIPRx1SyncTimeout OBJECT-TYPE
    SYNTAX      Integer32 ( 16 .. 250 )
    UNITS       "1 ms"
    MAX-ACCESS  read-write
    STATUS      current
    DESCRIPTION
        "Specifies the maximum time accepted between received TS packages."
    ::= { pt3080TSoIP  9 }

pt3080TSoIPRx2SyncTimeout OBJECT-TYPE
    SYNTAX      Integer32 ( 16 .. 250 )
    UNITS       "1 ms"
    MAX-ACCESS  read-write
    STATUS      current
    DESCRIPTION
        "Specifies the maximum time accepted between received TS packages."
    ::= { pt3080TSoIP  39 }

pt3080TSoIPRx1Status OBJECT-TYPE
    SYNTAX      INTEGER { locked(0), unlocked(1), disabled(2) }
    MAX-ACCESS  read-only
    STATUS      current
    DESCRIPTION
        "The current status of the receiver. Locked means minimum of 
        3 IP/UDP frames received per second."
    ::= { pt3080TSoIP  17 }

pt3080TSoIPRx2Status OBJECT-TYPE
    SYNTAX      INTEGER { locked(0), unlocked(1), disabled(2) }
    MAX-ACCESS  read-only
    STATUS      current
    DESCRIPTION
        "The current status of the receiver. Locked means minimum of 
        3 IP/UDP frames received per second."
    ::= { pt3080TSoIP  47 }

pt3080TSoIPRx1CurrentIPAddress OBJECT-TYPE
    SYNTAX      IpAddress
    MAX-ACCESS  read-only
    STATUS      current
    DESCRIPTION
        "The current receive IP address for the TSoIP interface."
    ::= { pt3080TSoIP  18 }

pt3080TSoIPRx2CurrentIPAddress OBJECT-TYPE
    SYNTAX      IpAddress
    MAX-ACCESS  read-only
    STATUS      current
    DESCRIPTION
        "The current receive IP address for the TSoIP interface."
    ::= { pt3080TSoIP  48 }

pt3080TSoIPRx1IpBitrate OBJECT-TYPE
    SYNTAX      Integer32
    UNITS       "0.001 Mbps"
    MAX-ACCESS  read-only
    STATUS      current
    DESCRIPTION
        "Shows the current bitrate of uncoming traffic for this UDP port."
    ::= { pt3080TSoIP  26 }

pt3080TSoIPRx2IpBitrate OBJECT-TYPE
    SYNTAX      Integer32
    UNITS       "0.001 Mbps"
    MAX-ACCESS  read-only
    STATUS      current
    DESCRIPTION
        "Shows the current bitrate of uncoming traffic for this UDP port."
    ::= { pt3080TSoIP  56 }

pt3080TSoIPRx1PacketErrorRatio OBJECT-TYPE
    SYNTAX      Integer32
    UNITS       "0.1 %"
    MAX-ACCESS  read-only
    STATUS      current
    DESCRIPTION
        "Shows the current error ratio of uncoming traffic for this UDP
         port."
    ::= { pt3080TSoIP  20 }

pt3080TSoIPRx2PacketErrorRatio OBJECT-TYPE
    SYNTAX      Integer32
    UNITS       "0.1 %"
    MAX-ACCESS  read-only
    STATUS      current
    DESCRIPTION
        "Shows the current error ratio of uncoming traffic for this UDP
         port."
    ::= { pt3080TSoIP  50 }

pt3080TSoIPRx1SequenceErrors OBJECT-TYPE
    SYNTAX      Integer32
    MAX-ACCESS  read-only
    STATUS      current
    DESCRIPTION
        "The number of sequence errors on this channel on the TSoIP interface."
    ::= { pt3080TSoIP  19 }

pt3080TSoIPRx2SequenceErrors OBJECT-TYPE
    SYNTAX      Integer32
    MAX-ACCESS  read-only
    STATUS      current
    DESCRIPTION
        "The number of sequence errors on this channel on the TSoIP interface."
    ::= { pt3080TSoIP  49 }

pt3080TSoIPRx1LostIPFrames OBJECT-TYPE
    SYNTAX      Integer32
    MAX-ACCESS  read-only
    STATUS      current
    DESCRIPTION
        "The number of lost IP frames on the channel on the TSoIP interface.
         The sequence numbers of frames employed by the RTP protocol
         are used to determine this statistic."
    ::= { pt3080TSoIP  21 }

pt3080TSoIPRx2LostIPFrames OBJECT-TYPE
    SYNTAX      Integer32
    MAX-ACCESS  read-only
    STATUS      current
    DESCRIPTION
        "The number of lost IP frames on the channel on the TSoIP interface.
         The sequence numbers of frames employed by the RTP protocol
         are used to determine this statistic."
    ::= { pt3080TSoIP  51 }

pt3080TSoIPRx1CorrectedIPFrames OBJECT-TYPE
    SYNTAX      Integer32
    MAX-ACCESS  read-only
    STATUS      current
    DESCRIPTION
        "The number of corrected IP frames (via FEC) on this cannel on
         the TSoIP interface."
    ::= { pt3080TSoIP  22 }

pt3080TSoIPRx2CorrectedIPFrames OBJECT-TYPE
    SYNTAX      Integer32
    MAX-ACCESS  read-only
    STATUS      current
    DESCRIPTION
        "The number of corrected IP frames (via FEC) on this cannel on
         the TSoIP interface."
    ::= { pt3080TSoIP  52 }

pt3080TSoIPRx1OverrunIPFrames OBJECT-TYPE
    SYNTAX      Integer32
    MAX-ACCESS  read-only
    STATUS      current
    DESCRIPTION
        "The number of IP frames lost on the channel on the TSoIP interface
         due to overrun. Overrun happens when the outgoing rate of the
         modulator is lower that the incoming rate of TSoIP data."
    ::= { pt3080TSoIP  30 }

pt3080TSoIPRx2OverrunIPFrames OBJECT-TYPE
    SYNTAX      Integer32
    MAX-ACCESS  read-only
    STATUS      current
    DESCRIPTION
        "The number of IP frames lost on the channel on the TSoIP interface
         due to overrun. Overrun happens when the outgoing rate of the
         modulator is lower that the incoming rate of TSoIP data."
    ::= { pt3080TSoIP  60 }

pt3080TSoIPRx1PacketsPerFrame OBJECT-TYPE
    SYNTAX      Integer32
    MAX-ACCESS  read-only
    STATUS      current
    DESCRIPTION
        "The curent number of TS packets per IP frames on this cannel
         on the TSoIP interface."
    ::= { pt3080TSoIP  25 }

pt3080TSoIPRx2PacketsPerFrame OBJECT-TYPE
    SYNTAX      Integer32
    MAX-ACCESS  read-only
    STATUS      current
    DESCRIPTION
        "The curent number of TS packets per IP frames on this cannel
         on the TSoIP interface."
    ::= { pt3080TSoIP  55 }

pt3080TSoIPRx1TSPacketSize OBJECT-TYPE
    SYNTAX      Integer32
    MAX-ACCESS  read-only
    STATUS      current
    DESCRIPTION
        "The curent size of TS packets on this cannel on the TSoIP interface.
         Usually 188 or 204."
    ::= { pt3080TSoIP  29 }

pt3080TSoIPRx2TSPacketSize OBJECT-TYPE
    SYNTAX      Integer32
    MAX-ACCESS  read-only
    STATUS      current
    DESCRIPTION
        "The curent size of TS packets on this cannel on the TSoIP interface.
         Usually 188 or 204."
    ::= { pt3080TSoIP  59 }

pt3080TSoIPRx1FecColumn OBJECT-TYPE
    SYNTAX      Integer32
    MAX-ACCESS  read-only
    STATUS      current
    DESCRIPTION
        "The curent FEC Column (L) number for this cannel on the TSoIP
         interface."
    ::= { pt3080TSoIP  23 }

pt3080TSoIPRx2FecColumn OBJECT-TYPE
    SYNTAX      Integer32
    MAX-ACCESS  read-only
    STATUS      current
    DESCRIPTION
        "The curent FEC Column (L) number for this cannel on the TSoIP
         interface."
    ::= { pt3080TSoIP  53 }

pt3080TSoIPRx1FecRow OBJECT-TYPE
    SYNTAX      Integer32
    MAX-ACCESS  read-only
    STATUS      current
    DESCRIPTION
        "The curent FEC Row (D) number for this cannel on the TSoIP interface."
    ::= { pt3080TSoIP  24 }

pt3080TSoIPRx2FecRow OBJECT-TYPE
    SYNTAX      Integer32
    MAX-ACCESS  read-only
    STATUS      current
    DESCRIPTION
        "The curent FEC Row (D) number for this cannel on the TSoIP interface."
    ::= { pt3080TSoIP  54 }

pt3080TSoIPRx1QueueSize OBJECT-TYPE
    SYNTAX      Integer32
    UNITS       "1 Frames"
    MAX-ACCESS  read-only
    STATUS      current
    DESCRIPTION
        "The curent queue size for this cannel on the TSoIP interface."
    ::= { pt3080TSoIP  27 }

pt3080TSoIPRx2QueueSize OBJECT-TYPE
    SYNTAX      Integer32
    UNITS       "1 Frames"
    MAX-ACCESS  read-only
    STATUS      current
    DESCRIPTION
        "The curent queue size for this cannel on the TSoIP interface."
    ::= { pt3080TSoIP  57 }

pt3080TSoIPRx1CurrentLatency OBJECT-TYPE
    SYNTAX      Integer32
    UNITS       "0.1 ms"
    MAX-ACCESS  read-only
    STATUS      current
    DESCRIPTION
        "The current latency incurrent by queue size on this channel 
        on the TSoIP interface."
    ::= { pt3080TSoIP  28 }

pt3080TSoIPRx2CurrentLatency OBJECT-TYPE
    SYNTAX      Integer32
    UNITS       "0.1 ms"
    MAX-ACCESS  read-only
    STATUS      current
    DESCRIPTION
        "The current latency incurrent by queue size on this channel 
        on the TSoIP interface."
    ::= { pt3080TSoIP  58 }



--
-- pt3080 Monitor sub-tree
--

pt3080MonitorSource OBJECT-TYPE
    SYNTAX      INTEGER { asi-in1(0), asi-in2(1), aux1(2), aux2(3), tsoiprx1(4), tsoiprx2(5), ts-hp(6), ts-lp(7), backplane1(8), backplane2(9) }
    MAX-ACCESS  read-write
    STATUS      current
    DESCRIPTION
        "Selects the source to be monitored on the ASI monitor output."
    ::= { pt3080Monitor  1 }

pt3080MonitorTSoIPEnable OBJECT-TYPE
    SYNTAX      INTEGER { disable(0), enable(1) }
    MAX-ACCESS  read-write
    STATUS      current
    DESCRIPTION
        "Enable or disable the generation of monitor data over TSoIP."
    ::= { pt3080Monitor  10 }

pt3080MonitorTSoIPSource OBJECT-TYPE
    SYNTAX      INTEGER { asi-in1(0), asi-in2(1), aux1(2), aux2(3), tsoiprx1(4), tsoiprx2(5), ts-hp(6), ts-lp(7), backplane1(8), backplane2(9) }
    MAX-ACCESS  read-write
    STATUS      current
    DESCRIPTION
        "Selects the source to be monitored on the TSoIP monitor output."
    ::= { pt3080Monitor  11 }

pt3080MonitorTSoIPMulticastLanSelect OBJECT-TYPE
    SYNTAX      INTEGER { flan(0), alan(1), tlan(2), blan(3), plan(4) }
    MAX-ACCESS  read-write
    STATUS      current
    DESCRIPTION
        "Specifies which virtual LAN interface to transmit Multicast 
        IP/UDP packets out via."
    ::= { pt3080Monitor  25 }

pt3080MonitorTSoIPDestIPAddress OBJECT-TYPE
    SYNTAX      IpAddress
    MAX-ACCESS  read-write
    STATUS      current
    DESCRIPTION
        "Selects the destination IP address of the data to be monitored
         on the TSoIP monitor output."
    ::= { pt3080Monitor  12 }

pt3080MonitorTSoIPDestPort OBJECT-TYPE
    SYNTAX      Integer32 ( 1 .. 65535 )
    MAX-ACCESS  read-write
    STATUS      current
    DESCRIPTION
        "Selects the destination UDP Port number of the data to be monitored
         on the TSoIP monitor output."
    ::= { pt3080Monitor  13 }

pt3080MonitorTSoIPProtocol OBJECT-TYPE
    SYNTAX      INTEGER { udp(0), rtp(1) }
    MAX-ACCESS  read-write
    STATUS      current
    DESCRIPTION
        "Selects the protocol to be used on the TSoIP monitor output."
    ::= { pt3080Monitor  14 }

pt3080MonitorTSoIPEnableFec OBJECT-TYPE
    SYNTAX      INTEGER { disable(0), enable(1) }
    MAX-ACCESS  read-write
    STATUS      current
    DESCRIPTION
        "Enable or disable FEC protocol on the output data from the TSoIP
         Monitor."
    ::= { pt3080Monitor  15 }

pt3080MonitorTSoIPFecColumn OBJECT-TYPE
    SYNTAX      Integer32 ( 1 .. 20 )
    MAX-ACCESS  read-write
    STATUS      current
    DESCRIPTION
        "Selects the FEC protocoll Column number (L) of the data to be
         monitored on the TSoIP monitor output."
    ::= { pt3080Monitor  16 }

pt3080MonitorTSoIPFecRow OBJECT-TYPE
    SYNTAX      Integer32 ( 4 .. 20 )
    MAX-ACCESS  read-write
    STATUS      current
    DESCRIPTION
        "Selects the FEC protocol Row number (D) of the data to be monitored
         on the TSoIP monitor output."
    ::= { pt3080Monitor  17 }

pt3080MonitorTSoIPFecSkew OBJECT-TYPE
    SYNTAX      Integer32 ( 0 .. 4 )
    MAX-ACCESS  read-write
    STATUS      current
    DESCRIPTION
        "Selects the FEC protocol Skew (non block alignment of FEC Frame)
         of the data to be monitored on the TSoIP monitor output."
    ::= { pt3080Monitor  18 }

pt3080MonitorTSoIPKeepNullPackets OBJECT-TYPE
    SYNTAX      INTEGER { disable(0), enable(1) }
    MAX-ACCESS  read-write
    STATUS      current
    DESCRIPTION
        "Retain or discard Null packets of the generation of monitor 
        data over TSoIP."
    ::= { pt3080Monitor  19 }

pt3080MonitorTSoIPPacketsPerFrame OBJECT-TYPE
    SYNTAX      Integer32 ( 1 .. 7 )
    MAX-ACCESS  read-write
    STATUS      current
    DESCRIPTION
        "Set the number of TS packets to send per IP frame on the TSoIP
         monitor output."
    ::= { pt3080Monitor  20 }

pt3080MonitorTSoIPUDPChecksum OBJECT-TYPE
    SYNTAX      INTEGER { disable(0), enable(1) }
    MAX-ACCESS  read-write
    STATUS      current
    DESCRIPTION
        "Generate UDP checksum in the outgoing packets of the TSoIP Monitor."
    ::= { pt3080Monitor  21 }

pt3080MonitorTSoIPDSCP OBJECT-TYPE
    SYNTAX      Integer32 ( 0 .. 255 )
    MAX-ACCESS  read-write
    STATUS      current
    DESCRIPTION
        "Selects the value of the TOS/DSCP field in IP packets to be 
        sent on the TSoIP monitor output."
    ::= { pt3080Monitor  22 }

pt3080MonitorTSoIPTTL OBJECT-TYPE
    SYNTAX      Integer32 ( 1 .. 255 )
    MAX-ACCESS  read-write
    STATUS      current
    DESCRIPTION
        "Selects the value of the TTL (Time-To-Live) field in IP packets
         to be sent on the TSoIP monitor output."
    ::= { pt3080Monitor  23 }

pt3080MonitorTSoIPGenerateError OBJECT-TYPE
    SYNTAX      Integer32 ( 0 .. 1000 )
    UNITS       "0.1 %"
    MAX-ACCESS  read-write
    STATUS      current
    DESCRIPTION
        "Artificially generate an error rate as a percentage of frames
         lost on the TSoIP monitor output."
    ::= { pt3080Monitor  24 }

pt3080MonitorTSoIPIpBitrate OBJECT-TYPE
    SYNTAX      Integer32
    UNITS       "0.001 Mbps"
    MAX-ACCESS  read-only
    STATUS      current
    DESCRIPTION
        "The current rate IP packets traffic to be sent on the TSoIP 
        monitor output."
    ::= { pt3080Monitor  30 }

pt3080MonitorTSoIPTSSize OBJECT-TYPE
    SYNTAX      Integer32
    UNITS       "1 bytes"
    MAX-ACCESS  read-only
    STATUS      current
    DESCRIPTION
        "The current TS packet size (188 or 204) on the TSoIP monitor
         output."
    ::= { pt3080Monitor  32 }

pt3080MonitorTSoIPLostIPFrames OBJECT-TYPE
    SYNTAX      Integer32
    UNITS       "1 Mbps"
    MAX-ACCESS  read-only
    STATUS      current
    DESCRIPTION
        "The number of IP packets traffic generated but lost on the TSoIP
         monitor output."
    ::= { pt3080Monitor  31 }


--
-- pt3080 Test sub-tree
--

pt3080TestEnable OBJECT-TYPE
    SYNTAX      INTEGER { off(0), scar(1), sweep2(2), prbs-on(3), prbs-auto(4) }
    MAX-ACCESS  read-write
    STATUS      current
    DESCRIPTION
        "controls the test signal generation. This cannot be used when
         network mode is SFN. Only a subset is available in repeater
         mode. test signal output state: - testSignalsArray[testSignals_OFF]
         Normal operation. No test signal. - testSignalsArray[testSignals_SCAR]
         A single carrier output is provided. - testSignalsArray[testSignals_SWEEP2]
         A test signal with full spectrum bandwidth and a 3dB peak to
         average power ratio. (OFDM PPR-3). - testSignalsArray[testSignals_PRBSON]
         Forced transmission of stuffing data only (null packets) irrespective
         of the status of the MPEG-2 transport stream input. - testSignalsArray[testSignals_PRBSAUTO]
         Automatic transmission of spectrum based on stuffing data when
         no MPEG-2 TS input is available."
    ::= { pt3080Test  1 }

pt3080TestEnableReconnect OBJECT-TYPE
    SYNTAX      INTEGER { off(0), on(1) }
    MAX-ACCESS  read-write
    STATUS      current
    DESCRIPTION
        "Controls whether the test signal shall reconnect after reset.
         This value is saved in non-volatile memory and thus survives
         a reboot. - onOffArray[TEXT_INDEX_OFF] The selected test signal
         will be set to OFF after reset. - onOffArray[TEXT_INDEX_ON]
         The selected test signal will be output after reset."
    ::= { pt3080Test  2 }

pt3080TestScarrierLevel OBJECT-TYPE
    SYNTAX      Integer32 ( 0 .. 65535 )
    MAX-ACCESS  read-write
    STATUS      current
    DESCRIPTION
        "Control level of the single carrier test signal."
    ::= { pt3080Test  3 }

pt3080TestscarrierFrequencyOffset OBJECT-TYPE
    SYNTAX      Integer32 ( -4000000 .. 4000000 )
    UNITS       "1 Hz"
    MAX-ACCESS  read-write
    STATUS      current
    DESCRIPTION
        "Control frequency offset of the single carrier test signal."
    ::= { pt3080Test  4 }


--
-- pt3080 Alarm sub-tree
--

-- Group Alarm table --

pt3080GroupAlarmTable           OBJECT-TYPE
    SYNTAX                      SEQUENCE OF Pt3080GroupAlarmEntry
    MAX-ACCESS                  not-accessible
    STATUS                      current
    DESCRIPTION
        "This table contains the group alarms"
    ::= { pt3080Alarm 1 }

pt3080GroupAlarmEntry           OBJECT-TYPE
    SYNTAX                      Pt3080GroupAlarmEntry
    MAX-ACCESS                  not-accessible
    STATUS                      current
    DESCRIPTION
        "An entry for the alarms"
    INDEX                       { pt3080GroupAlarmID }
    ::= { pt3080GroupAlarmTable 1 }

Pt3080GroupAlarmEntry ::= SEQUENCE {
    pt3080GroupAlarmID           Integer32,
    pt3080GroupAlarmDescription  DisplayString,
    pt3080GroupAlarmState        INTEGER,
    pt3080GroupAlarmActionEventlog INTEGER,
    pt3080GroupAlarmActionRelay1 INTEGER,
    pt3080GroupAlarmActionRelay2 INTEGER,
    pt3080GroupAlarmActionTrap   INTEGER,
    pt3080GroupAlarmActionEmail  INTEGER,
    pt3080GroupAlarmActionAlarmLED INTEGER,
    pt3080GroupAlarmActionForceMode INTEGER
}

pt3080GroupAlarmID              OBJECT-TYPE
    SYNTAX                      Integer32 ( 0 .. 255 )
    MAX-ACCESS                  not-accessible
    STATUS                      current
    DESCRIPTION
        "Unique ID for this alarm"
    ::= { pt3080GroupAlarmEntry 1 }

pt3080GroupAlarmDescription     OBJECT-TYPE
    SYNTAX                      DisplayString
    MAX-ACCESS                  read-only
    STATUS                      current
    DESCRIPTION
        "Description for this alarm"
    ::= { pt3080GroupAlarmEntry 2 }

pt3080GroupAlarmState           OBJECT-TYPE
    SYNTAX                      INTEGER { off(0), activated(1) }
    MAX-ACCESS                  read-only
    STATUS                      current
    DESCRIPTION
        "Current GroupAlarm state condition"
    ::= { pt3080GroupAlarmEntry 3 }

pt3080GroupAlarmActionEventlog  OBJECT-TYPE
    SYNTAX                      INTEGER { disabled(0), enabled(1) }
    MAX-ACCESS                  read-write
    STATUS                      current
    DESCRIPTION
        "Will the current alarm generate an event in the eventlog"
    ::= { pt3080GroupAlarmEntry 4 }

pt3080GroupAlarmActionRelay1    OBJECT-TYPE
    SYNTAX                      INTEGER { disabled(0), enabled(1) }
    MAX-ACCESS                  read-write
    STATUS                      current
    DESCRIPTION
        "Will the current alarm activate relay1"
    ::= { pt3080GroupAlarmEntry 5 }

pt3080GroupAlarmActionRelay2    OBJECT-TYPE
    SYNTAX                      INTEGER { disabled(0), enabled(1) }
    MAX-ACCESS                  read-write
    STATUS                      current
    DESCRIPTION
        "Will the current alarm activate relay2"
    ::= { pt3080GroupAlarmEntry 6 }

pt3080GroupAlarmActionTrap      OBJECT-TYPE
    SYNTAX                      INTEGER { disabled(0), enabled(1) }
    MAX-ACCESS                  read-write
    STATUS                      current
    DESCRIPTION
        "Will the current alarm generate a trap"
    ::= { pt3080GroupAlarmEntry 7 }

pt3080GroupAlarmActionEmail     OBJECT-TYPE
    SYNTAX                      INTEGER { disabled(0), enabled(1) }
    MAX-ACCESS                  read-write
    STATUS                      current
    DESCRIPTION
        "Will the current alarm generate an email"
    ::= { pt3080GroupAlarmEntry 8 }

pt3080GroupAlarmActionAlarmLED  OBJECT-TYPE
    SYNTAX                      INTEGER { disabled(0), enabled(1) }
    MAX-ACCESS                  read-write
    STATUS                      current
    DESCRIPTION
        "Will the current alarm turn Alarm LED on frontpanel on"
    ::= { pt3080GroupAlarmEntry 9 }

pt3080GroupAlarmActionForceMode OBJECT-TYPE
    SYNTAX                      INTEGER { none(0), mute(1), reboot(2) }
    MAX-ACCESS                  read-write
    STATUS                      current
    DESCRIPTION
        "Will the current alarm mute output"
    ::= { pt3080GroupAlarmEntry 10 }



-- ASI TS-Primary Alarm table --

pt3080ASITSPrimaryAlarmTable    OBJECT-TYPE
    SYNTAX                      SEQUENCE OF Pt3080ASITSPrimaryAlarmEntry
    MAX-ACCESS                  not-accessible
    STATUS                      current
    DESCRIPTION
        "This table contains the ASI TS-Primary alarms"
    ::= { pt3080Alarm 5 }

pt3080ASITSPrimaryAlarmEntry OBJECT-TYPE
    SYNTAX                      Pt3080ASITSPrimaryAlarmEntry
    MAX-ACCESS                  not-accessible
    STATUS                      current
    DESCRIPTION
        "An entry for the alarms"
    INDEX                       { pt3080ASITSPrimaryAlarmID }
    ::= { pt3080ASITSPrimaryAlarmTable 1 }

Pt3080ASITSPrimaryAlarmEntry ::= SEQUENCE {
    pt3080ASITSPrimaryAlarmID             Integer32,
    pt3080ASITSPrimaryAlarmDescription    DisplayString,
    pt3080ASITSPrimaryAlarmState          INTEGER,
    pt3080ASITSPrimaryAlarmActionEventlog INTEGER,
    pt3080ASITSPrimaryAlarmActionRelay1   INTEGER,
    pt3080ASITSPrimaryAlarmActionRelay2   INTEGER,
    pt3080ASITSPrimaryAlarmActionTrap     INTEGER,
    pt3080ASITSPrimaryAlarmActionEmail    INTEGER,
    pt3080ASITSPrimaryAlarmActionAlarmLED INTEGER,
    pt3080ASITSPrimaryAlarmActionForceMode INTEGER
}

pt3080ASITSPrimaryAlarmID       OBJECT-TYPE
    SYNTAX                      Integer32 ( 0 .. 255 )
    MAX-ACCESS                  not-accessible
    STATUS                      current
    DESCRIPTION
        "Unique ID for this alarm"
    ::= { pt3080ASITSPrimaryAlarmEntry 1 }

pt3080ASITSPrimaryAlarmDescription OBJECT-TYPE
    SYNTAX                      DisplayString
    MAX-ACCESS                  read-only
    STATUS                      current
    DESCRIPTION
        "Description for this alarm"
    ::= { pt3080ASITSPrimaryAlarmEntry 2 }

pt3080ASITSPrimaryAlarmState    OBJECT-TYPE
    SYNTAX                      INTEGER { off(0), activated(1) }
    MAX-ACCESS                  read-only
    STATUS                      current
    DESCRIPTION
        "Current ASITSPrimaryAlarm state condition"
    ::= { pt3080ASITSPrimaryAlarmEntry 3 }

pt3080ASITSPrimaryAlarmActionEventlog OBJECT-TYPE
    SYNTAX                      INTEGER { disabled(0), enabled(1) }
    MAX-ACCESS                  read-write
    STATUS                      current
    DESCRIPTION
        "Will the current alarm generate an event in the eventlog"
    ::= { pt3080ASITSPrimaryAlarmEntry 4 }

pt3080ASITSPrimaryAlarmActionRelay1 OBJECT-TYPE
    SYNTAX                      INTEGER { disabled(0), enabled(1) }
    MAX-ACCESS                  read-write
    STATUS                      current
    DESCRIPTION
        "Will the current alarm activate relay1"
    ::= { pt3080ASITSPrimaryAlarmEntry 5 }

pt3080ASITSPrimaryAlarmActionRelay2 OBJECT-TYPE
    SYNTAX                      INTEGER { disabled(0), enabled(1) }
    MAX-ACCESS                  read-write
    STATUS                      current
    DESCRIPTION
        "Will the current alarm activate relay2"
    ::= { pt3080ASITSPrimaryAlarmEntry 6 }

pt3080ASITSPrimaryAlarmActionTrap OBJECT-TYPE
    SYNTAX                      INTEGER { disabled(0), enabled(1) }
    MAX-ACCESS                  read-write
    STATUS                      current
    DESCRIPTION
        "Will the current alarm generate a trap"
    ::= { pt3080ASITSPrimaryAlarmEntry 7 }

pt3080ASITSPrimaryAlarmActionEmail OBJECT-TYPE
    SYNTAX                      INTEGER { disabled(0), enabled(1) }
    MAX-ACCESS                  read-write
    STATUS                      current
    DESCRIPTION
        "Will the current alarm generate an email"
    ::= { pt3080ASITSPrimaryAlarmEntry 8 }

pt3080ASITSPrimaryAlarmActionAlarmLED OBJECT-TYPE
    SYNTAX                      INTEGER { disabled(0), enabled(1) }
    MAX-ACCESS                  read-write
    STATUS                      current
    DESCRIPTION
        "Will the current alarm turn Alarm LED on frontpanel on"
    ::= { pt3080ASITSPrimaryAlarmEntry 9 }

pt3080ASITSPrimaryAlarmActionForceMode OBJECT-TYPE
    SYNTAX                      INTEGER { none(0), mute(1), reboot(2) }
    MAX-ACCESS                  read-write
    STATUS                      current
    DESCRIPTION
        "Will the current alarm mute output"
    ::= { pt3080ASITSPrimaryAlarmEntry 10 }

-- ASI TS-Secondary Alarm table --

pt3080ASITSSecondaryAlarmTable  OBJECT-TYPE
    SYNTAX                      SEQUENCE OF Pt3080ASITSSecondaryAlarmEntry
    MAX-ACCESS                  not-accessible
    STATUS                      current
    DESCRIPTION
        "This table contains the ASI alarms"
    ::= { pt3080Alarm 6 }

pt3080ASITSSecondaryAlarmEntry  OBJECT-TYPE
    SYNTAX                      Pt3080ASITSSecondaryAlarmEntry
    MAX-ACCESS                  not-accessible
    STATUS                      current
    DESCRIPTION
        "An entry for the alarms"
    INDEX                       { pt3080ASITSSecondaryAlarmID }
    ::= { pt3080ASITSSecondaryAlarmTable 1 }

Pt3080ASITSSecondaryAlarmEntry ::= SEQUENCE {
    pt3080ASITSSecondaryAlarmID             Integer32,
    pt3080ASITSSecondaryAlarmDescription    DisplayString,
    pt3080ASITSSecondaryAlarmState          INTEGER,
    pt3080ASITSSecondaryAlarmActionEventlog INTEGER,
    pt3080ASITSSecondaryAlarmActionRelay1   INTEGER,
    pt3080ASITSSecondaryAlarmActionRelay2   INTEGER,
    pt3080ASITSSecondaryAlarmActionTrap     INTEGER,
    pt3080ASITSSecondaryAlarmActionEmail    INTEGER,
    pt3080ASITSSecondaryAlarmActionAlarmLED INTEGER,
    pt3080ASITSSecondaryAlarmActionForceMode INTEGER
}

pt3080ASITSSecondaryAlarmID     OBJECT-TYPE
    SYNTAX                      Integer32 ( 0 .. 255 )
    MAX-ACCESS                  not-accessible
    STATUS                      current
    DESCRIPTION
        "Unique ID for this alarm"
    ::= { pt3080ASITSSecondaryAlarmEntry 1 }

pt3080ASITSSecondaryAlarmDescription OBJECT-TYPE
    SYNTAX                      DisplayString
    MAX-ACCESS                  read-only
    STATUS                      current
    DESCRIPTION
        "Description for this alarm"
    ::= { pt3080ASITSSecondaryAlarmEntry 2 }

pt3080ASITSSecondaryAlarmState  OBJECT-TYPE
    SYNTAX                      INTEGER { off(0), activated(1) }
    MAX-ACCESS                  read-only
    STATUS                      current
    DESCRIPTION
        "Current ASITSSecondaryAlarm state condition"
    ::= { pt3080ASITSSecondaryAlarmEntry 3 }

pt3080ASITSSecondaryAlarmActionEventlog OBJECT-TYPE
    SYNTAX                      INTEGER { disabled(0), enabled(1) }
    MAX-ACCESS                  read-write
    STATUS                      current
    DESCRIPTION
        "Will the current alarm generate an event in the eventlog"
    ::= { pt3080ASITSSecondaryAlarmEntry 4 }

pt3080ASITSSecondaryAlarmActionRelay1 OBJECT-TYPE
    SYNTAX                      INTEGER { disabled(0), enabled(1) }
    MAX-ACCESS                  read-write
    STATUS                      current
    DESCRIPTION
        "Will the current alarm activate relay1"
    ::= { pt3080ASITSSecondaryAlarmEntry 5 }

pt3080ASITSSecondaryAlarmActionRelay2 OBJECT-TYPE
    SYNTAX                      INTEGER { disabled(0), enabled(1) }
    MAX-ACCESS                  read-write
    STATUS                      current
    DESCRIPTION
        "Will the current alarm activate relay2"
    ::= { pt3080ASITSSecondaryAlarmEntry 6 }

pt3080ASITSSecondaryAlarmActionTrap OBJECT-TYPE
    SYNTAX                      INTEGER { disabled(0), enabled(1) }
    MAX-ACCESS                  read-write
    STATUS                      current
    DESCRIPTION
        "Will the current alarm generate a trap"
    ::= { pt3080ASITSSecondaryAlarmEntry 7 }

pt3080ASITSSecondaryAlarmActionEmail OBJECT-TYPE
    SYNTAX                      INTEGER { disabled(0), enabled(1) }
    MAX-ACCESS                  read-write
    STATUS                      current
    DESCRIPTION
        "Will the current alarm generate an email"
    ::= { pt3080ASITSSecondaryAlarmEntry 8 }

pt3080ASITSSecondaryAlarmActionAlarmLED OBJECT-TYPE
    SYNTAX                      INTEGER { disabled(0), enabled(1) }
    MAX-ACCESS                  read-write
    STATUS                      current
    DESCRIPTION
        "Will the current alarm turn Alarm LED on frontpanel on"
    ::= { pt3080ASITSSecondaryAlarmEntry 9 }

pt3080ASITSSecondaryAlarmActionForceMode OBJECT-TYPE
    SYNTAX                      INTEGER { none(0), mute(1), reboot(2) }
    MAX-ACCESS                  read-write
    STATUS                      current
    DESCRIPTION
        "Will the current alarm mute output"
    ::= { pt3080ASITSSecondaryAlarmEntry 10 }

-- SFN Alarm table --

pt3080SFNAlarmTable             OBJECT-TYPE
    SYNTAX                      SEQUENCE OF Pt3080SFNAlarmEntry
    MAX-ACCESS                  not-accessible
    STATUS                      current
    DESCRIPTION
        "This table contains the SFN alarms"
    ::= { pt3080Alarm 7 }

pt3080SFNAlarmEntry OBJECT-TYPE
    SYNTAX                      Pt3080SFNAlarmEntry
    MAX-ACCESS                  not-accessible
    STATUS                      current
    DESCRIPTION
        "An entry for the alarms"
    INDEX                       { pt3080SFNAlarmID }
    ::= { pt3080SFNAlarmTable 1 }

Pt3080SFNAlarmEntry ::= SEQUENCE {
    pt3080SFNAlarmID             Integer32,
    pt3080SFNAlarmDescription    DisplayString,
    pt3080SFNAlarmState          INTEGER,
    pt3080SFNAlarmActionEventlog INTEGER,
    pt3080SFNAlarmActionRelay1   INTEGER,
    pt3080SFNAlarmActionRelay2   INTEGER,
    pt3080SFNAlarmActionTrap     INTEGER,
    pt3080SFNAlarmActionEmail    INTEGER,
    pt3080SFNAlarmActionAlarmLED INTEGER,
    pt3080SFNAlarmActionForceMode INTEGER
}

pt3080SFNAlarmID                OBJECT-TYPE
    SYNTAX                      Integer32 ( 0 .. 255 )
    MAX-ACCESS                  not-accessible
    STATUS                      current
    DESCRIPTION
        "Unique ID for this alarm"
    ::= { pt3080SFNAlarmEntry 1 }

pt3080SFNAlarmDescription       OBJECT-TYPE
    SYNTAX                      DisplayString
    MAX-ACCESS                  read-only
    STATUS                      current
    DESCRIPTION
        "Description for this alarm"
    ::= { pt3080SFNAlarmEntry 2 }

pt3080SFNAlarmState             OBJECT-TYPE
    SYNTAX                      INTEGER { off(0), activated(1) }
    MAX-ACCESS                  read-only
    STATUS                      current
    DESCRIPTION
        "Current SFNAlarm state condition"
    ::= { pt3080SFNAlarmEntry 3 }

pt3080SFNAlarmActionEventlog    OBJECT-TYPE
    SYNTAX                      INTEGER { disabled(0), enabled(1) }
    MAX-ACCESS                  read-write
    STATUS                      current
    DESCRIPTION
        "Will the current alarm generate an event in the eventlog"
    ::= { pt3080SFNAlarmEntry 4 }

pt3080SFNAlarmActionRelay1      OBJECT-TYPE
    SYNTAX                      INTEGER { disabled(0), enabled(1) }
    MAX-ACCESS                  read-write
    STATUS                      current
    DESCRIPTION
        "Will the current alarm activate relay1"
    ::= { pt3080SFNAlarmEntry 5 }

pt3080SFNAlarmActionRelay2      OBJECT-TYPE
    SYNTAX                      INTEGER { disabled(0), enabled(1) }
    MAX-ACCESS                  read-write
    STATUS                      current
    DESCRIPTION
        "Will the current alarm activate relay2"
    ::= { pt3080SFNAlarmEntry 6 }

pt3080SFNAlarmActionTrap        OBJECT-TYPE
    SYNTAX                      INTEGER { disabled(0), enabled(1) }
    MAX-ACCESS                  read-write
    STATUS                      current
    DESCRIPTION
        "Will the current alarm generate a trap"
    ::= { pt3080SFNAlarmEntry 7 }

pt3080SFNAlarmActionEmail       OBJECT-TYPE
    SYNTAX                      INTEGER { disabled(0), enabled(1) }
    MAX-ACCESS                  read-write
    STATUS                      current
    DESCRIPTION
        "Will the current alarm generate an email"
    ::= { pt3080SFNAlarmEntry 8 }

pt3080SFNAlarmActionAlarmLED    OBJECT-TYPE
    SYNTAX                      INTEGER { disabled(0), enabled(1) }
    MAX-ACCESS                  read-write
    STATUS                      current
    DESCRIPTION
        "Will the current alarm turn Alarm LED on frontpanel on"
    ::= { pt3080SFNAlarmEntry 9 }

pt3080SFNAlarmActionForceMode   OBJECT-TYPE
    SYNTAX                      INTEGER { none(0), mute(1), reboot(2) }
    MAX-ACCESS                  read-write
    STATUS                      current
    DESCRIPTION
        "Will the current alarm mute output"
    ::= { pt3080SFNAlarmEntry 10 }



-- Reference Alarm table --

pt3080ReferenceAlarmTable       OBJECT-TYPE
    SYNTAX                      SEQUENCE OF Pt3080ReferenceAlarmEntry
    MAX-ACCESS                  not-accessible
    STATUS                      current
    DESCRIPTION
        "This table contains the Reference alarms"
    ::= { pt3080Alarm 8 }

pt3080ReferenceAlarmEntry       OBJECT-TYPE
    SYNTAX                      Pt3080ReferenceAlarmEntry
    MAX-ACCESS                  not-accessible
    STATUS                      current
    DESCRIPTION
        "An entry for the alarms"
    INDEX                       { pt3080ReferenceAlarmID }
    ::= { pt3080ReferenceAlarmTable 1 }

Pt3080ReferenceAlarmEntry ::= SEQUENCE {
    pt3080ReferenceAlarmID               Integer32,
    pt3080ReferenceAlarmDescription      DisplayString,
    pt3080ReferenceAlarmState            INTEGER,
    pt3080ReferenceAlarmActionEventlog   INTEGER,
    pt3080ReferenceAlarmActionRelay1     INTEGER,
    pt3080ReferenceAlarmActionRelay2     INTEGER,
    pt3080ReferenceAlarmActionTrap       INTEGER,
    pt3080ReferenceAlarmActionEmail      INTEGER,
    pt3080ReferenceAlarmActionAlarmLED   INTEGER,
    pt3080ReferenceAlarmActionForceMode  INTEGER
}

pt3080ReferenceAlarmID          OBJECT-TYPE
    SYNTAX                      Integer32 ( 0 .. 255 )
    MAX-ACCESS                  not-accessible
    STATUS                      current
    DESCRIPTION
        "Unique ID for this alarm"
    ::= { pt3080ReferenceAlarmEntry 1 }

pt3080ReferenceAlarmDescription OBJECT-TYPE
    SYNTAX                      DisplayString
    MAX-ACCESS                  read-only
    STATUS                      current
    DESCRIPTION
        "Description for this alarm"
    ::= { pt3080ReferenceAlarmEntry 2 }

pt3080ReferenceAlarmState       OBJECT-TYPE
    SYNTAX                      INTEGER { off(0), activated(1) }
    MAX-ACCESS                  read-only
    STATUS                      current
    DESCRIPTION
        "Current ReferenceAlarm state condition"
    ::= { pt3080ReferenceAlarmEntry 3 }

pt3080ReferenceAlarmActionEventlog OBJECT-TYPE
    SYNTAX                      INTEGER { disabled(0), enabled(1) }
    MAX-ACCESS                  read-write
    STATUS                      current
    DESCRIPTION
        "Will the current alarm generate an event in the eventlog"
    ::= { pt3080ReferenceAlarmEntry 4 }

pt3080ReferenceAlarmActionRelay1 OBJECT-TYPE
    SYNTAX                      INTEGER { disabled(0), enabled(1) }
    MAX-ACCESS                  read-write
    STATUS                      current
    DESCRIPTION
        "Will the current alarm activate relay1"
    ::= { pt3080ReferenceAlarmEntry 5 }

pt3080ReferenceAlarmActionRelay2 OBJECT-TYPE
    SYNTAX                      INTEGER { disabled(0), enabled(1) }
    MAX-ACCESS                  read-write
    STATUS                      current
    DESCRIPTION
        "Will the current alarm activate relay2"
    ::= { pt3080ReferenceAlarmEntry 6 }

pt3080ReferenceAlarmActionTrap  OBJECT-TYPE
    SYNTAX                      INTEGER { disabled(0), enabled(1) }
    MAX-ACCESS                  read-write
    STATUS                      current
    DESCRIPTION
        "Will the current alarm generate a trap"
    ::= { pt3080ReferenceAlarmEntry 7 }

pt3080ReferenceAlarmActionEmail OBJECT-TYPE
    SYNTAX                      INTEGER { disabled(0), enabled(1) }
    MAX-ACCESS                  read-write
    STATUS                      current
    DESCRIPTION
        "Will the current alarm generate an email"
    ::= { pt3080ReferenceAlarmEntry 8 }

pt3080ReferenceAlarmActionAlarmLED OBJECT-TYPE
    SYNTAX                      INTEGER { disabled(0), enabled(1) }
    MAX-ACCESS                  read-write
    STATUS                      current
    DESCRIPTION
        "Will the current alarm turn Alarm LED on frontpanel on"
    ::= { pt3080ReferenceAlarmEntry 9 }

pt3080ReferenceAlarmActionForceMode OBJECT-TYPE
    SYNTAX                      INTEGER { none(0), mute(1), reboot(2) }
    MAX-ACCESS                  read-write
    STATUS                      current
    DESCRIPTION
        "Will the current alarm mute output"
    ::= { pt3080ReferenceAlarmEntry 10 }


-- RF Alarm table --

pt3080RFAlarmTable              OBJECT-TYPE
    SYNTAX                      SEQUENCE OF Pt3080RFAlarmEntry
    MAX-ACCESS                  not-accessible
    STATUS                      current
    DESCRIPTION
        "This table contains the RF alarms"
    ::= { pt3080Alarm 9 }

pt3080RFAlarmEntry              OBJECT-TYPE
    SYNTAX                      Pt3080RFAlarmEntry
    MAX-ACCESS                  not-accessible
    STATUS                      current
    DESCRIPTION
        "An entry for the alarms"
    INDEX                       { pt3080RFAlarmID }
    ::= { pt3080RFAlarmTable 1 }

Pt3080RFAlarmEntry ::= SEQUENCE {
    pt3080RFAlarmID                Integer32,
    pt3080RFAlarmDescription       DisplayString,
    pt3080RFAlarmState             INTEGER,
    pt3080RFAlarmActionEventlog    INTEGER,
    pt3080RFAlarmActionRelay1      INTEGER,
    pt3080RFAlarmActionRelay2      INTEGER,
    pt3080RFAlarmActionTrap        INTEGER,
    pt3080RFAlarmActionEmail       INTEGER,
    pt3080RFAlarmActionAlarmLED    INTEGER,
    pt3080RFAlarmActionForceMode   INTEGER
}

pt3080RFAlarmID                 OBJECT-TYPE
    SYNTAX                      Integer32 ( 0 .. 255 )
    MAX-ACCESS                  not-accessible
    STATUS                      current
    DESCRIPTION
        "Unique ID for this alarm"
    ::= { pt3080RFAlarmEntry 1 }

pt3080RFAlarmDescription        OBJECT-TYPE
    SYNTAX                      DisplayString
    MAX-ACCESS                  read-only
    STATUS                      current
    DESCRIPTION
        "Description for this alarm"
    ::= { pt3080RFAlarmEntry 2 }

pt3080RFAlarmState              OBJECT-TYPE
    SYNTAX                      INTEGER { off(0), activated(1) }
    MAX-ACCESS                  read-only
    STATUS                      current
    DESCRIPTION
        "Current RFAlarm state condition"
    ::= { pt3080RFAlarmEntry 3 }

pt3080RFAlarmActionEventlog     OBJECT-TYPE
    SYNTAX                      INTEGER { disabled(0), enabled(1) }
    MAX-ACCESS                  read-write
    STATUS                      current
    DESCRIPTION
        "Will the current alarm generate an event in the eventlog"
    ::= { pt3080RFAlarmEntry 4 }

pt3080RFAlarmActionRelay1       OBJECT-TYPE
    SYNTAX                      INTEGER { disabled(0), enabled(1) }
    MAX-ACCESS                  read-write
    STATUS                      current
    DESCRIPTION
        "Will the current alarm activate relay1"
    ::= { pt3080RFAlarmEntry 5 }

pt3080RFAlarmActionRelay2       OBJECT-TYPE
    SYNTAX                      INTEGER { disabled(0), enabled(1) }
    MAX-ACCESS                  read-write
    STATUS                      current
    DESCRIPTION
        "Will the current alarm activate relay2"
    ::= { pt3080RFAlarmEntry 6 }

pt3080RFAlarmActionTrap         OBJECT-TYPE
    SYNTAX                      INTEGER { disabled(0), enabled(1) }
    MAX-ACCESS                  read-write
    STATUS                      current
    DESCRIPTION
        "Will the current alarm generate a trap"
    ::= { pt3080RFAlarmEntry 7 }

pt3080RFAlarmActionEmail        OBJECT-TYPE
    SYNTAX                      INTEGER { disabled(0), enabled(1) }
    MAX-ACCESS                  read-write
    STATUS                      current
    DESCRIPTION
        "Will the current alarm generate an email"
    ::= { pt3080RFAlarmEntry 8 }

pt3080RFAlarmActionAlarmLED     OBJECT-TYPE
    SYNTAX                      INTEGER { disabled(0), enabled(1) }
    MAX-ACCESS                  read-write
    STATUS                      current
    DESCRIPTION
        "Will the current alarm turn Alarm LED on frontpanel on"
    ::= { pt3080RFAlarmEntry 9 }

pt3080RFAlarmActionForceMode    OBJECT-TYPE
    SYNTAX                      INTEGER { none(0), mute(1), reboot(2) }
    MAX-ACCESS                  read-write
    STATUS                      current
    DESCRIPTION
        "Will the current alarm mute output"
    ::= { pt3080RFAlarmEntry 10 }

-- GPS Alarm table --

pt3080GPSAlarmTable             OBJECT-TYPE
    SYNTAX                      SEQUENCE OF Pt3080GPSAlarmEntry
    MAX-ACCESS                  not-accessible
    STATUS                      current
    DESCRIPTION
        "This table contains the GPS alarms"
    ::= { pt3080Alarm 10 }

pt3080GPSAlarmEntry OBJECT-TYPE
    SYNTAX                      Pt3080GPSAlarmEntry
    MAX-ACCESS                  not-accessible
    STATUS                      current
    DESCRIPTION
        "An entry for the alarms"
    INDEX                       { pt3080GPSAlarmID }
    ::= { pt3080GPSAlarmTable 1 }

Pt3080GPSAlarmEntry ::= SEQUENCE {
    pt3080GPSAlarmID             Integer32,
    pt3080GPSAlarmDescription    DisplayString,
    pt3080GPSAlarmState          INTEGER,
    pt3080GPSAlarmActionEventlog INTEGER,
    pt3080GPSAlarmActionRelay1   INTEGER,
    pt3080GPSAlarmActionRelay2   INTEGER,
    pt3080GPSAlarmActionTrap     INTEGER,
    pt3080GPSAlarmActionEmail    INTEGER,
    pt3080GPSAlarmActionAlarmLED INTEGER,
    pt3080GPSAlarmActionForceMode INTEGER
}

pt3080GPSAlarmID                OBJECT-TYPE
    SYNTAX                      Integer32 ( 0 .. 255 )
    MAX-ACCESS                  not-accessible
    STATUS                      current
    DESCRIPTION
        "Unique ID for this alarm"
    ::= { pt3080GPSAlarmEntry 1 }

pt3080GPSAlarmDescription       OBJECT-TYPE
    SYNTAX                      DisplayString
    MAX-ACCESS                  read-only
    STATUS                      current
    DESCRIPTION
        "Description for this alarm"
    ::= { pt3080GPSAlarmEntry 2 }

pt3080GPSAlarmState             OBJECT-TYPE
    SYNTAX                      INTEGER { off(0), activated(1) }
    MAX-ACCESS                  read-only
    STATUS                      current
    DESCRIPTION
        "Current GPSAlarm state condition"
    ::= { pt3080GPSAlarmEntry 3 }

pt3080GPSAlarmActionEventlog    OBJECT-TYPE
    SYNTAX                      INTEGER { disabled(0), enabled(1) }
    MAX-ACCESS                  read-write
    STATUS                      current
    DESCRIPTION
        "Will the current alarm generate an event in the eventlog"
    ::= { pt3080GPSAlarmEntry 4 }

pt3080GPSAlarmActionRelay1      OBJECT-TYPE
    SYNTAX                      INTEGER { disabled(0), enabled(1) }
    MAX-ACCESS                  read-write
    STATUS                      current
    DESCRIPTION
        "Will the current alarm activate relay1"
    ::= { pt3080GPSAlarmEntry 5 }

pt3080GPSAlarmActionRelay2      OBJECT-TYPE
    SYNTAX                      INTEGER { disabled(0), enabled(1) }
    MAX-ACCESS                  read-write
    STATUS                      current
    DESCRIPTION
        "Will the current alarm activate relay2"
    ::= { pt3080GPSAlarmEntry 6 }

pt3080GPSAlarmActionTrap        OBJECT-TYPE
    SYNTAX                      INTEGER { disabled(0), enabled(1) }
    MAX-ACCESS                  read-write
    STATUS                      current
    DESCRIPTION
        "Will the current alarm generate a trap"
    ::= { pt3080GPSAlarmEntry 7 }

pt3080GPSAlarmActionEmail       OBJECT-TYPE
    SYNTAX                      INTEGER { disabled(0), enabled(1) }
    MAX-ACCESS                  read-write
    STATUS                      current
    DESCRIPTION
        "Will the current alarm generate an email"
    ::= { pt3080GPSAlarmEntry 8 }

pt3080GPSAlarmActionAlarmLED    OBJECT-TYPE
    SYNTAX                      INTEGER { disabled(0), enabled(1) }
    MAX-ACCESS                  read-write
    STATUS                      current
    DESCRIPTION
        "Will the current alarm turn Alarm LED on frontpanel on"
    ::= { pt3080GPSAlarmEntry 9 }

pt3080GPSAlarmActionForceMode   OBJECT-TYPE
    SYNTAX                      INTEGER { none(0), mute(1), reboot(2) }
    MAX-ACCESS                  read-write
    STATUS                      current
    DESCRIPTION
        "Will the current alarm mute output"
    ::= { pt3080GPSAlarmEntry 10 }


-- TSoIP Alarm table --

pt3080TSoIPAlarmTable           OBJECT-TYPE
    SYNTAX                      SEQUENCE OF Pt3080TSoIPAlarmEntry
    MAX-ACCESS                  not-accessible
    STATUS                      current
    DESCRIPTION
        "This table contains the TSoIP alarms"
    ::= { pt3080Alarm 12 }

pt3080TSoIPAlarmEntry           OBJECT-TYPE
    SYNTAX                      Pt3080TSoIPAlarmEntry
    MAX-ACCESS                  not-accessible
    STATUS                      current
    DESCRIPTION
        "An entry for the alarms"
    INDEX                       { pt3080TSoIPAlarmID }
    ::= { pt3080TSoIPAlarmTable 1 }

Pt3080TSoIPAlarmEntry ::= SEQUENCE {
    pt3080TSoIPAlarmID             Integer32,
    pt3080TSoIPAlarmDescription    DisplayString,
    pt3080TSoIPAlarmState          INTEGER,
    pt3080TSoIPAlarmActionEventlog INTEGER,
    pt3080TSoIPAlarmActionRelay1   INTEGER,
    pt3080TSoIPAlarmActionRelay2   INTEGER,
    pt3080TSoIPAlarmActionTrap     INTEGER,
    pt3080TSoIPAlarmActionEmail    INTEGER,
    pt3080TSoIPAlarmActionAlarmLED INTEGER,
    pt3080TSoIPAlarmActionForceMode INTEGER
}

pt3080TSoIPAlarmID              OBJECT-TYPE
    SYNTAX                      Integer32 ( 0 .. 255 )
    MAX-ACCESS                  not-accessible
    STATUS                      current
    DESCRIPTION
        "Unique ID for this alarm"
    ::= { pt3080TSoIPAlarmEntry 1 }

pt3080TSoIPAlarmDescription     OBJECT-TYPE
    SYNTAX                      DisplayString
    MAX-ACCESS                  read-only
    STATUS                      current
    DESCRIPTION
        "Description for this alarm"
    ::= { pt3080TSoIPAlarmEntry 2 }

pt3080TSoIPAlarmState           OBJECT-TYPE
    SYNTAX                      INTEGER { off(0), activated(1) }
    MAX-ACCESS                  read-only
    STATUS                      current
    DESCRIPTION
        "Current TSoIPAlarm state condition"
    ::= { pt3080TSoIPAlarmEntry 3 }

pt3080TSoIPAlarmActionEventlog  OBJECT-TYPE
    SYNTAX                      INTEGER { disabled(0), enabled(1) }
    MAX-ACCESS                  read-write
    STATUS                      current
    DESCRIPTION
        "Will the current alarm generate an event in the eventlog"
    ::= { pt3080TSoIPAlarmEntry 4 }

pt3080TSoIPAlarmActionRelay1    OBJECT-TYPE
    SYNTAX                      INTEGER { disabled(0), enabled(1) }
    MAX-ACCESS                  read-write
    STATUS                      current
    DESCRIPTION
        "Will the current alarm activate relay1"
    ::= { pt3080TSoIPAlarmEntry 5 }

pt3080TSoIPAlarmActionRelay2    OBJECT-TYPE
    SYNTAX                      INTEGER { disabled(0), enabled(1) }
    MAX-ACCESS                  read-write
    STATUS                      current
    DESCRIPTION
        "Will the current alarm activate relay2"
    ::= { pt3080TSoIPAlarmEntry 6 }

pt3080TSoIPAlarmActionTrap      OBJECT-TYPE
    SYNTAX                      INTEGER { disabled(0), enabled(1) }
    MAX-ACCESS                  read-write
    STATUS                      current
    DESCRIPTION
        "Will the current alarm generate a trap"
    ::= { pt3080TSoIPAlarmEntry 7 }

pt3080TSoIPAlarmActionEmail     OBJECT-TYPE
    SYNTAX                      INTEGER { disabled(0), enabled(1) }
    MAX-ACCESS                  read-write
    STATUS                      current
    DESCRIPTION
        "Will the current alarm generate an email"
    ::= { pt3080TSoIPAlarmEntry 8 }

pt3080TSoIPAlarmActionAlarmLED  OBJECT-TYPE
    SYNTAX                      INTEGER { disabled(0), enabled(1) }
    MAX-ACCESS                  read-write
    STATUS                      current
    DESCRIPTION
        "Will the current alarm turn Alarm LED on frontpanel on"
    ::= { pt3080TSoIPAlarmEntry 9 }

pt3080TSoIPAlarmActionForceMode OBJECT-TYPE
    SYNTAX                      INTEGER { none(0), mute(1), reboot(2) }
    MAX-ACCESS                  read-write
    STATUS                      current
    DESCRIPTION
        "Will the current alarm mute output"
    ::= { pt3080TSoIPAlarmEntry 10 }

-- External Alarm table --

pt3080ExternalAlarmTable        OBJECT-TYPE
    SYNTAX                      SEQUENCE OF Pt3080ExternalAlarmEntry
    MAX-ACCESS                  not-accessible
    STATUS                      current
    DESCRIPTION
        "This table contains the External alarms"
    ::= { pt3080Alarm 13 }

pt3080ExternalAlarmEntry        OBJECT-TYPE
    SYNTAX                      Pt3080ExternalAlarmEntry
    MAX-ACCESS                  not-accessible
    STATUS                      current
    DESCRIPTION
        "An entry for the alarms"
    INDEX                       { pt3080ExternalAlarmID }
    ::= { pt3080ExternalAlarmTable 1 }

Pt3080ExternalAlarmEntry ::= SEQUENCE {
    pt3080ExternalAlarmID                Integer32,
    pt3080ExternalAlarmDescription       DisplayString,
    pt3080ExternalAlarmState             INTEGER,
    pt3080ExternalAlarmActionEventlog    INTEGER,
    pt3080ExternalAlarmActionRelay1      INTEGER,
    pt3080ExternalAlarmActionRelay2      INTEGER,
    pt3080ExternalAlarmActionTrap        INTEGER,
    pt3080ExternalAlarmActionEmail       INTEGER,
    pt3080ExternalAlarmActionAlarmLED    INTEGER,
    pt3080ExternalAlarmActionForceMode   INTEGER
}

pt3080ExternalAlarmID           OBJECT-TYPE
    SYNTAX                      Integer32 ( 0 .. 255 )
    MAX-ACCESS                  not-accessible
    STATUS                      current
    DESCRIPTION
        "Unique ID for this alarm"
    ::= { pt3080ExternalAlarmEntry 1 }

pt3080ExternalAlarmDescription  OBJECT-TYPE
    SYNTAX                      DisplayString
    MAX-ACCESS                  read-only
    STATUS                      current
    DESCRIPTION
        "Description for this alarm"
    ::= { pt3080ExternalAlarmEntry 2 }

pt3080ExternalAlarmState        OBJECT-TYPE
    SYNTAX                      INTEGER { off(0), activated(1) }
    MAX-ACCESS                  read-only
    STATUS                      current
    DESCRIPTION
        "Current ExternalAlarm state condition"
    ::= { pt3080ExternalAlarmEntry 3 }

pt3080ExternalAlarmActionEventlog OBJECT-TYPE
    SYNTAX                      INTEGER { disabled(0), enabled(1) }
    MAX-ACCESS                  read-write
    STATUS                      current
    DESCRIPTION
        "Will the current alarm generate an event in the eventlog"
    ::= { pt3080ExternalAlarmEntry 4 }

pt3080ExternalAlarmActionRelay1 OBJECT-TYPE
    SYNTAX                      INTEGER { disabled(0), enabled(1) }
    MAX-ACCESS                  read-write
    STATUS                      current
    DESCRIPTION
        "Will the current alarm activate relay1"
    ::= { pt3080ExternalAlarmEntry 5 }

pt3080ExternalAlarmActionRelay2 OBJECT-TYPE
    SYNTAX                      INTEGER { disabled(0), enabled(1) }
    MAX-ACCESS                  read-write
    STATUS                      current
    DESCRIPTION
        "Will the current alarm activate relay2"
    ::= { pt3080ExternalAlarmEntry 6 }

pt3080ExternalAlarmActionTrap   OBJECT-TYPE
    SYNTAX                      INTEGER { disabled(0), enabled(1) }
    MAX-ACCESS                  read-write
    STATUS                      current
    DESCRIPTION
        "Will the current alarm generate a trap"
    ::= { pt3080ExternalAlarmEntry 7 }

pt3080ExternalAlarmActionEmail  OBJECT-TYPE
    SYNTAX                      INTEGER { disabled(0), enabled(1) }
    MAX-ACCESS                  read-write
    STATUS                      current
    DESCRIPTION
        "Will the current alarm generate an email"
    ::= { pt3080ExternalAlarmEntry 8 }

pt3080ExternalAlarmActionAlarmLED OBJECT-TYPE
    SYNTAX                      INTEGER { disabled(0), enabled(1) }
    MAX-ACCESS                  read-write
    STATUS                      current
    DESCRIPTION
        "Will the current alarm turn Alarm LED on frontpanel on"
    ::= { pt3080ExternalAlarmEntry 9 }

pt3080ExternalAlarmActionForceMode OBJECT-TYPE
    SYNTAX                      INTEGER { none(0), mute(1), reboot(2) }
    MAX-ACCESS                  read-write
    STATUS                      current
    DESCRIPTION
        "Will the current alarm mute output"
    ::= { pt3080ExternalAlarmEntry 10 }

-- HW Monitor Alarm table --

pt3080HWMonitorAlarmTable       OBJECT-TYPE
    SYNTAX                      SEQUENCE OF Pt3080HWMonitorAlarmEntry
    MAX-ACCESS                  not-accessible
    STATUS                      current
    DESCRIPTION
        "This table contains the HW Monitor alarms"
    ::= { pt3080Alarm 14 }

pt3080HWMonitorAlarmEntry       OBJECT-TYPE
    SYNTAX                      Pt3080HWMonitorAlarmEntry
    MAX-ACCESS                  not-accessible
    STATUS                      current
    DESCRIPTION
        "An entry for the alarms"
    INDEX                       { pt3080HWMonitorAlarmID }
    ::= { pt3080HWMonitorAlarmTable 1 }

Pt3080HWMonitorAlarmEntry ::= SEQUENCE {
    pt3080HWMonitorAlarmID                Integer32,
    pt3080HWMonitorAlarmDescription       DisplayString,
    pt3080HWMonitorAlarmState             INTEGER,
    pt3080HWMonitorAlarmActionEventlog    INTEGER,
    pt3080HWMonitorAlarmActionRelay1      INTEGER,
    pt3080HWMonitorAlarmActionRelay2      INTEGER,
    pt3080HWMonitorAlarmActionTrap        INTEGER,
    pt3080HWMonitorAlarmActionEmail       INTEGER,
    pt3080HWMonitorAlarmActionAlarmLED    INTEGER,
    pt3080HWMonitorAlarmActionForceMode   INTEGER
}

pt3080HWMonitorAlarmID          OBJECT-TYPE
    SYNTAX                      Integer32 ( 0 .. 255 )
    MAX-ACCESS                  not-accessible
    STATUS                      current
    DESCRIPTION
        "Unique ID for this alarm"
    ::= { pt3080HWMonitorAlarmEntry 1 }

pt3080HWMonitorAlarmDescription OBJECT-TYPE
    SYNTAX                      DisplayString
    MAX-ACCESS                  read-only
    STATUS                      current
    DESCRIPTION
        "Description for this alarm"
    ::= { pt3080HWMonitorAlarmEntry 2 }

pt3080HWMonitorAlarmState       OBJECT-TYPE
    SYNTAX                      INTEGER { off(0), activated(1) }
    MAX-ACCESS                  read-only
    STATUS                      current
    DESCRIPTION
        "Current HWMonitorAlarm state condition"
    ::= { pt3080HWMonitorAlarmEntry 3 }

pt3080HWMonitorAlarmActionEventlog OBJECT-TYPE
    SYNTAX                      INTEGER { disabled(0), enabled(1) }
    MAX-ACCESS                  read-write
    STATUS                      current
    DESCRIPTION
        "Will the current alarm generate an event in the eventlog"
    ::= { pt3080HWMonitorAlarmEntry 4 }

pt3080HWMonitorAlarmActionRelay1 OBJECT-TYPE
    SYNTAX                      INTEGER { disabled(0), enabled(1) }
    MAX-ACCESS                  read-write
    STATUS                      current
    DESCRIPTION
        "Will the current alarm activate relay1"
    ::= { pt3080HWMonitorAlarmEntry 5 }

pt3080HWMonitorAlarmActionRelay2 OBJECT-TYPE
    SYNTAX                      INTEGER { disabled(0), enabled(1) }
    MAX-ACCESS                  read-write
    STATUS                      current
    DESCRIPTION
        "Will the current alarm activate relay2"
    ::= { pt3080HWMonitorAlarmEntry 6 }

pt3080HWMonitorAlarmActionTrap  OBJECT-TYPE
    SYNTAX                      INTEGER { disabled(0), enabled(1) }
    MAX-ACCESS                  read-write
    STATUS                      current
    DESCRIPTION
        "Will the current alarm generate a trap"
    ::= { pt3080HWMonitorAlarmEntry 7 }

pt3080HWMonitorAlarmActionEmail OBJECT-TYPE
    SYNTAX                      INTEGER { disabled(0), enabled(1) }
    MAX-ACCESS                  read-write
    STATUS                      current
    DESCRIPTION
        "Will the current alarm generate an email"
    ::= { pt3080HWMonitorAlarmEntry 8 }

pt3080HWMonitorAlarmActionAlarmLED OBJECT-TYPE
    SYNTAX                      INTEGER { disabled(0), enabled(1) }
    MAX-ACCESS                  read-write
    STATUS                      current
    DESCRIPTION
        "Will the current alarm turn Alarm LED on frontpanel on"
    ::= { pt3080HWMonitorAlarmEntry 9 }

pt3080HWMonitorAlarmActionForceMode OBJECT-TYPE
    SYNTAX                      INTEGER { none(0), mute(1), reboot(2) }
    MAX-ACCESS                  read-write
    STATUS                      current
    DESCRIPTION
        "Will the current alarm mute output"
    ::= { pt3080HWMonitorAlarmEntry 10 }

-- Communications Alarm table --

pt3080CommsAlarmTable           OBJECT-TYPE
    SYNTAX                      SEQUENCE OF Pt3080CommsAlarmEntry
    MAX-ACCESS                  not-accessible
    STATUS                      current
    DESCRIPTION
        "This table contains the Communication alarms"
    ::= { pt3080Alarm 15 }

pt3080CommsAlarmEntry           OBJECT-TYPE
    SYNTAX                      Pt3080CommsAlarmEntry
    MAX-ACCESS                  not-accessible
    STATUS                      current
    DESCRIPTION
        "An entry for the alarms"
    INDEX                       { pt3080CommsAlarmID }
    ::= { pt3080CommsAlarmTable 1 }

Pt3080CommsAlarmEntry ::= SEQUENCE {
    pt3080CommsAlarmID             Integer32,
    pt3080CommsAlarmDescription    DisplayString,
    pt3080CommsAlarmState          INTEGER,
    pt3080CommsAlarmActionEventlog INTEGER,
    pt3080CommsAlarmActionRelay1   INTEGER,
    pt3080CommsAlarmActionRelay2   INTEGER,
    pt3080CommsAlarmActionTrap     INTEGER,
    pt3080CommsAlarmActionEmail    INTEGER,
    pt3080CommsAlarmActionAlarmLED INTEGER,
    pt3080CommsAlarmActionForceMode INTEGER
}

pt3080CommsAlarmID              OBJECT-TYPE
    SYNTAX                      Integer32 ( 0 .. 255 )
    MAX-ACCESS                  not-accessible
    STATUS                      current
    DESCRIPTION
        "Unique ID for this alarm"
    ::= { pt3080CommsAlarmEntry 1 }

pt3080CommsAlarmDescription     OBJECT-TYPE
    SYNTAX                      DisplayString
    MAX-ACCESS                  read-only
    STATUS                      current
    DESCRIPTION
        "Description for this alarm"
    ::= { pt3080CommsAlarmEntry 2 }

pt3080CommsAlarmState           OBJECT-TYPE
    SYNTAX                      INTEGER { off(0), activated(1) }
    MAX-ACCESS                  read-only
    STATUS                      current
    DESCRIPTION
        "Current CommsAlarm state condition"
    ::= { pt3080CommsAlarmEntry 3 }

pt3080CommsAlarmActionEventlog  OBJECT-TYPE
    SYNTAX                      INTEGER { disabled(0), enabled(1) }
    MAX-ACCESS                  read-write
    STATUS                      current
    DESCRIPTION
        "Will the current alarm generate an event in the eventlog"
    ::= { pt3080CommsAlarmEntry 4 }

pt3080CommsAlarmActionRelay1    OBJECT-TYPE
    SYNTAX                      INTEGER { disabled(0), enabled(1) }
    MAX-ACCESS                  read-write
    STATUS                      current
    DESCRIPTION
        "Will the current alarm activate relay1"
    ::= { pt3080CommsAlarmEntry 5 }

pt3080CommsAlarmActionRelay2    OBJECT-TYPE
    SYNTAX                      INTEGER { disabled(0), enabled(1) }
    MAX-ACCESS                  read-write
    STATUS                      current
    DESCRIPTION
        "Will the current alarm activate relay2"
    ::= { pt3080CommsAlarmEntry 6 }

pt3080CommsAlarmActionTrap      OBJECT-TYPE
    SYNTAX                      INTEGER { disabled(0), enabled(1) }
    MAX-ACCESS                  read-write
    STATUS                      current
    DESCRIPTION
        "Will the current alarm generate a trap"
    ::= { pt3080CommsAlarmEntry 7 }

pt3080CommsAlarmActionEmail     OBJECT-TYPE
    SYNTAX                      INTEGER { disabled(0), enabled(1) }
    MAX-ACCESS                  read-write
    STATUS                      current
    DESCRIPTION
        "Will the current alarm generate an email"
    ::= { pt3080CommsAlarmEntry 8 }

pt3080CommsAlarmActionAlarmLED  OBJECT-TYPE
    SYNTAX                      INTEGER { disabled(0), enabled(1) }
    MAX-ACCESS                  read-write
    STATUS                      current
    DESCRIPTION
        "Will the current alarm turn Alarm LED on frontpanel on"
    ::= { pt3080CommsAlarmEntry 9 }

pt3080CommsAlarmActionForceMode OBJECT-TYPE
    SYNTAX                      INTEGER { none(0), mute(1), reboot(2) }
    MAX-ACCESS                  read-write
    STATUS                      current
    DESCRIPTION
        "Will the current alarm mute output"
    ::= { pt3080CommsAlarmEntry 10 }

-- ASI Alarm table --

pt3080ASIAlarmTable             OBJECT-TYPE
    SYNTAX                      SEQUENCE OF Pt3080ASIAlarmEntry
    MAX-ACCESS                  not-accessible
    STATUS                      current
    DESCRIPTION
        "This table contains the ASI alarms"
    ::= { pt3080Alarm 16 }

pt3080ASIAlarmEntry             OBJECT-TYPE
    SYNTAX                      Pt3080ASIAlarmEntry
    MAX-ACCESS                  not-accessible
    STATUS                      current
    DESCRIPTION
        "An entry for the alarms"
    INDEX                       { pt3080ASIAlarmID }
    ::= { pt3080ASIAlarmTable 1 }

Pt3080ASIAlarmEntry ::= SEQUENCE {
    pt3080ASIAlarmID             Integer32,
    pt3080ASIAlarmDescription    DisplayString,
    pt3080ASIAlarmState          INTEGER,
    pt3080ASIAlarmActionEventlog INTEGER,
    pt3080ASIAlarmActionRelay1   INTEGER,
    pt3080ASIAlarmActionRelay2   INTEGER,
    pt3080ASIAlarmActionTrap     INTEGER,
    pt3080ASIAlarmActionEmail    INTEGER,
    pt3080ASIAlarmActionAlarmLED INTEGER,
    pt3080ASIAlarmActionForceMode INTEGER
}

pt3080ASIAlarmID                OBJECT-TYPE
    SYNTAX                      Integer32 ( 0 .. 255 )
    MAX-ACCESS                  not-accessible
    STATUS                      current
    DESCRIPTION
        "Unique ID for this alarm"
    ::= { pt3080ASIAlarmEntry 1 }

pt3080ASIAlarmDescription       OBJECT-TYPE
    SYNTAX                      DisplayString
    MAX-ACCESS                  read-only
    STATUS                      current
    DESCRIPTION
        "Description for this alarm"
    ::= { pt3080ASIAlarmEntry 2 }

pt3080ASIAlarmState             OBJECT-TYPE
    SYNTAX                      INTEGER { off(0), activated(1) }
    MAX-ACCESS                  read-only
    STATUS                      current
    DESCRIPTION
        "Current ASIAlarm state condition"
    ::= { pt3080ASIAlarmEntry 3 }

pt3080ASIAlarmActionEventlog    OBJECT-TYPE
    SYNTAX                      INTEGER { disabled(0), enabled(1) }
    MAX-ACCESS                  read-write
    STATUS                      current
    DESCRIPTION
        "Will the current alarm generate an event in the eventlog"
    ::= { pt3080ASIAlarmEntry 4 }

pt3080ASIAlarmActionRelay1      OBJECT-TYPE
    SYNTAX                      INTEGER { disabled(0), enabled(1) }
    MAX-ACCESS                  read-write
    STATUS                      current
    DESCRIPTION
        "Will the current alarm activate relay1"
    ::= { pt3080ASIAlarmEntry 5 }

pt3080ASIAlarmActionRelay2      OBJECT-TYPE
    SYNTAX                      INTEGER { disabled(0), enabled(1) }
    MAX-ACCESS                  read-write
    STATUS                      current
    DESCRIPTION
        "Will the current alarm activate relay2"
    ::= { pt3080ASIAlarmEntry 6 }

pt3080ASIAlarmActionTrap        OBJECT-TYPE
    SYNTAX                      INTEGER { disabled(0), enabled(1) }
    MAX-ACCESS                  read-write
    STATUS                      current
    DESCRIPTION
        "Will the current alarm generate a trap"
    ::= { pt3080ASIAlarmEntry 7 }

pt3080ASIAlarmActionEmail       OBJECT-TYPE
    SYNTAX                      INTEGER { disabled(0), enabled(1) }
    MAX-ACCESS                  read-write
    STATUS                      current
    DESCRIPTION
        "Will the current alarm generate an email"
    ::= { pt3080ASIAlarmEntry 8 }

pt3080ASIAlarmActionAlarmLED    OBJECT-TYPE
    SYNTAX                      INTEGER { disabled(0), enabled(1) }
    MAX-ACCESS                  read-write
    STATUS                      current
    DESCRIPTION
        "Will the current alarm turn Alarm LED on frontpanel on"
    ::= { pt3080ASIAlarmEntry 9 }

pt3080ASIAlarmActionForceMode   OBJECT-TYPE
    SYNTAX                      INTEGER { none(0), mute(1), reboot(2) }
    MAX-ACCESS                  read-write
    STATUS                      current
    DESCRIPTION
        "Will the current alarm mute output"
    ::= { pt3080ASIAlarmEntry 10 }

-- Demodulator Alarm table --

pt3080DemodulatorAlarmTable     OBJECT-TYPE
    SYNTAX                      SEQUENCE OF Pt3080DemodulatorAlarmEntry
    MAX-ACCESS                  not-accessible
    STATUS                      current
    DESCRIPTION
        "This table contains the Demodulator alarms"
    ::= { pt3080Alarm 17 }

pt3080DemodulatorAlarmEntry     OBJECT-TYPE
    SYNTAX                      Pt3080DemodulatorAlarmEntry
    MAX-ACCESS                  not-accessible
    STATUS                      current
    DESCRIPTION
        "An entry for the alarms"
    INDEX                       { pt3080DemodulatorAlarmID }
    ::= { pt3080DemodulatorAlarmTable 1 }

Pt3080DemodulatorAlarmEntry ::= SEQUENCE {
    pt3080DemodulatorAlarmID                Integer32,
    pt3080DemodulatorAlarmDescription       DisplayString,
    pt3080DemodulatorAlarmState             INTEGER,
    pt3080DemodulatorAlarmActionEventlog    INTEGER,
    pt3080DemodulatorAlarmActionRelay1      INTEGER,
    pt3080DemodulatorAlarmActionRelay2      INTEGER,
    pt3080DemodulatorAlarmActionTrap        INTEGER,
    pt3080DemodulatorAlarmActionEmail       INTEGER,
    pt3080DemodulatorAlarmActionAlarmLED    INTEGER,
    pt3080DemodulatorAlarmActionForceMode   INTEGER
}

pt3080DemodulatorAlarmID        OBJECT-TYPE
    SYNTAX                      Integer32 ( 0 .. 255 )
    MAX-ACCESS                  not-accessible
    STATUS                      current
    DESCRIPTION
        "Unique ID for this alarm"
    ::= { pt3080DemodulatorAlarmEntry 1 }

pt3080DemodulatorAlarmDescription OBJECT-TYPE
    SYNTAX                      DisplayString
    MAX-ACCESS                  read-only
    STATUS                      current
    DESCRIPTION
        "Description for this alarm"
    ::= { pt3080DemodulatorAlarmEntry 2 }

pt3080DemodulatorAlarmState     OBJECT-TYPE
    SYNTAX                      INTEGER { off(0), activated(1) }
    MAX-ACCESS                  read-only
    STATUS                      current
    DESCRIPTION
        "Current DemodulatorAlarm state condition"
    ::= { pt3080DemodulatorAlarmEntry 3 }

pt3080DemodulatorAlarmActionEventlog OBJECT-TYPE
    SYNTAX                      INTEGER { disabled(0), enabled(1) }
    MAX-ACCESS                  read-write
    STATUS                      current
    DESCRIPTION
        "Will the current alarm generate an event in the eventlog"
    ::= { pt3080DemodulatorAlarmEntry 4 }

pt3080DemodulatorAlarmActionRelay1 OBJECT-TYPE
    SYNTAX                      INTEGER { disabled(0), enabled(1) }
    MAX-ACCESS                  read-write
    STATUS                      current
    DESCRIPTION
        "Will the current alarm activate relay1"
    ::= { pt3080DemodulatorAlarmEntry 5 }

pt3080DemodulatorAlarmActionRelay2 OBJECT-TYPE
    SYNTAX                      INTEGER { disabled(0), enabled(1) }
    MAX-ACCESS                  read-write
    STATUS                      current
    DESCRIPTION
        "Will the current alarm activate relay2"
    ::= { pt3080DemodulatorAlarmEntry 6 }

pt3080DemodulatorAlarmActionTrap OBJECT-TYPE
    SYNTAX                      INTEGER { disabled(0), enabled(1) }
    MAX-ACCESS                  read-write
    STATUS                      current
    DESCRIPTION
        "Will the current alarm generate a trap"
    ::= { pt3080DemodulatorAlarmEntry 7 }

pt3080DemodulatorAlarmActionEmail OBJECT-TYPE
    SYNTAX                      INTEGER { disabled(0), enabled(1) }
    MAX-ACCESS                  read-write
    STATUS                      current
    DESCRIPTION
        "Will the current alarm generate an email"
    ::= { pt3080DemodulatorAlarmEntry 8 }

pt3080DemodulatorAlarmActionAlarmLED OBJECT-TYPE
    SYNTAX                      INTEGER { disabled(0), enabled(1) }
    MAX-ACCESS                  read-write
    STATUS                      current
    DESCRIPTION
        "Will the current alarm turn Alarm LED on frontpanel on"
    ::= { pt3080DemodulatorAlarmEntry 9 }

pt3080DemodulatorAlarmActionForceMode OBJECT-TYPE
    SYNTAX                      INTEGER { none(0), mute(1), reboot(2) }
    MAX-ACCESS                  read-write
    STATUS                      current
    DESCRIPTION
        "Will the current alarm mute output"
    ::= { pt3080DemodulatorAlarmEntry 10 }

-- Internal Alarm table --

pt3080InternalAlarmTable        OBJECT-TYPE
    SYNTAX                      SEQUENCE OF Pt3080InternalAlarmEntry
    MAX-ACCESS                  not-accessible
    STATUS                      current
    DESCRIPTION
        "This table contains the Internal alarms"
    ::= { pt3080Alarm 18 }

pt3080InternalAlarmEntry        OBJECT-TYPE
    SYNTAX                      Pt3080InternalAlarmEntry
    MAX-ACCESS                  not-accessible
    STATUS                      current
    DESCRIPTION
        "An entry for the alarms"
    INDEX                       { pt3080InternalAlarmID }
    ::= { pt3080InternalAlarmTable 1 }

Pt3080InternalAlarmEntry ::= SEQUENCE {
    pt3080InternalAlarmID                Integer32,
    pt3080InternalAlarmDescription       DisplayString,
    pt3080InternalAlarmState             INTEGER,
    pt3080InternalAlarmActionEventlog    INTEGER,
    pt3080InternalAlarmActionRelay1      INTEGER,
    pt3080InternalAlarmActionRelay2      INTEGER,
    pt3080InternalAlarmActionTrap        INTEGER,
    pt3080InternalAlarmActionEmail       INTEGER,
    pt3080InternalAlarmActionAlarmLED    INTEGER,
    pt3080InternalAlarmActionForceMode   INTEGER
}

pt3080InternalAlarmID           OBJECT-TYPE
    SYNTAX                      Integer32 ( 0 .. 255 )
    MAX-ACCESS                  not-accessible
    STATUS                      current
    DESCRIPTION
        "Unique ID for this alarm"
    ::= { pt3080InternalAlarmEntry 1 }

pt3080InternalAlarmDescription  OBJECT-TYPE
    SYNTAX                      DisplayString
    MAX-ACCESS                  read-only
    STATUS                      current
    DESCRIPTION
        "Description for this alarm"
    ::= { pt3080InternalAlarmEntry 2 }

pt3080InternalAlarmState        OBJECT-TYPE
    SYNTAX                      INTEGER { off(0), activated(1) }
    MAX-ACCESS                  read-only
    STATUS                      current
    DESCRIPTION
        "Current InternalAlarm state condition"
    ::= { pt3080InternalAlarmEntry 3 }

pt3080InternalAlarmActionEventlog OBJECT-TYPE
    SYNTAX                      INTEGER { disabled(0), enabled(1) }
    MAX-ACCESS                  read-write
    STATUS                      current
    DESCRIPTION
        "Will the current alarm generate an event in the eventlog"
    ::= { pt3080InternalAlarmEntry 4 }

pt3080InternalAlarmActionRelay1 OBJECT-TYPE
    SYNTAX                      INTEGER { disabled(0), enabled(1) }
    MAX-ACCESS                  read-write
    STATUS                      current
    DESCRIPTION
        "Will the current alarm activate relay1"
    ::= { pt3080InternalAlarmEntry 5 }

pt3080InternalAlarmActionRelay2 OBJECT-TYPE
    SYNTAX                      INTEGER { disabled(0), enabled(1) }
    MAX-ACCESS                  read-write
    STATUS                      current
    DESCRIPTION
        "Will the current alarm activate relay2"
    ::= { pt3080InternalAlarmEntry 6 }

pt3080InternalAlarmActionTrap   OBJECT-TYPE
    SYNTAX                      INTEGER { disabled(0), enabled(1) }
    MAX-ACCESS                  read-write
    STATUS                      current
    DESCRIPTION
        "Will the current alarm generate a trap"
    ::= { pt3080InternalAlarmEntry 7 }

pt3080InternalAlarmActionEmail  OBJECT-TYPE
    SYNTAX                      INTEGER { disabled(0), enabled(1) }
    MAX-ACCESS                  read-write
    STATUS                      current
    DESCRIPTION
        "Will the current alarm generate an email"
    ::= { pt3080InternalAlarmEntry 8 }

pt3080InternalAlarmActionAlarmLED OBJECT-TYPE
    SYNTAX                      INTEGER { disabled(0), enabled(1) }
    MAX-ACCESS                  read-write
    STATUS                      current
    DESCRIPTION
        "Will the current alarm turn Alarm LED on frontpanel on"
    ::= { pt3080InternalAlarmEntry 9 }

pt3080InternalAlarmActionForceMode OBJECT-TYPE
    SYNTAX                      INTEGER { none(0), mute(1), reboot(2) }
    MAX-ACCESS                  read-write
    STATUS                      current
    DESCRIPTION
        "Will the current alarm mute output"
    ::= { pt3080InternalAlarmEntry 10 }


-- DVB-T2 Mode-A Alarm table --


--
-- pt3080 Preset sub-tree
--

pt3080PresetTable               OBJECT-TYPE
    SYNTAX                      SEQUENCE OF Pt3080PresetEntry
    MAX-ACCESS                  not-accessible
    STATUS                      current
    DESCRIPTION
        "This table contains the presets"
    ::= { pt3080Preset 1 }

pt3080PresetEntry               OBJECT-TYPE
    SYNTAX                      Pt3080PresetEntry
    MAX-ACCESS                  not-accessible
    STATUS                      current
    DESCRIPTION
        "An entry for the presets"
    INDEX                       { pt3080PresetNo }
    ::= { pt3080PresetTable 1 }

Pt3080PresetEntry ::= SEQUENCE {
    pt3080PresetNo               Integer32,
    pt3080PresetName             DisplayString
}

pt3080PresetNo                  OBJECT-TYPE
    SYNTAX                      Integer32 ( 1 .. 10 )
    MAX-ACCESS                  not-accessible
    STATUS                      current
    DESCRIPTION
        "Unique number for this preset"
    ::= { pt3080PresetEntry 1 }

pt3080PresetName                OBJECT-TYPE
    SYNTAX                      DisplayString
    MAX-ACCESS                  read-write
    STATUS                      current
    DESCRIPTION
        "Name for this preset"
    ::= { pt3080PresetEntry 2 }

pt3080PresetRecall              OBJECT-TYPE
    SYNTAX                      Integer32 ( 0 .. 10 )
    MAX-ACCESS                  read-write
    STATUS                      current
    DESCRIPTION
        "Install this preset into current running parameter set.
         Value will always read as 0 and setting it to 0 has no effect."
    ::= { pt3080Preset 2 }

pt3080PresetStore               OBJECT-TYPE
    SYNTAX                      Integer32 ( 0 .. 8 )
    MAX-ACCESS                  read-write
    STATUS                      current
    DESCRIPTION
        "Store the currently running parameter set into this preset
         Value will always read as 0 and setting it to 0 has no effect."
    ::= { pt3080Preset 3 }

--
-- pt3080 Eventlog sub-tree
--

pt3080EventlogTable             OBJECT-TYPE
    SYNTAX                      SEQUENCE OF Pt3080EventlogEntry
    MAX-ACCESS                  not-accessible
    STATUS                      current
    DESCRIPTION
        "This table contains the group alarms"
    ::= { pt3080Eventlog 1 }

pt3080EventlogEntry             OBJECT-TYPE
    SYNTAX                      Pt3080EventlogEntry
    MAX-ACCESS                  not-accessible
    STATUS                      current
    DESCRIPTION
        "An entry for the alarms"
    INDEX                       { pt3080EventlogNo }
    ::= { pt3080EventlogTable 1 }

Pt3080EventlogEntry ::= SEQUENCE {
    pt3080EventlogNo             Integer32,
    pt3080EventlogID             Integer32,
    pt3080EventlogTimestamp      DateAndTime,
    pt3080EventlogText           DisplayString
}

pt3080EventlogNo                OBJECT-TYPE
    SYNTAX                      Integer32 ( 1 .. 2047 )
    MAX-ACCESS                  not-accessible
    STATUS                      current
    DESCRIPTION
        "Unique number for this event"
    ::= { pt3080EventlogEntry 1 }

pt3080EventlogID                OBJECT-TYPE
    SYNTAX                      Integer32
    MAX-ACCESS                  read-only
    STATUS                      current
    DESCRIPTION
        "Unique ID for this type of event"
    ::= { pt3080EventlogEntry 2 }

pt3080EventlogTimestamp         OBJECT-TYPE
    SYNTAX                      DateAndTime
    MAX-ACCESS                  read-only
    STATUS                      current
    DESCRIPTION
        "Timestamp for this event"
    ::= { pt3080EventlogEntry 3 }

pt3080EventlogText              OBJECT-TYPE
    SYNTAX                      DisplayString
    MAX-ACCESS                  read-only
    STATUS                      current
    DESCRIPTION
        "Text for this event"
    ::= { pt3080EventlogEntry 4 }

pt3080EventlogClear             OBJECT-TYPE
    SYNTAX                      INTEGER { noop(0), clear(1) }
    MAX-ACCESS                  read-write
    STATUS                      current
    DESCRIPTION
        "Clear the entire eventlog by setting the value to 1."
    ::= { pt3080Eventlog 2 }

pt3080EventlogEnable            OBJECT-TYPE
    SYNTAX                      INTEGER { off(0), on(1) }
    MAX-ACCESS                  read-write
    STATUS                      current
    DESCRIPTION
        "Enable eventlog by setting the value to 1."
    ::= { pt3080Eventlog 3 }

pt3080EventlogMode              OBJECT-TYPE
    SYNTAX                      INTEGER { fifo(0), full(1) }
    MAX-ACCESS                  read-write
    STATUS                      current
    DESCRIPTION
        "Set eventlog mode to FIFO for keeping the newest entries.
         Set eventlog mode to FULL for keeping the oldest entries."
    ::= { pt3080Eventlog 4 }

--
-- pt3080 Comms sub-tree
--

pt3080CommsAlarmEmailReceiver OBJECT-TYPE
    SYNTAX      DisplayString
    MAX-ACCESS  read-write
    STATUS      current
    DESCRIPTION
        "The email address of the receipiant of alarm emails."
    ::= { pt3080Comms  34 }

pt3080CommsSeparatedSwitchPorts OBJECT-TYPE
    SYNTAX      INTEGER { off(0), on(1) }
    MAX-ACCESS  read-write
    STATUS      current
    DESCRIPTION
        "Will the ports on the switch in the backplane forward LAN traffic
         to each other or will they be separated and only forward traffic
         to/from the modulator/repeater."
    ::= { pt3080Comms  98 }

pt3080CommsBroadcastStormProtection OBJECT-TYPE
    SYNTAX      INTEGER { off(0), on(1) }
    MAX-ACCESS  read-write
    STATUS      current
    DESCRIPTION
        "Enable/Disable broadcast (and multicast) storm Protection. This
         will limit the network ingress rate on physical Ethernet port
         0 and 1 to roughly 100mbit/s."
    ::= { pt3080Comms  94 }

pt3080CommsLocalPhysicalInterface OBJECT-TYPE
    SYNTAX      INTEGER { eth0(0), eth1(1), eth2(2), eth3(3), eth4(4) }
    MAX-ACCESS  read-write
    STATUS      current
    DESCRIPTION
        "The Physical Ethernet Interface of this (virtual) interface."
    ::= { pt3080Comms  80 }

pt3080CommsLocalDhcpMode OBJECT-TYPE
    SYNTAX      INTEGER { off(0), client(1) }
    MAX-ACCESS  read-write
    STATUS      current
    DESCRIPTION
        "Enable/Disable DHCP client on this interface."
    ::= { pt3080Comms  3 }

pt3080CommsLocalStaticIpAddr OBJECT-TYPE
    SYNTAX      IpAddress
    MAX-ACCESS  read-write
    STATUS      current
    DESCRIPTION
        "The static IP address for this interface. Will be used if DHCP
         is disabled or unavailable."
    ::= { pt3080Comms  1 }

pt3080CommsLocalStaticNetmask OBJECT-TYPE
    SYNTAX      IpAddress
    MAX-ACCESS  read-write
    STATUS      current
    DESCRIPTION
        "The static IP netmask for this interface. Will be used if DHCP
         is disabled or unavailable."
    ::= { pt3080Comms  2 }

pt3080CommsLocalIpMulticastAddr OBJECT-TYPE
    SYNTAX      IpAddress
    MAX-ACCESS  read-write
    STATUS      current
    DESCRIPTION
        "The IP Multicast address for this interface."
    ::= { pt3080Comms  100 }

pt3080CommsLocalIpMulticastSourceFilterMode OBJECT-TYPE
    SYNTAX      INTEGER { sfinclude(0), sfexclude(1) }
    MAX-ACCESS  read-write
    STATUS      current
    DESCRIPTION
        "Specifies whether the Multicast Source Filter IP Address list
         is: SFINCLUDE: ONLY receive multicast frames from the source
         addresses in the list. SFEXCLUDE: Receive all multicast frames
         EXCEPT from the source addresses in the list."
    ::= { pt3080Comms  190 }

pt3080CommsLocalIpMulticastSourceFilterAddress1 OBJECT-TYPE
    SYNTAX      IpAddress
    MAX-ACCESS  read-write
    STATUS      current
    DESCRIPTION
        "The IP Multicast Source Filter address no 1 for this interface."
    ::= { pt3080Comms  200 }

pt3080CommsLocalIpMulticastSourceFilterAddress2 OBJECT-TYPE
    SYNTAX      IpAddress
    MAX-ACCESS  read-write
    STATUS      current
    DESCRIPTION
        "The IP Multicast Source Filter address no 2 for this interface."
    ::= { pt3080Comms  201 }

pt3080CommsLocalIpMulticastSourceFilterAddress3 OBJECT-TYPE
    SYNTAX      IpAddress
    MAX-ACCESS  read-write
    STATUS      current
    DESCRIPTION
        "The IP Multicast Source Filter address no 3 for this interface."
    ::= { pt3080Comms  202 }

pt3080CommsLocalIpMulticastSourceFilterAddress4 OBJECT-TYPE
    SYNTAX      IpAddress
    MAX-ACCESS  read-write
    STATUS      current
    DESCRIPTION
        "The IP Multicast Source Filter address no 4 for this interface."
    ::= { pt3080Comms  203 }

pt3080CommsLocalIpMulticastSourceFilterAddress5 OBJECT-TYPE
    SYNTAX      IpAddress
    MAX-ACCESS  read-write
    STATUS      current
    DESCRIPTION
        "The IP Multicast Source Filter address no 5 for this interface."
    ::= { pt3080Comms  204 }

pt3080CommsLocalIpMulticastSourceFilterAddress6 OBJECT-TYPE
    SYNTAX      IpAddress
    MAX-ACCESS  read-write
    STATUS      current
    DESCRIPTION
        "The IP Multicast Source Filter address no 6 for this interface."
    ::= { pt3080Comms  205 }

pt3080CommsLocalVlanEnable OBJECT-TYPE
    SYNTAX      INTEGER { disable(0), enable(1) }
    MAX-ACCESS  read-write
    STATUS      current
    DESCRIPTION
        "Enable/Disable VLAN on this interface."
    ::= { pt3080Comms  101 }

pt3080CommsLocalVlanId OBJECT-TYPE
    SYNTAX      Integer32 ( 1 .. 4095 )
    MAX-ACCESS  read-write
    STATUS      current
    DESCRIPTION
        "VLAN ID to use on this interface, if VLAN is enabled. Please
         note that VLAN ID 4001 and 4002 are used for internal switching
         and thus cannot be used on any interface."
    ::= { pt3080Comms  102 }

pt3080CommsLocalServiceSNMP OBJECT-TYPE
    SYNTAX      INTEGER { disable(0), enable(1) }
    MAX-ACCESS  read-write
    STATUS      current
    DESCRIPTION
        "Enable/Disable SNMP service on this interface."
    ::= { pt3080Comms  103 }

pt3080CommsLocalServiceSCPI OBJECT-TYPE
    SYNTAX      INTEGER { disable(0), enable(1) }
    MAX-ACCESS  read-write
    STATUS      current
    DESCRIPTION
        "Enable/Disable SCPI service on this interface."
    ::= { pt3080Comms  104 }

pt3080CommsLocalServiceTSoIP OBJECT-TYPE
    SYNTAX      INTEGER { disable(0), enable(1) }
    MAX-ACCESS  read-write
    STATUS      current
    DESCRIPTION
        "Enable/Disable TSoIP service on this interface."
    ::= { pt3080Comms  105 }

pt3080CommsLocalServiceRIP OBJECT-TYPE
    SYNTAX      INTEGER { disable(0), enable(1) }
    MAX-ACCESS  read-write
    STATUS      current
    DESCRIPTION
        "Enable/Disable RIP service on this interface."
    ::= { pt3080Comms  106 }

pt3080CommsLocalCurrentIpAddr OBJECT-TYPE
    SYNTAX      IpAddress
    MAX-ACCESS  read-only
    STATUS      current
    DESCRIPTION
        "The current IP address for this interface."
    ::= { pt3080Comms  4 }

pt3080CommsLocalCurrentNetmask OBJECT-TYPE
    SYNTAX      IpAddress
    MAX-ACCESS  read-only
    STATUS      current
    DESCRIPTION
        "The current IP netmask for this interface."
    ::= { pt3080Comms  5 }

pt3080CommsRemoteEnable OBJECT-TYPE
    SYNTAX      INTEGER { disable(0), enable(1) }
    MAX-ACCESS  read-write
    STATUS      current
    DESCRIPTION
        "Enable/Disable this interface."
    ::= { pt3080Comms  117 }

pt3080CommsRemotePhysicalInterface OBJECT-TYPE
    SYNTAX      INTEGER { eth0(0), eth1(1), eth2(2), eth3(3), eth4(4) }
    MAX-ACCESS  read-write
    STATUS      current
    DESCRIPTION
        "The Physical Ethernet Interface of this (virtual) interface."
    ::= { pt3080Comms  81 }

pt3080CommsRemoteDhcpMode OBJECT-TYPE
    SYNTAX      INTEGER { off(0), client(1) }
    MAX-ACCESS  read-write
    STATUS      current
    DESCRIPTION
        "Enable/Disable DHCP client on this interface."
    ::= { pt3080Comms  73 }

pt3080CommsRemoteStaticIpAddr OBJECT-TYPE
    SYNTAX      IpAddress
    MAX-ACCESS  read-write
    STATUS      current
    DESCRIPTION
        "The static IP address for this interface. Will be used if DHCP
         is disabled or unavailable."
    ::= { pt3080Comms  7 }

pt3080CommsRemoteStaticNetmask OBJECT-TYPE
    SYNTAX      IpAddress
    MAX-ACCESS  read-write
    STATUS      current
    DESCRIPTION
        "The static IP netmask for this interface. Will be used if DHCP
         is disabled or unavailable."
    ::= { pt3080Comms  8 }

pt3080CommsRemoteIpMulticastAddr OBJECT-TYPE
    SYNTAX      IpAddress
    MAX-ACCESS  read-write
    STATUS      current
    DESCRIPTION
        "The IP Multicast address for this interface."
    ::= { pt3080Comms  110 }

pt3080CommsRemoteIpMulticastSourceFilterMode OBJECT-TYPE
    SYNTAX      INTEGER { sfinclude(0), sfexclude(1) }
    MAX-ACCESS  read-write
    STATUS      current
    DESCRIPTION
        "Specifies whether the Multicast Source Filter IP Address list
         is: SFINCLUDE: ONLY receive multicast frames from the source
         addresses in the list. SFEXCLUDE: Receive all multicast frames
         EXCEPT from the source addresses in the list."
    ::= { pt3080Comms  191 }

pt3080CommsRemoteIpMulticastSourceFilterAddress1 OBJECT-TYPE
    SYNTAX      IpAddress
    MAX-ACCESS  read-write
    STATUS      current
    DESCRIPTION
        "The IP Multicast Source Filter address no 1 for this interface."
    ::= { pt3080Comms  220 }

pt3080CommsRemoteIpMulticastSourceFilterAddress2 OBJECT-TYPE
    SYNTAX      IpAddress
    MAX-ACCESS  read-write
    STATUS      current
    DESCRIPTION
        "The IP Multicast Source Filter address no 2 for this interface."
    ::= { pt3080Comms  221 }

pt3080CommsRemoteIpMulticastSourceFilterAddress3 OBJECT-TYPE
    SYNTAX      IpAddress
    MAX-ACCESS  read-write
    STATUS      current
    DESCRIPTION
        "The IP Multicast Source Filter address no 3 for this interface."
    ::= { pt3080Comms  222 }

pt3080CommsRemoteIpMulticastSourceFilterAddress4 OBJECT-TYPE
    SYNTAX      IpAddress
    MAX-ACCESS  read-write
    STATUS      current
    DESCRIPTION
        "The IP Multicast Source Filter address no 4 for this interface."
    ::= { pt3080Comms  223 }

pt3080CommsRemoteIpMulticastSourceFilterAddress5 OBJECT-TYPE
    SYNTAX      IpAddress
    MAX-ACCESS  read-write
    STATUS      current
    DESCRIPTION
        "The IP Multicast Source Filter address no 5 for this interface."
    ::= { pt3080Comms  224 }

pt3080CommsRemoteIpMulticastSourceFilterAddress6 OBJECT-TYPE
    SYNTAX      IpAddress
    MAX-ACCESS  read-write
    STATUS      current
    DESCRIPTION
        "The IP Multicast Source Filter address no 6 for this interface."
    ::= { pt3080Comms  225 }

pt3080CommsRemoteVlanEnable OBJECT-TYPE
    SYNTAX      INTEGER { disable(0), enable(1) }
    MAX-ACCESS  read-write
    STATUS      current
    DESCRIPTION
        "Enable/Disable VLAN on this interface."
    ::= { pt3080Comms  111 }

pt3080CommsRemoteVlanId OBJECT-TYPE
    SYNTAX      Integer32 ( 1 .. 4095 )
    MAX-ACCESS  read-write
    STATUS      current
    DESCRIPTION
        "VLAN ID to use on this interface, if VLAN is enabled. Please
         note that VLAN ID 4001 and 4002 are used for internal switching
         and thus cannot be used on any interface."
    ::= { pt3080Comms  112 }

pt3080CommsRemoteServiceSNMP OBJECT-TYPE
    SYNTAX      INTEGER { disable(0), enable(1) }
    MAX-ACCESS  read-write
    STATUS      current
    DESCRIPTION
        "Enable/Disable SNMP service on this interface."
    ::= { pt3080Comms  113 }

pt3080CommsRemoteServiceSCPI OBJECT-TYPE
    SYNTAX      INTEGER { disable(0), enable(1) }
    MAX-ACCESS  read-write
    STATUS      current
    DESCRIPTION
        "Enable/Disable SCPI service on this interface."
    ::= { pt3080Comms  114 }

pt3080CommsRemoteServiceTSoIP OBJECT-TYPE
    SYNTAX      INTEGER { disable(0), enable(1) }
    MAX-ACCESS  read-write
    STATUS      current
    DESCRIPTION
        "Enable/Disable TSoIP service on this interface."
    ::= { pt3080Comms  115 }

pt3080CommsRemoteServiceWeb OBJECT-TYPE
    SYNTAX      INTEGER { disable(0), enable(1) }
    MAX-ACCESS  read-write
    STATUS      current
    DESCRIPTION
        "Enable/Disable WEB (http) service on this interface."
    ::= { pt3080Comms  116 }

pt3080CommsRemoteServiceRIP OBJECT-TYPE
    SYNTAX      INTEGER { disable(0), enable(1) }
    MAX-ACCESS  read-write
    STATUS      current
    DESCRIPTION
        "Enable/Disable RIP service on this interface."
    ::= { pt3080Comms  118 }

pt3080CommsRemoteCurrentIpAddr OBJECT-TYPE
    SYNTAX      IpAddress
    MAX-ACCESS  read-only
    STATUS      current
    DESCRIPTION
        "The current IP address for this interface."
    ::= { pt3080Comms  10 }

pt3080CommsRemoteCurrentNetmask OBJECT-TYPE
    SYNTAX      IpAddress
    MAX-ACCESS  read-only
    STATUS      current
    DESCRIPTION
        "The current IP netmask for this interface."
    ::= { pt3080Comms  11 }

pt3080CommsGbeAdminEnable OBJECT-TYPE
    SYNTAX      INTEGER { disable(0), enable(1) }
    MAX-ACCESS  read-write
    STATUS      current
    DESCRIPTION
        "Enable/Disable this interface."
    ::= { pt3080Comms  127 }

pt3080CommsGbeAdminPhysicalInterface OBJECT-TYPE
    SYNTAX      INTEGER { eth0(0), eth1(1), eth2(2), eth3(3), eth4(4) }
    MAX-ACCESS  read-write
    STATUS      current
    DESCRIPTION
        "The Physical Ethernet Interface of this (virtual) interface."
    ::= { pt3080Comms  82 }

pt3080CommsGbeAdminDhcpMode OBJECT-TYPE
    SYNTAX      INTEGER { off(0), client(1) }
    MAX-ACCESS  read-write
    STATUS      current
    DESCRIPTION
        "Enable/Disable DHCP client on this interface."
    ::= { pt3080Comms  74 }

pt3080CommsGbeAdminStaticIpAddr OBJECT-TYPE
    SYNTAX      IpAddress
    MAX-ACCESS  read-write
    STATUS      current
    DESCRIPTION
        "The static IP address for this interface. Will be used if DHCP
         is disabled or unavailable."
    ::= { pt3080Comms  13 }

pt3080CommsGbeAdminStaticNetmask OBJECT-TYPE
    SYNTAX      IpAddress
    MAX-ACCESS  read-write
    STATUS      current
    DESCRIPTION
        "The static IP netmask for this interface. Will be used if DHCP
         is disabled or unavailable."
    ::= { pt3080Comms  14 }

pt3080CommsGbeAdminIpMulticastAddr OBJECT-TYPE
    SYNTAX      IpAddress
    MAX-ACCESS  read-write
    STATUS      current
    DESCRIPTION
        "The IP Multicast address for this interface."
    ::= { pt3080Comms  120 }

pt3080CommsGbeAdminIpMulticastSourceFilterMode OBJECT-TYPE
    SYNTAX      INTEGER { sfinclude(0), sfexclude(1) }
    MAX-ACCESS  read-write
    STATUS      current
    DESCRIPTION
        "Specifies whether the Multicast Source Filter IP Address list
         is: SFINCLUDE: ONLY receive multicast frames from the source
         addresses in the list. SFEXCLUDE: Receive all multicast frames
         EXCEPT from the source addresses in the list."
    ::= { pt3080Comms  192 }

pt3080CommsGbeAdminIpMulticastSourceFilterAddress1 OBJECT-TYPE
    SYNTAX      IpAddress
    MAX-ACCESS  read-write
    STATUS      current
    DESCRIPTION
        "The IP Multicast Source Filter address no 1 for this interface."
    ::= { pt3080Comms  230 }

pt3080CommsGbeAdminIpMulticastSourceFilterAddress2 OBJECT-TYPE
    SYNTAX      IpAddress
    MAX-ACCESS  read-write
    STATUS      current
    DESCRIPTION
        "The IP Multicast Source Filter address no 2 for this interface."
    ::= { pt3080Comms  231 }

pt3080CommsGbeAdminIpMulticastSourceFilterAddress3 OBJECT-TYPE
    SYNTAX      IpAddress
    MAX-ACCESS  read-write
    STATUS      current
    DESCRIPTION
        "The IP Multicast Source Filter address no 3 for this interface."
    ::= { pt3080Comms  232 }

pt3080CommsGbeAdminIpMulticastSourceFilterAddress4 OBJECT-TYPE
    SYNTAX      IpAddress
    MAX-ACCESS  read-write
    STATUS      current
    DESCRIPTION
        "The IP Multicast Source Filter address no 4 for this interface."
    ::= { pt3080Comms  233 }

pt3080CommsGbeAdminIpMulticastSourceFilterAddress5 OBJECT-TYPE
    SYNTAX      IpAddress
    MAX-ACCESS  read-write
    STATUS      current
    DESCRIPTION
        "The IP Multicast Source Filter address no 5 for this interface."
    ::= { pt3080Comms  234 }

pt3080CommsGbeAdminIpMulticastSourceFilterAddress6 OBJECT-TYPE
    SYNTAX      IpAddress
    MAX-ACCESS  read-write
    STATUS      current
    DESCRIPTION
        "The IP Multicast Source Filter address no 6 for this interface."
    ::= { pt3080Comms  235 }

pt3080CommsGbeAdminVlanEnable OBJECT-TYPE
    SYNTAX      INTEGER { disable(0), enable(1) }
    MAX-ACCESS  read-write
    STATUS      current
    DESCRIPTION
        "Enable/Disable VLAN on this interface."
    ::= { pt3080Comms  121 }

pt3080CommsGbeAdminVlanId OBJECT-TYPE
    SYNTAX      Integer32 ( 1 .. 4095 )
    MAX-ACCESS  read-write
    STATUS      current
    DESCRIPTION
        "VLAN ID to use on this interface, if VLAN is enabled. Please
         note that VLAN ID 4001 and 4002 are used for internal switching
         and thus cannot be used on any interface."
    ::= { pt3080Comms  122 }

pt3080CommsGbeAdminServiceSNMP OBJECT-TYPE
    SYNTAX      INTEGER { disable(0), enable(1) }
    MAX-ACCESS  read-write
    STATUS      current
    DESCRIPTION
        "Enable/Disable SNMP service on this interface."
    ::= { pt3080Comms  123 }

pt3080CommsGbeAdminServiceSCPI OBJECT-TYPE
    SYNTAX      INTEGER { disable(0), enable(1) }
    MAX-ACCESS  read-write
    STATUS      current
    DESCRIPTION
        "Enable/Disable SCPI service on this interface."
    ::= { pt3080Comms  124 }

pt3080CommsGbeAdminServiceTSoIP OBJECT-TYPE
    SYNTAX      INTEGER { disable(0), enable(1) }
    MAX-ACCESS  read-write
    STATUS      current
    DESCRIPTION
        "Enable/Disable TSoIP service on this interface."
    ::= { pt3080Comms  125 }

pt3080CommsGbeAdminServiceWeb OBJECT-TYPE
    SYNTAX      INTEGER { disable(0), enable(1) }
    MAX-ACCESS  read-write
    STATUS      current
    DESCRIPTION
        "Enable/Disable Web (http) service on this interface."
    ::= { pt3080Comms  126 }

pt3080CommsGbeAdminServiceRIP OBJECT-TYPE
    SYNTAX      INTEGER { disable(0), enable(1) }
    MAX-ACCESS  read-write
    STATUS      current
    DESCRIPTION
        "Enable/Disable RIP service on this interface."
    ::= { pt3080Comms  128 }

pt3080CommsGbeAdminCurrentIpAddr OBJECT-TYPE
    SYNTAX      IpAddress
    MAX-ACCESS  read-only
    STATUS      current
    DESCRIPTION
        "The current IP address for this interface."
    ::= { pt3080Comms  16 }

pt3080CommsGbeAdminCurrentNetmask OBJECT-TYPE
    SYNTAX      IpAddress
    MAX-ACCESS  read-only
    STATUS      current
    DESCRIPTION
        "The current IP netmask for this interface."
    ::= { pt3080Comms  17 }

pt3080CommsBackupEnable OBJECT-TYPE
    SYNTAX      INTEGER { disable(0), enable(1) }
    MAX-ACCESS  read-write
    STATUS      current
    DESCRIPTION
        "Enable/Disable this interface."
    ::= { pt3080Comms  150 }

pt3080CommsBackupPhysicalInterface OBJECT-TYPE
    SYNTAX      INTEGER { eth0(0), eth1(1), eth2(2), eth3(3), eth4(4) }
    MAX-ACCESS  read-write
    STATUS      current
    DESCRIPTION
        "The Physical Ethernet Interface of this (virtual) interface."
    ::= { pt3080Comms  151 }

pt3080CommsBackupDhcpMode OBJECT-TYPE
    SYNTAX      INTEGER { off(0), client(1) }
    MAX-ACCESS  read-write
    STATUS      current
    DESCRIPTION
        "Enable/Disable DHCP client on this interface."
    ::= { pt3080Comms  75 }

pt3080CommsBackupStaticIpAddr OBJECT-TYPE
    SYNTAX      IpAddress
    MAX-ACCESS  read-write
    STATUS      current
    DESCRIPTION
        "The static IP address for this interface. Will be used if DHCP
         is disabled or unavailable."
    ::= { pt3080Comms  152 }

pt3080CommsBackupStaticNetmask OBJECT-TYPE
    SYNTAX      IpAddress
    MAX-ACCESS  read-write
    STATUS      current
    DESCRIPTION
        "The static IP netmask for this interface. Will be used if DHCP
         is disabled or unavailable."
    ::= { pt3080Comms  153 }

pt3080CommsBackupIpMulticastAddr OBJECT-TYPE
    SYNTAX      IpAddress
    MAX-ACCESS  read-write
    STATUS      current
    DESCRIPTION
        "The IP Multicast address for this interface."
    ::= { pt3080Comms  154 }

pt3080CommsBackupIpMulticastSourceFilterMode OBJECT-TYPE
    SYNTAX      INTEGER { sfinclude(0), sfexclude(1) }
    MAX-ACCESS  read-write
    STATUS      current
    DESCRIPTION
        "Specifies whether the Multicast Source Filter IP Address list
         is: SFINCLUDE: ONLY receive multicast frames from the source
         addresses in the list. SFEXCLUDE: Receive all multicast frames
         EXCEPT from the source addresses in the list."
    ::= { pt3080Comms  193 }

pt3080CommsBackupIpMulticastSourceFilterAddress1 OBJECT-TYPE
    SYNTAX      IpAddress
    MAX-ACCESS  read-write
    STATUS      current
    DESCRIPTION
        "The IP Multicast Source Filter address no 1 for this interface."
    ::= { pt3080Comms  170 }

pt3080CommsBackupIpMulticastSourceFilterAddress2 OBJECT-TYPE
    SYNTAX      IpAddress
    MAX-ACCESS  read-write
    STATUS      current
    DESCRIPTION
        "The IP Multicast Source Filter address no 2 for this interface."
    ::= { pt3080Comms  171 }

pt3080CommsBackupIpMulticastSourceFilterAddress3 OBJECT-TYPE
    SYNTAX      IpAddress
    MAX-ACCESS  read-write
    STATUS      current
    DESCRIPTION
        "The IP Multicast Source Filter address no 3 for this interface."
    ::= { pt3080Comms  172 }

pt3080CommsBackupIpMulticastSourceFilterAddress4 OBJECT-TYPE
    SYNTAX      IpAddress
    MAX-ACCESS  read-write
    STATUS      current
    DESCRIPTION
        "The IP Multicast Source Filter address no 4 for this interface."
    ::= { pt3080Comms  173 }

pt3080CommsBackupIpMulticastSourceFilterAddress5 OBJECT-TYPE
    SYNTAX      IpAddress
    MAX-ACCESS  read-write
    STATUS      current
    DESCRIPTION
        "The IP Multicast Source Filter address no 5 for this interface."
    ::= { pt3080Comms  174 }

pt3080CommsBackupIpMulticastSourceFilterAddress6 OBJECT-TYPE
    SYNTAX      IpAddress
    MAX-ACCESS  read-write
    STATUS      current
    DESCRIPTION
        "The IP Multicast Source Filter address no 6 for this interface."
    ::= { pt3080Comms  175 }

pt3080CommsBackupVlanEnable OBJECT-TYPE
    SYNTAX      INTEGER { disable(0), enable(1) }
    MAX-ACCESS  read-write
    STATUS      current
    DESCRIPTION
        "Enable/Disable VLAN on this interface."
    ::= { pt3080Comms  155 }

pt3080CommsBackupVlanId OBJECT-TYPE
    SYNTAX      Integer32 ( 1 .. 4095 )
    MAX-ACCESS  read-write
    STATUS      current
    DESCRIPTION
        "VLAN ID to use on this interface, if VLAN is enabled. Please
         note that VLAN ID 4001 and 4002 are used for internal switching
         and thus cannot be used on any interface."
    ::= { pt3080Comms  156 }

pt3080CommsBackupServiceSNMP OBJECT-TYPE
    SYNTAX      INTEGER { disable(0), enable(1) }
    MAX-ACCESS  read-write
    STATUS      current
    DESCRIPTION
        "Enable/Disable SNMP service on this interface."
    ::= { pt3080Comms  157 }

pt3080CommsBackupServiceSCPI OBJECT-TYPE
    SYNTAX      INTEGER { disable(0), enable(1) }
    MAX-ACCESS  read-write
    STATUS      current
    DESCRIPTION
        "Enable/Disable SCPI service on this interface."
    ::= { pt3080Comms  158 }

pt3080CommsBackupServiceTSoIP OBJECT-TYPE
    SYNTAX      INTEGER { disable(0), enable(1) }
    MAX-ACCESS  read-write
    STATUS      current
    DESCRIPTION
        "Enable/Disable TSoIP service on this interface."
    ::= { pt3080Comms  159 }

pt3080CommsBackupServiceWeb OBJECT-TYPE
    SYNTAX      INTEGER { disable(0), enable(1) }
    MAX-ACCESS  read-write
    STATUS      current
    DESCRIPTION
        "Enable/Disable Web (http) service on this interface."
    ::= { pt3080Comms  160 }

pt3080CommsBackupServiceRIP OBJECT-TYPE
    SYNTAX      INTEGER { disable(0), enable(1) }
    MAX-ACCESS  read-write
    STATUS      current
    DESCRIPTION
        "Enable/Disable RIP service on this interface."
    ::= { pt3080Comms  161 }

pt3080CommsBackupCurrentIpAddr OBJECT-TYPE
    SYNTAX      IpAddress
    MAX-ACCESS  read-only
    STATUS      current
    DESCRIPTION
        "The current IP address for this interface."
    ::= { pt3080Comms  162 }

pt3080CommsBackupCurrentNetmask OBJECT-TYPE
    SYNTAX      IpAddress
    MAX-ACCESS  read-only
    STATUS      current
    DESCRIPTION
        "The current IP netmask for this interface."
    ::= { pt3080Comms  163 }

pt3080CommsPortEnable OBJECT-TYPE
    SYNTAX      INTEGER { disable(0), enable(1) }
    MAX-ACCESS  read-write
    STATUS      current
    DESCRIPTION
        "Enable/Disable this interface."
    ::= { pt3080Comms  2500 }

pt3080CommsPortPhysicalInterface OBJECT-TYPE
    SYNTAX      INTEGER { eth0(0), eth1(1), eth2(2), eth3(3), eth4(4) }
    MAX-ACCESS  read-write
    STATUS      current
    DESCRIPTION
        "The Physical Ethernet Interface of this (virtual) interface."
    ::= { pt3080Comms  2151 }

pt3080CommsPortDhcpMode OBJECT-TYPE
    SYNTAX      INTEGER { off(0), client(1) }
    MAX-ACCESS  read-write
    STATUS      current
    DESCRIPTION
        "Enable/Disable DHCP client on this interface."
    ::= { pt3080Comms  2075 }

pt3080CommsPortStaticIpAddr OBJECT-TYPE
    SYNTAX      IpAddress
    MAX-ACCESS  read-write
    STATUS      current
    DESCRIPTION
        "The static IP address for this interface. Will be used if DHCP
         is disabled or unavailable."
    ::= { pt3080Comms  2152 }

pt3080CommsPortStaticNetmask OBJECT-TYPE
    SYNTAX      IpAddress
    MAX-ACCESS  read-write
    STATUS      current
    DESCRIPTION
        "The static IP netmask for this interface. Will be used if DHCP
         is disabled or unavailable."
    ::= { pt3080Comms  2153 }

pt3080CommsPortIpMulticastAddr OBJECT-TYPE
    SYNTAX      IpAddress
    MAX-ACCESS  read-write
    STATUS      current
    DESCRIPTION
        "The IP Multicast address for this interface."
    ::= { pt3080Comms  2154 }

pt3080CommsPortIpMulticastSourceFilterMode OBJECT-TYPE
    SYNTAX      INTEGER { sfinclude(0), sfexclude(1) }
    MAX-ACCESS  read-write
    STATUS      current
    DESCRIPTION
        "Specifies whether the Multicast Source Filter IP Address list
         is: SFINCLUDE: ONLY receive multicast frames from the source
         addresses in the list. SFEXCLUDE: Receive all multicast frames
         EXCEPT from the source addresses in the list."
    ::= { pt3080Comms  2193 }

pt3080CommsPortIpMulticastSourceFilterAddress1 OBJECT-TYPE
    SYNTAX      IpAddress
    MAX-ACCESS  read-write
    STATUS      current
    DESCRIPTION
        "The IP Multicast Source Filter address no 1 for this interface."
    ::= { pt3080Comms  2170 }

pt3080CommsPortIpMulticastSourceFilterAddress2 OBJECT-TYPE
    SYNTAX      IpAddress
    MAX-ACCESS  read-write
    STATUS      current
    DESCRIPTION
        "The IP Multicast Source Filter address no 2 for this interface."
    ::= { pt3080Comms  2171 }

pt3080CommsPortIpMulticastSourceFilterAddress3 OBJECT-TYPE
    SYNTAX      IpAddress
    MAX-ACCESS  read-write
    STATUS      current
    DESCRIPTION
        "The IP Multicast Source Filter address no 3 for this interface."
    ::= { pt3080Comms  2172 }

pt3080CommsPortIpMulticastSourceFilterAddress4 OBJECT-TYPE
    SYNTAX      IpAddress
    MAX-ACCESS  read-write
    STATUS      current
    DESCRIPTION
        "The IP Multicast Source Filter address no 4 for this interface."
    ::= { pt3080Comms  2173 }

pt3080CommsPortIpMulticastSourceFilterAddress5 OBJECT-TYPE
    SYNTAX      IpAddress
    MAX-ACCESS  read-write
    STATUS      current
    DESCRIPTION
        "The IP Multicast Source Filter address no 5 for this interface."
    ::= { pt3080Comms  2174 }

pt3080CommsPortIpMulticastSourceFilterAddress6 OBJECT-TYPE
    SYNTAX      IpAddress
    MAX-ACCESS  read-write
    STATUS      current
    DESCRIPTION
        "The IP Multicast Source Filter address no 6 for this interface."
    ::= { pt3080Comms  2175 }

pt3080CommsPortVlanEnable OBJECT-TYPE
    SYNTAX      INTEGER { disable(0), enable(1) }
    MAX-ACCESS  read-write
    STATUS      current
    DESCRIPTION
        "Enable/Disable VLAN on this interface."
    ::= { pt3080Comms  2155 }

pt3080CommsPortVlanId OBJECT-TYPE
    SYNTAX      Integer32 ( 1 .. 4095 )
    MAX-ACCESS  read-write
    STATUS      current
    DESCRIPTION
        "VLAN ID to use on this interface, if VLAN is enabled. Please
         note that VLAN ID 4001 and 4002 are used for internal switching
         and thus cannot be used on any interface."
    ::= { pt3080Comms  2156 }

pt3080CommsPortServiceSNMP OBJECT-TYPE
    SYNTAX      INTEGER { disable(0), enable(1) }
    MAX-ACCESS  read-write
    STATUS      current
    DESCRIPTION
        "Enable/Disable SNMP service on this interface."
    ::= { pt3080Comms  2157 }

pt3080CommsPortServiceSCPI OBJECT-TYPE
    SYNTAX      INTEGER { disable(0), enable(1) }
    MAX-ACCESS  read-write
    STATUS      current
    DESCRIPTION
        "Enable/Disable SCPI service on this interface."
    ::= { pt3080Comms  2158 }

pt3080CommsPortServiceTSoIP OBJECT-TYPE
    SYNTAX      INTEGER { disable(0), enable(1) }
    MAX-ACCESS  read-write
    STATUS      current
    DESCRIPTION
        "Enable/Disable TSoIP service on this interface."
    ::= { pt3080Comms  2159 }

pt3080CommsPortServiceWeb OBJECT-TYPE
    SYNTAX      INTEGER { disable(0), enable(1) }
    MAX-ACCESS  read-write
    STATUS      current
    DESCRIPTION
        "Enable/Disable Web (http) service on this interface."
    ::= { pt3080Comms  2160 }

pt3080CommsPortServiceRIP OBJECT-TYPE
    SYNTAX      INTEGER { disable(0), enable(1) }
    MAX-ACCESS  read-write
    STATUS      current
    DESCRIPTION
        "Enable/Disable RIP service on this interface."
    ::= { pt3080Comms  2161 }

pt3080CommsPortCurrentIpAddr OBJECT-TYPE
    SYNTAX      IpAddress
    MAX-ACCESS  read-only
    STATUS      current
    DESCRIPTION
        "The current IP address for this interface."
    ::= { pt3080Comms  2162 }

pt3080CommsPortCurrentNetmask OBJECT-TYPE
    SYNTAX      IpAddress
    MAX-ACCESS  read-only
    STATUS      current
    DESCRIPTION
        "The current IP netmask for this interface."
    ::= { pt3080Comms  2163 }

pt3080CommsSNMPServicePort OBJECT-TYPE
    SYNTAX      Integer32 ( 1 .. 65535 )
    MAX-ACCESS  read-write
    STATUS      current
    DESCRIPTION
        "The UDP port number used for SNMP Service."
    ::= { pt3080Comms  55 }

pt3080CommsSNMPReadOnlyCommunity OBJECT-TYPE
    SYNTAX      DisplayString
    MAX-ACCESS  read-write
    STATUS      current
    DESCRIPTION
        "The Read-only community string used to access the SNMP Service."
    ::= { pt3080Comms  56 }

pt3080CommsSNMPReadWriteCommunity OBJECT-TYPE
    SYNTAX      DisplayString
    MAX-ACCESS  read-write
    STATUS      current
    DESCRIPTION
        "The Read-Write community string used to access the SNMP Service."
    ::= { pt3080Comms  57 }

pt3080CommsSNMPTrapCommunity OBJECT-TYPE
    SYNTAX      DisplayString
    MAX-ACCESS  read-write
    STATUS      current
    DESCRIPTION
        "The Trap community string used when sending SNMP Traps."
    ::= { pt3080Comms  58 }

pt3080CommsSNMPTrapDestination OBJECT-TYPE
    SYNTAX      DisplayString
    MAX-ACCESS  read-write
    STATUS      current
    DESCRIPTION
        "The destination IP address for the SNMP traps."
    ::= { pt3080Comms  59 }

pt3080CommsSNMPTrapDestination2 OBJECT-TYPE
    SYNTAX      DisplayString
    MAX-ACCESS  read-write
    STATUS      current
    DESCRIPTION
        "The destination 2 IP address for the SNMP traps."
    ::= { pt3080Comms  419 }

pt3080CommsSNMPTrapDestination3 OBJECT-TYPE
    SYNTAX      DisplayString
    MAX-ACCESS  read-write
    STATUS      current
    DESCRIPTION
        "The destination 3 IP address for the SNMP traps."
    ::= { pt3080Comms  779 }

pt3080CommsSNMPTrapDestination4 OBJECT-TYPE
    SYNTAX      DisplayString
    MAX-ACCESS  read-write
    STATUS      current
    DESCRIPTION
        "The destination 4 IP address for the SNMP traps."
    ::= { pt3080Comms  1139 }

pt3080CommsSNMPTrapDestination5 OBJECT-TYPE
    SYNTAX      DisplayString
    MAX-ACCESS  read-write
    STATUS      current
    DESCRIPTION
        "The destination 5 IP address for the SNMP traps."
    ::= { pt3080Comms  1499 }

pt3080CommsSNMPTrapDestinationPort OBJECT-TYPE
    SYNTAX      Integer32 ( 1 .. 65535 )
    MAX-ACCESS  read-write
    STATUS      current
    DESCRIPTION
        "The UDP port number used for Trap destination ."
    ::= { pt3080Comms  60 }

pt3080CommsSNMPTrapDestinationPort2 OBJECT-TYPE
    SYNTAX      Integer32 ( 1 .. 65535 )
    MAX-ACCESS  read-write
    STATUS      current
    DESCRIPTION
        "The UDP port number used for Trap destination 2."
    ::= { pt3080Comms  420 }

pt3080CommsSNMPTrapDestinationPort3 OBJECT-TYPE
    SYNTAX      Integer32 ( 1 .. 65535 )
    MAX-ACCESS  read-write
    STATUS      current
    DESCRIPTION
        "The UDP port number used for Trap destination 3."
    ::= { pt3080Comms  780 }

pt3080CommsSNMPTrapDestinationPort4 OBJECT-TYPE
    SYNTAX      Integer32 ( 1 .. 65535 )
    MAX-ACCESS  read-write
    STATUS      current
    DESCRIPTION
        "The UDP port number used for Trap destination 4."
    ::= { pt3080Comms  1140 }

pt3080CommsSNMPTrapDestinationPort5 OBJECT-TYPE
    SYNTAX      Integer32 ( 1 .. 65535 )
    MAX-ACCESS  read-write
    STATUS      current
    DESCRIPTION
        "The UDP port number used for Trap destination 5."
    ::= { pt3080Comms  1500 }

pt3080CommsStaticGateway OBJECT-TYPE
    SYNTAX      IpAddress
    MAX-ACCESS  read-write
    STATUS      current
    DESCRIPTION
        "The static IP address for the default router (gateway). Will
         be used unless DHCP is enabled and the DHCP server is configured
         to include a default router address."
    ::= { pt3080Comms  29 }

pt3080CommsCurrentGateway OBJECT-TYPE
    SYNTAX      IpAddress
    MAX-ACCESS  read-only
    STATUS      current
    DESCRIPTION
        "The Current IP address for the default router (gateway)."
    ::= { pt3080Comms  30 }

pt3080CommsStaticHostname OBJECT-TYPE
    SYNTAX      DisplayString
    MAX-ACCESS  read-write
    STATUS      current
    DESCRIPTION
        "The static hostname for the device. Will be used if DHCP is 
        disabled or unavailable."
    ::= { pt3080Comms  27 }

pt3080CommsCurrentHostname OBJECT-TYPE
    SYNTAX      DisplayString
    MAX-ACCESS  read-only
    STATUS      current
    DESCRIPTION
        "The static hostname for the device. Will be used if DHCP is 
        disabled or unavailable."
    ::= { pt3080Comms  28 }

pt3080CommsStaticDNSDomain OBJECT-TYPE
    SYNTAX      DisplayString
    MAX-ACCESS  read-write
    STATUS      current
    DESCRIPTION
        "The static DNS domain name for the device. Will be used if DHCP
         is disabled or unavailable."
    ::= { pt3080Comms  25 }

pt3080CommsCurrentDNSDomain OBJECT-TYPE
    SYNTAX      DisplayString
    MAX-ACCESS  read-only
    STATUS      current
    DESCRIPTION
        "The current DNS domain name for the device."
    ::= { pt3080Comms  26 }

pt3080CommsStaticDNS1ServerAddress OBJECT-TYPE
    SYNTAX      IpAddress
    MAX-ACCESS  read-write
    STATUS      current
    DESCRIPTION
        "The IP address of DNS server 1."
    ::= { pt3080Comms  19 }

pt3080CommsStaticDNS2ServerAddress OBJECT-TYPE
    SYNTAX      IpAddress
    MAX-ACCESS  read-write
    STATUS      current
    DESCRIPTION
        "The IP address of DNS server 2."
    ::= { pt3080Comms  21 }

pt3080CommsStaticDNS3ServerAddress OBJECT-TYPE
    SYNTAX      IpAddress
    MAX-ACCESS  read-write
    STATUS      current
    DESCRIPTION
        "The IP address of DNS server 3."
    ::= { pt3080Comms  23 }

pt3080CommsCurrentDNS1ServerAddress OBJECT-TYPE
    SYNTAX      IpAddress
    MAX-ACCESS  read-only
    STATUS      current
    DESCRIPTION
        "The Current IP address of DNS server 1."
    ::= { pt3080Comms  20 }

pt3080CommsCurrentDNS2ServerAddress OBJECT-TYPE
    SYNTAX      IpAddress
    MAX-ACCESS  read-only
    STATUS      current
    DESCRIPTION
        "The Current IP address of DNS server 2."
    ::= { pt3080Comms  22 }

pt3080CommsCurrentDNS3ServerAddress OBJECT-TYPE
    SYNTAX      IpAddress
    MAX-ACCESS  read-only
    STATUS      current
    DESCRIPTION
        "The Current IP address of DNS server 3."
    ::= { pt3080Comms  24 }

pt3080CommsStaticNtpServerAddress OBJECT-TYPE
    SYNTAX      DisplayString
    MAX-ACCESS  read-write
    STATUS      current
    DESCRIPTION
        "The DNS name or IP address of the NTP server."
    ::= { pt3080Comms  31 }

pt3080CommsCurrentNtpServerAddress OBJECT-TYPE
    SYNTAX      DisplayString
    MAX-ACCESS  read-only
    STATUS      current
    DESCRIPTION
        "The Current IP address of the NTP server."
    ::= { pt3080Comms  32 }

pt3080CommsEmailServerAddress OBJECT-TYPE
    SYNTAX      DisplayString
    MAX-ACCESS  read-write
    STATUS      current
    DESCRIPTION
        "The IP address of the Email (SMTP) server."
    ::= { pt3080Comms  33 }

pt3080CommsWebServicePort OBJECT-TYPE
    SYNTAX      Integer32 ( 1 .. 65535 )
    MAX-ACCESS  read-write
    STATUS      current
    DESCRIPTION
        "The TCP port number used for Web Service."
    ::= { pt3080Comms  35 }

pt3080CommsSCPIServicePort OBJECT-TYPE
    SYNTAX      Integer32 ( 1 .. 65535 )
    MAX-ACCESS  read-write
    STATUS      current
    DESCRIPTION
        "The TCP port number used for SCPI Service."
    ::= { pt3080Comms  36 }

pt3080CommsSCPIServerBaudrate OBJECT-TYPE
    SYNTAX      INTEGER { r2400(0), r4800(1), r9600(2), r19200(3), r38400(4), r57600(5), r115200(6) }
    MAX-ACCESS  read-write
    STATUS      current
    DESCRIPTION
        "The Baudrate used for SCPI Service on serial port."
    ::= { pt3080Comms  37 }

pt3080CommsSCPIUartInterface OBJECT-TYPE
    SYNTAX      INTEGER { rs232(0), rs485(1), rs485hd(2) }
    MAX-ACCESS  read-write
    STATUS      current
    DESCRIPTION
        "The Interface used for SCPI Service on serial port."
    ::= { pt3080Comms  39 }

pt3080CommsRipPort OBJECT-TYPE
    SYNTAX      Integer32 ( 1 .. 65535 )
    MAX-ACCESS  read-write
    STATUS      current
    DESCRIPTION
        "The UDP port number used for RIP Service."
    ::= { pt3080Comms  38 }

pt3080CommsIGMPVersion OBJECT-TYPE
    SYNTAX      INTEGER { auto(0), v1(1), v2(2), v3(3) }
    MAX-ACCESS  read-write
    STATUS      current
    DESCRIPTION
        "Select which IGMP Version to use."
    ::= { pt3080Comms  99 }

pt3080CommsIGMPQueryRobustnessCount OBJECT-TYPE
    SYNTAX      Integer32 ( 2 .. 16 )
    MAX-ACCESS  read-write
    STATUS      current
    DESCRIPTION
        "The Number of Query Replies sent. The higher a number, the more
         robust IGMP setup is. At the cost of traffic on the network.
         Note: Changing this parameter doesnt take effect on a network
         interface until it has (re-)enabled."
    ::= { pt3080Comms  97 }

pt3080CommsIGMPv3UnsolicitedReportInterval OBJECT-TYPE
    SYNTAX      Integer32 ( 1 .. 60000 )
    UNITS       "1 ms"
    MAX-ACCESS  read-write
    STATUS      current
    DESCRIPTION
        "The time interval between unsolicited IGMPv3 reports being sent.
         See RFC3376. The number of such report being sent is controlled
         by the Query Robustness Count."
    ::= { pt3080Comms  96 }

pt3080CommsIGMPv2UnsolicitedReportInterval OBJECT-TYPE
    SYNTAX      Integer32 ( 1 .. 60000 )
    UNITS       "1 ms"
    MAX-ACCESS  read-write
    STATUS      current
    DESCRIPTION
        "The time interval between unsolicited IGMPv2/v1 reports being
         sent. See RFC2236. The number of such report being sent is 
        controlled by the Query Robustness Count."
    ::= { pt3080Comms  95 }

pt3080CommsAccessAllowed OBJECT-TYPE
    SYNTAX      INTEGER { remote(0), local-disable-set(1) }
    MAX-ACCESS  read-write
    STATUS      current
    DESCRIPTION
        "Current access mode allowed: Remote: SNMP via Ethernet, Local:
         Frontpanel"
    ::= { pt3080Comms  48 }

pt3080CommsAccessAllowedTimeout OBJECT-TYPE
    SYNTAX      Integer32 ( 1 .. 1440 )
    UNITS       "1 min"
    MAX-ACCESS  read-write
    STATUS      current
    DESCRIPTION
        "Timeout (in minutes) before local mode reverts to remote mode."
    ::= { pt3080Comms  49 }

pt3080CommsAccessAllowedTimeLeft OBJECT-TYPE
    SYNTAX      Integer32
    UNITS       "1 secs"
    MAX-ACCESS  read-only
    STATUS      current
    DESCRIPTION
        "Current time left (in seconds) before local mode reverts to 
        remote mode."
    ::= { pt3080Comms  50 }


pt3080CommsAccessPasswordObserver OBJECT-TYPE
    SYNTAX                      DisplayString
    MAX-ACCESS                  read-write
    STATUS                      current
    DESCRIPTION
        "The access password for Observer level access. Will always read as empty."
    ::= { pt3080Comms 51 }

pt3080CommsAccessPasswordOperator OBJECT-TYPE
    SYNTAX                      DisplayString
    MAX-ACCESS                  read-write
    STATUS                      current
    DESCRIPTION
        "The access password for Operator level access. Will always read as empty."
    ::= { pt3080Comms 52 }

pt3080CommsAccessPasswordAdministrator OBJECT-TYPE
    SYNTAX                      DisplayString
    MAX-ACCESS                  read-write
    STATUS                      current
    DESCRIPTION
        "The access password for Administrator level access. Will always read as empty."
    ::= { pt3080Comms 53 }


pt3080CommsStaticRouteTable     OBJECT-TYPE
    SYNTAX                      SEQUENCE OF Pt3080CommsStaticRouteEntry
    MAX-ACCESS                  not-accessible
    STATUS                      current
    DESCRIPTION
        "This table contains the static routing table entries"
    ::= { pt3080Comms 300 }

pt3080CommsStaticRouteEntry     OBJECT-TYPE
    SYNTAX                      Pt3080CommsStaticRouteEntry
    MAX-ACCESS                  not-accessible
    STATUS                      current
    DESCRIPTION
        "An entry for the static network routing table"
    INDEX                       { pt3080CommsStaticRouteNO }
    ::= { pt3080CommsStaticRouteTable 1 }

Pt3080CommsStaticRouteEntry ::= SEQUENCE {
    pt3080CommsStaticRouteNO           Integer32,
    pt3080CommsStaticRouteType         INTEGER,
    pt3080CommsStaticRoutePrefix       IpAddress,
    pt3080CommsStaticRoutePrefixSize   Integer32,
    pt3080CommsStaticRouteTarget       IpAddress,
    pt3080CommsStaticRoutePhysicalInterface INTEGER
}

pt3080CommsStaticRouteNO        OBJECT-TYPE
    SYNTAX                      Integer32 ( 1 .. 16 )
    MAX-ACCESS                  not-accessible
    STATUS                      current
    DESCRIPTION
        "Unique ID for this static route entry"
    ::= { pt3080CommsStaticRouteEntry 1 }

pt3080CommsStaticRouteType      OBJECT-TYPE
    SYNTAX                      INTEGER { unused(0), normal(1), physicalif(2), recursive(3), drop(4) }
    MAX-ACCESS                  read-write
    STATUS                      current
    DESCRIPTION
        "Type of a Route table entry."
    ::= { pt3080CommsStaticRouteEntry 2 }

pt3080CommsStaticRoutePrefix    OBJECT-TYPE
    SYNTAX                      IpAddress
    MAX-ACCESS                  read-write
    STATUS                      current
    DESCRIPTION
        "The IP address part of prefix for a route table entry.
         If the address is 0.0.0.0, the entry will not be used."
    ::= { pt3080CommsStaticRouteEntry 3 }

pt3080CommsStaticRoutePrefixSize OBJECT-TYPE
    SYNTAX                      Integer32 ( 0 .. 32 )
    MAX-ACCESS                  read-write
    STATUS                      current
    DESCRIPTION
        "The number of bits in the network part of the prefix for route table entry $.
         If the number is 0 (zero), the entry will not be used."
    ::= { pt3080CommsStaticRouteEntry 4 }

pt3080CommsStaticRouteTarget OBJECT-TYPE
    SYNTAX                      IpAddress
    MAX-ACCESS                  read-write
    STATUS                      current
    DESCRIPTION
        "The target IP address for a route table entry.
         Only used if pt3080CommsStaticRouteType is normal(1) or recursive(3).
         If the target address is 0.0.0.0, the entry will not be used."
    ::= { pt3080CommsStaticRouteEntry 5 }

pt3080CommsStaticRoutePhysicalInterface OBJECT-TYPE
    SYNTAX                      INTEGER { eth0(0), eth1(1), eth2(2), eth3(3), eth4(4) }
    MAX-ACCESS                  read-write
    STATUS                      current
    DESCRIPTION
        "The Physical Ethernet Interface to use for a Route table entry.
         Only used when pt3080CommsStaticRouteType is physicalif(2)."
    ::= { pt3080CommsStaticRouteEntry 6 }




--
-- pt3080 Demodulator sub-tree
--
pt3080DemodulatorFollowMode OBJECT-TYPE
    SYNTAX      INTEGER { disable(0), enable(1) }
    MAX-ACCESS  read-write
    STATUS      current
    DESCRIPTION
        "Controls the Demodulators follow mode."
    ::= { pt3080Demodulator  1 }

pt3080Demodulator1Available OBJECT-TYPE
    SYNTAX      INTEGER { no(0), yes(1) }
    MAX-ACCESS  read-only
    STATUS      current
    DESCRIPTION
        "Status on the availability of Demodulator 1"
    ::= { pt3080Demodulator  2 }

pt3080Demodulator2Available OBJECT-TYPE
    SYNTAX      INTEGER { no(0), yes(1) }
    MAX-ACCESS  read-only
    STATUS      current
    DESCRIPTION
        "Status on the availability of Demodulator 2"
    ::= { pt3080Demodulator  29 }

pt3080Demodulator1FWVersion OBJECT-TYPE
    SYNTAX      DisplayString
    MAX-ACCESS  read-only
    STATUS      current
    DESCRIPTION
        "Demodulator 1 firmware version string"
    ::= { pt3080Demodulator  3 }

pt3080Demodulator2FWVersion OBJECT-TYPE
    SYNTAX      DisplayString
    MAX-ACCESS  read-only
    STATUS      current
    DESCRIPTION
        "Demodulator 2 firmware version string"
    ::= { pt3080Demodulator  30 }

pt3080Demodulator1OutputTS OBJECT-TYPE
    SYNTAX      INTEGER { hp(0), lp(1) }
    MAX-ACCESS  read-write
    STATUS      current
    DESCRIPTION
        "Controls which TS demodulator 1 shall output"
    ::= { pt3080Demodulator  4 }

pt3080Demodulator2OutputTS OBJECT-TYPE
    SYNTAX      INTEGER { hp(0), lp(1) }
    MAX-ACCESS  read-write
    STATUS      current
    DESCRIPTION
        "Controls which TS demodulator 2 shall output"
    ::= { pt3080Demodulator  31 }

pt3080Demodulator1MerLimit OBJECT-TYPE
    SYNTAX      Integer32 ( 10 .. 240 )
    UNITS       "0.1 dBm"
    MAX-ACCESS  read-write
    STATUS      current
    DESCRIPTION
        "Lower limit for MER Level"
    ::= { pt3080Demodulator  5 }

pt3080Demodulator2MerLimit OBJECT-TYPE
    SYNTAX      Integer32 ( 10 .. 240 )
    UNITS       "0.1 dBm"
    MAX-ACCESS  read-write
    STATUS      current
    DESCRIPTION
        "Lower limit for MER Level"
    ::= { pt3080Demodulator  32 }

pt3080Demodulator1PreVirterbiErrorRateLimit OBJECT-TYPE
    SYNTAX      Integer32 ( 1 .. 1000000 )
    MAX-ACCESS  read-write
    STATUS      current
    DESCRIPTION
        "Upper limit for Pre-Virterbi Bit Error Rate"
    ::= { pt3080Demodulator  6 }

pt3080Demodulator2PreVirterbiErrorRateLimit OBJECT-TYPE
    SYNTAX      Integer32 ( 1 .. 1000000 )
    MAX-ACCESS  read-write
    STATUS      current
    DESCRIPTION
        "Upper limit for Pre-Virterbi Bit Error Rate"
    ::= { pt3080Demodulator  33 }

pt3080Demodulator1PostVirterbiErrorRateLimit OBJECT-TYPE
    SYNTAX      Integer32 ( 1 .. 1000000 )
    MAX-ACCESS  read-write
    STATUS      current
    DESCRIPTION
        "Upper limit for Post-Virterbi Bit Error Rate"
    ::= { pt3080Demodulator  7 }

pt3080Demodulator2PostVirterbiErrorRateLimit OBJECT-TYPE
    SYNTAX      Integer32 ( 1 .. 1000000 )
    MAX-ACCESS  read-write
    STATUS      current
    DESCRIPTION
        "Upper limit for Post-Virterbi Bit Error Rate"
    ::= { pt3080Demodulator  34 }

pt3080Demodulator1FelStatus OBJECT-TYPE
    SYNTAX      INTEGER { locked(0), unlocked(1) }
    MAX-ACCESS  read-only
    STATUS      current
    DESCRIPTION
        "Received signal locked status on Demodulator 1"
    ::= { pt3080Demodulator  8 }

pt3080Demodulator2FelStatus OBJECT-TYPE
    SYNTAX      INTEGER { locked(0), unlocked(1) }
    MAX-ACCESS  read-only
    STATUS      current
    DESCRIPTION
        "Received signal locked status on Demodulator 2"
    ::= { pt3080Demodulator  35 }

pt3080Demodulator1UncorrectedPackets OBJECT-TYPE
    SYNTAX      Integer32
    MAX-ACCESS  read-only
    STATUS      current
    DESCRIPTION
        "Number of uncorrected packets received in Demodulator 1 since
         boot or since counter was last cleared."
    ::= { pt3080Demodulator  9 }

pt3080Demodulator2UncorrectedPackets OBJECT-TYPE
    SYNTAX      Integer32
    MAX-ACCESS  read-only
    STATUS      current
    DESCRIPTION
        "Number of uncorrected packets received in Demodulator 2 since
         boot or since counter was last cleared."
    ::= { pt3080Demodulator  36 }

pt3080Demodulator1Mer OBJECT-TYPE
    SYNTAX      Integer32
    UNITS       "0.1 dBm"
    MAX-ACCESS  read-only
    STATUS      current
    DESCRIPTION
        "Current MER level for Demodulator 1"
    ::= { pt3080Demodulator  11 }

pt3080Demodulator2Mer OBJECT-TYPE
    SYNTAX      Integer32
    UNITS       "0.1 dBm"
    MAX-ACCESS  read-only
    STATUS      current
    DESCRIPTION
        "Current MER level for Demodulator 2"
    ::= { pt3080Demodulator  38 }

pt3080Demodulator1PreVirterbiErrorRate OBJECT-TYPE
    SYNTAX      Integer32
    UNITS       "0.1 x1e-7"
    MAX-ACCESS  read-only
    STATUS      current
    DESCRIPTION
        "Current Pre-Virterbi Bit Error Rate for Demodulator 1"
    ::= { pt3080Demodulator  12 }

pt3080Demodulator2PreVirterbiErrorRate OBJECT-TYPE
    SYNTAX      Integer32
    UNITS       "0.1 x1e-7"
    MAX-ACCESS  read-only
    STATUS      current
    DESCRIPTION
        "Current Pre-Virterbi Bit Error Rate for Demodulator 2"
    ::= { pt3080Demodulator  39 }

pt3080Demodulator1PostVirterbiErrorRate OBJECT-TYPE
    SYNTAX      Integer32
    UNITS       "0.1 x1e-7"
    MAX-ACCESS  read-only
    STATUS      current
    DESCRIPTION
        "Current Post-Virterbi Bit Error Rate for Demodulator 1"
    ::= { pt3080Demodulator  13 }

pt3080Demodulator2PostVirterbiErrorRate OBJECT-TYPE
    SYNTAX      Integer32
    UNITS       "0.1 x1e-7"
    MAX-ACCESS  read-only
    STATUS      current
    DESCRIPTION
        "Current Post-Virterbi Bit Error Rate for Demodulator 2"
    ::= { pt3080Demodulator  40 }

pt3080Demodulator1ActualGuardInterval OBJECT-TYPE
    SYNTAX      INTEGER { g1-32(0), g1-16(1), g1-8(2), g1-4(3) }
    MAX-ACCESS  read-only
    STATUS      current
    DESCRIPTION
        "Guard Interval for the received signal on Demodulator 1"
    ::= { pt3080Demodulator  14 }

pt3080Demodulator2ActualGuardInterval OBJECT-TYPE
    SYNTAX      INTEGER { g1-32(0), g1-16(1), g1-8(2), g1-4(3) }
    MAX-ACCESS  read-only
    STATUS      current
    DESCRIPTION
        "Guard Interval for the received signal on Demodulator 2"
    ::= { pt3080Demodulator  41 }

pt3080Demodulator1Actualifft OBJECT-TYPE
    SYNTAX      INTEGER { f2k(0), f4k(1), f8k(2) }
    MAX-ACCESS  read-only
    STATUS      current
    DESCRIPTION
        "IFFT for the received signal on Demodulator 1"
    ::= { pt3080Demodulator  15 }

pt3080Demodulator2Actualifft OBJECT-TYPE
    SYNTAX      INTEGER { f2k(0), f4k(1), f8k(2) }
    MAX-ACCESS  read-only
    STATUS      current
    DESCRIPTION
        "IFFT for the received signal on Demodulator 2"
    ::= { pt3080Demodulator  42 }

pt3080Demodulator1ActualConstellation OBJECT-TYPE
    SYNTAX      INTEGER { qpsk(0), qam16(1), qam64(2) }
    MAX-ACCESS  read-only
    STATUS      current
    DESCRIPTION
        "Constellation for the received signal on Demodulator 1"
    ::= { pt3080Demodulator  16 }

pt3080Demodulator2ActualConstellation OBJECT-TYPE
    SYNTAX      INTEGER { qpsk(0), qam16(1), qam64(2) }
    MAX-ACCESS  read-only
    STATUS      current
    DESCRIPTION
        "Constellation for the received signal on Demodulator 2"
    ::= { pt3080Demodulator  43 }

pt3080Demodulator1ActualHierarchy OBJECT-TYPE
    SYNTAX      INTEGER { none(0), h-1(1), h-2(2), h-4(3) }
    MAX-ACCESS  read-only
    STATUS      current
    DESCRIPTION
        "Hierarchy for the received signal on Demodulator 1"
    ::= { pt3080Demodulator  17 }

pt3080Demodulator2ActualHierarchy OBJECT-TYPE
    SYNTAX      INTEGER { none(0), h-1(1), h-2(2), h-4(3) }
    MAX-ACCESS  read-only
    STATUS      current
    DESCRIPTION
        "Hierarchy for the received signal on Demodulator 2"
    ::= { pt3080Demodulator  44 }

pt3080Demodulator1ActualCodeRateHighPrio OBJECT-TYPE
    SYNTAX      INTEGER { r1-2(0), r2-3(1), r3-4(2), r5-6(3), r7-8(4) }
    MAX-ACCESS  read-only
    STATUS      current
    DESCRIPTION
        "High Priority Code Rate for the received signal on Demodulator
         1"
    ::= { pt3080Demodulator  18 }

pt3080Demodulator2ActualCodeRateHighPrio OBJECT-TYPE
    SYNTAX      INTEGER { r1-2(0), r2-3(1), r3-4(2), r5-6(3), r7-8(4) }
    MAX-ACCESS  read-only
    STATUS      current
    DESCRIPTION
        "High Priority Code Rate for the received signal on Demodulator
         2"
    ::= { pt3080Demodulator  45 }

pt3080Demodulator1ActualCodeRateLowPrio OBJECT-TYPE
    SYNTAX      INTEGER { r1-2(0), r2-3(1), r3-4(2), r5-6(3), r7-8(4) }
    MAX-ACCESS  read-only
    STATUS      current
    DESCRIPTION
        "High Priority Code Rate for the received signal on Demodulator
         1"
    ::= { pt3080Demodulator  19 }

pt3080Demodulator2ActualCodeRateLowPrio OBJECT-TYPE
    SYNTAX      INTEGER { r1-2(0), r2-3(1), r3-4(2), r5-6(3), r7-8(4) }
    MAX-ACCESS  read-only
    STATUS      current
    DESCRIPTION
        "High Priority Code Rate for the received signal on Demodulator
         2"
    ::= { pt3080Demodulator  46 }

pt3080Demodulator1ActualDeepInterleaver OBJECT-TYPE
    SYNTAX      INTEGER { off(0), on(1) }
    MAX-ACCESS  read-only
    STATUS      current
    DESCRIPTION
        "Deep Interleaver for the received signal on Demodulator 1"
    ::= { pt3080Demodulator  20 }

pt3080Demodulator2ActualDeepInterleaver OBJECT-TYPE
    SYNTAX      INTEGER { off(0), on(1) }
    MAX-ACCESS  read-only
    STATUS      current
    DESCRIPTION
        "Deep Interleaver for the received signal on Demodulator 2"
    ::= { pt3080Demodulator  47 }

pt3080Demodulator1ActualMpeFecHighPrio OBJECT-TYPE
    SYNTAX      INTEGER { off(0), on(1) }
    MAX-ACCESS  read-only
    STATUS      current
    DESCRIPTION
        "High Priority MPE/FEC mode for the received signal on Demodulator
         1"
    ::= { pt3080Demodulator  21 }

pt3080Demodulator2ActualMpeFecHighPrio OBJECT-TYPE
    SYNTAX      INTEGER { off(0), on(1) }
    MAX-ACCESS  read-only
    STATUS      current
    DESCRIPTION
        "High Priority MPE/FEC mode for the received signal on Demodulator
         2"
    ::= { pt3080Demodulator  48 }

pt3080Demodulator1ActualMpeFecLowPrio OBJECT-TYPE
    SYNTAX      INTEGER { off(0), on(1) }
    MAX-ACCESS  read-only
    STATUS      current
    DESCRIPTION
        "Low Priority MPE/FEC mode for the received signal on Demodulator
         1"
    ::= { pt3080Demodulator  22 }

pt3080Demodulator2ActualMpeFecLowPrio OBJECT-TYPE
    SYNTAX      INTEGER { off(0), on(1) }
    MAX-ACCESS  read-only
    STATUS      current
    DESCRIPTION
        "Low Priority MPE/FEC mode for the received signal on Demodulator
         2"
    ::= { pt3080Demodulator  49 }

pt3080Demodulator1ActualTimeSlicingHighPrio OBJECT-TYPE
    SYNTAX      INTEGER { off(0), on(1) }
    MAX-ACCESS  read-only
    STATUS      current
    DESCRIPTION
        "High Priority timeslicing mode for the received signal on Demodulator
         1"
    ::= { pt3080Demodulator  23 }

pt3080Demodulator2ActualTimeSlicingHighPrio OBJECT-TYPE
    SYNTAX      INTEGER { off(0), on(1) }
    MAX-ACCESS  read-only
    STATUS      current
    DESCRIPTION
        "High Priority timeslicing mode for the received signal on Demodulator
         2"
    ::= { pt3080Demodulator  50 }

pt3080Demodulator1ActualTimeSlicingLowPrio OBJECT-TYPE
    SYNTAX      INTEGER { off(0), on(1) }
    MAX-ACCESS  read-only
    STATUS      current
    DESCRIPTION
        "Low Priority timeslicing mode for the received signal on Demodulator
         1"
    ::= { pt3080Demodulator  24 }

pt3080Demodulator2ActualTimeSlicingLowPrio OBJECT-TYPE
    SYNTAX      INTEGER { off(0), on(1) }
    MAX-ACCESS  read-only
    STATUS      current
    DESCRIPTION
        "Low Priority timeslicing mode for the received signal on Demodulator
         2"
    ::= { pt3080Demodulator  51 }

pt3080Demodulator1ActualCellID OBJECT-TYPE
    SYNTAX      Integer32
    MAX-ACCESS  read-only
    STATUS      current
    DESCRIPTION
        "Current Cell ID value for the received signal on Demodulator
         1"
    ::= { pt3080Demodulator  25 }

pt3080Demodulator2ActualCellID OBJECT-TYPE
    SYNTAX      Integer32
    MAX-ACCESS  read-only
    STATUS      current
    DESCRIPTION
        "Current Cell ID value for the received signal on Demodulator
         1"
    ::= { pt3080Demodulator  52 }

pt3080Demodulator1ActualDVBHMode OBJECT-TYPE
    SYNTAX      INTEGER { off(0), on(1) }
    MAX-ACCESS  read-only
    STATUS      current
    DESCRIPTION
        "DVB-H mode for the received signal on Demodulator 1"
    ::= { pt3080Demodulator  26 }

pt3080Demodulator2ActualDVBHMode OBJECT-TYPE
    SYNTAX      INTEGER { off(0), on(1) }
    MAX-ACCESS  read-only
    STATUS      current
    DESCRIPTION
        "DVB-H mode for the received signal on Demodulator 2"
    ::= { pt3080Demodulator  53 }



--
-- pt3080 Precorrector sub-tree
--  

pt3080PrecorrectorLinearAdaptive OBJECT-TYPE
    SYNTAX      Integer32
    MAX-ACCESS  read-only
    STATUS      current
    DESCRIPTION
        "Linear precorrection curve active in the system"
    ::= { pt3080Precorrector  79 }

pt3080PrecorrectorLinearMode OBJECT-TYPE
    SYNTAX      INTEGER { monitoring(0), static(1), adaptive(2) }
    MAX-ACCESS  read-write
    STATUS      current
    DESCRIPTION
        "selection of the operational mode for the linear precorrector
         <br/>(note: legacy term used for backward compatibility. MONITORING
         Equal to the mode named BYPASS in the WEB GUI )"
    ::= { pt3080Precorrector  2 }

pt3080PrecorrectorLinearSenseEnable OBJECT-TYPE
    SYNTAX      INTEGER { disable(0), enable(1) }
    MAX-ACCESS  read-write
    STATUS      current
    DESCRIPTION
        "By using this, it is possible to control wether to use the linear
         Sense Input or not."
    ::= { pt3080Precorrector  46 }

pt3080PrecorrectorLinearMonitorStatus OBJECT-TYPE
    SYNTAX      INTEGER { not-running(0), monitoring(1), initialising(2), initialising-0(3), initialising-10(4), initialising-20(5), initialising-30(6), initialising-40(7), initialising-50(8), initialising-60(9), initialising-70(10), initialising-80(11), initialising-90(12), auto-applying(13), completed(14) }
    MAX-ACCESS  read-only
    STATUS      current
    DESCRIPTION
        "linear Precor state"
    ::= { pt3080Precorrector  24 }

pt3080PrecorrectorLinearMonitorSenseLevel OBJECT-TYPE
    SYNTAX      Integer32
    UNITS       "0.1 dBm"
    MAX-ACCESS  read-only
    STATUS      current
    DESCRIPTION
        "Level meassured at the linear sense input with offset defined
         by attenuation"
    ::= { pt3080Precorrector  22 }

pt3080PrecorrectorLinearMonitorSenseValid OBJECT-TYPE
    SYNTAX      Integer32
    MAX-ACCESS  read-only
    STATUS      current
    DESCRIPTION
        "Is linear sense input information valid"
    ::= { pt3080Precorrector  23 }

pt3080PrecorrectorLinearMonitorSenseBadCount OBJECT-TYPE
    SYNTAX      Integer32
    MAX-ACCESS  read-only
    STATUS      current
    DESCRIPTION
        "Number of bad/invalid sense counts, made by the linear adaptive
         precorrector."
    ::= { pt3080Precorrector  8 }

pt3080PrecorrectorLinearMonitorAmplitudeRipple OBJECT-TYPE
    SYNTAX      Integer32
    UNITS       "0.1 dB"
    MAX-ACCESS  read-only
    STATUS      current
    DESCRIPTION
        "Amplitude ripple"
    ::= { pt3080Precorrector  26 }

pt3080PrecorrectorLinearMonitorAmplitudeRippleValid OBJECT-TYPE
    SYNTAX      Integer32
    MAX-ACCESS  read-only
    STATUS      current
    DESCRIPTION
        "Is amplitude ripple information valid"
    ::= { pt3080Precorrector  30 }

pt3080PrecorrectorLinearMonitorGroupDelay OBJECT-TYPE
    SYNTAX      Integer32
    UNITS       "0.1 ns"
    MAX-ACCESS  read-only
    STATUS      current
    DESCRIPTION
        "Group delay"
    ::= { pt3080Precorrector  27 }

pt3080PrecorrectorLinearMonitorGroupDelayValid OBJECT-TYPE
    SYNTAX      Integer32
    MAX-ACCESS  read-only
    STATUS      current
    DESCRIPTION
        "Is group delay information valid"
    ::= { pt3080Precorrector  31 }

pt3080PrecorrectorLinearMonitorDiscartedIterations OBJECT-TYPE
    SYNTAX      Integer32
    MAX-ACCESS  read-only
    STATUS      current
    DESCRIPTION
        "Number of iterations discarded by the linear adaptive precorrector
         due to noisy signal samples."
    ::= { pt3080Precorrector  47 }

pt3080PrecorrectorLinearMonitorIterations OBJECT-TYPE
    SYNTAX      Integer32
    MAX-ACCESS  read-only
    STATUS      current
    DESCRIPTION
        "Number of iterations made by the linear adaptive precorrector."
    ::= { pt3080Precorrector  19 }

pt3080PrecorrectorLinearAdaptiveMode OBJECT-TYPE
    SYNTAX      INTEGER { idle(0), autorun(1), runtotarget(2), continuous(3), single(4) }
    MAX-ACCESS  read-write
    STATUS      current
    DESCRIPTION
        "selection of the operational mode for the linear adaptive precorrector
         <br/>(note: legacy term used for backward compatibility. IDLE
         Equal to the mode named MONITORING in the WEB GUI )"
    ::= { pt3080Precorrector  1 }

pt3080PrecorrectorLinearAdaptiveAmplitudeRippleTargetLevel OBJECT-TYPE
    SYNTAX      Integer32 ( 0 .. 10000 )
    UNITS       "0.1 dB"
    MAX-ACCESS  read-write
    STATUS      current
    DESCRIPTION
        "Define a adaptive target level for the amplitude ripple"
    ::= { pt3080Precorrector  42 }

pt3080PrecorrectorLinearAdaptiveAmplitudeRippleTargetHysteresis OBJECT-TYPE
    SYNTAX      Integer32 ( 0 .. 100000 )
    UNITS       "0.01 dB"
    MAX-ACCESS  read-write
    STATUS      current
    DESCRIPTION
        "Define a adaptive target level hysteresis for the amplitude 
        ripple"
    ::= { pt3080Precorrector  14 }

pt3080PrecorrectorLinearAdaptiveAmplitudeRippleEnable OBJECT-TYPE
    SYNTAX      INTEGER { off(0), on(1) }
    MAX-ACCESS  read-write
    STATUS      current
    DESCRIPTION
        "Enable amplitude ripple as a trigger for the AUTORUN and RUNTOTARGET
         modes"
    ::= { pt3080Precorrector  10 }

pt3080PrecorrectorLinearAdaptiveGroupDelayTargetLevel OBJECT-TYPE
    SYNTAX      Integer32 ( 0 .. 10000 )
    UNITS       "0.1 ns"
    MAX-ACCESS  read-write
    STATUS      current
    DESCRIPTION
        "Define a adaptive target level for the group delay"
    ::= { pt3080Precorrector  43 }

pt3080PrecorrectorLinearAdaptiveGroupDelayTargetHysteresis OBJECT-TYPE
    SYNTAX      Integer32 ( 0 .. 100000 )
    UNITS       "0.01 ns"
    MAX-ACCESS  read-write
    STATUS      current
    DESCRIPTION
        "Define a adaptive target level hysteresis for the group delay"
    ::= { pt3080Precorrector  15 }

pt3080PrecorrectorLinearAdaptiveGroupDelayEnable OBJECT-TYPE
    SYNTAX      INTEGER { off(0), on(1) }
    MAX-ACCESS  read-write
    STATUS      current
    DESCRIPTION
        "Enable group delay as a trigger for the AUTORUN and RUNTOTARGET
         modes"
    ::= { pt3080Precorrector  11 }

pt3080PrecorrectorLinearAttenuation OBJECT-TYPE
    SYNTAX      Integer32 ( -1000 .. 1000 )
    UNITS       "0.1 dB"
    MAX-ACCESS  read-write
    STATUS      current
    DESCRIPTION
        "Define a attenuation level for the sense input"
    ::= { pt3080Precorrector  78 }

pt3080PrecorrectorNonlinearAdaptive OBJECT-TYPE
    SYNTAX      Integer32
    MAX-ACCESS  read-only
    STATUS      current
    DESCRIPTION
        "Non-Linear precorrection curve active in the system"
    ::= { pt3080Precorrector  80 }

pt3080PrecorrectorNonlinearMode OBJECT-TYPE
    SYNTAX      INTEGER { monitoring(0), static(1), adaptive(2) }
    MAX-ACCESS  read-write
    STATUS      current
    DESCRIPTION
        "selection of the operational mode for the non-linear precorrector
         <br/>(note: legacy term used for backward compatibility. MONITORING
         Equal to the mode named BYPASS in the WEB GUI )"
    ::= { pt3080Precorrector  4 }

pt3080PrecorrectorNonlinearSenseEnable OBJECT-TYPE
    SYNTAX      INTEGER { disable(0), enable(1) }
    MAX-ACCESS  read-write
    STATUS      current
    DESCRIPTION
        "By using this, it is possible to control wether to use the nonlinear
         Sense Input or not."
    ::= { pt3080Precorrector  48 }

pt3080PrecorrectorNonlinearMonitorStatus OBJECT-TYPE
    SYNTAX      INTEGER { not-running(0), monitoring(1), initialising(2), initialising-0(3), initialising-10(4), initialising-20(5), initialising-30(6), initialising-40(7), initialising-50(8), initialising-60(9), initialising-70(10), initialising-80(11), initialising-90(12), auto-applying(13), completed(14) }
    MAX-ACCESS  read-only
    STATUS      current
    DESCRIPTION
        "Nonlinear Precor state"
    ::= { pt3080Precorrector  40 }

pt3080PrecorrectorNonlinearMonitorSenseLevel OBJECT-TYPE
    SYNTAX      Integer32
    UNITS       "0.1 dBm"
    MAX-ACCESS  read-only
    STATUS      current
    DESCRIPTION
        "Level meassured at the Nonlinear sense input with offset defined
         by attenuation"
    ::= { pt3080Precorrector  38 }

pt3080PrecorrectorNonlinearMonitorSenseValid OBJECT-TYPE
    SYNTAX      Integer32
    MAX-ACCESS  read-only
    STATUS      current
    DESCRIPTION
        "Is Nonlinear sense input information valid"
    ::= { pt3080Precorrector  39 }

pt3080PrecorrectorNonlinearMonitorSenseBadCount OBJECT-TYPE
    SYNTAX      Integer32
    MAX-ACCESS  read-only
    STATUS      current
    DESCRIPTION
        "Number of bad/invalid sense counts, made by the nonlinear adaptive
         precorrector."
    ::= { pt3080Precorrector  9 }

pt3080PrecorrectorNonlinearMonitorLowerShoulderLevel OBJECT-TYPE
    SYNTAX      Integer32
    UNITS       "0.1 dB"
    MAX-ACCESS  read-only
    STATUS      current
    DESCRIPTION
        "Lower shoulder level"
    ::= { pt3080Precorrector  28 }

pt3080PrecorrectorNonlinearMonitorLowerShoulderValid OBJECT-TYPE
    SYNTAX      Integer32
    MAX-ACCESS  read-only
    STATUS      current
    DESCRIPTION
        "Is Lower shoulder information valid"
    ::= { pt3080Precorrector  32 }

pt3080PrecorrectorNonlinearMonitorUpperShoulderLevel OBJECT-TYPE
    SYNTAX      Integer32
    UNITS       "0.1 dB"
    MAX-ACCESS  read-only
    STATUS      current
    DESCRIPTION
        "Upper shoulder level"
    ::= { pt3080Precorrector  29 }

pt3080PrecorrectorNonlinearMonitorUpperShoulderValid OBJECT-TYPE
    SYNTAX      Integer32
    MAX-ACCESS  read-only
    STATUS      current
    DESCRIPTION
        "Is Upper shoulder information valid"
    ::= { pt3080Precorrector  33 }

pt3080PrecorrectorNonlinearMonitorDiscartedIterations OBJECT-TYPE
    SYNTAX      Integer32
    MAX-ACCESS  read-only
    STATUS      current
    DESCRIPTION
        "Number of iterations discarded by the non-linear adaptive precorrector
         dur to noisy signal samples."
    ::= { pt3080Precorrector  49 }

pt3080PrecorrectorNonlinearMonitorIterations OBJECT-TYPE
    SYNTAX      Integer32
    MAX-ACCESS  read-only
    STATUS      current
    DESCRIPTION
        "Number of iterations made by the nonlinear adaptive precorrector."
    ::= { pt3080Precorrector  35 }

pt3080PrecorrectorNonlinearMonitorMer OBJECT-TYPE
    SYNTAX      Integer32
    UNITS       "0.1 dB"
    MAX-ACCESS  read-only
    STATUS      current
    DESCRIPTION
        "MER"
    ::= { pt3080Precorrector  50 }

pt3080PrecorrectorNonlinearMonitorMerValid OBJECT-TYPE
    SYNTAX      Integer32
    MAX-ACCESS  read-only
    STATUS      current
    DESCRIPTION
        "Is MER information valid"
    ::= { pt3080Precorrector  51 }

pt3080PrecorrectorNonlinearMonitorPapr OBJECT-TYPE
    SYNTAX      Integer32
    UNITS       "0.1 dB"
    MAX-ACCESS  read-only
    STATUS      current
    DESCRIPTION
        "PAPR level"
    ::= { pt3080Precorrector  52 }

pt3080PrecorrectorNonlinearMonitorPaprValid OBJECT-TYPE
    SYNTAX      Integer32
    MAX-ACCESS  read-only
    STATUS      current
    DESCRIPTION
        "Is Papr information valid"
    ::= { pt3080Precorrector  53 }

pt3080PrecorrectorNonlinearAttenuation OBJECT-TYPE
    SYNTAX      Integer32 ( -1000 .. 1000 )
    UNITS       "0.1 dB"
    MAX-ACCESS  read-write
    STATUS      current
    DESCRIPTION
        "Define a attenuation level for the sense input"
    ::= { pt3080Precorrector  77 }

pt3080PrecorrectorNonlinearAdaptiveMode OBJECT-TYPE
    SYNTAX      INTEGER { idle(0), autorun(1), runtotarget(2), continuous(3), single(4) }
    MAX-ACCESS  read-write
    STATUS      current
    DESCRIPTION
        "selection of the operational mode for the non-linear adaptive
         precorrector <br/>(note: legacy term used for backward compatibility.
         IDLE Equal to the mode named MONITORING in the WEB GUI )"
    ::= { pt3080Precorrector  3 }

pt3080PrecorrectorNonlinearAdaptiveAveraging OBJECT-TYPE
    SYNTAX      INTEGER { no(0), yes(1) }
    MAX-ACCESS  read-write
    STATUS      current
    DESCRIPTION
        "Choose wether or not to use averaging calulations"
    ::= { pt3080Precorrector  54 }

pt3080PrecorrectorNonlinearAdaptiveMaxRfPaprEnable OBJECT-TYPE
    SYNTAX      INTEGER { disable(0), enable(1) }
    MAX-ACCESS  read-write
    STATUS      current
    DESCRIPTION
        "Enable the modulator's output PAPR limiter function"
    ::= { pt3080Precorrector  55 }

pt3080PrecorrectorNonlinearAdaptiveMaxRfPaprLimit OBJECT-TYPE
    SYNTAX      Integer32 ( 20 .. 180 )
    UNITS       "0.1 dB"
    MAX-ACCESS  read-write
    STATUS      current
    DESCRIPTION
        "Maximum RF PAPR Limitation"
    ::= { pt3080Precorrector  56 }

pt3080PrecorrectorNonlinearAdaptiveMerTarget OBJECT-TYPE
    SYNTAX      Integer32 ( 0 .. 800 )
    UNITS       "0.1 dB"
    MAX-ACCESS  read-write
    STATUS      current
    DESCRIPTION
        "Define a target level for the MER"
    ::= { pt3080Precorrector  57 }

pt3080PrecorrectorNonlinearAdaptiveMerTargetHysteresis OBJECT-TYPE
    SYNTAX      Integer32 ( 0 .. 1000 )
    UNITS       "0.01 dB"
    MAX-ACCESS  read-write
    STATUS      current
    DESCRIPTION
        "Define a target MER hysteresis"
    ::= { pt3080Precorrector  58 }

pt3080PrecorrectorNonlinearAdaptiveMerEnable OBJECT-TYPE
    SYNTAX      INTEGER { off(0), on(1) }
    MAX-ACCESS  read-write
    STATUS      current
    DESCRIPTION
        "Enable MER as a trigger for the AUTORUN and RUNTOTARGET modes"
    ::= { pt3080Precorrector  59 }

pt3080PrecorrectorNonlinearAdaptiveLowerShoulderTargetLevel OBJECT-TYPE
    SYNTAX      Integer32 ( -800 .. 0 )
    UNITS       "0.1 dB"
    MAX-ACCESS  read-write
    STATUS      current
    DESCRIPTION
        "Define a adaptive target level for the lower shoulder"
    ::= { pt3080Precorrector  44 }

pt3080PrecorrectorNonlinearAdaptiveLowerShoulderTargetHysteresis OBJECT-TYPE
    SYNTAX      Integer32 ( 0 .. 1000 )
    UNITS       "0.01 dB"
    MAX-ACCESS  read-write
    STATUS      current
    DESCRIPTION
        "Define a adaptive target level hysteresis for the lower shoulder"
    ::= { pt3080Precorrector  16 }

pt3080PrecorrectorNonlinearAdaptiveLowerShoulderEnable OBJECT-TYPE
    SYNTAX      INTEGER { off(0), on(1) }
    MAX-ACCESS  read-write
    STATUS      current
    DESCRIPTION
        "Enable shoulder level (lower) as a trigger for the AUTORUN and
         RUNTOTARGET modes"
    ::= { pt3080Precorrector  12 }

pt3080PrecorrectorNonlinearAdaptiveUpperShoulderTargetLevel OBJECT-TYPE
    SYNTAX      Integer32 ( -800 .. 0 )
    UNITS       "0.1 dB"
    MAX-ACCESS  read-write
    STATUS      current
    DESCRIPTION
        "Define a adaptive target level for the upper shoulder"
    ::= { pt3080Precorrector  45 }

pt3080PrecorrectorNonlinearAdaptiveUpperShoulderTargetHysteresis OBJECT-TYPE
    SYNTAX      Integer32 ( 0 .. 1000 )
    UNITS       "0.01 dB"
    MAX-ACCESS  read-write
    STATUS      current
    DESCRIPTION
        "Define a adaptive target level hysteresis for the upper shoulder"
    ::= { pt3080Precorrector  17 }

pt3080PrecorrectorNonlinearAdaptiveUpperShoulderEnable OBJECT-TYPE
    SYNTAX      INTEGER { off(0), on(1) }
    MAX-ACCESS  read-write
    STATUS      current
    DESCRIPTION
        "Enable shoulder level (upper) as a trigger for the AUTORUN and
         RUNTOTARGET modes"
    ::= { pt3080Precorrector  13 }

pt3080PrecorrectorPaprClipping OBJECT-TYPE
    SYNTAX      Integer32 ( 200 .. 1200 )
    UNITS       "0.01 dB"
    MAX-ACCESS  read-write
    STATUS      current
    DESCRIPTION
        "set the built-in peak clipper function. The value 'max' corresponds
         to an unclipped COFDM signal (12dB peak to average ratio). 
        The value 'min' correspondsto COFDM signal where all peaks >2dB
         above average power are clipped. When feeding the output from
         the modulator through an amplifier the best overall performance
         result is normally obtained if the clipper value used by modulator
         clips the signal just a fraction before the amplifier would
         clip the signal."
    ::= { pt3080Precorrector  60 }

pt3080PrecorrectorPaprShaping OBJECT-TYPE
    SYNTAX      Integer32 ( 0 .. 100 )
    UNITS       "1 %"
    MAX-ACCESS  read-write
    STATUS      current
    DESCRIPTION
        "Set the output peak shaping filter hardness. The value 'min'
         correspond to traditional 'hard-clipping' where the clipper
         noise is equally distributed below, inside and above the COFDM
         spectrum (clipper noise clearly visible in the form of noise
         above and below the spectrum. The value 'max' corresponds to
         maximum soft clipping where the clipper noise in the sidebands
         (above and below the COFDM spectrum) is subjected to maximum
         suppression while still maintaining the exact clipper value
         (peak-to-average-ration). The suppression of the sideband noise
         is obtained as a tradeoff against the in band performance. 
        The clip filter setting is typically selected as a compromise
         between spectrum shoulder performance and in-band signal performance
         (MER)."
    ::= { pt3080Precorrector  61 }

pt3080PrecorrectorClipperMode OBJECT-TYPE
    SYNTAX      INTEGER { monitoring(0), static(1), adaptive(2) }
    MAX-ACCESS  read-write
    STATUS      current
    DESCRIPTION
        "Selection between no, static (manual) and adaptive clipper function"
    ::= { pt3080Precorrector  74 }

pt3080PrecorrectorClipperAdaptive OBJECT-TYPE
    SYNTAX      Integer32
    MAX-ACCESS  read-only
    STATUS      current
    DESCRIPTION
        "Clipper shaped by the OptiClipper algorithm"
    ::= { pt3080Precorrector  75 }

pt3080PrecorrectorClipperEnable OBJECT-TYPE
    SYNTAX      INTEGER { off(0), on(1) }
    MAX-ACCESS  read-only
    STATUS      current
    DESCRIPTION
        "Clipper enable"
    ::= { pt3080Precorrector  76 }

pt3080PrecorrectorClipperAdaptiveMode OBJECT-TYPE
    SYNTAX      INTEGER { monitoring(0), continuous(1), single(2) }
    MAX-ACCESS  read-write
    STATUS      current
    DESCRIPTION
        "Selection of the operational mode for the adaptive clipper function"
    ::= { pt3080Precorrector  63 }

pt3080PrecorrectorClipperAdaptiveShaping OBJECT-TYPE
    SYNTAX      Integer32 ( 99 .. 100 )
    UNITS       "1 %"
    MAX-ACCESS  read-write
    STATUS      current
    DESCRIPTION
        "Depricated Therefore min and max value are set to 100% Set the
         peak shaping filter hardness. The value 'min' correspond to
         traditional 'hard-clipping' where the clipper noise is equally
         distributed below, inside and above the COFDM spectrum (clipper
         noise clearly visible in the form of noise above and below 
        the spectrum. The value 'max' corresponds to maximum soft clipping
         where the clipper noise in the sidebands (above and below the
         COFDM spectrum) is subjected to maximum suppression while still
         maintaining the exact clipper value (peak-to-average-ration).
         The suppression of the sideband noise is obtained as a tradeoff
         against the in band performance. The clip filter setting is
         typically selected as a compromise between spectrum shoulder
         performance and in-band signal performance (MER)."
    ::= { pt3080Precorrector  81 }

pt3080PrecorrectorClipperMonitorStatus OBJECT-TYPE
    SYNTAX      INTEGER { not-running(0), monitoring(1), initialising(2), initialising-0(3), initialising-10(4), initialising-20(5), initialising-30(6), initialising-40(7), initialising-50(8), initialising-60(9), initialising-70(10), initialising-80(11), initialising-90(12), auto-applying(13), completed(14) }
    MAX-ACCESS  read-only
    STATUS      current
    DESCRIPTION
        "OptiClipper state"
    ::= { pt3080Precorrector  64 }

pt3080PrecorrectorClipperMonitorShoulderLevelLower OBJECT-TYPE
    SYNTAX      Integer32
    UNITS       "0.1 dB"
    MAX-ACCESS  read-only
    STATUS      current
    DESCRIPTION
        "Lower shoulder level"
    ::= { pt3080Precorrector  65 }

pt3080PrecorrectorClipperMonitorShoulderLevelLowerValid OBJECT-TYPE
    SYNTAX      Integer32
    MAX-ACCESS  read-only
    STATUS      current
    DESCRIPTION
        "Is Lower shoulder information valid"
    ::= { pt3080Precorrector  66 }

pt3080PrecorrectorClipperMonitorShoulderLevelUpper OBJECT-TYPE
    SYNTAX      Integer32
    UNITS       "0.1 dB"
    MAX-ACCESS  read-only
    STATUS      current
    DESCRIPTION
        "Upper shoulder level"
    ::= { pt3080Precorrector  67 }

pt3080PrecorrectorClipperMonitorShoulderLevelUpperValid OBJECT-TYPE
    SYNTAX      Integer32
    MAX-ACCESS  read-only
    STATUS      current
    DESCRIPTION
        "Is Upper shoulder information valid"
    ::= { pt3080Precorrector  68 }

pt3080PrecorrectorClipperMonitorMer OBJECT-TYPE
    SYNTAX      Integer32
    UNITS       "0.1 dB"
    MAX-ACCESS  read-only
    STATUS      current
    DESCRIPTION
        "MER level"
    ::= { pt3080Precorrector  69 }

pt3080PrecorrectorClipperMonitorMerValid OBJECT-TYPE
    SYNTAX      Integer32
    MAX-ACCESS  read-only
    STATUS      current
    DESCRIPTION
        "Is MER information valid"
    ::= { pt3080Precorrector  70 }

pt3080PrecorrectorClipperMonitorPapr OBJECT-TYPE
    SYNTAX      Integer32
    UNITS       "0.1 dB"
    MAX-ACCESS  read-only
    STATUS      current
    DESCRIPTION
        "PAPR level"
    ::= { pt3080Precorrector  71 }

pt3080PrecorrectorClipperMonitorPaprValid OBJECT-TYPE
    SYNTAX      Integer32
    MAX-ACCESS  read-only
    STATUS      current
    DESCRIPTION
        "Is Papr information valid"
    ::= { pt3080Precorrector  72 }

pt3080PrecorrectorClipperMonitorIterations OBJECT-TYPE
    SYNTAX      Integer32
    MAX-ACCESS  read-only
    STATUS      current
    DESCRIPTION
        "Number of Iterations performed by the OptiClipper algorithm"
    ::= { pt3080Precorrector  73 }


pt3080PrecorrectorLastTurnAroundTime OBJECT-TYPE
    SYNTAX                      Integer32
    MAX-ACCESS                  read-only
    STATUS                      current
    DESCRIPTION                 "PrecorrectorLastTurnAroundTime "
    ::= { pt3080Precorrector 6 }

pt3080PrecorrectorSecondsSinceLastUpdate OBJECT-TYPE
    SYNTAX                      Integer32
    MAX-ACCESS                  read-only
    STATUS                      current
    DESCRIPTION                 "PrecorrectorSecondsSinceLastUpdate "
    ::= { pt3080Precorrector 7 }

pt3080PrecorrectorLinCleanrun   OBJECT-TYPE
    SYNTAX                      Integer32
    MAX-ACCESS                  read-only
    STATUS                      current
    DESCRIPTION                 "PrecorrectorLinCleanrun "
    ::= { pt3080Precorrector 18 }

pt3080PrecorrectorNlinCleanrun  OBJECT-TYPE
    SYNTAX                      INTEGER { no(0), yes(1) }
    MAX-ACCESS                  read-only
    STATUS                      current
    DESCRIPTION                 "PrecorrectorNlinCleanrun "
    ::= { pt3080Precorrector 34 }

pt3080PrecorrectorLinearLoadNeutral OBJECT-TYPE
    SYNTAX                      INTEGER { noop(0), load(1) }
    MAX-ACCESS                  read-write
    STATUS                      current
    DESCRIPTION                 "PrecorrectorLinearLoadNeutral "
    ::= { pt3080Precorrector 20 }

pt3080PrecorrectorLinearLoadFactory        OBJECT-TYPE
    SYNTAX                      INTEGER { noop(0), load(1) }
    MAX-ACCESS                  read-write
    STATUS                      current
    DESCRIPTION                 "PrecorrectorLinearLoadFactory "
    ::= { pt3080Precorrector 21 }

pt3080PrecorrectorLinearUpdateFactoryCurve OBJECT-TYPE
    SYNTAX                      INTEGER { noop(0), update(1) }
    MAX-ACCESS                  read-write
    STATUS                      current
    DESCRIPTION                 "PrecorrectorLinearUpdateFactoryCurve "
    ::= { pt3080Precorrector 25 }

pt3080PrecorrectorNonlinearLoadNeutral       OBJECT-TYPE
    SYNTAX                      INTEGER { noop(0), load(1) }
    MAX-ACCESS                  read-write
    STATUS                      current
    DESCRIPTION                 "PrecorrectorNonlinearLoadNeutral "
    ::= { pt3080Precorrector 36 }

pt3080PrecorrectorNonlinearLoadFactory       OBJECT-TYPE
    SYNTAX                      INTEGER { noop(0), load(1) }
    MAX-ACCESS                  read-write
    STATUS                      current
    DESCRIPTION                 "PrecorrectorNonlinearLoadFactory "
    ::= { pt3080Precorrector 37 }

pt3080PrecorrectorNonlinearUpdateFactoryCurve OBJECT-TYPE
    SYNTAX                      INTEGER { noop(0), update(1) }
    MAX-ACCESS                  read-write
    STATUS                      current
    DESCRIPTION                 "PrecorrectorNonlinearUpdateFactoryCurve "
    ::= { pt3080Precorrector 41 }

--
-- pt3080 Backplane sub-tree
--

pt3080BackplanePolarityHardMute OBJECT-TYPE
    SYNTAX      INTEGER { activelow(0), activehigh(1) }
    MAX-ACCESS  read-write
    STATUS      current
    DESCRIPTION
        "Set the polarity of the Hard Mute input pin on the PTT2 backplane."
    ::= { pt3080Backplane  1 }

pt3080BackplanePolarityRFFail OBJECT-TYPE
    SYNTAX      INTEGER { activelow(0), activehigh(1) }
    MAX-ACCESS  read-write
    STATUS      current
    DESCRIPTION
        "Set the polarity of the RF Fail output pin on the PTT2 backplane."
    ::= { pt3080Backplane  2 }


--
-- pt3080 Notifications sub-tree
--  

pt3080Notif OBJECT IDENTIFIER ::= { pt3080Notifs 0 }

pt3080NotifMessage OBJECT-TYPE
    SYNTAX                      DisplayString
    MAX-ACCESS                  accessible-for-notify
    STATUS                      current
    DESCRIPTION
        "The current alarm notification message"
    ::= { pt3080Notifs 1 }

pt3080NotifState OBJECT-TYPE
    SYNTAX                      INTEGER { off(0), activated(1) }
    MAX-ACCESS                  accessible-for-notify
    STATUS                      current
    DESCRIPTION
        "The current alarm notification state"
    ::= { pt3080Notifs 2 }


pt3080NotifLocalTime OBJECT-TYPE
    SYNTAX                      DateAndTime
    MAX-ACCESS                  accessible-for-notify
    STATUS                      current
    DESCRIPTION
        "The time the current alarm notification state changed"
    ::= { pt3080Notifs 3 }


-- SNMPv2 compliance nonsense --
pt3080Compliance MODULE-COMPLIANCE
    STATUS  current
    DESCRIPTION
      "The compliance statement for systems supporting
       the this MIB."
    MODULE -- this module
      MANDATORY-GROUPS {
         pt3080SystemGroup, pt3080InputGroup, pt3080OutputGroup,
         pt3080MonitorGroup,
         pt3080TestGroup, pt3080AlarmGroup, pt3080PresetGroup,
         pt3080EventlogGroup, pt3080CommsGroup, pt3080PrecorrectorGroup
      }
      GROUP pt3080ModeGroup
          DESCRIPTION
              "This group is optional."
      GROUP pt3080GpsGroup
          DESCRIPTION
              "This group is optional."
      GROUP pt3080ChannelFilterGroup
          DESCRIPTION
              "This group is optional."
      GROUP pt3080TSoIPGroup
          DESCRIPTION
              "This group is optional."
      GROUP pt3080DemodulatorGroup
          DESCRIPTION
              "This group is optional."
      GROUP pt3080ReceptionGroup
          DESCRIPTION
              "This group is optional."
      GROUP pt3080ASIGroup
          DESCRIPTION
              "This group is optional."
     ::= { pt3080Compliances 1 }

   pt3080Groups OBJECT IDENTIFIER ::= { pt3080Conformance 2 }

   pt3080SystemGroup OBJECT-GROUP
     OBJECTS {
              pt3080SystemInstrumentFW1Rev,
              pt3080SystemInstrumentFW1RevBL,
              pt3080SystemInstrumentFW2Rev,
              pt3080SystemInstrumentFW2RevBL,
              pt3080SystemInstrumentFW3Rev,
              pt3080SystemInstrumentFW4Rev,
              pt3080SystemInstrumentPCBRev,
              pt3080SystemInstrumentCalibrationRev,
              pt3080SystemInstrumentCalibrationDate,
              pt3080SystemReboot,
              pt3080SystemRebootDefaultConfig,
              pt3080SystemDateTime,
              pt3080SystemImage0Version,
              pt3080SystemImage0InstalledDate,
              pt3080SystemImage1version,
              pt3080SystemImage1InstalledDate,
              pt3080SystemScheduledActionRecurrence,
              pt3080SystemScheduledActionHour,
              pt3080SystemScheduledActionMinute,
              pt3080SystemScheduledActionWeekday,
              pt3080SystemScheduledActionMonthDay,
              pt3080SystemScheduledActionDate,
              pt3080SystemScheduledActionRandomDelay,
              pt3080SystemScheduledActionAction,
              pt3080SystemScheduledActionRepeaterMode,
              pt3080SystemScheduledActionPresetNo,
              pt3080SystemScheduledActionRebootImage,
              pt3080SystemScheduledActionRebootSystemType,
              pt3080SystemScheduledActionMute,
              pt3080SystemScheduledActionSWUpgradeProtocol,
              pt3080SystemScheduledActionSWUpgradeUsername,
              pt3080SystemScheduledActionSWUpgradePassword,
              pt3080SystemScheduledActionSWUpgradeImageServer,
              pt3080SystemScheduledActionSWUpgradeImagePath,
        pt3080SystemServiceLED
,
        pt3080SystemLanguage
,
        pt3080SystemType,
        pt3080SystemModulationStandard,
        pt3080SystemCurrentImage,
        pt3080SystemInstrumentKU,
        pt3080SystemInstrumentType,
        pt3080SystemInstrumentOptions,
        pt3080SystemDateTimeSync,
        pt3080SystemDateTimeSyncActual,
        pt3080SystemTimezone,
        pt3080SystemInstrumentSWRev,
        pt3080SystemInstrumentBootLoaderRev,
        pt3080SystemInstrumentKernelRev,
        pt3080SystemOperationOnTime,
        pt3080SystemOperationOnAirTime,
        pt3080SystemOperationNumberOfBoots,
        pt3080SystemBackplaneid,
        pt3080SystemBackplaneIdRaw,
        pt3080SystemBackplaneIdPcb,
        pt3080SystemBackplaneIdCableOptions,
        pt3080SystemBackplaneIdMAnuf,
        pt3080SystemBackplaneCalibrationDate,
        pt3080SystemBackplaneCalibrationSw,
        pt3080SystemBackplaneIdPartlist
            }
    STATUS   current
    DESCRIPTION
            "System group"
    ::= { pt3080Groups 1}

   pt3080ModeGroup OBJECT-GROUP
     OBJECTS {
        pt3080ModeListenBroadcast
       ,
       pt3080ModeNetwork,
       pt3080ModeHierarchy,
       pt3080Modeifft,
       pt3080ModeCodeRateHighPrio,
       pt3080ModeCodeRateLowPrio,
       pt3080ModeConstellation,
       pt3080ModeGuardInterval,
       pt3080ModeCellID,
       pt3080ModeEnableCellID,
       pt3080ModeDeepInterleaver,
       pt3080ModeEnableDVBH,
       pt3080ModeMpeFecLowPrio,
       pt3080ModeMpeFecHighPrio,
       pt3080ModeTimeSlicingLowPrio,
       pt3080ModeTimeSlicingHighPrio,
       pt3080ModeSfnDelayOffset,
       pt3080ModeTxIdent,
       pt3080ModeMipControl,
       pt3080ModeNetworkDelayHP,
       pt3080ModeNetworkDelayMinHP,
       pt3080ModeNetworkDelayMaxHP,
       pt3080ModeMaxNetworkDelayHP,
       pt3080ModeNetworkDelayMarginHP,
       pt3080ModeNetworkDelayLP,
       pt3080ModeNetworkDelayMinLP,
       pt3080ModeNetworkDelayMaxLP,
       pt3080ModeMaxNetworkDelayLP,
       pt3080ModeNetworkDelayMarginLP,
       pt3080ModeNetworkDelayReset,
       pt3080ModeDefaultMIPOutputPower,
       pt3080ModeDefaultMIPOutputTimeOffset,
       pt3080ModeDefaultMIPOutputCellID,
       pt3080ModeDefaultMIPOutputFreqOffset,
       pt3080ModeMIPMaxSFNDelay,
       pt3080ModeMipControlOutputPower,
       pt3080ModeMipControlOutputTimeOffset,
       pt3080ModeMipControlOutputCellId,
       pt3080ModeMipControlOutputFreqOffset,
       pt3080ModeMfnKeepNullPackets
    }
    STATUS   current
    DESCRIPTION
            "DVB-T Mode group"
    ::= { pt3080Groups 2}

  pt3080InputGroup OBJECT-GROUP
     OBJECTS {
              pt3080InputASITSPrimarySource,
              pt3080InputASITSSecondarySource,
              pt3080InputASIAutoRoutingPolicy,
        pt3080InputTSPrimaryMaxPATDelay,
        pt3080InputTSPrimaryMaxPATDelayEnable,
        pt3080InputTSPrimaryExpectedTSID,
        pt3080InputTSPrimaryExpectedTSIDEnable,
        pt3080InputTSPrimaryExpectedNWID,
        pt3080InputTSPrimaryExpectedNWIDEnable,
        pt3080InputTSPrimaryMaxStuffingrate,
        pt3080InputTSPrimaryMaxStuffingrateEnable,
        pt3080InputTSPrimaryMinDelaymargin,
        pt3080InputTSPrimaryMinDelaymarginEnable,
        pt3080InputTSPrimaryMaxMissingmip,
        pt3080InputTSPrimaryMaxMissingmipEnable,
        pt3080InputTSSecondaryMaxPATDelay,
        pt3080InputTSSecondaryMaxPATDelayEnable,
        pt3080InputTSSecondaryExpectedTSID,
        pt3080InputTSSecondaryExpectedTSIDEnable,
        pt3080InputTSSecondaryExpectedNWID,
        pt3080InputTSSecondaryExpectedNWIDEnable,
        pt3080InputTSSecondaryMaxStuffingrate,
        pt3080InputTSSecondaryMaxStuffingrateEnable,
        pt3080InputTSSecondaryMinDelaymargin,
        pt3080InputTSSecondaryMinDelaymarginEnable,
        pt3080InputTSSecondaryMaxMissingmip,
        pt3080InputTSSecondaryMaxMissingmipEnable
,
              pt3080InputTSPrimaryMaxStsJitter,
              pt3080InputTSSecondaryMaxStsJitter,
              pt3080InputTSPrimaryStatus,
              pt3080InputTSSecondaryStatus,
              pt3080InputTSHp,
              pt3080InputTSLp,
              pt3080InputEffectiveAutoroutingPolicy,
              pt3080InputTSHpBitrate,
              pt3080InputTSLpBitrate,
              pt3080InputTSHpPacketsBuffered,
              pt3080InputTSHpPacketSize,
              pt3080InputTSHpStuffingrate,
              pt3080InputTSHpTSID,
              pt3080InputTSLpPacketsBuffered,
              pt3080InputTSLpPacketSize,
              pt3080InputTSLpStuffingrate,
              pt3080InputTSLpTSID,
              
              pt3080InputTSHpNWID,
              pt3080InputTSLpNWID,
              pt3080InputTSPrimaryStsJitter,
              pt3080InputTSPrimaryStsJitterMax,
              pt3080InputTSPrimaryStsJitterMin,
              pt3080InputTSPrimaryStsJitterReset,
              pt3080InputTSSecondaryStsJitter,
              pt3080InputTSSecondaryStsJitterMax,
              pt3080InputTSSecondaryStsJitterMin,
              pt3080InputTSSecondaryStsJitterReset,
        pt3080InputRefDevType,
        pt3080InputRefCalDate,
        pt3080InputRefCalVer
,
        pt3080InputRefDirection

,
        pt3080InputRefSource,
        pt3080InputRefStatus,
        pt3080InputRef10MhzImpedance,
        pt3080InputRef10MhzHoldoverDelay,
        pt3080InputRef10MhzHoldoverForever,
        pt3080InputRef1PPSImpedance,
        pt3080InputRef1PPSHoldoverDelay,
        pt3080InputRef1PPSHoldoverForever,
        pt3080InputRef1PPSTrigSlope,
        pt3080InputRef1PPSTrigLevel,
        pt3080InputASIAutoRoutingDelayHp2Lp,
        pt3080InputASIAutoRoutingDelayLp2Hp,
        pt3080InputASIHoldoverTimeout
            }
    STATUS   current
    DESCRIPTION
            "Input group"
    ::= { pt3080Groups 3}

   pt3080OutputGroup OBJECT-GROUP
      OBJECTS {
        pt3080OutputIfEnable,
        pt3080OutputIfFrequency,
        pt3080OutputIfPolarity,
        pt3080OutputIfLevel,
        pt3080OutputMode,
        pt3080OutputEffectiveLevel,
        pt3080OutputActualLevel,
        pt3080OutputPolarity,
        pt3080OutputRfFrequency,
        pt3080OutputRfFrequencyOffset,
        pt3080OutputRfLevel,
        pt3080OutputRfCableMode,
        pt3080OutputRfCableConstantLevelOffset,
        pt3080OutputRfCableFrequencyLevelOffset0,
        pt3080OutputRfCableFrequencyLevelOffset1,
        pt3080OutputRfCableFrequencyLevelOffset2,
        pt3080OutputRfCableFrequencyLevelOffset3,
        pt3080OutputRfCableFrequencyLevelOffset4,
        pt3080OutputRfCableFrequencyLevelOffset5,
        pt3080OutputRfDetectedActualLevel,
        pt3080OutputRfDetectedLowerLevelLimit,
        pt3080OutputRfDetectedLowerLevelcontrol,
        pt3080OutputRfDetectedHigherLevelLimit,
        pt3080OutputRfDetectedHigherLevelcontrol,
        pt3080OutputRfAlcControl,
        pt3080OutputRfAlcSense,
        pt3080OutputRfAlcSetpointPort1,
        pt3080OutputRfAlcSetpointPort2,
        pt3080OutputRfAlcStatus,
        pt3080OutputRfAlcStatusInformation
                ,pt3080OutputBandwidth,
                pt3080OutputChannel,
                pt3080OutputSynchronized,
                pt3080OutputMute,
                pt3080OutputPowerLevel
              }
    STATUS   current
    DESCRIPTION
            "Output group"
    ::= { pt3080Groups 4}
 
   pt3080GpsGroup OBJECT-GROUP
      OBJECTS {
        pt3080GpsBias,
        pt3080GpsbiasVoltage
,
        pt3080GpsCableDelay
,
        pt3080GpsHoldoverForever,
        pt3080GpsHoldoverTime,
        pt3080GpsSatelliteSystemGPS,
        pt3080GpsSatelliteSystemGLONASS,
        pt3080GpsSatelliteSystemGALILEO,
        pt3080GpsSatelliteSystemCOMPASS,
        pt3080GpsVersion,
        pt3080Gps1PPSStatus,
        pt3080GpsState,
        pt3080GpsVisibleSatellitesSnr,
        pt3080GpsVisibleSatellites,
        pt3080GpsTrackedSatellites,
        pt3080GpsLongtitude,
        pt3080GpsLatitude,
        pt3080GpsAltitude
      }
    STATUS   current
    DESCRIPTION
            "GPS group"
    ::= { pt3080Groups 7}

   pt3080ChannelFilterGroup OBJECT-GROUP
      OBJECTS {
        pt3080ChannelFiltersSelect
      }
    STATUS   current
    DESCRIPTION
            "Channel Filter group"
    ::= { pt3080Groups 8}



   pt3080TSoIPGroup OBJECT-GROUP
      OBJECTS {
        pt3080TSoIPRx1ReceiverEnable,
        pt3080TSoIPRx2ReceiverEnable,
        pt3080TSoIPRx1LanSelect,
        pt3080TSoIPRx2LanSelect,
        pt3080TSoIPRx1Multicast,
        pt3080TSoIPRx2Multicast,
        pt3080TSoIPRx1Protocol,
        pt3080TSoIPRx2Protocol,
        pt3080TSoIPRx1Portnumber,
        pt3080TSoIPRx2Portnumber,
        pt3080TSoIPRx1PacketErrorRatioLimit,
        pt3080TSoIPRx2PacketErrorRatioLimit,
        pt3080TSoIPRx1MinumimLatency,
        pt3080TSoIPRx2MinumimLatency,
        pt3080TSoIPRx1SyncTimeout,
        pt3080TSoIPRx2SyncTimeout,
        pt3080TSoIPRx1Status,
        pt3080TSoIPRx2Status,
        pt3080TSoIPRx1CurrentIPAddress,
        pt3080TSoIPRx2CurrentIPAddress,
        pt3080TSoIPRx1IpBitrate,
        pt3080TSoIPRx2IpBitrate,
        pt3080TSoIPRx1PacketErrorRatio,
        pt3080TSoIPRx2PacketErrorRatio,
        pt3080TSoIPRx1SequenceErrors,
        pt3080TSoIPRx2SequenceErrors,
        pt3080TSoIPRx1LostIPFrames,
        pt3080TSoIPRx2LostIPFrames,
        pt3080TSoIPRx1CorrectedIPFrames,
        pt3080TSoIPRx2CorrectedIPFrames,
        pt3080TSoIPRx1OverrunIPFrames,
        pt3080TSoIPRx2OverrunIPFrames,
        pt3080TSoIPRx1PacketsPerFrame,
        pt3080TSoIPRx2PacketsPerFrame,
        pt3080TSoIPRx1TSPacketSize,
        pt3080TSoIPRx2TSPacketSize,
        pt3080TSoIPRx1FecColumn,
        pt3080TSoIPRx2FecColumn,
        pt3080TSoIPRx1FecRow,
        pt3080TSoIPRx2FecRow,
        pt3080TSoIPRx1QueueSize,
        pt3080TSoIPRx2QueueSize,
        pt3080TSoIPRx1CurrentLatency,
        pt3080TSoIPRx2CurrentLatency
      }
    STATUS   current
    DESCRIPTION
            "TSoIP group"
    ::= { pt3080Groups 10}

   pt3080MonitorGroup OBJECT-GROUP
      OBJECTS {
        pt3080MonitorSource,
        pt3080MonitorTSoIPEnable,
        pt3080MonitorTSoIPSource,
        pt3080MonitorTSoIPMulticastLanSelect,
        pt3080MonitorTSoIPDestIPAddress,
        pt3080MonitorTSoIPDestPort,
        pt3080MonitorTSoIPProtocol,
        pt3080MonitorTSoIPEnableFec,
        pt3080MonitorTSoIPFecColumn,
        pt3080MonitorTSoIPFecRow,
        pt3080MonitorTSoIPFecSkew,
        pt3080MonitorTSoIPKeepNullPackets,
        pt3080MonitorTSoIPPacketsPerFrame,
        pt3080MonitorTSoIPUDPChecksum,
        pt3080MonitorTSoIPDSCP,
        pt3080MonitorTSoIPTTL,
        pt3080MonitorTSoIPGenerateError,
        pt3080MonitorTSoIPIpBitrate,
        pt3080MonitorTSoIPTSSize,
        pt3080MonitorTSoIPLostIPFrames
      }
    STATUS   current
    DESCRIPTION
            "Signal monitor group"
    ::= { pt3080Groups 12}

   pt3080TestGroup OBJECT-GROUP
      OBJECTS {
        pt3080TestEnable,
        pt3080TestEnableReconnect,
        pt3080TestScarrierLevel,
        pt3080TestscarrierFrequencyOffset
      }
    STATUS   current
    DESCRIPTION
            "Test Signal group"
    ::= { pt3080Groups 13}

  pt3080AlarmGroup OBJECT-GROUP
     OBJECTS {
               pt3080GroupAlarmDescription,
               pt3080GroupAlarmState,
               pt3080GroupAlarmActionEventlog,
               pt3080GroupAlarmActionRelay1,
               pt3080GroupAlarmActionRelay2,
               pt3080GroupAlarmActionTrap,
               pt3080GroupAlarmActionEmail,
               pt3080GroupAlarmActionAlarmLED,
               pt3080GroupAlarmActionForceMode,
               pt3080ASITSPrimaryAlarmDescription,
               pt3080ASITSPrimaryAlarmState,
               pt3080ASITSPrimaryAlarmActionEventlog,
               pt3080ASITSPrimaryAlarmActionRelay1,
               pt3080ASITSPrimaryAlarmActionRelay2,
               pt3080ASITSPrimaryAlarmActionTrap,
               pt3080ASITSPrimaryAlarmActionEmail,
               pt3080ASITSPrimaryAlarmActionAlarmLED,
               pt3080ASITSPrimaryAlarmActionForceMode,
               pt3080ASITSSecondaryAlarmDescription,
               pt3080ASITSSecondaryAlarmState,
               pt3080ASITSSecondaryAlarmActionEventlog,
               pt3080ASITSSecondaryAlarmActionRelay1,
               pt3080ASITSSecondaryAlarmActionRelay2,
               pt3080ASITSSecondaryAlarmActionTrap,
               pt3080ASITSSecondaryAlarmActionEmail,
               pt3080ASITSSecondaryAlarmActionAlarmLED,
               pt3080ASITSSecondaryAlarmActionForceMode,
               pt3080SFNAlarmDescription,
               pt3080SFNAlarmState,
               pt3080SFNAlarmActionEventlog,
               pt3080SFNAlarmActionRelay1,
               pt3080SFNAlarmActionRelay2,
               pt3080SFNAlarmActionTrap,
               pt3080SFNAlarmActionEmail,
               pt3080SFNAlarmActionAlarmLED,
               pt3080SFNAlarmActionForceMode,
               pt3080TSoIPAlarmDescription,
               pt3080TSoIPAlarmState,
               pt3080TSoIPAlarmActionEventlog,
               pt3080TSoIPAlarmActionRelay1,
               pt3080TSoIPAlarmActionRelay2,
               pt3080TSoIPAlarmActionTrap,
               pt3080TSoIPAlarmActionEmail,
               pt3080TSoIPAlarmActionAlarmLED,
               pt3080TSoIPAlarmActionForceMode,
               pt3080DemodulatorAlarmDescription,
               pt3080DemodulatorAlarmState,
               pt3080DemodulatorAlarmActionEventlog,
               pt3080DemodulatorAlarmActionRelay1,
               pt3080DemodulatorAlarmActionRelay2,
               pt3080DemodulatorAlarmActionTrap,
               pt3080DemodulatorAlarmActionEmail,
               pt3080DemodulatorAlarmActionAlarmLED,
               pt3080DemodulatorAlarmActionForceMode,
               pt3080ReferenceAlarmDescription,
               pt3080ReferenceAlarmState,
               pt3080ReferenceAlarmActionEventlog,
               pt3080ReferenceAlarmActionRelay1,
               pt3080ReferenceAlarmActionRelay2,
               pt3080ReferenceAlarmActionTrap,
               pt3080ReferenceAlarmActionEmail,
               pt3080ReferenceAlarmActionAlarmLED,
               pt3080ReferenceAlarmActionForceMode,
               pt3080RFAlarmDescription,
               pt3080RFAlarmState,
               pt3080RFAlarmActionEventlog,
               pt3080RFAlarmActionRelay1,
               pt3080RFAlarmActionRelay2,
               pt3080RFAlarmActionTrap,
               pt3080RFAlarmActionEmail,
               pt3080RFAlarmActionAlarmLED,
               pt3080RFAlarmActionForceMode,
               pt3080GPSAlarmDescription,
               pt3080GPSAlarmState,
               pt3080GPSAlarmActionEventlog,
               pt3080GPSAlarmActionRelay1,
               pt3080GPSAlarmActionRelay2,
               pt3080GPSAlarmActionTrap,
               pt3080GPSAlarmActionEmail,
               pt3080GPSAlarmActionAlarmLED,
               pt3080GPSAlarmActionForceMode,
               pt3080ExternalAlarmDescription,
               pt3080ExternalAlarmState,
               pt3080ExternalAlarmActionEventlog,
               pt3080ExternalAlarmActionRelay1,
               pt3080ExternalAlarmActionRelay2,
               pt3080ExternalAlarmActionTrap,
               pt3080ExternalAlarmActionEmail,
               pt3080ExternalAlarmActionAlarmLED,
               pt3080ExternalAlarmActionForceMode,
               pt3080HWMonitorAlarmDescription,
               pt3080HWMonitorAlarmState,
               pt3080HWMonitorAlarmActionEventlog,
               pt3080HWMonitorAlarmActionRelay1,
               pt3080HWMonitorAlarmActionRelay2,
               pt3080HWMonitorAlarmActionTrap,
               pt3080HWMonitorAlarmActionEmail,
               pt3080HWMonitorAlarmActionAlarmLED,
               pt3080HWMonitorAlarmActionForceMode,
               pt3080CommsAlarmDescription,
               pt3080CommsAlarmState,
               pt3080CommsAlarmActionEventlog,
               pt3080CommsAlarmActionRelay1,
               pt3080CommsAlarmActionRelay2,
               pt3080CommsAlarmActionTrap,
               pt3080CommsAlarmActionEmail,
               pt3080CommsAlarmActionAlarmLED,
               pt3080CommsAlarmActionForceMode,
               pt3080InternalAlarmDescription,
               pt3080InternalAlarmState,
               pt3080InternalAlarmActionEventlog,
               pt3080InternalAlarmActionRelay1,
               pt3080InternalAlarmActionRelay2,
               pt3080InternalAlarmActionTrap,
               pt3080InternalAlarmActionEmail,
               pt3080InternalAlarmActionAlarmLED,
               pt3080InternalAlarmActionForceMode,
               pt3080ASIAlarmDescription,
               pt3080ASIAlarmState,
               pt3080ASIAlarmActionEventlog,
               pt3080ASIAlarmActionRelay1,
               pt3080ASIAlarmActionRelay2,
               pt3080ASIAlarmActionTrap,
               pt3080ASIAlarmActionEmail,
               pt3080ASIAlarmActionAlarmLED,
               pt3080ASIAlarmActionForceMode
             }
    STATUS   current
    DESCRIPTION
            "Alarm group"
    ::= { pt3080Groups 14}
     
  pt3080PresetGroup OBJECT-GROUP
     OBJECTS {
               pt3080PresetName,
               pt3080PresetRecall,
               pt3080PresetStore
             }
    STATUS   current
    DESCRIPTION
            "Preset group"
    ::= { pt3080Groups 15}
     
  pt3080EventlogGroup OBJECT-GROUP
     OBJECTS {
               pt3080EventlogID,
               pt3080EventlogTimestamp,
               pt3080EventlogText,
               pt3080EventlogClear,
               pt3080EventlogEnable,
               pt3080EventlogMode
             }
    STATUS   current
    DESCRIPTION
            "Eventlog group"
    ::= { pt3080Groups 16}
     
   pt3080CommsGroup OBJECT-GROUP
      OBJECTS {
                pt3080CommsAccessPasswordObserver,
                pt3080CommsAccessPasswordOperator,
                pt3080CommsAccessPasswordAdministrator,
                pt3080CommsStaticRouteType,
                pt3080CommsStaticRoutePrefix,
                pt3080CommsStaticRoutePrefixSize,
                pt3080CommsStaticRouteTarget,
                pt3080CommsStaticRoutePhysicalInterface,
        pt3080CommsAlarmEmailReceiver,
        pt3080CommsSeparatedSwitchPorts,
        pt3080CommsBroadcastStormProtection,
        pt3080CommsLocalPhysicalInterface,
        pt3080CommsLocalDhcpMode,
        pt3080CommsLocalStaticIpAddr,
        pt3080CommsLocalStaticNetmask,
        pt3080CommsLocalIpMulticastAddr,
        pt3080CommsLocalIpMulticastSourceFilterMode,
        pt3080CommsLocalIpMulticastSourceFilterAddress1,
        pt3080CommsLocalIpMulticastSourceFilterAddress2,
        pt3080CommsLocalIpMulticastSourceFilterAddress3,
        pt3080CommsLocalIpMulticastSourceFilterAddress4,
        pt3080CommsLocalIpMulticastSourceFilterAddress5,
        pt3080CommsLocalIpMulticastSourceFilterAddress6,
        pt3080CommsLocalVlanEnable,
        pt3080CommsLocalVlanId,
        pt3080CommsLocalServiceSNMP,
        pt3080CommsLocalServiceSCPI,
        pt3080CommsLocalServiceTSoIP,
        pt3080CommsLocalServiceRIP,
        pt3080CommsLocalCurrentIpAddr,
        pt3080CommsLocalCurrentNetmask,
        pt3080CommsRemoteEnable,
        pt3080CommsRemotePhysicalInterface,
        pt3080CommsRemoteDhcpMode,
        pt3080CommsRemoteStaticIpAddr,
        pt3080CommsRemoteStaticNetmask,
        pt3080CommsRemoteIpMulticastAddr,
        pt3080CommsRemoteIpMulticastSourceFilterMode,
        pt3080CommsRemoteIpMulticastSourceFilterAddress1,
        pt3080CommsRemoteIpMulticastSourceFilterAddress2,
        pt3080CommsRemoteIpMulticastSourceFilterAddress3,
        pt3080CommsRemoteIpMulticastSourceFilterAddress4,
        pt3080CommsRemoteIpMulticastSourceFilterAddress5,
        pt3080CommsRemoteIpMulticastSourceFilterAddress6,
        pt3080CommsRemoteVlanEnable,
        pt3080CommsRemoteVlanId,
        pt3080CommsRemoteServiceSNMP,
        pt3080CommsRemoteServiceSCPI,
        pt3080CommsRemoteServiceTSoIP,
        pt3080CommsRemoteServiceWeb,
        pt3080CommsRemoteServiceRIP,
        pt3080CommsRemoteCurrentIpAddr,
        pt3080CommsRemoteCurrentNetmask,
        pt3080CommsGbeAdminEnable,
        pt3080CommsGbeAdminPhysicalInterface,
        pt3080CommsGbeAdminDhcpMode,
        pt3080CommsGbeAdminStaticIpAddr,
        pt3080CommsGbeAdminStaticNetmask,
        pt3080CommsGbeAdminIpMulticastAddr,
        pt3080CommsGbeAdminIpMulticastSourceFilterMode,
        pt3080CommsGbeAdminIpMulticastSourceFilterAddress1,
        pt3080CommsGbeAdminIpMulticastSourceFilterAddress2,
        pt3080CommsGbeAdminIpMulticastSourceFilterAddress3,
        pt3080CommsGbeAdminIpMulticastSourceFilterAddress4,
        pt3080CommsGbeAdminIpMulticastSourceFilterAddress5,
        pt3080CommsGbeAdminIpMulticastSourceFilterAddress6,
        pt3080CommsGbeAdminVlanEnable,
        pt3080CommsGbeAdminVlanId,
        pt3080CommsGbeAdminServiceSNMP,
        pt3080CommsGbeAdminServiceSCPI,
        pt3080CommsGbeAdminServiceTSoIP,
        pt3080CommsGbeAdminServiceWeb,
        pt3080CommsGbeAdminServiceRIP,
        pt3080CommsGbeAdminCurrentIpAddr,
        pt3080CommsGbeAdminCurrentNetmask,
        pt3080CommsBackupEnable,
        pt3080CommsBackupPhysicalInterface,
        pt3080CommsBackupDhcpMode,
        pt3080CommsBackupStaticIpAddr,
        pt3080CommsBackupStaticNetmask,
        pt3080CommsBackupIpMulticastAddr,
        pt3080CommsBackupIpMulticastSourceFilterMode,
        pt3080CommsBackupIpMulticastSourceFilterAddress1,
        pt3080CommsBackupIpMulticastSourceFilterAddress2,
        pt3080CommsBackupIpMulticastSourceFilterAddress3,
        pt3080CommsBackupIpMulticastSourceFilterAddress4,
        pt3080CommsBackupIpMulticastSourceFilterAddress5,
        pt3080CommsBackupIpMulticastSourceFilterAddress6,
        pt3080CommsBackupVlanEnable,
        pt3080CommsBackupVlanId,
        pt3080CommsBackupServiceSNMP,
        pt3080CommsBackupServiceSCPI,
        pt3080CommsBackupServiceTSoIP,
        pt3080CommsBackupServiceWeb,
        pt3080CommsBackupServiceRIP,
        pt3080CommsBackupCurrentIpAddr,
        pt3080CommsBackupCurrentNetmask,
        pt3080CommsPortEnable,
        pt3080CommsPortPhysicalInterface,
        pt3080CommsPortDhcpMode,
        pt3080CommsPortStaticIpAddr,
        pt3080CommsPortStaticNetmask,
        pt3080CommsPortIpMulticastAddr,
        pt3080CommsPortIpMulticastSourceFilterMode,
        pt3080CommsPortIpMulticastSourceFilterAddress1,
        pt3080CommsPortIpMulticastSourceFilterAddress2,
        pt3080CommsPortIpMulticastSourceFilterAddress3,
        pt3080CommsPortIpMulticastSourceFilterAddress4,
        pt3080CommsPortIpMulticastSourceFilterAddress5,
        pt3080CommsPortIpMulticastSourceFilterAddress6,
        pt3080CommsPortVlanEnable,
        pt3080CommsPortVlanId,
        pt3080CommsPortServiceSNMP,
        pt3080CommsPortServiceSCPI,
        pt3080CommsPortServiceTSoIP,
        pt3080CommsPortServiceWeb,
        pt3080CommsPortServiceRIP,
        pt3080CommsPortCurrentIpAddr,
        pt3080CommsPortCurrentNetmask,
        pt3080CommsSNMPServicePort,
        pt3080CommsSNMPReadOnlyCommunity,
        pt3080CommsSNMPReadWriteCommunity,
        pt3080CommsSNMPTrapCommunity,
        pt3080CommsSNMPTrapDestination,
        pt3080CommsSNMPTrapDestination2,
        pt3080CommsSNMPTrapDestination3,
        pt3080CommsSNMPTrapDestination4,
        pt3080CommsSNMPTrapDestination5,
        pt3080CommsSNMPTrapDestinationPort,
        pt3080CommsSNMPTrapDestinationPort2,
        pt3080CommsSNMPTrapDestinationPort3,
        pt3080CommsSNMPTrapDestinationPort4,
        pt3080CommsSNMPTrapDestinationPort5,
        pt3080CommsStaticGateway,
        pt3080CommsCurrentGateway,
        pt3080CommsStaticHostname,
        pt3080CommsCurrentHostname,
        pt3080CommsStaticDNSDomain,
        pt3080CommsCurrentDNSDomain,
        pt3080CommsStaticDNS1ServerAddress,
        pt3080CommsStaticDNS2ServerAddress,
        pt3080CommsStaticDNS3ServerAddress,
        pt3080CommsCurrentDNS1ServerAddress,
        pt3080CommsCurrentDNS2ServerAddress,
        pt3080CommsCurrentDNS3ServerAddress,
        pt3080CommsStaticNtpServerAddress,
        pt3080CommsCurrentNtpServerAddress,
        pt3080CommsEmailServerAddress,
        pt3080CommsWebServicePort,
        pt3080CommsSCPIServicePort,
        pt3080CommsSCPIServerBaudrate,
        pt3080CommsSCPIUartInterface,
        pt3080CommsRipPort,
        pt3080CommsIGMPVersion,
        pt3080CommsIGMPQueryRobustnessCount,
        pt3080CommsIGMPv3UnsolicitedReportInterval,
        pt3080CommsIGMPv2UnsolicitedReportInterval,
        pt3080CommsAccessAllowed,
        pt3080CommsAccessAllowedTimeout,
        pt3080CommsAccessAllowedTimeLeft
      }
    STATUS   current
    DESCRIPTION
            "Data network communications group"
    ::= { pt3080Groups 17}

   pt3080DemodulatorGroup OBJECT-GROUP
      OBJECTS {
        pt3080DemodulatorFollowMode,
        pt3080Demodulator1Available,
        pt3080Demodulator2Available,
        pt3080Demodulator1FWVersion,
        pt3080Demodulator2FWVersion,
        pt3080Demodulator1OutputTS,
        pt3080Demodulator2OutputTS,
        pt3080Demodulator1MerLimit,
        pt3080Demodulator2MerLimit,
        pt3080Demodulator1PreVirterbiErrorRateLimit,
        pt3080Demodulator2PreVirterbiErrorRateLimit,
        pt3080Demodulator1PostVirterbiErrorRateLimit,
        pt3080Demodulator2PostVirterbiErrorRateLimit,
        pt3080Demodulator1FelStatus,
        pt3080Demodulator2FelStatus,
        pt3080Demodulator1UncorrectedPackets,
        pt3080Demodulator2UncorrectedPackets,
        pt3080Demodulator1Mer,
        pt3080Demodulator2Mer,
        pt3080Demodulator1PreVirterbiErrorRate,
        pt3080Demodulator2PreVirterbiErrorRate,
        pt3080Demodulator1PostVirterbiErrorRate,
        pt3080Demodulator2PostVirterbiErrorRate,
        pt3080Demodulator1ActualGuardInterval,
        pt3080Demodulator2ActualGuardInterval,
        pt3080Demodulator1Actualifft,
        pt3080Demodulator2Actualifft,
        pt3080Demodulator1ActualConstellation,
        pt3080Demodulator2ActualConstellation,
        pt3080Demodulator1ActualHierarchy,
        pt3080Demodulator2ActualHierarchy,
        pt3080Demodulator1ActualCodeRateHighPrio,
        pt3080Demodulator2ActualCodeRateHighPrio,
        pt3080Demodulator1ActualCodeRateLowPrio,
        pt3080Demodulator2ActualCodeRateLowPrio,
        pt3080Demodulator1ActualDeepInterleaver,
        pt3080Demodulator2ActualDeepInterleaver,
        pt3080Demodulator1ActualMpeFecHighPrio,
        pt3080Demodulator2ActualMpeFecHighPrio,
        pt3080Demodulator1ActualMpeFecLowPrio,
        pt3080Demodulator2ActualMpeFecLowPrio,
        pt3080Demodulator1ActualTimeSlicingHighPrio,
        pt3080Demodulator2ActualTimeSlicingHighPrio,
        pt3080Demodulator1ActualTimeSlicingLowPrio,
        pt3080Demodulator2ActualTimeSlicingLowPrio,
        pt3080Demodulator1ActualCellID,
        pt3080Demodulator2ActualCellID,
        pt3080Demodulator1ActualDVBHMode,
        pt3080Demodulator2ActualDVBHMode
      }
    STATUS   current
    DESCRIPTION
            "Demodulator group"
    ::= { pt3080Groups 24}

   pt3080PrecorrectorGroup OBJECT-GROUP
      OBJECTS {
                pt3080PrecorrectorLastTurnAroundTime,
                pt3080PrecorrectorSecondsSinceLastUpdate,
                pt3080PrecorrectorLinCleanrun,
                pt3080PrecorrectorNlinCleanrun,
                pt3080PrecorrectorLinearLoadNeutral,
                pt3080PrecorrectorLinearLoadFactory,
                pt3080PrecorrectorLinearUpdateFactoryCurve,
                pt3080PrecorrectorNonlinearLoadNeutral,
                pt3080PrecorrectorNonlinearLoadFactory,
                pt3080PrecorrectorNonlinearUpdateFactoryCurve,
        pt3080PrecorrectorLinearAdaptive,
        pt3080PrecorrectorLinearMode,
        pt3080PrecorrectorLinearSenseEnable,
        pt3080PrecorrectorLinearMonitorStatus,
        pt3080PrecorrectorLinearMonitorSenseLevel,
        pt3080PrecorrectorLinearMonitorSenseValid,
        pt3080PrecorrectorLinearMonitorSenseBadCount,
        pt3080PrecorrectorLinearMonitorAmplitudeRipple,
        pt3080PrecorrectorLinearMonitorAmplitudeRippleValid,
        pt3080PrecorrectorLinearMonitorGroupDelay,
        pt3080PrecorrectorLinearMonitorGroupDelayValid,
        pt3080PrecorrectorLinearMonitorDiscartedIterations,
        pt3080PrecorrectorLinearMonitorIterations,
        pt3080PrecorrectorLinearAdaptiveMode,
        pt3080PrecorrectorLinearAdaptiveAmplitudeRippleTargetLevel,
        pt3080PrecorrectorLinearAdaptiveAmplitudeRippleTargetHysteresis,
        pt3080PrecorrectorLinearAdaptiveAmplitudeRippleEnable,
        pt3080PrecorrectorLinearAdaptiveGroupDelayTargetLevel,
        pt3080PrecorrectorLinearAdaptiveGroupDelayTargetHysteresis,
        pt3080PrecorrectorLinearAdaptiveGroupDelayEnable,
        pt3080PrecorrectorLinearAttenuation,
        pt3080PrecorrectorNonlinearAdaptive,
        pt3080PrecorrectorNonlinearMode,
        pt3080PrecorrectorNonlinearSenseEnable,
        pt3080PrecorrectorNonlinearMonitorStatus,
        pt3080PrecorrectorNonlinearMonitorSenseLevel,
        pt3080PrecorrectorNonlinearMonitorSenseValid,
        pt3080PrecorrectorNonlinearMonitorSenseBadCount,
        pt3080PrecorrectorNonlinearMonitorLowerShoulderLevel,
        pt3080PrecorrectorNonlinearMonitorLowerShoulderValid,
        pt3080PrecorrectorNonlinearMonitorUpperShoulderLevel,
        pt3080PrecorrectorNonlinearMonitorUpperShoulderValid,
        pt3080PrecorrectorNonlinearMonitorDiscartedIterations,
        pt3080PrecorrectorNonlinearMonitorIterations,
        pt3080PrecorrectorNonlinearMonitorMer,
        pt3080PrecorrectorNonlinearMonitorMerValid,
        pt3080PrecorrectorNonlinearMonitorPapr,
        pt3080PrecorrectorNonlinearMonitorPaprValid,
        pt3080PrecorrectorNonlinearAttenuation,
        pt3080PrecorrectorNonlinearAdaptiveMode,
        pt3080PrecorrectorNonlinearAdaptiveAveraging,
        pt3080PrecorrectorNonlinearAdaptiveMaxRfPaprEnable,
        pt3080PrecorrectorNonlinearAdaptiveMaxRfPaprLimit,
        pt3080PrecorrectorNonlinearAdaptiveMerTarget,
        pt3080PrecorrectorNonlinearAdaptiveMerTargetHysteresis,
        pt3080PrecorrectorNonlinearAdaptiveMerEnable,
        pt3080PrecorrectorNonlinearAdaptiveLowerShoulderTargetLevel,
        pt3080PrecorrectorNonlinearAdaptiveLowerShoulderTargetHysteresis,
        pt3080PrecorrectorNonlinearAdaptiveLowerShoulderEnable,
        pt3080PrecorrectorNonlinearAdaptiveUpperShoulderTargetLevel,
        pt3080PrecorrectorNonlinearAdaptiveUpperShoulderTargetHysteresis,
        pt3080PrecorrectorNonlinearAdaptiveUpperShoulderEnable,
        pt3080PrecorrectorPaprClipping,
        pt3080PrecorrectorPaprShaping,
        pt3080PrecorrectorClipperMode,
        pt3080PrecorrectorClipperAdaptive,
        pt3080PrecorrectorClipperEnable,
        pt3080PrecorrectorClipperAdaptiveMode,
        pt3080PrecorrectorClipperAdaptiveShaping,
        pt3080PrecorrectorClipperMonitorStatus,
        pt3080PrecorrectorClipperMonitorShoulderLevelLower,
        pt3080PrecorrectorClipperMonitorShoulderLevelLowerValid,
        pt3080PrecorrectorClipperMonitorShoulderLevelUpper,
        pt3080PrecorrectorClipperMonitorShoulderLevelUpperValid,
        pt3080PrecorrectorClipperMonitorMer,
        pt3080PrecorrectorClipperMonitorMerValid,
        pt3080PrecorrectorClipperMonitorPapr,
        pt3080PrecorrectorClipperMonitorPaprValid,
        pt3080PrecorrectorClipperMonitorIterations
      }
    STATUS   current
    DESCRIPTION
            "Precorrector group"
    ::= { pt3080Groups 25}

   pt3080ReceptionGroup OBJECT-GROUP
      OBJECTS {
        pt3080ReceptionGainControl,
        pt3080ReceptionGainManualValue,
        pt3080ReceptionGainLimitEnable,
        pt3080ReceptionGainLimit,
        pt3080ReceptionGainCurrent,
        pt3080ReceptionAGCMode,
        pt3080ReceptionAGCHysteresis,
        pt3080ReceptionBandwidth,
        pt3080ReceptionRFFrequency,
        pt3080ReceptionRFFrequencyOffset,
        pt3080ReceptionRFPolarity,
        pt3080ReceptionRFSquelchEnable,
        pt3080ReceptionRFSquelchThreshold,
        pt3080ReceptionRFSquelchHysteresis,
        pt3080ReceptionRFTrackingFilterEnable,
        pt3080ReceptionRFifLevel,
        pt3080ReceptionRFNominalInputLevel,
        pt3080ReceptionRFInputLevel,
        pt3080ReceptionRFInputLevelThreshold,
        pt3080ReceptionRFInputLevelHysteresis,
        pt3080ReceptionIFFrequency,
        pt3080ReceptionIFPolarity,
        pt3080ReceptionIFInputLevel,
        pt3080ReceptionIFInputPolicy,
        pt3080ReceptionIFInput,
        pt3080ReceptionIFRFtoIFHoldoverDelay,
        pt3080ReceptionIFIFtoRFHoldoverDelay,
        pt3080ReceptionTunerHWVersion,
        pt3080ReceptionTunerHWType,
        pt3080ReceptionTunerHWID,
        pt3080ReceptionTunerHWSerialNumber,
        pt3080ReceptionTunerHWCalibrationDate,
        pt3080ReceptionTunerHWCalibrationDataVersion,
        pt3080ReceptionTunerHWCalibrationSWVersion
      }
    STATUS   current
    DESCRIPTION
            "Reception group"
    ::= { pt3080Groups 26}

   pt3080BackplaneGroup OBJECT-GROUP
      OBJECTS {
        pt3080BackplanePolarityHardMute,
        pt3080BackplanePolarityRFFail
      }
    STATUS   current
    DESCRIPTION
            "Backplane group"
    ::= { pt3080Groups 27}


   pt3080ASIGroup OBJECT-GROUP
      OBJECTS {
        pt3080ASIInput1SyncTimeout,
        pt3080ASIInput2SyncTimeout,
        pt3080ASIInput1DataErrorLimit,
        pt3080ASIInput2DataErrorLimit,
        pt3080ASIInput1SyncStatus,
        pt3080ASIInput2SyncStatus,
        pt3080ASIInput1SyncSignal,
        pt3080ASIInput2SyncSignal,
        pt3080ASIInput1SyncTSSize,
        pt3080ASIInput2SyncTSSize,
        pt3080ASIInput1LineErrors,
        pt3080ASIInput2LineErrors,
        pt3080ASIInput1LineRate,
        pt3080ASIInput2LineRate,
        pt3080ASIInput1LineErrorRate,
        pt3080ASIInput2LineErrorRate,
        pt3080ASIInput1DataErrors,
        pt3080ASIInput2DataErrors,
        pt3080ASIInput1DataRate,
        pt3080ASIInput2DataRate,
        pt3080ASIInput1DataErrorRate,
        pt3080ASIInput2DataErrorRate,
        pt3080ASIInput1ClearErrorCounters,
        pt3080ASIInput2ClearErrorCounters
      }
    STATUS   current
    DESCRIPTION
            "ASI media group"
    ::= { pt3080Groups 30}

   pt3080NotifsGroup OBJECT-GROUP
      OBJECTS {
        pt3080NotifMessage, pt3080NotifState, pt3080NotifLocalTime
      }
    STATUS   current
    DESCRIPTION
            "Notification objects group"
    ::= { pt3080Groups 64 }

--
-- Agent Capability
--
pt3080Agent AGENT-CAPABILITIES
  PRODUCT-RELEASE  "SWPROTELEVISION_P3_1_02_157 build 1441106393"
  STATUS           current
  DESCRIPTION      "PT2080 DVB-T/H Modulator agent"
  SUPPORTS         PT2080-MIB
    INCLUDES       {
                     pt3080SystemGroup,
                     pt3080ModeGroup,
                     pt3080GpsGroup,
                     pt3080ChannelFilterGroup,
                     pt3080TSoIPGroup,
                     pt3080MonitorGroup,
                     pt3080TestGroup,
                     pt3080AlarmGroup,
                     pt3080PresetGroup,
                     pt3080EventlogGroup,
                     pt3080CommsGroup,
                     pt3080DemodulatorGroup,
                     pt3080BackplaneGroup,
                     pt3080ReceptionGroup,
                     pt3080ASIGroup
                   }
::= { pt3080Conformance 3 }


--
-- System Notifications (aka Traps)
--
pt3080NotificationsGroups OBJECT IDENTIFIER ::= { pt3080Conformance 4 }

pt3080NotifModulatorAlarm NOTIFICATION-TYPE
    OBJECTS { pt3080NotifMessage, pt3080NotifState, pt3080NotifLocalTime }
    STATUS current
    DESCRIPTION
        "Modulator Alarms"
  ::= { pt3080Notif 3 }

pt3080NotifTSPrimaryAlarm NOTIFICATION-TYPE
    OBJECTS { pt3080NotifMessage, pt3080NotifState, pt3080NotifLocalTime }
    STATUS current
    DESCRIPTION
        "ASI TS Primary Alarms"
  ::= { pt3080Notif 5 }

pt3080NotifTSSecondaryAlarm NOTIFICATION-TYPE
    OBJECTS { pt3080NotifMessage, pt3080NotifState, pt3080NotifLocalTime }
    STATUS current
    DESCRIPTION
        "ASI TS Secondary Alarms"
  ::= { pt3080Notif 6 }

pt3080NotifSFNAlarm NOTIFICATION-TYPE
    OBJECTS { pt3080NotifMessage, pt3080NotifState, pt3080NotifLocalTime }
    STATUS current
    DESCRIPTION
        "SFN Alarms"
  ::= { pt3080Notif 7 }

pt3080NotifRefenceClockAlarm NOTIFICATION-TYPE
    OBJECTS { pt3080NotifMessage, pt3080NotifState, pt3080NotifLocalTime }
    STATUS current
    DESCRIPTION
        "Reference Alarms"
  ::= { pt3080Notif 8 }

pt3080NotifRFAlarm NOTIFICATION-TYPE
    OBJECTS { pt3080NotifMessage, pt3080NotifState, pt3080NotifLocalTime }
    STATUS current
    DESCRIPTION
        "RF Alarms"
  ::= { pt3080Notif 9 }

pt3080NotifGNSSAlarm NOTIFICATION-TYPE
    OBJECTS { pt3080NotifMessage, pt3080NotifState, pt3080NotifLocalTime }
    STATUS current
    DESCRIPTION
        "GNSS Alarms"
  ::= { pt3080Notif 10 }

pt3080NotifTSoIPAlarm NOTIFICATION-TYPE
    OBJECTS { pt3080NotifMessage, pt3080NotifState, pt3080NotifLocalTime }
    STATUS current
    DESCRIPTION
        "TSoIP Alarms"
  ::= { pt3080Notif 12 }

pt3080NotifExternalAlarm NOTIFICATION-TYPE
    OBJECTS { pt3080NotifMessage, pt3080NotifState, pt3080NotifLocalTime }
    STATUS current
    DESCRIPTION
        "External Alarms"
  ::= { pt3080Notif 13 }

pt3080NotifHWMonitorAlarm NOTIFICATION-TYPE
    OBJECTS { pt3080NotifMessage, pt3080NotifState, pt3080NotifLocalTime }
    STATUS current
    DESCRIPTION
        "HW Monitor Alarms"
  ::= { pt3080Notif 14 }

pt3080NotifCommAlarm NOTIFICATION-TYPE
    OBJECTS { pt3080NotifMessage, pt3080NotifState, pt3080NotifLocalTime }
    STATUS current
    DESCRIPTION
        "Communications Alarms"
  ::= { pt3080Notif 15 }

pt3080NotifASIAlarm NOTIFICATION-TYPE
    OBJECTS { pt3080NotifMessage, pt3080NotifState, pt3080NotifLocalTime }
    STATUS current
    DESCRIPTION
        "ASI Alarms"
  ::= { pt3080Notif 16 }

pt3080NotifInternalAlarm NOTIFICATION-TYPE
    OBJECTS { pt3080NotifMessage, pt3080NotifState, pt3080NotifLocalTime }
    STATUS current
    DESCRIPTION
        "Internal Alarms"
  ::= { pt3080Notif 18 }

pt3080NotifTSPrimarySyncLossAlarm NOTIFICATION-TYPE
    OBJECTS { pt3080NotifMessage, pt3080NotifState, pt3080NotifLocalTime }
    STATUS current
    DESCRIPTION
        "TS Primary Sync Loss"
  ::= { pt3080Notif 21 }

pt3080NotifTSPrimarySyncErrorAlarm NOTIFICATION-TYPE
    OBJECTS { pt3080NotifMessage, pt3080NotifState, pt3080NotifLocalTime }
    STATUS current
    DESCRIPTION
        "TS Primary Sync Error"
  ::= { pt3080Notif 22 }

pt3080NotifTSPrimaryPCRErrorAlarm NOTIFICATION-TYPE
    OBJECTS { pt3080NotifMessage, pt3080NotifState, pt3080NotifLocalTime }
    STATUS current
    DESCRIPTION
        "TS Primary PCR Error"
  ::= { pt3080Notif 23 }

pt3080NotifTSPrimaryPATLossAlarm NOTIFICATION-TYPE
    OBJECTS { pt3080NotifMessage, pt3080NotifState, pt3080NotifLocalTime }
    STATUS current
    DESCRIPTION
        "TS Primary PAT Loss"
  ::= { pt3080Notif 24 }

pt3080NotifTSPrimaryTSIDWrongAlarm NOTIFICATION-TYPE
    OBJECTS { pt3080NotifMessage, pt3080NotifState, pt3080NotifLocalTime }
    STATUS current
    DESCRIPTION
        "TS Primary Transport Stream ID"
  ::= { pt3080Notif 25 }

pt3080NotifTSPrimaryNWIDWrongAlarm NOTIFICATION-TYPE
    OBJECTS { pt3080NotifMessage, pt3080NotifState, pt3080NotifLocalTime }
    STATUS current
    DESCRIPTION
        "TS Primary Network ID"
  ::= { pt3080Notif 26 }

pt3080NotifTSPrimaryStuffingRateExceededAlarm NOTIFICATION-TYPE
    OBJECTS { pt3080NotifMessage, pt3080NotifState, pt3080NotifLocalTime }
    STATUS current
    DESCRIPTION
        "TS Primary Stuffing Rate"
  ::= { pt3080Notif 27 }

pt3080NotifTSPrimaryBufferPoolExceededAlarm NOTIFICATION-TYPE
    OBJECTS { pt3080NotifMessage, pt3080NotifState, pt3080NotifLocalTime }
    STATUS current
    DESCRIPTION
        "TS Primary Buffer Pool"
  ::= { pt3080Notif 28 }

pt3080NotifTSPrimarySTSJitterExceededAlarm NOTIFICATION-TYPE
    OBJECTS { pt3080NotifMessage, pt3080NotifState, pt3080NotifLocalTime }
    STATUS current
    DESCRIPTION
        "TS Primary STS Jitter"
  ::= { pt3080Notif 29 }

pt3080NotifTSPrimaryMIPDataMissingAlarm NOTIFICATION-TYPE
    OBJECTS { pt3080NotifMessage, pt3080NotifState, pt3080NotifLocalTime }
    STATUS current
    DESCRIPTION
        "TS Primary MIP Data Missing"
  ::= { pt3080Notif 30 }

pt3080NotifTSPrimaryMIPPriorityBadAlarm NOTIFICATION-TYPE
    OBJECTS { pt3080NotifMessage, pt3080NotifState, pt3080NotifLocalTime }
    STATUS current
    DESCRIPTION
        "TS Primary Bad Priority in MIP"
  ::= { pt3080Notif 31 }

pt3080NotifTSSecondarySyncLossAlarm NOTIFICATION-TYPE
    OBJECTS { pt3080NotifMessage, pt3080NotifState, pt3080NotifLocalTime }
    STATUS current
    DESCRIPTION
        "TS Secondary Sync Loss"
  ::= { pt3080Notif 32 }

pt3080NotifTSSecondarySyncErrorAlarm NOTIFICATION-TYPE
    OBJECTS { pt3080NotifMessage, pt3080NotifState, pt3080NotifLocalTime }
    STATUS current
    DESCRIPTION
        "TS Secondary Sync Error"
  ::= { pt3080Notif 33 }

pt3080NotifTSSecondaryPCRErrorAlarm NOTIFICATION-TYPE
    OBJECTS { pt3080NotifMessage, pt3080NotifState, pt3080NotifLocalTime }
    STATUS current
    DESCRIPTION
        "TS Secondary PCR Error"
  ::= { pt3080Notif 34 }

pt3080NotifTSSecondaryPATLossAlarm NOTIFICATION-TYPE
    OBJECTS { pt3080NotifMessage, pt3080NotifState, pt3080NotifLocalTime }
    STATUS current
    DESCRIPTION
        "TS Secondary PAT Loss"
  ::= { pt3080Notif 35 }

pt3080NotifTSSecondaryTSIDWrongAlarm NOTIFICATION-TYPE
    OBJECTS { pt3080NotifMessage, pt3080NotifState, pt3080NotifLocalTime }
    STATUS current
    DESCRIPTION
        "TS Secondary Transport Stream ID"
  ::= { pt3080Notif 36 }

pt3080NotifTSSecondaryNWIDWrongAlarm NOTIFICATION-TYPE
    OBJECTS { pt3080NotifMessage, pt3080NotifState, pt3080NotifLocalTime }
    STATUS current
    DESCRIPTION
        "TS Secondary Network ID"
  ::= { pt3080Notif 37 }

pt3080NotifTSSecondaryStuffingRateExceededAlarm NOTIFICATION-TYPE
    OBJECTS { pt3080NotifMessage, pt3080NotifState, pt3080NotifLocalTime }
    STATUS current
    DESCRIPTION
        "TS Secondary Stuffing Rate"
  ::= { pt3080Notif 38 }

pt3080NotifTSSecondaryBufferPoolExceededAlarm NOTIFICATION-TYPE
    OBJECTS { pt3080NotifMessage, pt3080NotifState, pt3080NotifLocalTime }
    STATUS current
    DESCRIPTION
        "TS Secondary Buffer Pool"
  ::= { pt3080Notif 39 }

pt3080NotifTSSecondarySTSJitterExceededAlarm NOTIFICATION-TYPE
    OBJECTS { pt3080NotifMessage, pt3080NotifState, pt3080NotifLocalTime }
    STATUS current
    DESCRIPTION
        "TS Secondary STS Jitter"
  ::= { pt3080Notif 40 }

pt3080NotifTSSecondaryMIPDataMissingAlarm NOTIFICATION-TYPE
    OBJECTS { pt3080NotifMessage, pt3080NotifState, pt3080NotifLocalTime }
    STATUS current
    DESCRIPTION
        "TS Secondary MIP Data Missing"
  ::= { pt3080Notif 41 }

pt3080NotifTSSecondaryMIPPriorityBadAlarm NOTIFICATION-TYPE
    OBJECTS { pt3080NotifMessage, pt3080NotifState, pt3080NotifLocalTime }
    STATUS current
    DESCRIPTION
        "TS Secondary Bad Priority in MIP"
  ::= { pt3080Notif 42 }

pt3080NotifRFOverloadProtectionAlarm NOTIFICATION-TYPE
    OBJECTS { pt3080NotifMessage, pt3080NotifState, pt3080NotifLocalTime }
    STATUS current
    DESCRIPTION
        "Overload Protection"
  ::= { pt3080Notif 44 }

pt3080NotifCommeth0Alarm NOTIFICATION-TYPE
    OBJECTS { pt3080NotifMessage, pt3080NotifState, pt3080NotifLocalTime }
    STATUS current
    DESCRIPTION
        "ETH0 Conn. State"
  ::= { pt3080Notif 55 }

pt3080NotifCommeth1Alarm NOTIFICATION-TYPE
    OBJECTS { pt3080NotifMessage, pt3080NotifState, pt3080NotifLocalTime }
    STATUS current
    DESCRIPTION
        "ETH1 Conn. State"
  ::= { pt3080Notif 56 }

pt3080NotifCommeth2Alarm NOTIFICATION-TYPE
    OBJECTS { pt3080NotifMessage, pt3080NotifState, pt3080NotifLocalTime }
    STATUS current
    DESCRIPTION
        "ETH2 Conn. State"
  ::= { pt3080Notif 57 }

pt3080NotifCommeth3Alarm NOTIFICATION-TYPE
    OBJECTS { pt3080NotifMessage, pt3080NotifState, pt3080NotifLocalTime }
    STATUS current
    DESCRIPTION
        "ETH3 Conn. State"
  ::= { pt3080Notif 58 }

pt3080NotifCommeth4Alarm NOTIFICATION-TYPE
    OBJECTS { pt3080NotifMessage, pt3080NotifState, pt3080NotifLocalTime }
    STATUS current
    DESCRIPTION
        "ETH4 Conn. State"
  ::= { pt3080Notif 59 }

pt3080NotifExternalInput1Alarm NOTIFICATION-TYPE
    OBJECTS { pt3080NotifMessage, pt3080NotifState, pt3080NotifLocalTime }
    STATUS current
    DESCRIPTION
        "Alarm Input 1"
  ::= { pt3080Notif 72 }

pt3080NotifExternalInput2Alarm NOTIFICATION-TYPE
    OBJECTS { pt3080NotifMessage, pt3080NotifState, pt3080NotifLocalTime }
    STATUS current
    DESCRIPTION
        "Alarm Input 2"
  ::= { pt3080Notif 73 }

pt3080NotifExternalInput3Alarm NOTIFICATION-TYPE
    OBJECTS { pt3080NotifMessage, pt3080NotifState, pt3080NotifLocalTime }
    STATUS current
    DESCRIPTION
        "Alarm Input 3"
  ::= { pt3080Notif 74 }

pt3080NotifExternalInput4Alarm NOTIFICATION-TYPE
    OBJECTS { pt3080NotifMessage, pt3080NotifState, pt3080NotifLocalTime }
    STATUS current
    DESCRIPTION
        "Alarm Input 4"
  ::= { pt3080Notif 75 }

pt3080NotifRefenceClockExtern1PPSLossAlarm NOTIFICATION-TYPE
    OBJECTS { pt3080NotifMessage, pt3080NotifState, pt3080NotifLocalTime }
    STATUS current
    DESCRIPTION
        "Ext. 1PPS Loss"
  ::= { pt3080Notif 76 }

pt3080NotifRefenceClockIntern1PPSLossAlarm NOTIFICATION-TYPE
    OBJECTS { pt3080NotifMessage, pt3080NotifState, pt3080NotifLocalTime }
    STATUS current
    DESCRIPTION
        "Int. 10MHz Loss"
  ::= { pt3080Notif 77 }

pt3080NotifRefenceClockExtern10MHzLossAlarm NOTIFICATION-TYPE
    OBJECTS { pt3080NotifMessage, pt3080NotifState, pt3080NotifLocalTime }
    STATUS current
    DESCRIPTION
        "Ext. 10MHz Loss"
  ::= { pt3080Notif 78 }

pt3080NotifRFAlcRangeAlarm NOTIFICATION-TYPE
    OBJECTS { pt3080NotifMessage, pt3080NotifState, pt3080NotifLocalTime }
    STATUS current
    DESCRIPTION
        "ALC Range"
  ::= { pt3080Notif 79 }

pt3080NotifSFNResyncAlarm NOTIFICATION-TYPE
    OBJECTS { pt3080NotifMessage, pt3080NotifState, pt3080NotifLocalTime }
    STATUS current
    DESCRIPTION
        "SFN Resync Error"
  ::= { pt3080Notif 80 }

pt3080NotifSFNTSPrimaryMaxDelayOffsetExceededAlarm NOTIFICATION-TYPE
    OBJECTS { pt3080NotifMessage, pt3080NotifState, pt3080NotifLocalTime }
    STATUS current
    DESCRIPTION
        "Primary SFN Max Delay + Offset OOR"
  ::= { pt3080Notif 81 }

pt3080NotifSFNTSPrimaryNetworkDelayExceededAlarm NOTIFICATION-TYPE
    OBJECTS { pt3080NotifMessage, pt3080NotifState, pt3080NotifLocalTime }
    STATUS current
    DESCRIPTION
        "Primary SFN NW Delay Greater Than Max"
  ::= { pt3080Notif 82 }

pt3080NotifSFNTSSecondaryMaxDelayOffsetExceededAlarm NOTIFICATION-TYPE
    OBJECTS { pt3080NotifMessage, pt3080NotifState, pt3080NotifLocalTime }
    STATUS current
    DESCRIPTION
        "Secondary SFN Max. Delay + Offset OOR"
  ::= { pt3080Notif 84 }

pt3080NotifSFNTSSecondaryNetworkDelayExceededAlarm NOTIFICATION-TYPE
    OBJECTS { pt3080NotifMessage, pt3080NotifState, pt3080NotifLocalTime }
    STATUS current
    DESCRIPTION
        "Secondary SFN NW Delay Greater Than Max"
  ::= { pt3080Notif 85 }

pt3080NotifRFLevelOutOfRangeAlarm NOTIFICATION-TYPE
    OBJECTS { pt3080NotifMessage, pt3080NotifState, pt3080NotifLocalTime }
    STATUS current
    DESCRIPTION
        "RF Level Out of Range"
  ::= { pt3080Notif 87 }

pt3080NotifRefenceClockNTPSyncLossAlarm NOTIFICATION-TYPE
    OBJECTS { pt3080NotifMessage, pt3080NotifState, pt3080NotifLocalTime }
    STATUS current
    DESCRIPTION
        "NTP Sync Loss"
  ::= { pt3080Notif 89 }

pt3080NotifSFNTSPrimarySeamlessDelayTooSmallAlarm NOTIFICATION-TYPE
    OBJECTS { pt3080NotifMessage, pt3080NotifState, pt3080NotifLocalTime }
    STATUS current
    DESCRIPTION
        "Primary Delay Margin too Small for Seamless and Holdover"
  ::= { pt3080Notif 92 }

pt3080NotifSFNTSPrimaryMIPConfigErrorAlarm NOTIFICATION-TYPE
    OBJECTS { pt3080NotifMessage, pt3080NotifState, pt3080NotifLocalTime }
    STATUS current
    DESCRIPTION
        "Primary SFN and MIP Config Differ"
  ::= { pt3080Notif 93 }

pt3080NotifSFNTSSecondarySeamlessDelayTooSmallAlarm NOTIFICATION-TYPE
    OBJECTS { pt3080NotifMessage, pt3080NotifState, pt3080NotifLocalTime }
    STATUS current
    DESCRIPTION
        "Secondary Delay Margin too Small for Seamless and Holdover"
  ::= { pt3080Notif 94 }

pt3080NotifSFNTSSecondaryMIPConfigErrorAlarm NOTIFICATION-TYPE
    OBJECTS { pt3080NotifMessage, pt3080NotifState, pt3080NotifLocalTime }
    STATUS current
    DESCRIPTION
        "Secondary SFN and MIP Config Differ"
  ::= { pt3080Notif 95 }

pt3080NotifGNSSUnlockedAlarm NOTIFICATION-TYPE
    OBJECTS { pt3080NotifMessage, pt3080NotifState, pt3080NotifLocalTime }
    STATUS current
    DESCRIPTION
        "GNSS Unlocked"
  ::= { pt3080Notif 98 }

pt3080NotifGNSSAntennaFaultAlarm NOTIFICATION-TYPE
    OBJECTS { pt3080NotifMessage, pt3080NotifState, pt3080NotifLocalTime }
    STATUS current
    DESCRIPTION
        "GNSS Antenna Fault"
  ::= { pt3080Notif 107 }

pt3080NotifGNSSHoldOverAlarm NOTIFICATION-TYPE
    OBJECTS { pt3080NotifMessage, pt3080NotifState, pt3080NotifLocalTime }
    STATUS current
    DESCRIPTION
        "GNSS Holdover"
  ::= { pt3080Notif 108 }

pt3080NotifRefenceClockExternal10MHzHoldOverAlarm NOTIFICATION-TYPE
    OBJECTS { pt3080NotifMessage, pt3080NotifState, pt3080NotifLocalTime }
    STATUS current
    DESCRIPTION
        "Ext. 10MHz Ref Holdover"
  ::= { pt3080Notif 109 }

pt3080NotifRefenceClockExternal1PPSHoldOverAlarm NOTIFICATION-TYPE
    OBJECTS { pt3080NotifMessage, pt3080NotifState, pt3080NotifLocalTime }
    STATUS current
    DESCRIPTION
        "Ext. 1PPS Ref Holdover"
  ::= { pt3080Notif 110 }

pt3080NotifASIASI1ErrorRateEceeededAlarm NOTIFICATION-TYPE
    OBJECTS { pt3080NotifMessage, pt3080NotifState, pt3080NotifLocalTime }
    STATUS current
    DESCRIPTION
        "ASI-IN1 Error Rate"
  ::= { pt3080Notif 113 }

pt3080NotifASIASI2ErrorRateEceeededAlarm NOTIFICATION-TYPE
    OBJECTS { pt3080NotifMessage, pt3080NotifState, pt3080NotifLocalTime }
    STATUS current
    DESCRIPTION
        "ASI-IN2 Error Rate"
  ::= { pt3080Notif 114 }

pt3080NotifTSoIPRx1PackageErrorRationExceededAlarm NOTIFICATION-TYPE
    OBJECTS { pt3080NotifMessage, pt3080NotifState, pt3080NotifLocalTime }
    STATUS current
    DESCRIPTION
        "TSoIP RX1 Package Error Ratio Exceeded"
  ::= { pt3080Notif 115 }

pt3080NotifTSoIPRx2PackageErrorRationExceededAlarm NOTIFICATION-TYPE
    OBJECTS { pt3080NotifMessage, pt3080NotifState, pt3080NotifLocalTime }
    STATUS current
    DESCRIPTION
        "TSoIP RX2 Package Error Ratio Exceeded"
  ::= { pt3080Notif 117 }

pt3080NotifTSoIPRx1SyncLossAlarm NOTIFICATION-TYPE
    OBJECTS { pt3080NotifMessage, pt3080NotifState, pt3080NotifLocalTime }
    STATUS current
    DESCRIPTION
        "TSoIP RX1 Signal Loss"
  ::= { pt3080Notif 119 }

pt3080NotifTSoIPRx2SyncLossAlarm NOTIFICATION-TYPE
    OBJECTS { pt3080NotifMessage, pt3080NotifState, pt3080NotifLocalTime }
    STATUS current
    DESCRIPTION
        "TSoIP RX2 Signal Loss"
  ::= { pt3080Notif 121 }

pt3080NotifInternalBackplaneAlarm NOTIFICATION-TYPE
    OBJECTS { pt3080NotifMessage, pt3080NotifState, pt3080NotifLocalTime }
    STATUS current
    DESCRIPTION
        "Backplane Status"
  ::= { pt3080Notif 129 }

pt3080NotifInternalReferenceClockAlarm NOTIFICATION-TYPE
    OBJECTS { pt3080NotifMessage, pt3080NotifState, pt3080NotifLocalTime }
    STATUS current
    DESCRIPTION
        "Reference Status"
  ::= { pt3080Notif 132 }

pt3080NotifInternalUpConverterAlarm NOTIFICATION-TYPE
    OBJECTS { pt3080NotifMessage, pt3080NotifState, pt3080NotifLocalTime }
    STATUS current
    DESCRIPTION
        "Upconverter Status"
  ::= { pt3080Notif 134 }

pt3080NotifInternalDownConverterAlarm NOTIFICATION-TYPE
    OBJECTS { pt3080NotifMessage, pt3080NotifState, pt3080NotifLocalTime }
    STATUS current
    DESCRIPTION
        "Downconverter Status"
  ::= { pt3080Notif 135 }

pt3080NotifInternalMainboardAlarm NOTIFICATION-TYPE
    OBJECTS { pt3080NotifMessage, pt3080NotifState, pt3080NotifLocalTime }
    STATUS current
    DESCRIPTION
        "Main board Status"
  ::= { pt3080Notif 136 }

pt3080NotifInternalBatteryAlarm NOTIFICATION-TYPE
    OBJECTS { pt3080NotifMessage, pt3080NotifState, pt3080NotifLocalTime }
    STATUS current
    DESCRIPTION
        "Main Board Battery"
  ::= { pt3080Notif 137 }

pt3080NotifInternalFirmware1Alarm NOTIFICATION-TYPE
    OBJECTS { pt3080NotifMessage, pt3080NotifState, pt3080NotifLocalTime }
    STATUS current
    DESCRIPTION
        "Firmware 1 Status"
  ::= { pt3080Notif 139 }

pt3080NotifInternalGNSSAlarm NOTIFICATION-TYPE
    OBJECTS { pt3080NotifMessage, pt3080NotifState, pt3080NotifLocalTime }
    STATUS current
    DESCRIPTION
        "GNSS Status"
  ::= { pt3080Notif 142 }

pt3080NotifInternalSatelliteAlarm NOTIFICATION-TYPE
    OBJECTS { pt3080NotifMessage, pt3080NotifState, pt3080NotifLocalTime }
    STATUS current
    DESCRIPTION
        "Satrecv Status"
  ::= { pt3080Notif 143 }

pt3080NotifInternalEthAlarm NOTIFICATION-TYPE
    OBJECTS { pt3080NotifMessage, pt3080NotifState, pt3080NotifLocalTime }
    STATUS current
    DESCRIPTION
        "EtherNet Port Failure"
  ::= { pt3080Notif 146 }

pt3080NotifHWMonitorFPGAAlarm NOTIFICATION-TYPE
    OBJECTS { pt3080NotifMessage, pt3080NotifState, pt3080NotifLocalTime }
    STATUS current
    DESCRIPTION
        "Main Board FPGA Temperature"
  ::= { pt3080Notif 156 }

pt3080NotifHWMonitorMainBoardCPUTemperatureAlarm NOTIFICATION-TYPE
    OBJECTS { pt3080NotifMessage, pt3080NotifState, pt3080NotifLocalTime }
    STATUS current
    DESCRIPTION
        "Main Board CPU Temperature"
  ::= { pt3080Notif 157 }

pt3080NotifHWMonitorMainBoardTemperatureAlarm NOTIFICATION-TYPE
    OBJECTS { pt3080NotifMessage, pt3080NotifState, pt3080NotifLocalTime }
    STATUS current
    DESCRIPTION
        "Main Board Temperature"
  ::= { pt3080Notif 158 }

pt3080NotifHWMonitorLeftFanAlarm NOTIFICATION-TYPE
    OBJECTS { pt3080NotifMessage, pt3080NotifState, pt3080NotifLocalTime }
    STATUS current
    DESCRIPTION
        "Left Chassis Fan"
  ::= { pt3080Notif 159 }

pt3080NotifHWMonitorRightFan2Alarm NOTIFICATION-TYPE
    OBJECTS { pt3080NotifMessage, pt3080NotifState, pt3080NotifLocalTime }
    STATUS current
    DESCRIPTION
        "Right Chassis Fan"
  ::= { pt3080Notif 160 }

pt3080NotifHWMonitorBackplaneTemperatureAlarm NOTIFICATION-TYPE
    OBJECTS { pt3080NotifMessage, pt3080NotifState, pt3080NotifLocalTime }
    STATUS current
    DESCRIPTION
        "Backplane Temperature"
  ::= { pt3080Notif 162 }

pt3080NotifTSPrimaryInputTSHoldOverAlarm NOTIFICATION-TYPE
    OBJECTS { pt3080NotifMessage, pt3080NotifState, pt3080NotifLocalTime }
    STATUS current
    DESCRIPTION
        "Input TS Holdover"
  ::= { pt3080Notif 180 }

pt3080NotifInternalPLLUnlockedAlarm NOTIFICATION-TYPE
    OBJECTS { pt3080NotifMessage, pt3080NotifState, pt3080NotifLocalTime }
    STATUS current
    DESCRIPTION
        "PLL Out of Lock"
  ::= { pt3080Notif 182 }

pt3080NotifExternalInput5Alarm NOTIFICATION-TYPE
    OBJECTS { pt3080NotifMessage, pt3080NotifState, pt3080NotifLocalTime }
    STATUS current
    DESCRIPTION
        "Alarm Input 5"
  ::= { pt3080Notif 183 }

pt3080NotifSFNUntimedModeAlarm NOTIFICATION-TYPE
    OBJECTS { pt3080NotifMessage, pt3080NotifState, pt3080NotifLocalTime }
    STATUS current
    DESCRIPTION
        "SFN Mode Untimed"
  ::= { pt3080Notif 184 }

pt3080NotifSFNFreeRunningModeAlarm NOTIFICATION-TYPE
    OBJECTS { pt3080NotifMessage, pt3080NotifState, pt3080NotifLocalTime }
    STATUS current
    DESCRIPTION
        "SFN Mode Free Running"
  ::= { pt3080Notif 185 }

pt3080NotifExternalInput6Alarm NOTIFICATION-TYPE
    OBJECTS { pt3080NotifMessage, pt3080NotifState, pt3080NotifLocalTime }
    STATUS current
    DESCRIPTION
        "Alarm Input 6"
  ::= { pt3080Notif 186 }

pt3080NotifExternalInput7Alarm NOTIFICATION-TYPE
    OBJECTS { pt3080NotifMessage, pt3080NotifState, pt3080NotifLocalTime }
    STATUS current
    DESCRIPTION
        "Alarm Input 7"
  ::= { pt3080Notif 187 }

pt3080NotifExternalInput8Alarm NOTIFICATION-TYPE
    OBJECTS { pt3080NotifMessage, pt3080NotifState, pt3080NotifLocalTime }
    STATUS current
    DESCRIPTION
        "Alarm Input 8"
  ::= { pt3080Notif 188 }

pt3080NotifTSPrimaryDelayMarginAlarm NOTIFICATION-TYPE
    OBJECTS { pt3080NotifMessage, pt3080NotifState, pt3080NotifLocalTime }
    STATUS current
    DESCRIPTION
        "TS Primary Delay Margin"
  ::= { pt3080Notif 190 }

pt3080NotifTSSecondaryDelayMarginAlarm NOTIFICATION-TYPE
    OBJECTS { pt3080NotifMessage, pt3080NotifState, pt3080NotifLocalTime }
    STATUS current
    DESCRIPTION
        "TS Secondary Delay Margin"
  ::= { pt3080Notif 191 }

pt3080NotifGroupModulatorAlarm NOTIFICATION-GROUP
    NOTIFICATIONS {
        pt3080NotifModulatorAlarm
    }
    STATUS current
    DESCRIPTION
        "Modulator Alarms"
  ::= { pt3080NotificationsGroups 3 }

pt3080NotifGroupTSPrimaryAlarm NOTIFICATION-GROUP
    NOTIFICATIONS {
        pt3080NotifTSPrimaryAlarm,
        pt3080NotifTSPrimarySyncLossAlarm,
        pt3080NotifTSPrimarySyncErrorAlarm,
        pt3080NotifTSPrimaryPCRErrorAlarm,
        pt3080NotifTSPrimaryPATLossAlarm,
        pt3080NotifTSPrimaryTSIDWrongAlarm,
        pt3080NotifTSPrimaryNWIDWrongAlarm,
        pt3080NotifTSPrimaryStuffingRateExceededAlarm,
        pt3080NotifTSPrimaryBufferPoolExceededAlarm,
        pt3080NotifTSPrimarySTSJitterExceededAlarm,
        pt3080NotifTSPrimaryMIPDataMissingAlarm,
        pt3080NotifTSPrimaryMIPPriorityBadAlarm,
        pt3080NotifTSPrimaryInputTSHoldOverAlarm,
        pt3080NotifTSPrimaryDelayMarginAlarm
    }
    STATUS current
    DESCRIPTION
        "ASI TS Primary Alarms"
  ::= { pt3080NotificationsGroups 5 }

pt3080NotifGroupTSSecondaryAlarm NOTIFICATION-GROUP
    NOTIFICATIONS {
        pt3080NotifTSSecondaryAlarm,
        pt3080NotifTSSecondarySyncLossAlarm,
        pt3080NotifTSSecondarySyncErrorAlarm,
        pt3080NotifTSSecondaryPCRErrorAlarm,
        pt3080NotifTSSecondaryPATLossAlarm,
        pt3080NotifTSSecondaryTSIDWrongAlarm,
        pt3080NotifTSSecondaryNWIDWrongAlarm,
        pt3080NotifTSSecondaryStuffingRateExceededAlarm,
        pt3080NotifTSSecondaryBufferPoolExceededAlarm,
        pt3080NotifTSSecondarySTSJitterExceededAlarm,
        pt3080NotifTSSecondaryMIPDataMissingAlarm,
        pt3080NotifTSSecondaryMIPPriorityBadAlarm,
        pt3080NotifTSSecondaryDelayMarginAlarm
    }
    STATUS current
    DESCRIPTION
        "ASI TS Secondary Alarms"
  ::= { pt3080NotificationsGroups 6 }

pt3080NotifGroupSFNAlarm NOTIFICATION-GROUP
    NOTIFICATIONS {
        pt3080NotifSFNAlarm,
        pt3080NotifSFNResyncAlarm,
        pt3080NotifSFNTSPrimaryMaxDelayOffsetExceededAlarm,
        pt3080NotifSFNTSPrimaryNetworkDelayExceededAlarm,
        pt3080NotifSFNTSSecondaryMaxDelayOffsetExceededAlarm,
        pt3080NotifSFNTSSecondaryNetworkDelayExceededAlarm,
        pt3080NotifSFNTSPrimarySeamlessDelayTooSmallAlarm,
        pt3080NotifSFNTSPrimaryMIPConfigErrorAlarm,
        pt3080NotifSFNTSSecondarySeamlessDelayTooSmallAlarm,
        pt3080NotifSFNTSSecondaryMIPConfigErrorAlarm,
        pt3080NotifSFNUntimedModeAlarm,
        pt3080NotifSFNFreeRunningModeAlarm
    }
    STATUS current
    DESCRIPTION
        "SFN Alarms"
  ::= { pt3080NotificationsGroups 7 }

pt3080NotifGroupRefenceClockAlarm NOTIFICATION-GROUP
    NOTIFICATIONS {
        pt3080NotifRefenceClockAlarm,
        pt3080NotifRefenceClockExtern1PPSLossAlarm,
        pt3080NotifRefenceClockIntern1PPSLossAlarm,
        pt3080NotifRefenceClockExtern10MHzLossAlarm,
        pt3080NotifRefenceClockNTPSyncLossAlarm,
        pt3080NotifRefenceClockExternal10MHzHoldOverAlarm,
        pt3080NotifRefenceClockExternal1PPSHoldOverAlarm
    }
    STATUS current
    DESCRIPTION
        "Reference Alarms"
  ::= { pt3080NotificationsGroups 8 }

pt3080NotifGroupRFAlarm NOTIFICATION-GROUP
    NOTIFICATIONS {
        pt3080NotifRFAlarm,
        pt3080NotifRFOverloadProtectionAlarm,
        pt3080NotifRFAlcRangeAlarm,
        pt3080NotifRFLevelOutOfRangeAlarm
    }
    STATUS current
    DESCRIPTION
        "RF Alarms"
  ::= { pt3080NotificationsGroups 9 }

pt3080NotifGroupGNSSAlarm NOTIFICATION-GROUP
    NOTIFICATIONS {
        pt3080NotifGNSSAlarm,
        pt3080NotifGNSSUnlockedAlarm,
        pt3080NotifGNSSAntennaFaultAlarm,
        pt3080NotifGNSSHoldOverAlarm
    }
    STATUS current
    DESCRIPTION
        "GNSS Alarms"
  ::= { pt3080NotificationsGroups 10 }

pt3080NotifGroupTSoIPAlarm NOTIFICATION-GROUP
    NOTIFICATIONS {
        pt3080NotifTSoIPAlarm,
        pt3080NotifTSoIPRx1PackageErrorRationExceededAlarm,
        pt3080NotifTSoIPRx2PackageErrorRationExceededAlarm,
        pt3080NotifTSoIPRx1SyncLossAlarm,
        pt3080NotifTSoIPRx2SyncLossAlarm
    }
    STATUS current
    DESCRIPTION
        "TSoIP Alarms"
  ::= { pt3080NotificationsGroups 12 }

pt3080NotifGroupExternalAlarm NOTIFICATION-GROUP
    NOTIFICATIONS {
        pt3080NotifExternalAlarm,
        pt3080NotifExternalInput1Alarm,
        pt3080NotifExternalInput2Alarm,
        pt3080NotifExternalInput3Alarm,
        pt3080NotifExternalInput4Alarm,
        pt3080NotifExternalInput5Alarm,
        pt3080NotifExternalInput6Alarm,
        pt3080NotifExternalInput7Alarm,
        pt3080NotifExternalInput8Alarm
    }
    STATUS current
    DESCRIPTION
        "External Alarms"
  ::= { pt3080NotificationsGroups 13 }

pt3080NotifGroupHWMonitorAlarm NOTIFICATION-GROUP
    NOTIFICATIONS {
        pt3080NotifHWMonitorAlarm,
        pt3080NotifHWMonitorFPGAAlarm,
        pt3080NotifHWMonitorMainBoardCPUTemperatureAlarm,
        pt3080NotifHWMonitorMainBoardTemperatureAlarm,
        pt3080NotifHWMonitorLeftFanAlarm,
        pt3080NotifHWMonitorRightFan2Alarm,
        pt3080NotifHWMonitorBackplaneTemperatureAlarm
    }
    STATUS current
    DESCRIPTION
        "HW Monitor Alarms"
  ::= { pt3080NotificationsGroups 14 }

pt3080NotifGroupCommAlarm NOTIFICATION-GROUP
    NOTIFICATIONS {
        pt3080NotifCommAlarm,
        pt3080NotifCommeth0Alarm,
        pt3080NotifCommeth1Alarm,
        pt3080NotifCommeth2Alarm,
        pt3080NotifCommeth3Alarm,
        pt3080NotifCommeth4Alarm
    }
    STATUS current
    DESCRIPTION
        "Communications Alarms"
  ::= { pt3080NotificationsGroups 15 }

pt3080NotifGroupASIAlarm NOTIFICATION-GROUP
    NOTIFICATIONS {
        pt3080NotifASIAlarm,
        pt3080NotifASIASI1ErrorRateEceeededAlarm,
        pt3080NotifASIASI2ErrorRateEceeededAlarm
    }
    STATUS current
    DESCRIPTION
        "ASI Alarms"
  ::= { pt3080NotificationsGroups 16 }

pt3080NotifGroupInternalAlarm NOTIFICATION-GROUP
    NOTIFICATIONS {
        pt3080NotifInternalAlarm,
        pt3080NotifInternalBackplaneAlarm,
        pt3080NotifInternalReferenceClockAlarm,
        pt3080NotifInternalUpConverterAlarm,
        pt3080NotifInternalDownConverterAlarm,
        pt3080NotifInternalMainboardAlarm,
        pt3080NotifInternalBatteryAlarm,
        pt3080NotifInternalFirmware1Alarm,
        pt3080NotifInternalGNSSAlarm,
        pt3080NotifInternalSatelliteAlarm,
        pt3080NotifInternalEthAlarm,
        pt3080NotifInternalPLLUnlockedAlarm
    }
    STATUS current
    DESCRIPTION
        "Internal Alarms"
  ::= { pt3080NotificationsGroups 18 }

END
