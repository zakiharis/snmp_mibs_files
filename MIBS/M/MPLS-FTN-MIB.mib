-- extracted from draft-ietf-mpls-ftn-mib-06.txt
-- at Fri May  2 06:12:54 2003

MPLS-FTN-MIB DEFINITIONS ::= BEGIN

IMPORTS
   MODULE-IDENTITY, OBJECT-TYPE, Unsigned32, Counter64, Integer32
      FROM SNMPv2-SMI
   MODULE-COMPLIANCE, OBJECT-GROUP
      FROM SNMPv2-CONF
   RowStatus, StorageType, RowPointer,
   TEXTUAL-CONVENTION, TimeStamp
      FROM SNMPv2-TC
   SnmpAdminString
      FROM SNMP-FRAMEWORK-MIB
   InterfaceIndexOrZero
      FROM IF-MIB
   mplsMIB
      FROM MPLS-TC-MIB
   InetAddressType, InetAddress, InetPortNumber
      FROM INET-ADDRESS-MIB
   Dscp
      FROM DIFFSERV-DSCP-TC
      ;

mplsFTNMIB MODULE-IDENTITY
   LAST-UPDATED "200304301200Z"  -- 30 April 2003 12:00:00 GMT
   ORGANIZATION "Multiprotocol Label Switching (MPLS) Working Group"
   CONTACT-INFO
       "
                Thomas D. Nadeau
        Postal: Cisco Systems, Inc.
                250 Apollo Drive
                Chelmsford, MA 01824
        Tel:    +1-978-244-3051
        Email:  tnadeau@cisco.com
       
                Cheenu Srinivasan
        Postal: Parama Networks, Inc.
                1030 Broad Street
                Shrewsbury, NJ 07702
        Tel:    +1-732-544-9120 x731
        Email:  cheenu@paramanet.com
       
                Arun Viswanathan
        Postal: Force10 Networks, Inc.
                1440 McCarthy Blvd
                Milpitas, CA 95035
        Tel:    +1-408-571-3516
        Email:  arun@force10networks.com
       
        IETF MPLS Working Group email: mpls@uu.net"
   
   DESCRIPTION
       "Copyright (C) The Internet Society (2003). This version of this
        MIB module is part of RFC xxxx; see the RFC itself for full
        legal notices.
       
        This MIB module contains managed object definitions for
        specifying FEC to NHLFE (FTN) mappings and corresponding
        performance for MPLS."
       
   -- Revision history.
       
   REVISION
       "200304301200Z"  -- 30 April 2002 12:00:00 GMT
   DESCRIPTION
       "Initial version issued as part of RFC XXXX."
    ::= { mplsMIB 5 }

-- Textual conventions used in this MIB.
MplsFTNEntryIndex ::= TEXTUAL-CONVENTION
   STATUS              current
   DESCRIPTION
       "Index for an entry in mplsFTNTable."
   SYNTAX              Unsigned32 (1..4294967295)

MplsFTNEntryIndexOrZero ::= TEXTUAL-CONVENTION
   STATUS              current
   DESCRIPTION
       "Index for an entry in mplsFTNTable or the special value
        zero. The value zero is object-specific and must
        therefore be defined as part of the description of any
        object which uses this syntax.  Examples of the usage
        of zero might include situations when none or all
        entries in mplsFTNTable need to be referenced."
   SYNTAX              Unsigned32 (0..4294967295)

-- Top-Level Components of this MIB.

mplsFTNNotifications OBJECT IDENTIFIER ::= { mplsFTNMIB 0 }
mplsFTNObjects       OBJECT IDENTIFIER ::= { mplsFTNMIB 1 }
mplsFTNConformance   OBJECT IDENTIFIER ::= { mplsFTNMIB 2 }

-- Next free index in mplsFTNTable.
mplsFTNIndexNext OBJECT-TYPE
   SYNTAX              MplsFTNEntryIndexOrZero
   MAX-ACCESS          read-only
   STATUS              current
   DESCRIPTION
       "This object contains the next available valid value to
        be used for mplsFTNIndex when creating entries in the
        mplsFTNTable.
       
        When creating a new conceptual row (configuration
        entry) in mplsFTNTable with an SNMP SET operation the
        command generator (Network Management Application) must
        first issue a management protocol retrieval operation
        to obtain the current value of this object.
       
        If the Command Responder (agent) does not wish to allow
        creation of more entries in mplsFTNTable, possibly
        because of resource exhaustion, this object MUST return
        a value of 0.
       
        If a non-zero value is returned it must determine
        whether the value is indeed still unused since two
        Network Management Applications may attempt to create a
        row simultaneously and use the same value.
       
        If it is currently unused and the SET succeeds, the
        agent MUST change the value of this object to a
        currently unused non-zero value (according to an
        implementation specific algorithm) or zero (if no
        further row creation will be permitted).
       
        If the value is in use, however, the SET fails and the
        Network Management Application must then reread this
        object to obtain a new usable value."
   ::= { mplsFTNObjects 1 }

-- Last time an object in mplsFTNTable changed.
mplsFTNTableLastChanged OBJECT-TYPE
   SYNTAX              TimeStamp
   MAX-ACCESS          read-only
   STATUS              current
   DESCRIPTION
       "Indicates the last time an entry was added, deleted or
        modified in mplsFTNTable. Management stations should
        consult this object to determine if mplsFTNTable
        requires their attention."
   ::=  { mplsFTNObjects 2 }

-- Table of FTN entries.
mplsFTNTable  OBJECT-TYPE
   SYNTAX          SEQUENCE OF MplsFTNEntry
   MAX-ACCESS      not-accessible
   STATUS          current
   DESCRIPTION
       "This table contains the currently defined FTN entries.
        This table allows FEC to NHLFE mappings to be
        specified.  Each entry in this table defines a rule to
        be applied to incoming packets (on interfaces that the
        FTN entry is activated on using mplsFTNMapTable) and an
        action to be taken on matching packets
        (mplsFTNActionPointer). This table provides a 5-tuple
        matching and allows addresses, port ranges and the exp
        bits to be specified.
       
        The action pointer points at either an mplsXCEntry in
        MPLS-LSR MIB when the NHLFE entry is a non-TE LSP, or
        it points at an mplsTunnelEntry in the MPLS-TE MIB when
        the NHLFE is an originating TE tunnel."
   REFERENCE
       "Srinivasan, C., A. Viswanathan, and T. Nadeau, MPLS
        Label Switch Router Management Information Base, draft-
        ietf-mpls-lsr-mib-09.txt
       
        Srinivasan, C., A. Viswanathan, and T. Nadeau, MPLS
        Traffic Engineering Management Information Base, draft-
        ietf-mpls-te-mib-09.txt"
   ::=  { mplsFTNObjects 3 }

mplsFTNEntry  OBJECT-TYPE
   SYNTAX          MplsFTNEntry
   MAX-ACCESS      not-accessible
   STATUS          current
   DESCRIPTION
       "Each entry represents one FTN entry which defines a
        rule to compare incoming packets with and an action to
        be taken on matching packets."
   INDEX { mplsFTNIndex }
   ::=  { mplsFTNTable 1 }

MplsFTNEntry  ::=  SEQUENCE {
      mplsFTNIndex               MplsFTNEntryIndex,
      mplsFTNRowStatus           RowStatus,
      mplsFTNDescr               SnmpAdminString,
      mplsFTNMask                BITS,
      mplsFTNAddrType            InetAddressType,
      mplsFTNSourceAddrMin       InetAddress,
      mplsFTNSourceAddrMax       InetAddress,
      mplsFTNDestAddrMin         InetAddress,
      mplsFTNDestAddrMax         InetAddress,
      mplsFTNSourcePortMin       InetPortNumber,
      mplsFTNSourcePortMax       InetPortNumber,
      mplsFTNDestPortMin         InetPortNumber,
      mplsFTNDestPortMax         InetPortNumber,
      mplsFTNProtocol            Integer32,
      mplsFTNDscp                Dscp,
      mplsFTNActionType          INTEGER,
      mplsFTNActionPointer       RowPointer,
      mplsFTNStorageType         StorageType
   }

mplsFTNIndex   OBJECT-TYPE
   SYNTAX              MplsFTNEntryIndex
   MAX-ACCESS          not-accessible
   STATUS              current
   DESCRIPTION
       "This is the unique index for a conceptual row in
        mplsFTNTable.
       
        To create a new conceptual row in mplsFTNTable a
        Network Management Application SHOULD retrieve the
        current value of mplsFTNIndexNext to determine the next
        valid available value of mplsFTNIndex."
   ::= { mplsFTNEntry 1 }

mplsFTNRowStatus OBJECT-TYPE
   SYNTAX              RowStatus
   MAX-ACCESS          read-create
   STATUS              current
   DESCRIPTION
       "Used for controlling the creation and deletion of this
        row. All writeable objects in this row may be modified
        at any time. If a Network Management Application
        attempts to delete a conceptual row by setting this
        object to 'destroy' and there are one or more entries
        in mplsFTNMapTable pointing to the row (i.e. when
        mplsFTNIndex of the conceptual row being deleted is
        equal to mplsFTNMapCurrIndex for one or more entries in
        mplsFTNMapTable), the agent MUST also destroy the
        corresponding entries in mplsFTNMapTable."
   ::= { mplsFTNEntry 2 }

mplsFTNDescr   OBJECT-TYPE
   SYNTAX              SnmpAdminString
   MAX-ACCESS          read-create
   STATUS              current
   DESCRIPTION
       "The description of this FTN entry. Since the index for
        this table has no particular significance or meaning,
        this object should contain some meaningful text that an
        operator could use to further distinguish entries in
        this table."
   ::= { mplsFTNEntry 3 }

mplsFTNMask OBJECT-TYPE
   SYNTAX             BITS {
                       sourceAddr(0),
                       destAddr(1),
                       sourcePort(2),
                       destPort(3),
                       protocol(4),
                       dscp(5)
                      }
   MAX-ACCESS          read-create
   STATUS              current
   DESCRIPTION
       "This bit map indicates which of the fields described
        next, namely source address range, destination address
        range, source port range, destination port range, IPv4
        Protocol field or IPv6 next-header field and
        Differentiated Services Code Point (DSCP) is active for
        this FTN entry. If a particular bit is set to zero then
        the corresponding field in the packet MUST be ignored
        for comparison purposes."
   ::= { mplsFTNEntry 4 }

mplsFTNAddrType OBJECT-TYPE
   SYNTAX             InetAddressType
   MAX-ACCESS         read-create
   STATUS             current
   DESCRIPTION
       "This object determines the type of address contained in
        the source and destination address objects
        (mplsFTNSourceAddrMin, mplsFTNSourceAddrMax,
        mplsFTNDestAddrMin and mplsFTNDestAddrMax) of a
        conceptual row.
       
        This object MUST NOT be set to unknown(0) when
        mplsFTNMask has bit positions sourceAddr(0) or
        destAddr(1) set to one.
       
        When both these bit positions of mplsFTNMask are set to
        zero the value of mplsFTNAddrType SHOULD be set to
        unknown(0) and the corresponding source and destination
        address objects SHOULD be set to zero-length strings."
   DEFVAL { ipv4 }
   ::= { mplsFTNEntry 5 }

mplsFTNSourceAddrMin OBJECT-TYPE
   SYNTAX             InetAddress
   MAX-ACCESS         read-create
   STATUS             current
   DESCRIPTION
       "The lower end of the source address range. The type of
        this object is determined by the corresponding
        mplsFTNAddrType object."
   ::= { mplsFTNEntry 6 }

mplsFTNSourceAddrMax OBJECT-TYPE
   SYNTAX             InetAddress
   MAX-ACCESS         read-create
   STATUS             current
   DESCRIPTION
       "The upper end of the source address range. The type of
        this object is determined by the corresponding
        mplsFTNAddrType object."
   ::= { mplsFTNEntry 7 }

mplsFTNDestAddrMin OBJECT-TYPE
   SYNTAX             InetAddress
   MAX-ACCESS         read-create
   STATUS             current
   DESCRIPTION
       "The lower end of the destination address range. The
        type of this object is determined by the corresponding
        mplsFTNAddrType object."
   ::= { mplsFTNEntry 8 }

mplsFTNDestAddrMax OBJECT-TYPE
   SYNTAX             InetAddress
   MAX-ACCESS         read-create
   STATUS             current
   DESCRIPTION
       "The higher end of the destination address range. The
        type of this object is determined by the corresponding
        mplsFTNAddrType object."
   ::= { mplsFTNEntry 9 }

mplsFTNSourcePortMin OBJECT-TYPE
   SYNTAX             InetPortNumber
   MAX-ACCESS         read-create
   STATUS             current
   DESCRIPTION
       "The lower end of the source port range."
   ::= { mplsFTNEntry 10 }

mplsFTNSourcePortMax OBJECT-TYPE
   SYNTAX             InetPortNumber
   MAX-ACCESS         read-create
   STATUS             current
   DESCRIPTION
       "The higher end of the source port range "
   ::= { mplsFTNEntry 11 }

mplsFTNDestPortMin OBJECT-TYPE
   SYNTAX             InetPortNumber
   MAX-ACCESS         read-create
   STATUS             current
   DESCRIPTION
       "The lower end of the destination port range."
   ::= { mplsFTNEntry 12 }

mplsFTNDestPortMax OBJECT-TYPE
   SYNTAX             InetPortNumber
   MAX-ACCESS         read-create
   STATUS             current
   DESCRIPTION
       "The higher end of the destination port range."
   ::= { mplsFTNEntry 13 }

mplsFTNProtocol OBJECT-TYPE
   SYNTAX             Integer32 (0..65535)
   MAX-ACCESS         read-create
   STATUS             current
   DESCRIPTION
       "The contents of the IPv4 Protocol field or IPv6 next-
        header field."
   ::= { mplsFTNEntry 14 }

mplsFTNDscp OBJECT-TYPE
   SYNTAX             Dscp
   MAX-ACCESS         read-create
   STATUS             current
   DESCRIPTION
       "The contents of the DSCP field."
   REFERENCE
       "Nichols, K., Blake, S., Baker, F. and D. Black,
        Definition of the Differentiated Services Field (DS
        Field) in the IPv4 and IPv6 Headers, RFC 2474, December
        1998."
   ::= { mplsFTNEntry 15 }

mplsFTNActionType OBJECT-TYPE
   SYNTAX    INTEGER {
                redirectLsp(1),   -- redirect into LSP
                redirectTunnel(2) -- redirect into tunnel
             }
   MAX-ACCESS         read-create
   STATUS             current
   DESCRIPTION
       "The type of action to be taken on packets matching this
        FTN entry."
   ::= { mplsFTNEntry 16 }

mplsFTNActionPointer OBJECT-TYPE
   SYNTAX             RowPointer
   MAX-ACCESS         read-create
   STATUS             current
   DESCRIPTION
       "If mplsFTNActionType is redirectLsp(2), then this
        object MUST contain zeroDotZero or point to a instance
        of mplsXCEntry indicating the LSP to redirect matching
        packets to.
       
        If mplsFTNActionType is redirectTunnel(3), then this
        object MUST contain zeroDotZero or point to a instance
        of mplsTunnelEntry indicating the MPLS TE tunnel to
        redirect matching packets to.
       
        If this object points to a conceptual row instance in a
        table consistent with mplsFTNActionType but this
        instance does not currently exist then no action will
        be taken on packets matching such an FTN entry till
        this instance comes into existence.
       
        If this object contains zeroDotZero then no action will
        be taken on packets matching such an FTN entry till it
        is populated with a valid pointer consistent with the
        value of mplsFTNActionType as explained above."
   ::= { mplsFTNEntry 17 }

mplsFTNStorageType OBJECT-TYPE
   SYNTAX             StorageType
   MAX-ACCESS         read-create
   STATUS             current
   DESCRIPTION
       "The storage type for this FTN entry. Conceptual rows
        having the value 'permanent' need not allow write-
        access to any columnar objects in the row."
   ::= { mplsFTNEntry 18 }

-- End of mplsFTNTable.

-- Last time an object in mplsFTNMapTable changed.
mplsFTNMapTableLastChanged OBJECT-TYPE
   SYNTAX              TimeStamp
   MAX-ACCESS          read-only
   STATUS              current
   DESCRIPTION
       "Indicates the last time an entry was added, deleted or
        modified in mplsFTNMapTable. Management stations should
        consult this object to determine if the table requires
        their attention."
   ::=  { mplsFTNObjects 4 }

-- FTN to interface mapping table.
mplsFTNMapTable OBJECT-TYPE
   SYNTAX              SEQUENCE OF MplsFTNMapEntry
   MAX-ACCESS          not-accessible
   STATUS              current
   DESCRIPTION
       "This table contains objects for mapping previously
        defined entries in mplsFTNTable to interfaces.
       
        This table provides the capability to activate or map
        FTN entries defined in mplsFTNTable to specific
        interfaces in the system. FTN entries are compared with
        incoming packets in the order in which they are applied
        on an interface. For this reason, this table provides a
        mechanism to 'insert' an FTN entry between two existing
        FTN entries already applied on an interface.
       
        Using this linked-list structure, one can retrieve FTN
        entries in the order of application on a per-interface
        basis as follows:
       
        - To determine the first FTN entry on an interface
          with index ifIndex perform a GETNEXT retrieval
          operation on mplsFTNMapIndex.ifIndex.0.0; the
          returned object, if one exists, is (say)
          mplsFTNMapIndex.ifIndex.0.n. Then the index of the
          first FTN entry applied on this interface is n.
        
        - To determine the FTN entry applied after the one
          indexed by n perform a GETNEXT retrieval operation on
          mplsFTNMapIndex.ifIndex.n.0; the returned object, if
          one exists, is (say) mplsFTNMapIndex.ifIndex.n.m.
          Then the index of the next FTN entry applied on this
          interface is m.
       
        Use the above steps to retrieve all the applied FTN
        entries on a per-interface basis in application order.
        Note that the number of retrieval operations is the
        same as the number of applied FTN entries (i.e. the
        minimum number of GETNEXT operations needed using any
        indexing scheme)."
   ::=  { mplsFTNObjects 5 }

mplsFTNMapEntry OBJECT-TYPE
   SYNTAX              MplsFTNMapEntry
   MAX-ACCESS          not-accessible
   STATUS              current
   DESCRIPTION
       "Each entry indicates the application of a particular
        entry as defined in mplsFTNTable on an interface. The
        order of application of FTN entries on an interface is
        the order in which they will be compared against
        incoming packets for a match. Each entry of this table
        is indexed by the interface index that the FTN entry is
        applied to, with the value 0 representing all
        interfaces, the index of the previous FTN entry applied
        on the interface and the index of the current FTN
        entry. This linked-list indexing style structure allows
        FTN entries to be inserted at arbitrary positions in
        the list. Agents MUST NOT allow the same FTN entries to
        be applied multiple times to the same interface. Agents
        MUST NOT allow the creation of rows in this table until
        the corresponding rows are created in the mplsFTNTable.
        If the corresponding row in the FTN table is destroyed,
        the agent MUST destroy the corresponding entries in
        this table as well. Although it is strongly recommended
        that managers destroy rows in this table in such a way
        that keeps the remainder of the table consistent,
        agents MUST ultimately make sure that if an entry in
        this table is destroyed, that inconsistencies in the
        table are not allowed to occur. To this end, rows that
        are no longer appropriate should be taken out of
        service."
   INDEX {
         mplsFTNMapIndex,
         mplsFTNMapPrevIndex,
         mplsFTNMapCurrIndex
   }
   ::=  { mplsFTNMapTable 1 }

MplsFTNMapEntry  ::=  SEQUENCE {
      mplsFTNMapIndex       InterfaceIndexOrZero,
      mplsFTNMapPrevIndex    MplsFTNEntryIndexOrZero,
      mplsFTNMapCurrIndex    MplsFTNEntryIndex,
      mplsFTNMapRowStatus    RowStatus,
      mplsFTNMapStorageType  StorageType
   }

mplsFTNMapIndex OBJECT-TYPE
   SYNTAX              InterfaceIndexOrZero
   MAX-ACCESS          not-accessible
   STATUS              current
   DESCRIPTION
       "The interface index that this FTN entry is being
        applied to. A value of zero indicates an entry that is
        applied all interfaces.
       
        Entries mapped to an interface by specifying its (non-
        zero) interface index in mplsFTNMapIndex are applied
        ahead of entries with mplsFTNMapIndex equal to zero."
   ::= { mplsFTNMapEntry 1 }
   
mplsFTNMapPrevIndex OBJECT-TYPE
   SYNTAX              MplsFTNEntryIndexOrZero
   MAX-ACCESS          not-accessible
   STATUS              current
   DESCRIPTION
       "The index of the previous FTN entry that was applied to
        this interface. The special value zero indicates that
        this should be the first FTN entry in the list."
   ::=  { mplsFTNMapEntry 2 }

mplsFTNMapCurrIndex OBJECT-TYPE
   SYNTAX              MplsFTNEntryIndex
   MAX-ACCESS          not-accessible
   STATUS              current
   DESCRIPTION
       "Index of the current FTN entry that is being applied to
        this interface."
   ::=  { mplsFTNMapEntry 3 }

mplsFTNMapRowStatus OBJECT-TYPE
   SYNTAX              RowStatus
   MAX-ACCESS          read-create
   STATUS              current
   DESCRIPTION
       "Used for controlling the creation and deletion of this
        row.
       
        All writable objects in this row may be modified at any
        time.
       
        If a conceptual row instance of mplsFTNMapTable points
        to a conceptual row instance in mplsFTNTable which is
        subsequently deleted, the corresponding conceptual row
        in mplsFTNMapTable MUST also be deleted by the agent."
   ::=  { mplsFTNMapEntry 5 }

mplsFTNMapStorageType OBJECT-TYPE
   SYNTAX              StorageType
   MAX-ACCESS          read-create
   STATUS              current
   DESCRIPTION
       "The storage type for this entry. Conceptual rows having
        the value 'permanent' need not allow write-access to
        any columnar objects in this row."
   ::= { mplsFTNMapEntry 6 }

-- End of mplsFTNMapTable

-- FTN entry performance table

mplsFTNPerfTable OBJECT-TYPE
   SYNTAX              SEQUENCE OF MplsFTNPerfEntry
   MAX-ACCESS          not-accessible
   STATUS              current
   DESCRIPTION
       "This table contains performance statistics on FTN
        entries on a per-interface basis."
   ::= { mplsFTNObjects 6 }

mplsFTNPerfEntry OBJECT-TYPE
   SYNTAX              MplsFTNPerfEntry
   MAX-ACCESS          not-accessible
   STATUS              current
   DESCRIPTION
       "Each entry contains performance information for the
        specified interface and an FTN entry mapped to this
        interface."
   INDEX  { mplsFTNPerfIndex, mplsFTNPerfCurrIndex }
   ::=  { mplsFTNPerfTable 1 }

MplsFTNPerfEntry  ::=  SEQUENCE {
      mplsFTNPerfIndex                     InterfaceIndexOrZero,
      mplsFTNPerfCurrIndex                 MplsFTNEntryIndex,
      mplsFTNPerfMatchedPackets            Counter64,
      mplsFTNPerfMatchedOctets             Counter64,
      mplsFTNPerfDiscontinuityTime         TimeStamp
   }

mplsFTNPerfIndex OBJECT-TYPE
   SYNTAX              InterfaceIndexOrZero
   MAX-ACCESS          not-accessible
   STATUS              current
   DESCRIPTION
       "The interface index of an interface that an FTN entry
        has been applied/mapped to. Each instance of this
        object corresponds to an instance of mplsFTNMapIndex."
   ::= { mplsFTNPerfEntry 1 }
   
mplsFTNPerfCurrIndex OBJECT-TYPE
   SYNTAX              MplsFTNEntryIndex
   MAX-ACCESS          not-accessible
   STATUS              current
   DESCRIPTION
       "Index of an FTN entry that has being applied/mapped to
        the specified interface. Each instance of this object
        corresponds to an instance of mplsFTNMapCurrIndex."
   ::=  { mplsFTNPerfEntry 2 }

mplsFTNPerfMatchedPackets OBJECT-TYPE
   SYNTAX              Counter64
   MAX-ACCESS          read-only
   STATUS              current
   DESCRIPTION
       "Number of packets that matched the specified FTN entry
        if it is applied/mapped to the specified interface.
        Discontinuities in the value of this counter can occur
        at re-initialization of the management system, and at
        other times as indicated by the value of
        mplsFTNDiscontinuityTime."
   ::= { mplsFTNPerfEntry 3 }

mplsFTNPerfMatchedOctets OBJECT-TYPE
   SYNTAX              Counter64
   MAX-ACCESS          read-only
   STATUS              current
   DESCRIPTION
       "Number of octets that matched the specified FTN entry
        if it is applied/mapped to the specified interface.
        Discontinuities in the value of this counter can occur
        at re-initialization of the management system, and at
        other times as indicated by the value of
        mplsFTNDiscontinuityTime."
   ::= { mplsFTNPerfEntry 4 }

mplsFTNPerfDiscontinuityTime OBJECT-TYPE
   SYNTAX              TimeStamp
   MAX-ACCESS          read-only
   STATUS              current
   DESCRIPTION
       "The value of sysUpTime on the most recent occasion at
        which any one or more of this entry's counters suffered
        a discontinuity. If no such discontinuities have
        occurred since the last re-initialization of the local
        management subsystem, then this object contains a zero
        value."
   ::= { mplsFTNPerfEntry 5 }

-- End of mplsFTNPerfTable

-- Module compliance.

-- Top level object IDs.
mplsFTNGroups
   OBJECT IDENTIFIER ::= { mplsFTNConformance 1 }
mplsFTNCompliances
   OBJECT IDENTIFIER ::= { mplsFTNConformance 2 }

-- Compliance requirement for fully compliant implementations.
mplsFTNModuleFullCompliance MODULE-COMPLIANCE
   STATUS current
   DESCRIPTION
       "Compliance statement for agents that provide full
        support for MPLS-FTN-MIB."

   MODULE IF-MIB -- The Interfaces Group MIB, RFC 2863.
   MANDATORY-GROUPS {
      ifGeneralInformationGroup,
      ifCounterDiscontinuityGroup
   }

   MODULE -- This module.
   MANDATORY-GROUPS {
      mplsFTNRuleGroup,
      mplsFTNMapGroup,
      mplsFTNPerfGroup
   }

   OBJECT mplsFTNAddrType
   SYNTAX InetAddressType { ipv4(1), ipv6(2) }
   MIN-ACCESS read-only
   DESCRIPTION
       "Write access is not required. An implementation is only
        required to support IPv4 and IPv6 addresses."
       
   ::= { mplsFTNCompliances 1 }

-- Compliance requirement for read-only implementations.
mplsFTNModuleReadOnlyCompliance MODULE-COMPLIANCE
   STATUS current
   DESCRIPTION
       "Compliance requirement for implementations that only
        provide read-only support for MPLS-FTN-MIB. Such
        devices can then be monitored but cannot be configured
        using this MIB."

   MODULE IF-MIB -- The interfaces Group MIB, RFC 2863
   MANDATORY-GROUPS {
      ifGeneralInformationGroup,
      ifCounterDiscontinuityGroup
   }
   
   MODULE -- This module
   MANDATORY-GROUPS {
      mplsFTNRuleGroup,
      mplsFTNMapGroup,
      mplsFTNPerfGroup

   }
   
   OBJECT mplsFTNIndexNext
   MIN-ACCESS   not-accessible
   DESCRIPTION
       "This object is not needed when mplsFTNTable is
        implemented as read-only."

   OBJECT mplsFTNRowStatus
   SYNTAX       RowStatus { active(1) }
   MIN-ACCESS   read-only
   DESCRIPTION
       "Write access is not required, and active is the only
        status that needs to be supported."

   OBJECT mplsFTNDescr
   MIN-ACCESS   read-only
   DESCRIPTION
       "Write access is not required."

   OBJECT mplsFTNMask
   MIN-ACCESS   read-only
   DESCRIPTION
       "Write access is not required."

   OBJECT mplsFTNAddrType
   SYNTAX       InetAddressType { ipv4(1), ipv6(2) }
   MIN-ACCESS   read-only
   DESCRIPTION
       "Write access is not required. An implementation is only
        required to support IPv4 and IPv6 addresses."

   OBJECT mplsFTNSourceAddrMin
   SYNTAX       InetAddress (SIZE (4 | 20))
   MIN-ACCESS   read-only
   DESCRIPTION
       "Write access is not required. An implementation is only
        required to support IPv4 and IPv6 addresses."

   OBJECT mplsFTNSourceAddrMax
   SYNTAX       InetAddress (SIZE (4 | 20))
   MIN-ACCESS   read-only
   DESCRIPTION
       "Write access is not required. An implementation is only
        required to support IPv4 and IPv6 addresses."

   OBJECT mplsFTNDestAddrMin
   SYNTAX       InetAddress (SIZE (4 | 20))
   MIN-ACCESS   read-only
   DESCRIPTION
       "Write access is not required. An implementation is only
        required to support IPv4 and IPv6 addresses."

   OBJECT mplsFTNDestAddrMax
   SYNTAX       InetAddress (SIZE (4 | 20))
   MIN-ACCESS   read-only
   DESCRIPTION
       "Write access is not required. An implementation is only
        required to support IPv4 and IPv6 addresses."

   OBJECT mplsFTNSourcePortMin
   MIN-ACCESS   read-only
   DESCRIPTION
       "Write access is not required."


   OBJECT mplsFTNSourcePortMax
   MIN-ACCESS   read-only
   DESCRIPTION
       "Write access is not required."

   OBJECT mplsFTNDestPortMin
   MIN-ACCESS   read-only
   DESCRIPTION
       "Write access is not required."

   OBJECT mplsFTNDestPortMax
   MIN-ACCESS   read-only
   DESCRIPTION
       "Write access is not required."

   OBJECT mplsFTNProtocol
   MIN-ACCESS   read-only
   DESCRIPTION
       "Write access is not required."

   OBJECT mplsFTNActionType
   MIN-ACCESS   read-only
   DESCRIPTION
       "Write access is not required."

   OBJECT mplsFTNActionPointer
   MIN-ACCESS   read-only
   DESCRIPTION
       "Write access is not required."

   OBJECT mplsFTNDscp
   MIN-ACCESS   read-only
   DESCRIPTION
       "Write access is not required."

   OBJECT mplsFTNStorageType
   MIN-ACCESS   read-only
   DESCRIPTION
       "Write access is not required."

   OBJECT mplsFTNMapRowStatus
   SYNTAX       RowStatus { active(1) }
   MIN-ACCESS   read-only
   DESCRIPTION
       "Write access is not required, and active is the only
        status that needs to be supported."

   OBJECT mplsFTNMapStorageType
   MIN-ACCESS   read-only
   DESCRIPTION
       "Write access is not required."

   ::= { mplsFTNCompliances 2 }
   
-- Units of conformance.
mplsFTNRuleGroup OBJECT-GROUP
   OBJECTS {
         mplsFTNIndexNext,
         mplsFTNTableLastChanged,
         mplsFTNRowStatus,
         mplsFTNDescr,
         mplsFTNMask,
         mplsFTNAddrType,
         mplsFTNSourceAddrMin,
         mplsFTNSourceAddrMax,
         mplsFTNDestAddrMin,
         mplsFTNDestAddrMax,
         mplsFTNSourcePortMin,
         mplsFTNSourcePortMax,
         mplsFTNDestPortMin,
         mplsFTNDestPortMax,
         mplsFTNProtocol,
         mplsFTNActionType,
         mplsFTNActionPointer,
         mplsFTNDscp,
         mplsFTNStorageType
   }
   STATUS current
   DESCRIPTION
       "Collection of objects that implement MPLS FTN rules."
   ::= { mplsFTNGroups 1 }

mplsFTNMapGroup OBJECT-GROUP
   OBJECTS {
         mplsFTNMapTableLastChanged,
         mplsFTNMapRowStatus,
         mplsFTNMapStorageType
   }
   STATUS current
   DESCRIPTION
       "Collection of objects that implement activation of MPLS
        FTN entries on interfaces."
   ::= { mplsFTNGroups 2 }

mplsFTNPerfGroup OBJECT-GROUP
   OBJECTS {
         mplsFTNPerfMatchedPackets,
         mplsFTNPerfMatchedOctets,
         mplsFTNPerfDiscontinuityTime
   }
   STATUS current
   DESCRIPTION
       "Collection of objects providing MPLS FTN performance
        information."
   ::= { mplsFTNGroups 3 }

END

--    
--    Copyright (C) The Internet Society (2001). All Rights Reserved.
--    
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the purpose of
--    developing Internet standards in which case the procedures for
--    copyrights defined in the Internet Standards process must be
--    followed, or as required to translate it into languages other than
--    English.
--    
--    The limited permissions granted above are perpetual and will not be
--    revoked by the Internet Society or its successors or assigns. This
--    document and the information contained herein is provided on an "AS
--    IS" basis and THE INTERNET SOCIETY AND THE INTERNET ENGINEERING TASK
--    FORCE DISCLAIMS ALL WARRANTIES, EXPRESS OR IMPLIED, INCLUDING BUT
--    NOT LIMITED TO ANY WARRANTY THAT THE USE OF THE INFORMATION HEREIN
--    WILL NOT INFRINGE ANY RIGHTS OR ANY IMPLIED WARRANTIES OF
--    MERCHANTABILITY OR FITNESS FOR A PARTICULAR PURPOSE.
-- 
--
