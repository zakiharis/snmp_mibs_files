-- extracted from draft-ietf-mpls-fastreroute-mib-07.txt
-- at Tue Mar  6 06:08:27 2007

MPLS-FRR-STD-MIB DEFINITIONS ::= BEGIN

    IMPORTS
       MODULE-IDENTITY, OBJECT-TYPE,
       Integer32, Unsigned32,
       NOTIFICATION-TYPE, Gauge32
          FROM SNMPv2-SMI                            -- [RFC2578]
       MODULE-COMPLIANCE, OBJECT-GROUP, 
       NOTIFICATION-GROUP
          FROM SNMPv2-CONF                           -- [RFC2580]
       TruthValue, RowStatus, StorageType



          FROM SNMPv2-TC                             -- [RFC2579]
       InterfaceIndex, InterfaceIndexOrZero,
       ifGeneralInformationGroup, 
       ifCounterDiscontinuityGroup
          FROM IF-MIB                                -- [RFC2863]
       MplsTunnelIndex, MplsTunnelInstanceIndex,
       MplsLsrIdentifier, MplsBitRate, mplsStdMIB,
       MplsTunnelAffinity
          FROM MPLS-TC-STD-MIB                       -- [RFC3811]
       mplsTunnelGroup, mplsTunnelScalarGroup,
       mplsTunnelARHopListIndex, mplsTunnelARHopIndex
          FROM MPLS-TE-STD-MIB                       -- [RFC3812]
       InetAddressType, InetAddress
          FROM INET-ADDRESS-MIB                      -- [RFC3291]
       ;

    mplsFrrMIB MODULE-IDENTITY
       LAST-UPDATED
          "200508011200Z" -- 01 August 2005 12:00:00 GMT
       ORGANIZATION
          "Multiprotocol Label Switching (MPLS) Working Group"
       CONTACT-INFO
            "
                     Riza Cetin
              Email: riza.cetin@alcatel.be

                     Thomas D. Nadeau
              Email: tnadeau@cisco.com

                     Stefaan De Cnodder
              Email: Stefaan.de_cnodder@alcatel.be

                     Der-Hwa Gan
              Email: dhg@juniper.net
            "
       DESCRIPTION
         "Copyright (C) 2006 The IETF Trust.  This 
          MIB module is part of RFC 4327; see the RFC itself
          for full legal notices.

          This MIB module contains managed object definitions for
          MPLS Traffic Engineering Fast Reroute as defined in
          RFC4090."

    -- Revision history.
       REVISION
          "200508011200Z" -- 01 August 2005 12:00:00 GMT
       DESCRIPTION
          "Initial version. Published as RFC xxxx." 



                          -- RFC-editor pls fill in xxxx
   ::= { mplsStdMIB 1 } -- RFC-editor please fill in
                          -- XXX with value assigned by IANA, 
                          -- see section 18.1 for details

    -- Top level components of this MIB module.
    mplsFrrNotif         OBJECT IDENTIFIER ::= { mplsFrrMIB 0 }
    mplsFrrScalars       OBJECT IDENTIFIER ::= { mplsFrrMIB 1 }
    mplsFrrObjects       OBJECT IDENTIFIER ::= { mplsFrrMIB 2 }

    -- objects that work for either method of FRR
    mplsFrrGeneralObjects OBJECT IDENTIFIER ::= { mplsFrrObjects 1 }

    -- objects defined for 1-to-1 style FRR
    mplsFrrOne2OneObjects OBJECT IDENTIFIER ::= { mplsFrrObjects 2 }

    -- objects defined for Facility Backup style FRR
    mplsFrrFacObjects  OBJECT IDENTIFIER ::= { mplsFrrObjects 3 }

    mplsFrrConformance   OBJECT IDENTIFIER ::= { mplsFrrMIB 3 }


    -- MPLS Fast Reroute scalars.
    mplsFrrDetourIncoming OBJECT-TYPE
       SYNTAX        Integer32 (-1|0..2147483647)
       MAX-ACCESS    read-only
       STATUS        current
       DESCRIPTION
         "The number of detour LSPs entering the device 
          (greater than or equal to 0) if mplsFrrProtectionMethod 
          is set to oneToOneBackup(1), or -1 if
          mplsFrrProtectionMethod is set to facilityBackup(2)."
       DEFVAL { 0 }
       ::= { mplsFrrScalars 1 }

    mplsFrrDetourOutgoing OBJECT-TYPE
       SYNTAX        Integer32 (-1|0..2147483647)
       MAX-ACCESS    read-only
       STATUS        current
       DESCRIPTION
         "The number of detour LSPs leaving the device (greater
          than or equal to 0) if mplsFrrProtectionMethod 
          is set to oneToOneBackup(1), or -1 if 
          mplsFrrProtectionMethod is set to 
          facilityBackup(2)."
       DEFVAL { 0 }
      ::= { mplsFrrScalars 2 }

    mplsFrrDetourOriginating OBJECT-TYPE



       SYNTAX        Integer32(-1|0..2147483647)
       MAX-ACCESS    read-only
       STATUS        current
       DESCRIPTION
         "The number of detour LSPs originating at this PLR (greater
          than or equal to 0) if mplsFrrProtectionMethod 
          is set to oneToOneBackup(1).  This object MUST 
          return -1 if the mplsFrrProtectionMethod is set to 
          facilityBackup(2)."
       DEFVAL { 0 }
       ::= { mplsFrrScalars 3 }

    mplsFrrSwitchover OBJECT-TYPE
       SYNTAX        Unsigned32
       MAX-ACCESS    read-only
       STATUS        current
       DESCRIPTION
         "The number of tunnel instances for which this LSR
          is the ingress that are currently using a detour
          or bypass LSP to reach their egress."
       DEFVAL { 0 }
       ::= { mplsFrrScalars 4 }

    mplsFrrConfIfs OBJECT-TYPE
       SYNTAX        Integer32(-1|0..2147483647)
       MAX-ACCESS    read-only
       STATUS        current
       DESCRIPTION
         "Indicates the number of MPLS interfaces configured for
          protection by the FRR feature if 
          mplsFrrProtectionMethod
          is set to facilityBackup(2), otherwise this value
          MUST return -1 to indicate that LSPs traversing any
          interface are not protected."
       DEFVAL { 0 }
       ::= { mplsFrrScalars 5 }

    mplsFrrActProtectedIfs OBJECT-TYPE
       SYNTAX        Unsigned32
       MAX-ACCESS    read-only
       STATUS        current
       DESCRIPTION
         "Indicates the number of interfaces currently being 
          protected by the FRR feature if 
          mplsFrrProtectionMethod is set to
          facilityBackup(2), otherwise this value should return 
          0 to indicate that LSPs traversing any interface may  
          not be protected. This value MUST be less than or equal 
          to mplsFrrConfIfs except when mplsFrrConfIfs is



          set to -1, in which case the value of this object
          is meaningless and SHOULD be ignored."
       DEFVAL { 0 }
       ::= { mplsFrrScalars 6 }

    mplsFrrConfProtectionTuns OBJECT-TYPE
       SYNTAX        Unsigned32
       MAX-ACCESS    read-only
       STATUS        current
       DESCRIPTION
         "Indicates the number of bypass tunnels configured to
          protect TE tunnels on this LSR using the FRR feature
          if mplsFrrProtectionMethod is set to
          facilityBackup(2), otherwise this value MUST return
          0 and SHOULD be ignored."
       DEFVAL { 0 }
       ::= { mplsFrrScalars 7 }

    mplsFrrActProtectionTuns OBJECT-TYPE
       SYNTAX        Unsigned32
       MAX-ACCESS    read-only
       STATUS        current
       DESCRIPTION
         "Indicates the number of bypass tunnels indicated in
          mplsFrrConfProtectionTuns whose operStatus
          is up(1) indicating that they are currently protecting
          TE tunnels on this LSR using the FRR feature. This
          object MUST return 0 if mplsFrrProtectionMethod
          is set to oneToOneBackup(1)."
       DEFVAL { 0 }
       ::= { mplsFrrScalars 8 }

    mplsFrrActProtectedLSPs OBJECT-TYPE
       SYNTAX        Unsigned32
       MAX-ACCESS    read-only
       STATUS        current
       DESCRIPTION
         "Indicates the number of LSPs currently protected by
          the FRR feature where this device acts as the PLR
          for those LSPs. If mplsFrrProtectionMethod 
          is set to facilityBackup(2) this object MUST return 
          0."
       DEFVAL { 0 }
       ::= { mplsFrrScalars 9 }

    mplsFrrProtectionMethod OBJECT-TYPE
       SYNTAX        INTEGER { oneToOneBackup(1),
                               facilityBackup(2)
                             }




       MAX-ACCESS    read-write
       STATUS        current
       DESCRIPTION
         "Indicates which protection method is to be used for fast
          reroute on this device. Some devices may require a reboot 
          if this variable is to take affect after being modified."
       ::= { mplsFrrScalars 10 }

    mplsFrrNotifsEnabled OBJECT-TYPE
        SYNTAX            TruthValue
        MAX-ACCESS        read-write
        STATUS            current
        DESCRIPTION
            "Enables or disables FRR notifications defined in this 
             MIB module. Notifications are disabled by default."
        DEFVAL { false }
    ::= { mplsFrrScalars 11 }

    mplsFrrNotifMaxRate OBJECT-TYPE
       SYNTAX       Unsigned32
       UNITS        "Notifications per Second"
       MAX-ACCESS   read-write
       STATUS       current
       DESCRIPTION
           "This variable indicates the maximum number of
             notifications issued per second. If events occur
             more rapidly, the implementation may simply fail to
             emit these notifications during that period, or may
             queue them until an appropriate time. A value of 0
             means no throttling is applied and events may be
             notified at the rate at which they occur."
       DEFVAL       { 0 }
    ::= { mplsFrrScalars 12 }

    --
    --  General FRR Table Section
    --
    --  These tables apply to both types of FRR
    --  and should be implemented by all LSRs supporting
    --  FRR.
    --

    -- MPLS Fast Reroute Constraints table

    mplsFrrConstTable OBJECT-TYPE
       SYNTAX        SEQUENCE OF MplsFrrConstEntry
       MAX-ACCESS    not-accessible
       STATUS        current
       DESCRIPTION



         "This table shows detour LSP or bypass tunnel setup
          constraints."
       ::= {  mplsFrrGeneralObjects 1 }

    mplsFrrConstEntry OBJECT-TYPE
       SYNTAX        MplsFrrConstEntry
       MAX-ACCESS    not-accessible
       STATUS        current
       DESCRIPTION
         "An entry in this table represents detour LSP or bypass 
          tunnel setup constraints for a tunnel instance to be 
          protected by detour LSPs or a bypass tunnel.

          Agents must only allow entries in this table to be
          created for tunnel instances that require fast-reroute
          as indicated by the presense of the FAST_REROUTE Object 
          in the signaling for the LSP in question, as speciifed 
          in section 4.1 of RFC4090.

          Entries indexed with mplsFrrConstIfIndex set to 0 apply to 
          all interfaces on this device for which the FRR feature can 
          operate.

          Note that as per [RFC3812] the mplsTunnelInstance object
          set to a value of 0 indicates that the mplsTunnelEntry
          contains at a tunnel ingress. This is typically how 
          configuration of this feature is performed on devices 
          where the actual protection LSP used is left up to the 
          protecting tunnel. However, in cases where static 
          configuration is possible, any valid tunnel
          instance is possible; however, in these cases, it is 
          STRONGLY RECOMMENDED that the instance index SHOULD 
          use the following convention to identify backup LSPs:

          - lower 16 bits : protected tunnel instance
          - higher 16 bits: must be all zeros
       "
       INDEX { mplsFrrConstIfIndex,
               mplsFrrConstTunnelIndex,
               mplsFrrConstTunnelInstance
             }
       ::= { mplsFrrConstTable 1 }

    MplsFrrConstEntry ::= SEQUENCE {
          mplsFrrConstIfIndex         InterfaceIndexOrZero,
          mplsFrrConstTunnelIndex     MplsTunnelIndex,
          mplsFrrConstTunnelInstance  MplsTunnelInstanceIndex,
          mplsFrrConstProtectionType  INTEGER,
          mplsFrrConstSetupPrio       Unsigned32,



          mplsFrrConstHoldingPrio     Unsigned32,
          mplsFrrConstInclAnyAffinity MplsTunnelAffinity,
          mplsFrrConstInclAllAffinity MplsTunnelAffinity,
          mplsFrrConstExclAnyAffinity MplsTunnelAffinity,
          mplsFrrConstHopLimit        Unsigned32,
          mplsFrrConstBandwidth       MplsBitRate,
          mplsFrrConstStorageType     StorageType,
          mplsFrrConstRowStatus       RowStatus
    }

    mplsFrrConstIfIndex  OBJECT-TYPE
       SYNTAX        InterfaceIndexOrZero
       MAX-ACCESS    not-accessible
       STATUS        current
       DESCRIPTION
         "Uniquely identifies an interface which a fast reroute 
          protection tunnel is configured to potentially protect
          in the event of a fault. Entries with this index set to 
          0 indicates that the protection tunnel configured protects 
          all interfaces on this device (i.e.: node protection)."
       ::= { mplsFrrConstEntry 1 }

    mplsFrrConstTunnelIndex OBJECT-TYPE
       SYNTAX        MplsTunnelIndex
       MAX-ACCESS    not-accessible
       STATUS        current
       DESCRIPTION
         "Uniquely identifies a tunnel for which is configured 
          to possibly protect the interface(s) specified by
          mplsFrrConstIfIndex in the event of a fault as 
          must exist in the mplsTunnelTable."
       REFERENCE "mplsTunnelTable from RFC3812."
       ::= { mplsFrrConstEntry 2 }

    mplsFrrConstTunnelInstance OBJECT-TYPE
       SYNTAX        MplsTunnelInstanceIndex
       MAX-ACCESS    not-accessible
       STATUS        current
       DESCRIPTION
         "Uniquely identifies an existing instance of this tunnel 
          for which fast reroute is requested. Note that a value of 
          0 indicates that the configuration points at a tunnel 
          head (as specified in RFC3812). This is typically how 
          configuration of this feature is performed on devices 
          where the actual protection LSP used is left up to the 
          protecting tunnel. However, in cases where static 
          configuration is possible, any valid tunnel
          instance is permissible.  In these cases, it is recommended
          that the instance index follow the following convention



          as to make identication of backup LSPs easier:

          - lower 16 bits : protected tunnel instance
          - higher 16 bits: must be all zeros"
       ::= { mplsFrrConstEntry 3 }

    mplsFrrConstProtectionType OBJECT-TYPE
       SYNTAX        INTEGER { linkProtection(1),
                               nodeProtection(2)
                             }
       MAX-ACCESS    read-create
       STATUS        current
       DESCRIPTION
         "Indicates type of the resource protection:

          linkProtection(1) indicates that this tunnel is
            setup to protect a particular link's resources.

          nodeProtection(2) indicates that this tunnel is
            setup to protect an entire node from failure.
         "
       DEFVAL { nodeProtection }
       ::= { mplsFrrConstEntry 4 }

    mplsFrrConstSetupPrio OBJECT-TYPE
       SYNTAX        Unsigned32 (0..7)
       MAX-ACCESS    read-create
       STATUS        current
       DESCRIPTION
         "Indicates the setup priority of the detour LSP
          or bypass tunnel."
       REFERENCE
         "RFC 3209"
       DEFVAL { 7 }
       ::= { mplsFrrConstEntry 5 }

    mplsFrrConstHoldingPrio OBJECT-TYPE
       SYNTAX        Unsigned32 (0..7)
       MAX-ACCESS    read-create
       STATUS        current
       DESCRIPTION
         "Indicates the holding priority for detour LSP
          or bypass tunnel."
       REFERENCE
         "RFC 3209"
       DEFVAL { 0 }
       ::= { mplsFrrConstEntry 6 }

    mplsFrrConstInclAnyAffinity OBJECT-TYPE



       SYNTAX        MplsTunnelAffinity
       MAX-ACCESS    read-create
       STATUS        current
       DESCRIPTION
         "Indicates the include-any link constraint for the
          detour LSP or bypass tunnel. A link satisfies the
          include-any constraint if and only if the constraint
          is zero, or the link and the constraint have a
          resource class in common."
       REFERENCE
         "RFC 3209"
       DEFVAL { 0 }
       ::= { mplsFrrConstEntry 7 }

    mplsFrrConstInclAllAffinity OBJECT-TYPE
       SYNTAX        MplsTunnelAffinity
       MAX-ACCESS    read-create
       STATUS        current
       DESCRIPTION
         "Indicates the include-all link constraint for the
          detour LSP or bypass tunnel. A link satisfies the
          include-all constraint if and only if the link contains
          all of the administrative groups specified in the
          constraint."
       REFERENCE
         "RFC 3209"
       DEFVAL { 0 }
       ::= { mplsFrrConstEntry 8 }

    mplsFrrConstExclAnyAffinity OBJECT-TYPE
       SYNTAX        MplsTunnelAffinity
       MAX-ACCESS    read-create
       STATUS        current
       DESCRIPTION
         "Indicates the exclude-any link constraint for the
          detour LSP or bypass tunnel. A link satisfies the
          exclude-any constraint if and only if the link contains
          none of the administrative groups specified in the
          constraint."
       REFERENCE
         "RFC 3209"
       DEFVAL { 0 }
       ::= { mplsFrrConstEntry 9 }

    mplsFrrConstHopLimit OBJECT-TYPE
       SYNTAX        Unsigned32
       MAX-ACCESS    read-create
       STATUS        current
       DESCRIPTION



         "The maximum number of hops that the detour LSP or
          bypass tunnel may traverse."
       REFERENCE
         "RFC4090."
       DEFVAL { 32 }
    ::= { mplsFrrConstEntry 10 }

    mplsFrrConstBandwidth OBJECT-TYPE
       SYNTAX        MplsBitRate
       UNITS         "kilobits per second"
       MAX-ACCESS    read-create
       STATUS        current
       DESCRIPTION
         "The maximum bandwidth specifically reserved for detour
          LSP or bypass tunnel, in units of thousands of bits 
          per second (Kbps). Note that setting this value to 0 
          indicates best-effort treatment."
       DEFVAL { 0 }
       ::= { mplsFrrConstEntry 11 }

   mplsFrrConstStorageType OBJECT-TYPE
   SYNTAX        StorageType
   MAX-ACCESS    read-create
   STATUS        current
   DESCRIPTION  
        "The storage type for this configuration entry.
         Conceptual rows having the value 'permanent'
         need not allow write-access to any columnar
         objects in the row."
   REFERENCE
        "RFC2579"
   DEFVAL { volatile }
       ::= { mplsFrrConstEntry 12 }

    mplsFrrConstRowStatus OBJECT-TYPE
       SYNTAX        RowStatus
       MAX-ACCESS    read-create
       STATUS        current
       DESCRIPTION
         "This object is used to create, modify, and/or delete a row in
          this table. When a row in this table is in active(1) 
          state, no objects in that row can be modified by the agent 
          except mplsFrrConstRowStatus and mplsFrrConstStorageType."
       ::= { mplsFrrConstEntry 13 }

    -- MPLS Fast Reroute Tunnel Actual Route Hop table

    mplsFrrTunARHopTable OBJECT-TYPE
       SYNTAX             SEQUENCE OF MplsFrrTunARHopEntry



       MAX-ACCESS         not-accessible
       STATUS             current
       DESCRIPTION
         "This table sparsely extends mplsTunnelARHopTable defined 
          in the MPLS-TE-STD-MIB MIB module with fast-reroute objects. 
          These objects specify the status of local protection including
          availability and active use, on a per-hop basis, of hops
          traversed by a protected tunnel.  Note that object 
          availability in this table is governed by the support of 
          the Record Route Object in the RSVP-TE signaling of the 
          implementation."
       ::= {  mplsFrrGeneralObjects 2 }

    mplsFrrTunARHopEntry  OBJECT-TYPE
       SYNTAX             MplsFrrTunARHopEntry
       MAX-ACCESS         not-accessible
       STATUS             current
       DESCRIPTION
         "This entry contains fast-reroute protection status of a single
          protected tunnel hop."
     INDEX {
       mplsTunnelARHopListIndex,
       mplsTunnelARHopIndex
     }
       ::= { mplsFrrTunARHopTable 1 }

    MplsFrrTunARHopEntry    ::= SEQUENCE {
        mplsFrrTunARHopProtectType      BITS,
        mplsFrrTunARHopProtectTypeInUse BITS
    }

     mplsFrrTunARHopProtectType  OBJECT-TYPE
       SYNTAX                       BITS { path(0), node(1), link(2) }
       MAX-ACCESS                   read-only
       STATUS                       current
       DESCRIPTION
         "This object indicates the protection type or types of the 
          associated path hop object.  Note that since this object is a
          BITS type, one, none or all of the bits may be set to indicate
          various combinations of protection types."
        REFERENCE 
          "See section 4 of RFC4090 where the SESSION_ATTRIBUTE 
           and RECORD_ROUTE objects are extended to
           support bandwidth and node protection features."
       ::= { mplsFrrTunARHopEntry 1 }

     mplsFrrTunARHopProtectTypeInUse OBJECT-TYPE
       SYNTAX                       BITS { path(0), node(1), 
                                           link(2) }




       MAX-ACCESS                   read-only
       STATUS                       current
       DESCRIPTION
         "This object indicates the protection type or types that are 
          currently in use by the associated path hop object.
          Note that since this object is a BITS type, one, none or all 
          of the bits may be set to indicate various combinations of 
          protection types.  If no bits are set, this indicates that
          no protection types are in use."
        REFERENCE 
          "See section 4 of RFC4090 where the SESSION_ATTRIBUTE 
           and RECORD_ROUTE objects are extended to
           support bandwidth and node protection features."
       ::= { mplsFrrTunARHopEntry 2 }

    --
    -- One-to-One Specific Tables
    --
    -- Tables in this section pertain only to the 1-1
    -- style of FRR.
    --

    -- MPLS Fast Reroute Point of Local Repair table

    mplsFrrOne2OnePlrTable  OBJECT-TYPE
       SYNTAX        SEQUENCE OF MplsFrrOne2OnePlrEntry
       MAX-ACCESS    not-accessible
       STATUS        current
       DESCRIPTION
         "This table shows a list of protected TE tunnels with
          the corresponding protecting tunnel, as well as the PLR 
          where the protecting tunnel that initiated the detour 
          LSPs that traverse this node."
       ::= { mplsFrrOne2OneObjects 1 }

    mplsFrrOne2OnePlrEntry  OBJECT-TYPE
       SYNTAX        MplsFrrOne2OnePlrEntry
       MAX-ACCESS    not-accessible
       STATUS        current
       DESCRIPTION
         "An entry in this table represents a protected tunnel LSP
          together with its detour tunnel instance. An entry in 
          this table is only created by an SNMP agent as instructed 
          by an MPLS signaling protocol.

          The entries of this table are present in all LSRs on the path
          of the detour LSP.

          The objects mplsFrrOne2OnePlrTunIdx,



          mplsFrrOne2OnePlrTunDetourInst, mplsFrrOne2OnePlrTunIngrLSRId
          and mplsFrrOne2OnePlrTunEgrLSRId have the same values as
          the objects mplsTunnelIndex, mplsTunnelInstance,
          mplsTunnelIngressLSRId and mplsTunnelEgressLSRId of the detour
          tunnel instance created in the mplsTunnelTable
          (MPLS-TE-STD-MIB)."
       INDEX { mplsFrrOne2OnePlrTunIdx,       -- from MPLS-TE-STD-MIB
               mplsFrrOne2OnePlrTunDetourInst,-- mplsTunnelTable
               mplsFrrOne2OnePlrTunIngrLSRId, -- Tunnels must exist
               mplsFrrOne2OnePlrTunEgrLSRId,  -- a priori
               mplsFrrOne2OnePlrId    }
       ::= { mplsFrrOne2OnePlrTable 1 }

    MplsFrrOne2OnePlrEntry ::= SEQUENCE {
          mplsFrrOne2OnePlrTunIdx         MplsTunnelIndex,
          mplsFrrOne2OnePlrTunDetourInst  MplsTunnelInstanceIndex,
          mplsFrrOne2OnePlrTunIngrLSRId   MplsLsrIdentifier,
          mplsFrrOne2OnePlrTunEgrLSRId    MplsLsrIdentifier,
          mplsFrrOne2OnePlrId             MplsLsrIdentifier,
          mplsFrrOne2OnePlrSenderAddrType InetAddressType,
          mplsFrrOne2OnePlrSenderAddr     InetAddress,
          mplsFrrOne2OnePlrAvoidNAddrType InetAddressType,
          mplsFrrOne2OnePlrAvoidNAddr     InetAddress
    }

    mplsFrrOne2OnePlrTunIdx OBJECT-TYPE
       SYNTAX        MplsTunnelIndex
       MAX-ACCESS    not-accessible
       STATUS        current
       DESCRIPTION
         "Uniquely identifies a tunnel between a pair of LSRs
          from the mplsTunnelEntry."
       ::= { mplsFrrOne2OnePlrEntry 1 }

    mplsFrrOne2OnePlrTunDetourInst OBJECT-TYPE
       SYNTAX        MplsTunnelInstanceIndex
       MAX-ACCESS    not-accessible
       STATUS        current
       DESCRIPTION
         "Uniquely identifies a detour instance of a tunnel from
          the mplsTunnelEntry.

         - lower 16 bits : protected tunnel instance
         - higher 16 bits: detour instance"
       ::= { mplsFrrOne2OnePlrEntry 2 }

    mplsFrrOne2OnePlrTunIngrLSRId OBJECT-TYPE
       SYNTAX        MplsLsrIdentifier
       MAX-ACCESS    not-accessible



       STATUS        current
       DESCRIPTION
         "The purpose of this object is to uniquely identity a
           tunnel within a network. When the MPLS signalling
           protocol is rsvp(2) this object SHOULD contain the 
           same value as the Extended Tunnel Id field in the 
           SESSION object. When the MPLS signalling protocol 
           is crldp(3) this object SHOULD contain the same 
           value as the Ingress LSR Router ID field in the 
           LSPID TLV object.

           This value represents the head-end of the protected 
           tunnel instance."
       REFERENCE
         "RFC3209"
       ::= { mplsFrrOne2OnePlrEntry 3 }

     mplsFrrOne2OnePlrTunEgrLSRId OBJECT-TYPE
       SYNTAX        MplsLsrIdentifier
       MAX-ACCESS    not-accessible
       STATUS        current
       DESCRIPTION
         "Specifies the egress LSR ID of the protected tunnel instance."
       ::= { mplsFrrOne2OnePlrEntry 4 }

    mplsFrrOne2OnePlrId OBJECT-TYPE
       SYNTAX        MplsLsrIdentifier
       MAX-ACCESS    not-accessible
       STATUS        current
       DESCRIPTION
         "This value represents the PLR that has initiated a detour LSP
          to protect a tunnel instance.
          This value is signalled via the DETOUR object defined in MPLS
          RSVP protocol as described in RFC-4090."
       ::= { mplsFrrOne2OnePlrEntry 5 }

    mplsFrrOne2OnePlrSenderAddrType OBJECT-TYPE
       SYNTAX        InetAddressType
       MAX-ACCESS    read-create
       STATUS        current
       DESCRIPTION
         "Denotes the address type of this detour instance's sender
          address."
       DEFVAL        { ipv4 }
       ::= { mplsFrrOne2OnePlrEntry 6 }

    mplsFrrOne2OnePlrSenderAddr OBJECT-TYPE
       SYNTAX        InetAddress
       MAX-ACCESS    read-create



       STATUS        current
       DESCRIPTION
         "The IP address of the PLR which has initiated the detour LSP.
          The type of this address is determined by the value of the
          mplsFrrOne2OnePlrSenderAddrType object."
       ::= { mplsFrrOne2OnePlrEntry 7 }

    mplsFrrOne2OnePlrAvoidNAddrType OBJECT-TYPE
       SYNTAX        InetAddressType
       MAX-ACCESS    read-only
       STATUS        current
       DESCRIPTION
         "Denotes the address type of the node that this PLR tries to
          avoid."
       DEFVAL        { ipv4 }
       ::= { mplsFrrOne2OnePlrEntry 8 }

    mplsFrrOne2OnePlrAvoidNAddr OBJECT-TYPE
       SYNTAX        InetAddress
       MAX-ACCESS    read-only
       STATUS        current
       DESCRIPTION
         "The IP address of the node that this PLR tries to avoid.
          The type of this address is determined by the value of the
          mplsFrrOne2OnePlrAvoidNAddrType object.
          This value is signalled via the DETOUR object defined in MPLS
          RSVP protocol as described in RFC-4090."
       ::= { mplsFrrOne2OnePlrEntry 9 }

    -- MPLS One-To-One Fast Reroute Detour table.

    mplsFrrDetourTable OBJECT-TYPE
       SYNTAX        SEQUENCE OF MplsFrrDetourEntry
       MAX-ACCESS    not-accessible
       STATUS        current
       DESCRIPTION
         "This table shows detour LSPs."
       ::= { mplsFrrOne2OneObjects 2 }

    mplsFrrDetourEntry OBJECT-TYPE
       SYNTAX        MplsFrrDetourEntry
       MAX-ACCESS    not-accessible
       STATUS        current
       DESCRIPTION
         "An entry in this table represents a detour. An entry in this
         table is only created by an SNMP agent as instructed by an MPLS
         signaling protocol. "
       INDEX {
               mplsFrrOne2OnePlrTunIdx,        -- from MPLS-TE-STD-MIB



               mplsFrrOne2OnePlrTunDetourInst, -- mplsTunnelTable
               mplsFrrOne2OnePlrTunIngrLSRId,  -- Tunnels must exist
               mplsFrrOne2OnePlrTunEgrLSRId    -- a priori
          }
       ::= { mplsFrrDetourTable 1 }

    MplsFrrDetourEntry ::= SEQUENCE {
          mplsFrrDetourActive             TruthValue,
          mplsFrrDetourMerging            INTEGER,
          mplsFrrDetourMergedDetourInst   MplsTunnelInstanceIndex
    }

    mplsFrrDetourActive OBJECT-TYPE
       SYNTAX        TruthValue
       MAX-ACCESS    read-only
       STATUS        current
       DESCRIPTION
         "Indicates whether or not the main LSP has switched over to 
          this detour LSP. This is only relevant for detours 
          originated by this node."
       ::= { mplsFrrDetourEntry 1 }

    mplsFrrDetourMerging OBJECT-TYPE
       SYNTAX        INTEGER { none(1),
                               protectedTunnel(2),
                               detour(3)
                             }
       MAX-ACCESS    read-only
       STATUS        current
       DESCRIPTION
         "This value represents whether or not this detour is merged.
          This value MUST be set to none(1) if this detour is not 
          merged.

          This value MUST be set to protectedTunnel(2) if this detour is
          merged with the protected tunnel. This value MUST be set to
          detour(3) if this detour is merged with another detour
          protecting the same tunnel."
       ::= { mplsFrrDetourEntry 2 }

    mplsFrrDetourMergedDetourInst OBJECT-TYPE
       SYNTAX        MplsTunnelInstanceIndex
       MAX-ACCESS    read-only
       STATUS        current
       DESCRIPTION
         "This value represents the instance of the detour with which
          this detour is merged. This object is only valid when
          mplsFrrDetourMerging is set to detour(3).



          - lower 16 bits : protected tunnel instance
          - higher 16 bits: detour instance"
       ::= { mplsFrrDetourEntry 3 }

    --
    -- Facility-based FRR-specific Tables
    -- 
    -- Tables in this section pertain only to the facility-
    -- based style of FRR.
    --

    mplsFrrFacRouteDBTable OBJECT-TYPE
        SYNTAX            SEQUENCE OF MplsFrrFacRouteDBEntry
        MAX-ACCESS        not-accessible
        STATUS            current
        DESCRIPTION
            "The mplsFrrDBTable provides information about the fast
             reroute database.  Each entry belongs to a protected 
             interface, protecting backup tunnel and protected tunnel. 
             MPLS interfaces defined on this node are protected by 
             backup tunnels and are indicated by the index 
             mplsFrrFacRouteProtIfIdx. If the interface index is set 
             to 0, this indicates that the remaining indexes apply 
             to all configured protected interfaces.
             The protecting tunnel is indicated by the second two 
             indexes (mplsTunnelIndex and mplsTunnelInstance) and 
             represents a valid mplsTunnelEntry. Note that the tunnel 
             instance index of the protecting tunnel may be set to 0
             which indicates the tunnel head interface for the 
             protecting tunnel, as per RFC3812, but it may also be
             defined using the following semantics:

             - lower 16 bits : protected tunnel instance
             - higher 16 bits: must be all zeros
           "
    ::= { mplsFrrFacObjects 1 }

    mplsFrrFacRouteDBEntry OBJECT-TYPE
       SYNTAX        MplsFrrFacRouteDBEntry
       MAX-ACCESS    not-accessible
       STATUS        current
       DESCRIPTION
            "An entry in the mplsFrrDBTable represents a single
             protected LSP, protected by a backup tunnel on a
             specific protected interface, or if the interface
             index is set to 0, on all interfaces. Note that for
             brevity, managers should consult the mplsTunnelTable
             present in the MPLS-TE-STD-MIB MIB module for
             additional information about the protecting and protected



             tunnels, and the ifEntry in the IF-MIB MIB module
             for the protected interface."
        INDEX {
                mplsFrrFacRouteProtIfIdx,       -- protected ifIndex 	
                mplsFrrFacRouteProtTunIdx,      -- protecting TE tun
                mplsFrrFacRouteBkupTunIdx,      -- protected TE tun
                mplsFrrFacRouteBkupTunInst,     -- LSP
                mplsFrrFacRouteBkupTunIngrLSRId,  
                mplsFrrFacRouteBkupTunEgrLSRId }  
    ::= { mplsFrrFacRouteDBTable 1 }

    MplsFrrFacRouteDBEntry ::= SEQUENCE {
        mplsFrrFacRouteProtIfIdx          InterfaceIndex,
        mplsFrrFacRouteProtTunIdx         MplsTunnelIndex,
        mplsFrrFacRouteBkupTunIdx         MplsTunnelIndex,
        mplsFrrFacRouteBkupTunInst        MplsTunnelInstanceIndex,
        mplsFrrFacRouteBkupTunIngrLSRId   MplsLsrIdentifier,
        mplsFrrFacRouteBkupTunEgrLSRId    MplsLsrIdentifier,
        mplsFrrFacRouteDBNumProtTunOnIf   Gauge32,
        mplsFrrFacRouteDBNumProtLspOnIf   Gauge32,
        mplsFrrFacRouteDBNumProtTun       Gauge32,
        mplsFrrFacRouteDBProtTunStatus    INTEGER,
        mplsFrrFacRouteDBProtTunResvBw    MplsBitRate
    }

    mplsFrrFacRouteProtIfIdx OBJECT-TYPE
       SYNTAX        InterfaceIndex
       MAX-ACCESS    not-accessible
       STATUS        current
       DESCRIPTION
         "Uniquely identifies the interface configured for FRR 
          protection. If this object is set to 0, this indicates
          that the remaining indexing combinations for this row 
          applies to all interfaces on this device for which 
          the FRR feature can operate."
      ::= { mplsFrrFacRouteDBEntry 1 }

    mplsFrrFacRouteProtTunIdx OBJECT-TYPE
       SYNTAX        MplsTunnelIndex
       MAX-ACCESS    not-accessible
       STATUS        current
       DESCRIPTION
         "Uniquely identifies the mplsTunnelEntry primary index for
          the tunnel head interface designated to protect the
          interface as specified in the mplsFrrFacRouteIfProtIdx
          (and all of the tunnels using this interface). Note 
          that the corresponding mplsTunnelInstance MUST BE
          0 as per the indexing convention stipulated in RFC3812,
          and thus can be inferred."



       ::= { mplsFrrFacRouteDBEntry 2 }

    mplsFrrFacRouteBkupTunIdx OBJECT-TYPE
       SYNTAX        MplsTunnelIndex
       MAX-ACCESS    not-accessible
       STATUS        current
       DESCRIPTION
        "Uniquely identifies the mplsTunnelEntry primary index for
          the TE tunnel LSP being protected on the specified
          interface as specified in the mplsFrrFacRouteIfProtIdx."
       ::= { mplsFrrFacRouteDBEntry 3 }

    mplsFrrFacRouteBkupTunInst OBJECT-TYPE
       SYNTAX        MplsTunnelInstanceIndex
       MAX-ACCESS    not-accessible
       STATUS        current
       DESCRIPTION
        "Uniquely identifies the mplsTunnelEntry secondary index 
         for the TE tunnel LSP being protected on the specified
         interface as specified in the mplsFrrFacRouteIfProtIdx."
       ::= { mplsFrrFacRouteDBEntry 4 }

    mplsFrrFacRouteBkupTunIngrLSRId OBJECT-TYPE
       SYNTAX        MplsLsrIdentifier
       MAX-ACCESS    not-accessible
       STATUS        current
       DESCRIPTION
        "Uniquely identifies the mplsTunnelEntry third index 
         for the TE tunnel LSP being protected on the specified
         interface as specified in the mplsFrrFacRouteIfProtIdx."
       REFERENCE
         "RFC3209, RFC3212"
       ::= { mplsFrrFacRouteDBEntry 5 }

    mplsFrrFacRouteBkupTunEgrLSRId  OBJECT-TYPE
       SYNTAX        MplsLsrIdentifier
       MAX-ACCESS    not-accessible
       STATUS        current
       DESCRIPTION
        "Uniquely identifies the mplsTunnelEntry fourth index 
         for the TE tunnel LSP being protected on the specified
         interface as specified in the mplsFrrFacRouteIfProtIdx."
       ::= { mplsFrrFacRouteDBEntry 6 }

    mplsFrrFacRouteDBNumProtTunOnIf OBJECT-TYPE
        SYNTAX            Gauge32
        MAX-ACCESS        read-only
        STATUS            current
        DESCRIPTION



            "The number of backup tunnels protecting the specified
             interface."
       ::= { mplsFrrFacRouteDBEntry 7 }

    mplsFrrFacRouteDBNumProtLspOnIf OBJECT-TYPE
        SYNTAX            Gauge32
        MAX-ACCESS        read-only
        STATUS            current
        DESCRIPTION
            "The number of LSPs currently being protected on 
             the specified interface."
       ::= { mplsFrrFacRouteDBEntry 8 }

    mplsFrrFacRouteDBNumProtTun OBJECT-TYPE
        SYNTAX            Gauge32
        MAX-ACCESS        read-only
        STATUS            current
        DESCRIPTION
            "The number of tunnels protected on this interface."
    ::= { mplsFrrFacRouteDBEntry 9 }

    mplsFrrFacRouteDBProtTunStatus OBJECT-TYPE
        SYNTAX            INTEGER {
                              active(1),
                              ready(2),
                              partial(3)
                          }
        MAX-ACCESS        read-only
        STATUS            current
        DESCRIPTION
            "Specifies the state of the protected tunnel.

             active  This tunnel's label has been placed in the
                      LFIB and is ready to be applied to incoming
                      packets.

             ready -  This tunnel's label entry has been created but is
                      not yet in the LFIB.

             partial - This tunnel's label entry as not been fully
                       created."
    ::= { mplsFrrFacRouteDBEntry 10 }

    mplsFrrFacRouteDBProtTunResvBw  OBJECT-TYPE
        SYNTAX            MplsBitRate
        UNITS             "kilobits per second"
        MAX-ACCESS        read-only
        STATUS            current
        DESCRIPTION



            "Specifies the amount of bandwidth in units 
             of '1,000 bits per second', actually reserved by 
             the protection tunnel for facility backup purposes. 
             This value is repeated here from the 
             MPLS-TE-STD-MIB MIB module because the tunnel entry will 
             reveal the bandwidth reserved by the signaling protocol, 
             which is typically 0 for backup tunnels so as to not 
             over-book bandwidth. However, internal reservations are 
             typically made on the PLR, thus this value should be 
             revealed here as it is often different from the one found 
             in the MPLS-TE-STD-MIB MIB module."
     ::= { mplsFrrFacRouteDBEntry 11 }

    -- Notifications

    mplsFrrFacProtected NOTIFICATION-TYPE
        OBJECTS { mplsFrrFacRouteDBNumProtTunOnIf,
                  mplsFrrFacRouteDBNumProtLspOnIf,
                  mplsFrrFacRouteDBNumProtTun,
                  mplsFrrFacRouteDBProtTunStatus,
                  mplsFrrFacRouteDBProtTunResvBw
                }
    STATUS      current
    DESCRIPTION
        "This notification is generated when a tunnel running over an
         interface as specified in the mplsFrrConstTable is initially
         protected by the backup tunnel also specified in the
         mplsFrrConstTable. In some implementations there may be
         a difference between when the control plane triggers 
         this notification and when the hardware is programmed to
         utilize the protection path. Due to the urgency of this
         operation, it is acceptable for the control plane to 
         either issue this notification before or after it programs
         the hardware. In cases where it is the latter approach,
         the notification MUST be sent immediately after the
         data plane has been altered.

         This notification should not be generated
         for each subsequent tunnel that is backed up by the FRR feature
         on this LSR, as this may result in potential scaling issues
         with regard to LSR performance and network loading. Note also
         that notifications MUST be generated in accordance with the
         mplsFrrNotifMaxRate.

         Note this notification only applicable to the facility based
         fastreroute protection method, and should be ignored by
         implementations that do not support this method."
        ::= { mplsFrrNotif 1 }



    mplsFrrFacUnProtected NOTIFICATION-TYPE
        OBJECTS { mplsFrrFacRouteDBNumProtTunOnIf,
                  mplsFrrFacRouteDBNumProtLspOnIf,
                  mplsFrrFacRouteDBNumProtTun,
                  mplsFrrFacRouteDBProtTunStatus,
                  mplsFrrFacRouteDBProtTunResvBw
                }
    STATUS      current
    DESCRIPTION
        "This notification is generated when the final tunnel that is
         being protected by a backup tunnel as specified in the
         mplsFrrConstTable is restored to normal operation. This
         notification should not be generated for each restored tunnel,
         as this may result in potential scaling issues with regard to
         LSR performance and network loading. Note also that
         notifications MUST be generated in accordance with the
         mplsFrrNotifMaxRate.  

         Note this notification only applicable to the facility based
         fastreroute protection method, and should be ignored by
         implementations that do not support this method."
        ::= { mplsFrrNotif 2 }

    -- Module Conformance Statement

    mplsFrrGroups
       OBJECT IDENTIFIER ::= {mplsFrrConformance 1 }

    mplsFrrCompliances
       OBJECT IDENTIFIER ::= {mplsFrrConformance 2 }

    mplsFrrModuleFullCompliance MODULE-COMPLIANCE
       STATUS current
       DESCRIPTION
         "Compliance statements for agents that support the 
          MPLS-FRR-STD-MIB MIB module."

      MODULE IF-MIB -- The Interfaces Group MIB module, RFC 2863.
         MANDATORY-GROUPS {
            ifGeneralInformationGroup,
            ifCounterDiscontinuityGroup
         }

      MODULE MPLS-TE-STD-MIB  -- The MPLS Traffic Engineering 
                              -- MIB module, RFC 3812
         MANDATORY-GROUPS {
            mplsTunnelGroup,
            mplsTunnelScalarGroup
         }




       MODULE -- this module
           MANDATORY-GROUPS {
                             mplsFrrScalarGroup,
                             mplsFrrTunARHopGroup,
                             mplsFrrConstGroup
                            }

       OBJECT       mplsFrrConstRowStatus
       SYNTAX       RowStatus { active(1), notInService(2) }
       WRITE-SYNTAX RowStatus { active(1), notInService(2),
                                createAndGo(4), destroy(6)
                              }
       DESCRIPTION "Support for createAndWait and notReady is 
                    not required."

       GROUP mplsFrrOne2OnePLRDetourGroup
       DESCRIPTION
           "This group is mandatory for devices which support
            the one-to-one FRR mechanism, and is optional for
            those which do not."

       GROUP mplsFrrOne2OnePlrGroup
       DESCRIPTION
           "This group is mandatory for devices which support
            the one-to-one FRR mechanism, and is optional for
            those which do not."

       GROUP mplsFrrFacRouteDBGroup
       DESCRIPTION
           "This group is mandatory for devices which support
            the Facility Backup FRR mechanism, and is optional
            for those which do not."

       GROUP mplsFrrNotifGroup
       DESCRIPTION
           "This group is mandatory for devices which support
            the Facility Backup FRR mechanism, and is optional
            for those which do not."

       ::= { mplsFrrCompliances 1 }

    mplsFrrModuleReadOnlyCompliance MODULE-COMPLIANCE
       STATUS current
       DESCRIPTION
         "Compliance statements for agents that support the MPLS FRR
         MIB."
       MODULE
           MANDATORY-GROUPS {



                             mplsFrrScalarGroup,
                             mplsFrrTunARHopGroup,
                             mplsFrrConstGroup
                            }

       GROUP mplsFrrOne2OnePLRDetourGroup
       DESCRIPTION
           "This group is mandatory for devices which support
            the one-to-one FRR mechanism, and is optional for
            those which do not."

       GROUP mplsFrrOne2OnePlrGroup
       DESCRIPTION
           "This group is mandatory for devices which support
            the one-to-one FRR mechanism, and is optional for
            those which do not."

       GROUP mplsFrrFacRouteDBGroup
       DESCRIPTION
           "This group is mandatory for devices which support
            the Facility Backup FRR mechanism, and is optional
            for those which do not."

       GROUP mplsFrrNotifGroup
       DESCRIPTION
           "This group is mandatory for devices which support
            the Facility Backup FRR mechanism, and is optional
            for those which do not."

       -- mplsFrrConstTable
       OBJECT        mplsFrrProtectionMethod
       MIN-ACCESS    read-only
       DESCRIPTION
         "Write access is not required."

       OBJECT        mplsFrrConstProtectionType
       MIN-ACCESS    read-only
       DESCRIPTION
         "Write access is not required."

       OBJECT        mplsFrrConstHopLimit
       MIN-ACCESS    read-only
       DESCRIPTION
         "Write access is not required."

       OBJECT        mplsFrrConstStorageType
       MIN-ACCESS    read-only
       DESCRIPTION
         "Write access is not required."




       OBJECT        mplsFrrConstRowStatus
       MIN-ACCESS    read-only
       DESCRIPTION
         "Write access is not required."

       ::= { mplsFrrCompliances 2 }

    -- Units of conformance

    mplsFrrScalarGroup OBJECT-GROUP
       OBJECTS {
                mplsFrrDetourIncoming,
                mplsFrrDetourOutgoing,
                mplsFrrDetourOriginating,
                mplsFrrSwitchover,
                mplsFrrConfIfs,
                mplsFrrActProtectedIfs,
                mplsFrrConfProtectionTuns,
                mplsFrrActProtectionTuns,
                mplsFrrActProtectedLSPs,
                mplsFrrProtectionMethod,
                mplsFrrNotifsEnabled,
                mplsFrrNotifMaxRate
               }
       STATUS        current
       DESCRIPTION
         "Objects that are required to gather fast reroute statistics."
       ::= { mplsFrrGroups 1 }

    mplsFrrConstGroup OBJECT-GROUP
       OBJECTS {
          mplsFrrConstProtectionType,
          mplsFrrConstHopLimit,
          mplsFrrConstBandwidth,
          mplsFrrConstStorageType,
          mplsFrrConstRowStatus
       }
       STATUS        current
       DESCRIPTION
         "Objects that are required to configure fast reroute
          constraints at the ingress LSR of the tunnel that requires 
          fast reroute service."
       ::= { mplsFrrGroups 2 }

    mplsFrrTunARHopGroup         OBJECT-GROUP
     OBJECTS {
               mplsFrrTunARHopProtectType,
               mplsFrrTunARHopProtectTypeInUse



             }
     STATUS        current
     DESCRIPTION
         "Objects that are required to present per hop fast-reroute
          protection status."
    ::= { mplsFrrGroups 3}

    mplsFrrOne2OnePLRDetourGroup OBJECT-GROUP
     OBJECTS {
              mplsFrrDetourActive,
              mplsFrrDetourMerging,
              mplsFrrDetourMergedDetourInst
             }
     STATUS        current
     DESCRIPTION
         "Objects that are required to present the detour LSP 
          information at the detour ingress, transit and egress LSRs."
     ::= { mplsFrrGroups 4 }

    mplsFrrOne2OnePlrGroup OBJECT-GROUP
      OBJECTS {
          mplsFrrOne2OnePlrSenderAddrType,
          mplsFrrOne2OnePlrSenderAddr,
          mplsFrrOne2OnePlrAvoidNAddrType,
          mplsFrrOne2OnePlrAvoidNAddr
         }
    STATUS        current
    DESCRIPTION
       "Objects that are required to represent the FRR
        One-2-One PLR information."
    ::= { mplsFrrGroups 5 }

    mplsFrrFacRouteDBGroup OBJECT-GROUP
      OBJECTS { mplsFrrFacRouteDBNumProtTunOnIf,
                mplsFrrFacRouteDBNumProtLspOnIf,
                mplsFrrFacRouteDBNumProtTun,
                mplsFrrFacRouteDBProtTunStatus,
                mplsFrrFacRouteDBProtTunResvBw
        }
    STATUS        current
    DESCRIPTION
       "Objects that are required to represent the FRR
        Facility Route Database information."
    ::= { mplsFrrGroups 6 }

    mplsFrrNotifGroup NOTIFICATION-GROUP
    NOTIFICATIONS { mplsFrrFacProtected,
                    mplsFrrFacUnProtected
                  }




    STATUS        current
    DESCRIPTION
         "Objects that are required to represent FRR notifications."
    ::= { mplsFrrGroups 7 }

    END

--    Copyright (C) The IETF Trust (2007).
-- 
--    This document is subject to the rights, licenses and restrictions
--    contained in BCP 78, and except as set forth therein, the authors
--    retain all their rights.
-- 
--    This document and the information contained herein are provided on an
--    "AS IS" basis and THE CONTRIBUTOR, THE ORGANIZATION HE/SHE REPRESENTS
--    OR IS SPONSORED BY (IF ANY), THE INTERNET SOCIETY, THE IETF TRUST AND
--    THE INTERNET ENGINEERING TASK FORCE DISCLAIM ALL WARRANTIES, EXPRESS
--    OR IMPLIED, INCLUDING BUT NOT LIMITED TO ANY WARRANTY THAT THE USE OF
--    THE INFORMATION HEREIN WILL NOT INFRINGE ANY RIGHTS OR ANY IMPLIED
--    WARRANTIES OF MERCHANTABILITY OR FITNESS FOR A PARTICULAR PURPOSE.
-- 
-- 
-- Intellectual Property
-- 
--    The IETF takes no position regarding the validity or scope of any
--    Intellectual Property Rights or other rights that might be claimed to
--    pertain to the implementation or use of the technology described in
--    this document or the extent to which any license under such rights
--    might or might not be available; nor does it represent that it has
--    made any independent effort to identify any such rights.  Information
--    on the procedures with respect to rights in RFC documents can be
--    found in BCP 78 and BCP 79.
-- 
--    Copies of IPR disclosures made to the IETF Secretariat and any
--    assurances of licenses to be made available, or the result of an
--    attempt made to obtain a general license or permission for the use of
--    such proprietary rights by implementers or users of this
--    specification can be obtained from the IETF on-line IPR repository at
--    http://www.ietf.org/ipr.
-- 
--    The IETF invites any interested party to bring to its attention any
--    copyrights, patents or patent applications, or other proprietary
--    rights that may cover technology that may be required to implement
--    this standard.  Please address the information to the IETF at
--    ietf-ipr@ietf.org.
--
