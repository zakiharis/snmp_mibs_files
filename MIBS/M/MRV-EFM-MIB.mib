-- ===================================================================
--  File        : MRV-EFM.MIB
--  Description : Ethernet in the First Mile
--              : Private MIB for MRV 802.3ah devices
--  By          : Grant Schnebly
--  Version     : $Revision: 1.0 $
--  Date        : $Date: 2003/06/23 12:38:07 $
--  Updates     :
--              :
--  ==================================================================
--
--
-- *******************************************************************
-- Copyright (c) 2003 MRV Communications, Inc.  All Rights Reserved.
--
-- Reproduction of this document is authorized on condition that this
-- copyright notice is included.  This MRV SNMP MIB Specification
-- embodies MRV's proprietary intellectual property.  MRV
-- retains all title and ownership in the specification, including any
-- revisions.
--
-- It is MRV's intent to encourage the widespread use of this
-- specification in connection with the management of MRV's
-- products. MRV grants vendor, end-users, and other interested
-- parties a non-exclusive license to use this specification in
-- connection with the management of MRV's products.
--
-- This specification is supplied "AS IS," and MRV makes no
-- warranty, either express or implied, as to the use, operation,
-- condition, or performance of the specification.
--
--
-- MRV retains the right to change this MIB without notification.
--
-- *******************************************************************


MRV-EFM-MIB DEFINITIONS ::= BEGIN

IMPORTS
    Unsigned32, Counter32, Counter64,
    OBJECT-TYPE, MODULE-IDENTITY, OBJECT-IDENTITY
        FROM SNMPv2-SMI
    TEXTUAL-CONVENTION
        FROM SNMPv2-TC
    OBJECT-GROUP
        FROM SNMPv2-CONF
    InterfaceIndex, nbs
        FROM NBS-CMMC-MIB;

mrvEfmMib  MODULE-IDENTITY
    LAST-UPDATED  "200306231238Z"
    ORGANIZATION  "MRV Communications, Inc."
    CONTACT-INFO
        "Contact:  Grant Schnebly
         Postal:   20520 Nordhoff St,
                   Chatsworth
                   CA 91311
                   USA
            Tel:   (818) 772-6235
            Fax:   (818) 772-0576
          Email:   gschnebly@mrv.com"

    DESCRIPTION
        "Private MRV MIB for representing 802.3ah (Ethernet in the
         First Mile) information"
    ::= { nbs 300 }


mrvEfmProduct          OBJECT IDENTIFIER ::= { mrvEfmMib 2 }
mrvEfmNc316Nm          OBJECT IDENTIFIER ::= { mrvEfmProduct  1 }

-- *******************************************************************
-- Textual conventions
-- *******************************************************************

Unsigned16 ::= TEXTUAL-CONVENTION
     STATUS       current
     DESCRIPTION
        "Used to represent an unsigned two-octet integer"
     SYNTAX    Unsigned32 (0..65535)

Unsigned64 ::= TEXTUAL-CONVENTION
    STATUS      current
    DESCRIPTION
        "Used to represent an unsigned eight-octet integer"
    SYNTAX      Counter64

-- *******************************************************************
-- MRVEFM MIB Objects Identifier Definition
-- *******************************************************************
mrvEfmObjects  OBJECT-IDENTITY
    STATUS current
    DESCRIPTION
        "all MIB objects in mrvEfm MIB."
::= { mrvEfmMib 1 }

-- *******************************************************************
-- Groups in MRVEFM-MIB - all under mrvEfmObjects
-- *******************************************************************


-- mrvEfmDteMacGrp  OBJECT-IDENTITY
--     STATUS current
--     DESCRIPTION
--         "All DTE MAC Objects."
-- ::= { mrvEfmObjects 1 }

-- mrvEfmMauGrp  OBJECT-IDENTITY
--     STATUS current
--     DESCRIPTION
--         "All MAU objects."
-- ::= { mrvEfmObjects 2 }

mrvEfmOamGrp  OBJECT-IDENTITY
    STATUS  current
    DESCRIPTION
        "All OAM objects."
::= { mrvEfmObjects 3 }

-- mrvEfmOmpGrp  OBJECT-IDENTITY
--     STATUS  current
--     DESCRIPTION
--         "All OMP objects."
-- ::= { mrvEfmObjects 4 }

-- mrvOsTraps OBJECT-IDENTITY
--     STATUS current
--     DESCRIPTION
--         "All Defined Specific Traps."
-- ::= { mrvOsMIBObjects 5 }



-- *******************************************************************
-- Objects in the OAM Group.
-- *******************************************************************



mrvEfmOamTable  OBJECT-TYPE
    SYNTAX      SEQUENCE OF MrvEfmOamEntry
    MAX-ACCESS  not-accessible
    STATUS      current
    DESCRIPTION
        "Operations, Administration, and Management information"
    ::= { mrvEfmOamGrp 1 }

mrvEfmOamEntry      OBJECT-TYPE
    SYNTAX  MrvEfmOamEntry
    MAX-ACCESS  not-accessible
    STATUS      current
    DESCRIPTION
        "Contains a desription of a particular Oam.  There are two
        entries for each OAM link, one entry for the local side,
        one for the remote."
    INDEX { mrvEfmPhysicalIfIndex }
    ::= { mrvEfmOamTable 1 }


MrvEfmOamEntry ::= SEQUENCE {
    mrvEfmPhysicalIfIndex            InterfaceIndex,
    mrvEfmOamIfIndex                 InterfaceIndex,
    mrvEfmOamPeerIfIndex             InterfaceIndex,
    mrvEfmOamMode                    INTEGER,
    mrvEfmOamCfg                     OCTET STRING,
    mrvEfmOamPduCfg                  Unsigned16,
    mrvEfmOamFlagsField              OCTET STRING,
    mrvEfmOamState                   OCTET STRING,
    mrvEfmOamVendorOUI               OCTET STRING,
    mrvEfmOamVendorDeviceId          Unsigned16,
    mrvEfmOamVendorDeviceVersion     Unsigned16,
    mrvEfmOamPDUTx                   Counter32,
    mrvEfmOamPDURx                   Counter32,
    mrvEfmOamUnsupportedCodesRx      Counter32,
    mrvEfmOamInformationTx           Counter32,
    mrvEfmOamInformationRx           Counter32,
    mrvEfmOamEventNotificationTx     Counter32,
    mrvEfmOamUniEventNotificationRx  Counter32,
    mrvEfmOamDupEventNotificationRx  Counter32,
    mrvEfmOamLoopbackControlTx       Counter32,
    mrvEfmOamLoopbackControlRx       Counter32,
    mrvEfmOamVariableRequestTx       Counter32,
    mrvEfmOamVariableRequestRx       Counter32,
    mrvEfmOamVariableResponseTx      Counter32,
    mrvEfmOamVariableResponseRx      Counter32,
    mrvEfmOamOrganizationSpecificTx  Counter32,
    mrvEfmOamOrganizationSpecificRx  Counter32,
    mrvEfmOamErrSymPerCfgDuration    Unsigned64,
    mrvEfmOamErrSymPerCfgThreshld    Unsigned32,
    mrvEfmOamErrSymPerEvtTime        Unsigned16,
    mrvEfmOamErrSymPerEvtWindow      Unsigned64,
    mrvEfmOamErrSymPerEvtThreshld    Unsigned64,
    mrvEfmOamErrSymPerEvtCount       Counter64,
    mrvEfmOamErrFrmCfgDuration       Unsigned32,
    mrvEfmOamErrFrmCfgThreshld       Unsigned32,
    mrvEfmOamErrFrmEvtTime           Unsigned16,
    mrvEfmOamErrFrmEvtWindow         Unsigned16,
    mrvEfmOamErrFrmEvtThreshld       Unsigned32,
    mrvEfmOamErrFrmEvtCount          Counter64,
    mrvEfmOamErrFrmPerCfgDuration    Unsigned32,
    mrvEfmOamErrFrmPerCfgThreshld    Unsigned32,
    mrvEfmOamErrFrmPerEvtTime        Unsigned16,
    mrvEfmOamErrFrmPerEvtWindow      Unsigned32,
    mrvEfmOamErrFrmPerEvtThreshld    Unsigned32,
    mrvEfmOamErrFrmPerEvtCount       Counter64,
    mrvEfmOamErrFrmSecSumCfgDuration Unsigned16,
    mrvEfmOamErrFrmSecSumCfgThreshld Unsigned16,
    mrvEfmOamErrFrmSecSumEvtTime     Unsigned16,
    mrvEfmOamErrFrmSecSumEvtWindow   Unsigned16,
    mrvEfmOamErrFrmSecSumEvtThreshld Unsigned16,
    mrvEfmOamErrFrmSecSumEvtCount    Counter32,
    mrvEfmOamFramesLostDueToOamError Counter32,
    mrvEfmOamAdminState              INTEGER,
    mrvEfmOamOperState               OCTET STRING
}

mrvEfmPhysicalIfIndex  OBJECT-TYPE
    SYNTAX      InterfaceIndex
    MAX-ACCESS  read-only
    STATUS      current
    DESCRIPTION
        "ifIndex from the MIB-II Interface Table for the physical
        port on which this OAM traffic flows."
    ::= { mrvEfmOamEntry 1 }

mrvEfmOamIfIndex OBJECT-TYPE
    SYNTAX      InterfaceIndex
    MAX-ACCESS  read-only
    STATUS      current
    DESCRIPTION
        "ifIndex from the MIB-II Interface Table for this OAM
         interface."
    ::= {mrvEfmOamEntry  2 }

mrvEfmOamPeerIfIndex OBJECT-TYPE
    SYNTAX      InterfaceIndex
    MAX-ACCESS  read-only
    STATUS      current
    DESCRIPTION
        "ifIndex from the MIB-II Interface Table for the physical
        port on the other side of the OAM link.  For
        example, if this table entry corresponds to a local
        OAM device, this object would hold the ifIndex of the
        remote port."
    ::= { mrvEfmOamEntry 3 }

mrvEfmOamMode  OBJECT-TYPE
    SYNTAX      INTEGER {
        notSupported    (1),
        passive         (2),
        active          (3)
    }
    MAX-ACCESS  read-only
    STATUS      current
    DESCRIPTION
        "A GET operation returns the current mode of the OAM
        sublayer entity (see 57.2.6), either passive or
        active. A SET operation changes the mode of operation
        of the OAM entity to the indicated value. A SET
        operation shall have no effect on a device whose mode
        cannot be changed through management or that can only
        operate in a single mode."
    REFERENCE   "IEEE 802.3ah, Clause 57"
    ::= {mrvEfmOamEntry  4 }


-- mrvEfmOamRemoteMACAddress OBJECT-TYPE
--     SYNTAX  MacAddress
--     ACCESS  read-only
--     STATUS  mandatory
--     DESCRIPTION
--         "The value of the source-address parameter of the last
--         OAMPDU passed by the OAM subordinate sublayer to the OAM
--         sublayer. This value is updated on reception of a valid
--         frame with (1) a destinationField equal to the reserved
--         multicast address for Slow-Protocols specified in CROSS
--         REF Table 43B-1, (2) lengthOrType field value equal to
--         the reserved Type for Slow-Protocols as specified in
--         CROSS REF Table 43B-2, (3) a Slow-Protocols subtype
--         value equal to the subtype reserved for OAM as specified
--         in Table 43B-3."
--     ::= {mrvEfmOamEntry  4 }

mrvEfmOamCfg OBJECT-TYPE
    SYNTAX      OCTET STRING (SIZE(1))
    MAX-ACCESS  read-only
    STATUS      current
    DESCRIPTION
        "A string of three bits corresponding to the OAM
        Configuration field (see Table 57-7) in the most recently
        received Information OAMPDU. The first bit corresponds to
        the OAM Mode bit in the OAM Configuration field. The
        second bit corresponds to the Unidirectional Support bit
        in the OAM Configuration field. The third bit corresponds
        to the Loopback Support bit in the OAM Configuration
        field.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        the OAM code equals the OAM Information code."
    REFERENCE   "IEEE 802.3ah, Clause 57"
    ::= { mrvEfmOamEntry 5 }

mrvEfmOamPduCfg OBJECT-TYPE
    SYNTAX      Unsigned16
    MAX-ACCESS  read-only
    STATUS      current
    DESCRIPTION
        "An eleven bit value corresponding to the Maximum PDU Size
        value within the OAMPDU Configuration field (see Table
        57-8) in the most recently sent Information OAMPDU.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        the OAM code equals the OAM Information code."
    REFERENCE   "IEEE 802.3ah, Clause 57"
    ::= { mrvEfmOamEntry 6 }

mrvEfmOamFlagsField OBJECT-TYPE
    SYNTAX      OCTET STRING (SIZE(1))
    MAX-ACCESS  read-only
    STATUS      current
    DESCRIPTION
        "A string of five bits corresponding to the Flags field
        (see Table 57-3) in the most recently transmitted OAMPDU.
        The first bit corresponds to the Link Fault bit in the
        Flags field. The second bit corresponds to the Dying Gasp
        bit in the Flags field. The third bit corresponds to the
        Critical Event bit in the Flags field. The fourth bit
        corresponds to the Remote Stable bit in the Flags field.
        The fifth bit corresponds to the Local Stable bit in the
        Flags field."
    REFERENCE   "IEEE 802.3ah, Clause 57"
    ::= { mrvEfmOamEntry 7 }


mrvEfmOamState OBJECT-TYPE
    SYNTAX      OCTET STRING (SIZE(1))
    MAX-ACCESS  read-only
    STATUS      current
    DESCRIPTION
        "A string of three bits corresponding to the State field
        (see Table 57-6) of the most recently sent Information
        OAMPDU. The first and second bits corresponds to the
        Parser Action bits in the State field. The third bit
        corresponds to the Multiplexer Action bit in the State
        field.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        a OAMPDU code equal to the Information code as specified
        in Table 57-4."
    REFERENCE   "IEEE 802.3ah, Clause 57"
    ::= { mrvEfmOamEntry 8 }

mrvEfmOamVendorOUI  OBJECT-TYPE
    SYNTAX      OCTET STRING (SIZE(3))
    MAX-ACCESS  read-only
    STATUS      current
    DESCRIPTION
        "The value of the OUI variable in the Vendor Identifier
        field (see Table 57-9) of the most recently sent
        Information OAMPDU.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        a OAMPDU code equal to the Information code as specified
        in Table 57-4."
    REFERENCE   "IEEE 802.3ah, Clause 57"
    ::= { mrvEfmOamEntry 9 }

mrvEfmOamVendorDeviceId OBJECT-TYPE
    SYNTAX      Unsigned16
    MAX-ACCESS  read-only
    STATUS      current
    DESCRIPTION
        "The value of the Device Identifier variable in the Vendor
        Identifier field (see Table 57-9) of the most recently
        sent Information OAMPDU.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        a OAMPDU code equal to the Information code as specified
        in Table 57-4."
    REFERENCE   "IEEE 802.3ah, Clause 57"
    ::= { mrvEfmOamEntry 10 }

mrvEfmOamVendorDeviceVersion  OBJECT-TYPE
    SYNTAX      Unsigned16
    MAX-ACCESS  read-only
    STATUS      current
    DESCRIPTION
        "The value of the Version Identifier variable in the
        Vendor Identifier field (see Table 57-9) of the most
        recently sent Information OAMPDU.
        This value is updated on reception of a valid frame, with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        a OAMPDU code equal to the Information code as specified
        in Table 57-4."
    REFERENCE   "IEEE 802.3ah, Clause 57"
    ::= { mrvEfmOamEntry 11 }

mrvEfmOamPDUTx OBJECT-TYPE
    SYNTAX      Counter32
    MAX-ACCESS  read-only
    STATUS      current
    DESCRIPTION
        "A count of OAMPDUs passed to the OAM subordinate sublayer
        for transmission. This counter is incremented when a
        OAM:MA_DATA.request service service primitive is generated
        within the OAM sublayer."
    REFERENCE   "IEEE 802.3ah, Clause 57"
    ::= { mrvEfmOamEntry 12 }

mrvEfmOamPDURx OBJECT-TYPE
    SYNTAX      Counter32
    MAX-ACCESS  read-only
    STATUS      current
    DESCRIPTION
        "A count of OAMPDUs passed by the OAM subordinate sublayer
        to the OAM sublayer. This counter is incremented on
        reception of a valid frame with (1) a destinationField
        equal to the reserved multicast address for Slow_Protocols
        specified in CROSS REF Table 43B-1, (2) lengthOrType field
        value equal to the reserved Type for Slow_Protocols as
        specified in CROSS REF Table 43B-2, (3) a Slow_Protocols
        subtype value equal to the subtype reserved for OAM as
        specified in Table 43B-3."
    REFERENCE   "IEEE 802.3ah, Clause 57"
    ::= { mrvEfmOamEntry 13 }

mrvEfmOamUnsupportedCodesRx  OBJECT-TYPE
    SYNTAX      Counter32
    MAX-ACCESS  read-only
    STATUS      current
    DESCRIPTION
        "A count of OAMPDUs received that contain an OAM code from
        Table 57-4 that are not supported by the device. This
        counter is incremented on reception of a valid frame with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        an OAM code for a function that is not supported by the
        device."
    REFERENCE   "IEEE 802.3ah, Clause 57"
    ::= { mrvEfmOamEntry 14 }

mrvEfmOamInformationTx OBJECT-TYPE
    SYNTAX      Counter32
    MAX-ACCESS  read-only
    STATUS      current
    DESCRIPTION
        "A count of OAMPDUs passed to the OAM subordinate sublayer
        for transmission that contain the OAM Information code
        specified in Table CROSS REF 57-4. This counter is
        incremented when a OAM:MA_DATA.request service primitive
        is generated within the OAM sublayer with an OAM code
        indicating an OAM Information operation."
    REFERENCE   "IEEE 802.3ah, Clause 57"
    ::= { mrvEfmOamEntry 15 }

mrvEfmOamInformationRx OBJECT-TYPE
    SYNTAX      Counter32
    MAX-ACCESS  read-only
    STATUS      current
    DESCRIPTION
        "A count of OAMPDUs received that contain the OAM
        Information code specified in Table 57-4. This
        counter is incremented on reception of a valid frame with
        (1) destinationField equal to the reserved multicast
        address for Slow_Protocols specified in CROSS REF Table
        43B-1, (2) lengthOrType field value equal to the reserved
        Type for Slow_Protocols as specified in CROSS REF Table
        43B-2, (3) a Slow_Protocols subtype value equal to the
        subtype reserved for OAM as specified in Table 43B-3, (4)
        an OAM code for a function that is not supported by the
        device."
    REFERENCE   "IEEE 802.3ah, Clause 57"
    ::= { mrvEfmOamEntry 16 }

mrvEfmOamEventNotificationTx OBJECT-TYPE
    SYNTAX      Counter32
    MAX-ACCESS  read-only
    STATUS      current
    DESCRIPTION
        "A count of OAMPDUs passed to the OAM subordinate sublayer
        for transmission that contain the Event Notification code
        specified in Table 57-4. This counter is incremented when
        a OAM:MA_DATA.request service primitive is generated
        within the OAM sublayer with an OAM code indicating an
        Event Notification operation."
    REFERENCE   "IEEE 802.3ah, Clause 57"
    ::= { mrvEfmOamEntry 17 }


mrvEfmOamUniEventNotificationRx OBJECT-TYPE
    SYNTAX      Counter32
    MAX-ACCESS  read-only
    STATUS      current
    DESCRIPTION
        "A count of the OAMPDUs received that contain the Event
        Notification code specified in Table 57-4. This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in CROSS REF Table 43B-3,
        (4) the OAM code equals the Event Notification code, (5)
        the Sequence Number field is not equal to the Sequence
        Number field of the last received Event Notification
        OAMPDU and is supported by the device."
    REFERENCE   "IEEE 802.3ah, Clause 57"
    ::= { mrvEfmOamEntry 18 }

mrvEfmOamDupEventNotificationRx OBJECT-TYPE
    SYNTAX      Counter32
    MAX-ACCESS  read-only
    STATUS      current
    DESCRIPTION
        "A count of the OAMPDUs received that contain the Event
        Notification code specified in Table 57-4. This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in CROSS REF Table 43B-3,
        (4) the OAM code equals the Event Notification code, (5)
        the Sequence Number field is equal to the Sequence
        Number field of the last received Event Notification
        OAMPDU."
    REFERENCE   "IEEE 802.3ah, Clause 57"
    ::= { mrvEfmOamEntry 19 }

mrvEfmOamLoopbackControlTx  OBJECT-TYPE
    SYNTAX      Counter32
    MAX-ACCESS  read-only
    STATUS      current
    DESCRIPTION
        "A count of OAMPDUs passed to the OAM subordinate
        sublayer for transmission that contain the Loopback
        Control code specified in Table 57-4. This counter is
        incremented when a OAM:MA_DATA.request service primitive
        is generated within the OAM sublayer with an OAM code
        indicating a Loopback Control operation."
    REFERENCE   "IEEE 802.3ah, Clause 57"
    ::= { mrvEfmOamEntry 20 }


mrvEfmOamLoopbackControlRx  OBJECT-TYPE
    SYNTAX      Counter32
    MAX-ACCESS  read-only
    STATUS      current
    DESCRIPTION
        "A count of OAMPDUs received that contain the Loopback
        Control code specified in Table 57-4. This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in Table 43B-3, (4) the OAM
        code equals the Loopback Control code and is supported by
        the device."
    REFERENCE   "IEEE 802.3ah, Clause 57"
    ::= { mrvEfmOamEntry 21 }

mrvEfmOamVariableRequestTx OBJECT-TYPE
    SYNTAX      Counter32
    MAX-ACCESS  read-only
    STATUS      current
    DESCRIPTION
        "A count of OAMPDUs passed to the OAM subordinate sublayer
        for transmission that contain the Variable Request code
        specified in Table 57-4. This counter is incremented when
        a OAM:MA_DATA.request service primitive is generated
        within the OAM sublayer with an OAM code indicating a
        Variable Request operation."
    REFERENCE   "IEEE 802.3ah, Clause 57"
    ::= { mrvEfmOamEntry 22 }

mrvEfmOamVariableRequestRx  OBJECT-TYPE
    SYNTAX      Counter32
    MAX-ACCESS  read-only
    STATUS      current
    DESCRIPTION
        "A count of OAMPDUs received that contain the Variable
        Request code specified in Table 57-4.  This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in Table 43B-3, (4) the OAM
        code equals the Variable Request code and is supported by
        the device."
    REFERENCE   "IEEE 802.3ah, Clause 57"
    ::= { mrvEfmOamEntry 23 }

mrvEfmOamVariableResponseTx OBJECT-TYPE
    SYNTAX      Counter32
    MAX-ACCESS  read-only
    STATUS      current
    DESCRIPTION
        "A count of OAMPDUs passed to the OAM subordinate sublayer
        for transmission that contain the Variable Response code
        specified in Table 57-4. This counter is incremented when
        a OAM:MA_DATA.request service primitive is generated
        within the OAM sublayer with an OAM code indicating a
        Variable Response operation."
    REFERENCE   "IEEE 802.3ah, Clause 57"
    ::= { mrvEfmOamEntry 24 }

mrvEfmOamVariableResponseRx OBJECT-TYPE
    SYNTAX      Counter32
    MAX-ACCESS  read-only
    STATUS      current
    DESCRIPTION
        "A count of OAMPDUs received that contain the Variable
        Response code specified in Table 57-4. This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in Table 43B-3, (4) the OAM
        code equals the Variable Response code and is supported by
        the device."
    REFERENCE   "IEEE 802.3ah, Clause 57"
    ::= { mrvEfmOamEntry 25 }

mrvEfmOamOrganizationSpecificTx  OBJECT-TYPE
    SYNTAX      Counter32
    MAX-ACCESS  read-only
    STATUS      current
    DESCRIPTION
        "A count of Organization Specific OAMPDUs passed to the
        OAM subordinate sublayer for transmission that contain the
        Organization Specific code specified in Table 57-4. This
        counter is incremented when a OAM:MA_DATA.request service
        primitive is generated within the OAM sublayer with an OAM
        code indicating a Organization Specific operation."
    REFERENCE   "IEEE 802.3ah, Clause 57"
    ::= { mrvEfmOamEntry 26 }

mrvEfmOamOrganizationSpecificRx OBJECT-TYPE
    SYNTAX      Counter32
    MAX-ACCESS  read-only
    STATUS      current
    DESCRIPTION
        "A count of OAMPDUs received that contain the Organization
        Specific code specified in Table 57-4. This counter is
        incremented on reception of a valid frame, with (1)
        destinationField equal to the reserved multicast address
        for Slow_Protocols specified in CROSS REF Table 43B-1, (2)
        lengthOrType field value equal to the reserved Type for
        Slow_Protocols as specified in CROSS REF Table 43B-2, (3)
        a Slow_Protocols subtype value equal to the subtype
        reserved for OAM as specified in Table 43B-3, (4) the OAM
        code equals the Organization Specific code and is
        supported by the device."
    REFERENCE   "IEEE 802.3ah, Clause 57"
    ::= { mrvEfmOamEntry 27 }

mrvEfmOamErrSymPerCfgDuration OBJECT-TYPE
    SYNTAX      Unsigned64
    MAX-ACCESS  read-only
    STATUS      current
    DESCRIPTION
        "An eight-octet value indicating the duration of the
        Errored Symbol Period Event (see 57.5.3.1) window, in
        terms of symbols."
    REFERENCE   "IEEE 802.3ah, Clause 57"
    ::= { mrvEfmOamEntry 28 }

mrvEfmOamErrSymPerCfgThreshld OBJECT-TYPE
    SYNTAX      Unsigned32
    MAX-ACCESS  read-only
    STATUS      current
    DESCRIPTION
        "A four-octet value indicating the number of errored
        symbols in the period that must be exceeded in order for
        the Errored Symbol Period Event to be generated."
    REFERENCE   "IEEE 802.3ah, Clause 57"
    ::= { mrvEfmOamEntry 29 }

mrvEfmOamErrSymPerEvtTime OBJECT-TYPE
    SYNTAX      Unsigned16
    MAX-ACCESS  read-only
    STATUS      current
    DESCRIPTION
        "An integer corresponding to the Event Time Stamp field in
        the most recently transmitted Errored Symbol Period Event
        TLV in an Event Notification OAMPDU (see 57.4.3.2).
        This integer is updated when a OAM:MA_DATA.request
        service primitive is generated within the OAM sublayer
        with an OAMPDU Code field value equal to the Event
        Notification code as specified in Table 57-4 and Event TLV
        Type field equal to the Errored Symbol Period Event value
        as specified in Table 57-10."
    REFERENCE   "IEEE 802.3ah, Clause 57"
    ::= {mrvEfmOamEntry  30 }

mrvEfmOamErrSymPerEvtWindow OBJECT-TYPE
    SYNTAX      Unsigned64
    MAX-ACCESS  read-only
    STATUS      current
    DESCRIPTION
        "An integer corresponding to the Errored Symbol Window
        field in the most recently transmitted Errored Symbol
        Period Event TLV in an Event Notification OAMPDU (see
        57.4.3.2).
        This integer is updated when a OAM:MA_DATA.request
        service primitive is generated within the OAM sublayer
        with an OAMPDU Code field value equal to the Event
        Notification code as specified in Table 57-4 and Event TLV
        Type field equal to the Errored Symbol Period Event value
        as specified in Table 57-10."
    REFERENCE   "IEEE 802.3ah, Clause 57"
    ::= {mrvEfmOamEntry  31 }

mrvEfmOamErrSymPerEvtThreshld OBJECT-TYPE
    SYNTAX      Unsigned64
    MAX-ACCESS  read-only
    STATUS      current
    DESCRIPTION
        "An integer corresponding to the Errored Symbol Threshold
        field in the most recently transmitted Errored Symbol
        Period Event TLV in an Event Notification OAMPDU (see
        57.4.3.2).
        This integer is updated when a OAM:MA_DATA.request
        service primitive is generated within the OAM sublayer
        with an OAMPDU Code field value equal to the Event
        Notification code as specified in Table 57-4 and Event TLV
        Type field equal to the Errored Symbol Period Event value
        as specified in Table 57-10."
    REFERENCE   "IEEE 802.3ah, Clause 57"
    ::= {mrvEfmOamEntry  32 }

mrvEfmOamErrSymPerEvtCount OBJECT-TYPE
    SYNTAX      Counter64
    MAX-ACCESS  read-only
    STATUS      current
    DESCRIPTION
        "An integer corresponding to the Error Running Total field
        in the most recently transmitted Errored Symbol Period
        Event TLV in an Event Notification OAMPDU (see 57.4.3.2).
        This integer is updated when a OAM:MA_DATA.request
        service primitive is generated within the OAM sublayer
        with an OAMPDU Code field value equal to the Event
        Notification code as specified in Table 57-4 and Event TLV
        Type field equal to the Errored Symbol Period Event value
        as specified in Table 57-10."
    REFERENCE   "IEEE 802.3ah, Clause 57"
    ::= {mrvEfmOamEntry  33 }

mrvEfmOamErrFrmCfgDuration  OBJECT-TYPE
    SYNTAX      Unsigned32
    MAX-ACCESS  read-only
    STATUS      current
    DESCRIPTION
        "A four-octet value indicating the duration of the Errored
        Frame Event (see 57.5.3.2) window, in terms of number of
        100ms intervals."
    REFERENCE   "IEEE 802.3ah, Clause 57"
    ::= { mrvEfmOamEntry 34 }

mrvEfmOamErrFrmCfgThreshld OBJECT-TYPE
    SYNTAX      Unsigned32
    MAX-ACCESS  read-only
    STATUS      current
    DESCRIPTION
        "A four-octet field indicating the number of errored
        frames in the period that must be exceeded in order for
        the Errored Frame Event to be generated."
    REFERENCE   "IEEE 802.3ah, Clause 57"
    ::= { mrvEfmOamEntry 35 }

mrvEfmOamErrFrmEvtTime  OBJECT-TYPE
    SYNTAX      Unsigned16
    MAX-ACCESS  read-only
    STATUS      current
    DESCRIPTION
        "An integer corresponding to the Event Time Stamp field in
        the most recently transmitted Errored Frame Event TLV in
        an Event Notification OAMPDU (see 57.4.3.2). This integer
        is updated when a OAM:MA_DATA.request service primitive is
        generated within the OAM sublayer with an OAMPDU Code
        field value equal to the Event Notification code as
        specified in Table 57-4 and Event TLV Type field equal to
        the Errored Frame Event value as specified in Table 57-10."
    REFERENCE   "IEEE 802.3ah, Clause 57"
    ::= {mrvEfmOamEntry  36 }

mrvEfmOamErrFrmEvtWindow OBJECT-TYPE
    SYNTAX      Unsigned16
    MAX-ACCESS  read-only
    STATUS      current
    DESCRIPTION
        "An integer corresponding to the Errored Frame Window
        field in the most recently transmitted Errored Frame
        Event TLV in an Event Notification OAMPDU (see
        57.4.3.2).
        This integer is updated when a OAM:MA_DATA.request
        service primitive is generated within the OAM sublayer
        with an OAMPDU Code field value equal to the Event
        Notification code as specified in Table 57-4 and Event TLV
        Type field equal to the Errored Frame Event value as
        specified in Table 57-10."
    REFERENCE   "IEEE 802.3ah, Clause 57"
    ::= {mrvEfmOamEntry  37 }

mrvEfmOamErrFrmEvtThreshld OBJECT-TYPE
    SYNTAX      Unsigned32
    MAX-ACCESS  read-only
    STATUS      current
    DESCRIPTION
        "An integer corresponding to the Errored Frame Threshold
        field in the most recently transmitted Errored Frame Event
        TLV in an Event Notification OAMPDU (see 57.4.3.2).
        This integer is updated when a OAM:MA_DATA.request
        service primitive is generated within the OAM sublayer
        with an OAMPDU Code field value equal to the Event
        Notification code as specified in Table 57-4 and Event TLV
        Type field equal to the Errored Frame Event value as
        specified in Table 57-10."
    REFERENCE   "IEEE 802.3ah, Clause 57"
    ::= {mrvEfmOamEntry  38 }

mrvEfmOamErrFrmEvtCount OBJECT-TYPE
    SYNTAX      Counter64
    MAX-ACCESS  read-only
    STATUS      current
    DESCRIPTION
        "An integer corresponding to the Error Running Total field
        in the most recently transmitted Errored Frame Event TLV
        in an Event Notification OAMPDU (see 57.4.3.2).
        This integer is updated when a OAM:MA_DATA.request
        service primitive is generated within the OAM sublayer
        with an OAMPDU Code field value equal to the Event
        Notification code as specified in Table 57-4 and Event TLV
        Type field equal to the Errored Frame Event value as
        specified in Table 57-10."
    REFERENCE   "IEEE 802.3ah, Clause 57"
    ::= {mrvEfmOamEntry  39 }

mrvEfmOamErrFrmPerCfgDuration  OBJECT-TYPE
    SYNTAX      Unsigned32
    MAX-ACCESS  read-only
    STATUS      current
    DESCRIPTION
        "A four-octet value indicating the duration of the Errored
        Frame Period Event (see 57.5.3.3) window, in terms of the
        number of minFrameSize frames that can be transmitted on
        the underlying physical layer."
    REFERENCE   "IEEE 802.3ah, Clause 57"
    ::= {mrvEfmOamEntry  40 }

mrvEfmOamErrFrmPerCfgThreshld OBJECT-TYPE
    SYNTAX      Unsigned32
    MAX-ACCESS  read-only
    STATUS      current
    DESCRIPTION
        "A four-octet value indicating the number of errored
        frames in the period that must be exceeded in order for
        the Errored Frame Period Event to be generated."
    REFERENCE   "IEEE 802.3ah, Clause 57"
    ::= {mrvEfmOamEntry  41 }

mrvEfmOamErrFrmPerEvtTime OBJECT-TYPE
    SYNTAX      Unsigned16
    MAX-ACCESS  read-only
    STATUS      current
    DESCRIPTION
        "An integer corresponding to the Event Time Stamp field
        in the most recently transmitted Errored Frame Period
        Event TLV in an Event Notification OAMPDU (see 57.4.3.2).
        This integer is updated when a OAM:MA_DATA.request
        service primitive is generated within the OAM sublayer
        with an OAMPDU Code field value equal to the Event
        Notification code as specified in Table 57-4 and Event TLV
        Type field equal to the Errored Frame Period Event value
        as specified in Table 57-10."
    REFERENCE   "IEEE 802.3ah, Clause 57"
    ::= {mrvEfmOamEntry  42 }

mrvEfmOamErrFrmPerEvtWindow OBJECT-TYPE
    SYNTAX      Unsigned32
    MAX-ACCESS  read-only
    STATUS      current
    DESCRIPTION
        "An integer corresponding to the Errored Frame Window field
        in the most recently transmitted Errored Frame Period
        Event TLV in an Event Notification OAMPDU (see 57.4.3.2).
        This integer is updated when a OAM:MA_DATA.request
        service primitive is generated within the OAM sublayer
        with an OAMPDU Code field value equal to the Event
        Notification code as specified in Table 57-4 and Event TLV
        Type field equal to the Errored Frame Period Event value
        as specified in Table 57-10."
    REFERENCE   "IEEE 802.3ah, Clause 57"
    ::= {mrvEfmOamEntry  43 }

mrvEfmOamErrFrmPerEvtThreshld OBJECT-TYPE
    SYNTAX      Unsigned32
    MAX-ACCESS  read-only
    STATUS      current
    DESCRIPTION
        "An integer corresponding to the Errored Frame Threshold field
        in the most recently transmitted Errored Frame Period
        Event TLV in an Event Notification OAMPDU (see 57.4.3.2).
        This integer is updated when a OAM:MA_DATA.request
        service primitive is generated within the OAM sublayer
        with an OAMPDU Code field value equal to the Event
        Notification code as specified in Table 57-4 and Event TLV
        Type field equal to the Errored Frame Period Event value
        as specified in Table 57-10."
    REFERENCE   "IEEE 802.3ah, Clause 57"
    ::= {mrvEfmOamEntry  44 }

mrvEfmOamErrFrmPerEvtCount OBJECT-TYPE
    SYNTAX      Counter64
    MAX-ACCESS  read-only
    STATUS      current
    DESCRIPTION
        "An integer corresponding to the Error Running Total field
        in the most recently transmitted Errored Frame Period
        Event TLV in an Event Notification OAMPDU (see 57.4.3.2).
        This integer is updated when a OAM:MA_DATA.request
        service primitive is generated within the OAM sublayer
        with an OAMPDU Code field value equal to the Event
        Notification code as specified in Table 57-4 and Event TLV
        Type field equal to the Errored Frame Period Event value
        as specified in Table 57-10."
    REFERENCE   "IEEE 802.3ah, Clause 57"
    ::= {mrvEfmOamEntry  45 }

mrvEfmOamErrFrmSecSumCfgDuration OBJECT-TYPE
    SYNTAX      Unsigned16
    MAX-ACCESS  read-only
    STATUS      current
    DESCRIPTION
        "A two-octet value indicating the duration of the Errored
        Frame Seconds Summary Event (see 57.5.3.4) window, in
        terms of number of 100ms intervals."
    REFERENCE   "IEEE 802.3ah, Clause 57"
    ::= {mrvEfmOamEntry  46 }

mrvEfmOamErrFrmSecSumCfgThreshld OBJECT-TYPE
    SYNTAX      Unsigned16
    MAX-ACCESS  read-only
    STATUS      current
    DESCRIPTION
        "A two-octet value indicating the number of errored frame
        seconds in the period that must be exceeded in order for
        the Errored Frame Seconds Summary Event to be generated."
    REFERENCE   "IEEE 802.3ah, Clause 57"
    ::= {mrvEfmOamEntry  47 }

mrvEfmOamErrFrmSecSumEvtTime  OBJECT-TYPE
    SYNTAX      Unsigned16
    MAX-ACCESS  read-only
    STATUS      current
    DESCRIPTION
        "An integer corresponding to the Event Time Stamp field
        in the most recently transmitted Errored Frame Seconds
        Summary Event TLV in an Event Notification OAMPDU (see
        57.4.3.2). This integer is updated when a
        OAM:MA_DATA.request service primitive is generated within
        the OAM sublayer with an OAMPDU Code field value equal to
        the Event Notification code as specified in Table 57-4 and
        Event TLV Type field equal to the Errored Frame Seconds
        Summary Event value as specified in Table 57-10."
    REFERENCE   "IEEE 802.3ah, Clause 57"
    ::= {mrvEfmOamEntry  48 }

mrvEfmOamErrFrmSecSumEvtWindow OBJECT-TYPE
    SYNTAX      Unsigned16
    MAX-ACCESS  read-only
    STATUS      current
    DESCRIPTION
        "An integer corresponding to the Errored Frame Seconds
        Window field in the most recently transmitted Errored
        Frame Seconds Summary Event TLV in an Event Notification
        OAMPDU (see 57.4.3.2). This integer is updated when a
        OAM:MA_DATA.request service primitive is generated within
        the OAM sublayer with an OAMPDU Code field value equal to
        the Event Notification code as specified in Table 57-4 and
        Event TLV Type field equal to the Errored Frame Seconds
        Summary Event value as specified in Table 57-10."
    REFERENCE   "IEEE 802.3ah, Clause 57"
    ::= {mrvEfmOamEntry  49 }

mrvEfmOamErrFrmSecSumEvtThreshld OBJECT-TYPE
    SYNTAX      Unsigned16
    MAX-ACCESS  read-only
    STATUS      current
    DESCRIPTION
        "An integer corresponding to the Errored Frame Seconds
        Threshold field in the most recently transmitted Errored
        Frame Seconds Summary Event TLV in an Event Notification
        OAMPDU (see 57.4.3.2). This integer is updated when a
        OAM:MA_DATA.request service primitive is generated within
        the OAM sublayer with an OAMPDU Code field value equal to
        the Event Notification code as specified in Table 57-4 and
        Event TLV Type field equal to the Errored Frame Seconds
        Summary Event value as specified in Table 57-10."
    REFERENCE   "IEEE 802.3ah, Clause 57"
    ::= {mrvEfmOamEntry  50 }

mrvEfmOamErrFrmSecSumEvtCount OBJECT-TYPE
    SYNTAX      Counter32
    MAX-ACCESS  read-only
    STATUS      current
    DESCRIPTION
        "An integer corresponding to the Error Running Total field
        in the most recently transmitted Errored Frame Seconds
        Summary Event TLV in an Event Notification OAMPDU (see
        57.4.3.2). This integer is updated when a
        OAM:MA_DATA.request service primitive is generated within
        the OAM sublayer with an OAMPDU Code field value equal to
        the Event Notification code as specified in Table 57-4 and
        Event TLV Type field equal to the Errored Frame Seconds
        Summary Event value as specified in Table 57-10."
    REFERENCE   "IEEE 802.3ah, Clause 57"
    ::= {mrvEfmOamEntry  51 }

mrvEfmOamFramesLostDueToOamError OBJECT-TYPE
    SYNTAX      Counter32
    MAX-ACCESS  read-only
    STATUS      current
    DESCRIPTION
        "A count of frames that would otherwise be transmitted by
        the OAM sublayer, but could not be due to an internal OAM
        sublayer transmit error. If this counter is incremented,
        then none of the other counters in this section are
        incremented. The exact meaning and mechanism for
        incrementing this counter is implementation dependent."
    REFERENCE   "IEEE 802.3ah, Clause 57"
    ::= { mrvEfmOamEntry 52 }

mrvEfmOamAdminState  OBJECT-TYPE
     SYNTAX  INTEGER {
         notSupported    (1),
         disable         (2),
         enable          (3)
     }
     MAX-ACCESS read-write
     STATUS     current
     DESCRIPTION
         "A value that identifies the operational state of the OAM
         sublayer. An interface which can provide the OAM sublayer
         functions specified in Clause 57 will be enabled to do so
         when this attribute has the enumeration enable(3). When
         this attribute has the enumeration disable(2) the interface
         will act as it would if it had no OAM sublayer."
        DEFVAL { enable }
     ::= {mrvEfmOamEntry  53 }

mrvEfmOamOperState OBJECT-TYPE

     SYNTAX      OCTET STRING(SIZE(1))
     MAX-ACCESS  read-only
     STATUS      current
     DESCRIPTION
         "This object declares configurable (*) and operational reasons for
         disabling OAM service. The reason applies only if the bit is set.
         Multiple bits may be set concurrently. OAM service is enabled
         when no bits are set.

         Bit  Reason to disable
         --- ----------------------------------------------
         0  reserved
         1  reserved
         2  reserved
         3  reserved
         4  reserved
         5  Temporarily disabled for download processing
         6  Administratively disabled (*)
         7  OAM service is not available

         OCTET STRING bitmasks count the leftmost bit (MSB) as 0."

     ::= {mrvEfmOamEntry  54 }





-- ***********************************************************************
-- Conformance information.
-- ***********************************************************************
mrvEfmConformance OBJECT IDENTIFIER ::= { mrvEfmMib 3 }
mrvEfmGroups      OBJECT IDENTIFIER ::= { mrvEfmConformance 1 }

-- units of conformance
mrvEfmOamGroup  OBJECT-GROUP
OBJECTS {
    mrvEfmPhysicalIfIndex,
    mrvEfmOamIfIndex,
    mrvEfmOamPeerIfIndex,
    mrvEfmOamMode,
    mrvEfmOamCfg,
    mrvEfmOamPduCfg,
    mrvEfmOamFlagsField,
    mrvEfmOamState,
    mrvEfmOamVendorOUI,
    mrvEfmOamVendorDeviceId,
    mrvEfmOamVendorDeviceVersion,
    mrvEfmOamPDUTx,
    mrvEfmOamPDURx,
    mrvEfmOamUnsupportedCodesRx,
    mrvEfmOamInformationTx,
    mrvEfmOamInformationRx,
    mrvEfmOamEventNotificationTx,
    mrvEfmOamUniEventNotificationRx,
    mrvEfmOamDupEventNotificationRx,
    mrvEfmOamLoopbackControlTx,
    mrvEfmOamLoopbackControlRx,
    mrvEfmOamVariableRequestTx,
    mrvEfmOamVariableRequestRx,
    mrvEfmOamVariableResponseTx,
    mrvEfmOamVariableResponseRx,
    mrvEfmOamOrganizationSpecificTx,
    mrvEfmOamOrganizationSpecificRx,
    mrvEfmOamErrSymPerCfgDuration,
    mrvEfmOamErrSymPerCfgThreshld,
    mrvEfmOamErrSymPerEvtTime,
    mrvEfmOamErrSymPerEvtWindow,
    mrvEfmOamErrSymPerEvtThreshld,
    mrvEfmOamErrSymPerEvtCount,
    mrvEfmOamErrFrmCfgDuration,
    mrvEfmOamErrFrmCfgThreshld,
    mrvEfmOamErrFrmEvtTime,
    mrvEfmOamErrFrmEvtWindow,
    mrvEfmOamErrFrmEvtThreshld,
    mrvEfmOamErrFrmEvtCount,
    mrvEfmOamErrFrmPerCfgDuration,
    mrvEfmOamErrFrmPerCfgThreshld,
    mrvEfmOamErrFrmPerEvtTime,
    mrvEfmOamErrFrmPerEvtWindow,
    mrvEfmOamErrFrmPerEvtThreshld,
    mrvEfmOamErrFrmPerEvtCount,
    mrvEfmOamErrFrmSecSumCfgDuration,
    mrvEfmOamErrFrmSecSumCfgThreshld,
    mrvEfmOamErrFrmSecSumEvtTime,
    mrvEfmOamErrFrmSecSumEvtWindow,
    mrvEfmOamErrFrmSecSumEvtThreshld,
    mrvEfmOamErrFrmSecSumEvtCount,
    mrvEfmOamFramesLostDueToOamError,
    mrvEfmOamAdminState,
    mrvEfmOamOperState
}
STATUS  current
DESCRIPTION
    "OAM attributes."
::= { mrvEfmGroups 3 }

END

--  vim: expandtab
--  vim: ts=8
--  vim: sw=2
--  vim: tw=71
--  vim: nojoinspaces
