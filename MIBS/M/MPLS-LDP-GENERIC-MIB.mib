-- extracted from draft-ietf-mpls-ldp-mib-09.txt
-- at Fri May 14 06:21:07 2004

   MPLS-LDP-GENERIC-MIB DEFINITIONS ::= BEGIN

   IMPORTS

       OBJECT-TYPE,
       MODULE-IDENTITY,
       Unsigned32
           FROM SNMPv2-SMI

       MODULE-COMPLIANCE,
       OBJECT-GROUP
           FROM SNMPv2-CONF

       RowStatus,
       StorageType
           FROM SNMPv2-TC

       InterfaceIndexOrZero
           FROM IF-MIB

       mplsMIB
           FROM MPLS-TC-MIB

       mplsLdpEntityObjects,
       mplsLdpEntityLdpId,
       mplsLdpEntityIndex
           FROM MPLS-LDP-MIB
       ;


   mplsLdpGenericMIB MODULE-IDENTITY
       LAST-UPDATED "200208081200Z"  -- 8 August 2002
       ORGANIZATION "Multiprotocol Label Switching (mpls)
                     Working Group"
       CONTACT-INFO
           "Joan Cucchiara (jcucchiara@crescentnetworks.com)
            Crescent Networks
            Hans Sjostrand (hans@ipunplugged.com)
            ipUnplugged

            James V. Luciani (jluciani@crescentnetworks.com)
            Crescent Networks

            Working Group Chairs:
            George Swallow,   email: swallow@cisco.com
            Loa Andersson,    email: loa.andersson@utfors.se

            MPLS Working Group, email: mpls@uu.net
       "
       DESCRIPTION
           "This MIB contains managed object definitions for the
           'Multiprotocol Label Switching, Label Distribution
           Protocol, LDP' document which use as their Layer 2
           ethernet."
       REVISION "200208081200Z"  -- 8 August 2002
       DESCRIPTION
           "Initial version published as part of RFC XXXX."

       ::= { mplsMIB 6 } -- to be assigned

   --****************************************************************


   mplsLdpGenericObjects
            OBJECT IDENTIFIER ::= { mplsLdpGenericMIB 1 }
   mplsLdpGenericConformance
            OBJECT IDENTIFIER ::= { mplsLdpGenericMIB 3 }

   --****************************************************************
   -- MPLS LDP GENERIC Objects
   --****************************************************************

   --
   -- Ldp Entity Objects for Generic Labels
   --



   mplsLdpEntityGenericObjects  OBJECT IDENTIFIER ::=
                                 { mplsLdpEntityObjects 5 }


   --
   -- The MPLS LDP Entity Generic Label Range Table
   --

   mplsLdpEntityGenLRTable OBJECT-TYPE
       SYNTAX SEQUENCE OF MplsLdpEntityGenLREntry
       MAX-ACCESS not-accessible
       STATUS current
       DESCRIPTION
           "The MPLS LDP Entity Generic Label Range
           Table.

           The purpose of this table is to provide a mechanism
           for configurating a contiguous range of generic labels,
           or a 'label range' for LDP Entities.

           LDP Entities which use Generic Labels must have at least
           one entry in this table."
       ::= { mplsLdpEntityGenericObjects 1 }

   mplsLdpEntityGenLREntry OBJECT-TYPE
       SYNTAX MplsLdpEntityGenLREntry
       MAX-ACCESS not-accessible
       STATUS current
       DESCRIPTION
           "A row in the LDP Entity Generic Label
           Range Table.  One entry in this table contains
           information on a single range of labels
           represented by the configured Upper and Lower
           Bounds pairs.  NOTE: there is NO corresponding
           LDP message which relates to the information
           in this table, however, this table does provide
           a way for a user to 'reserve' a generic label
           range.

           NOTE:  The ranges for a specific LDP Entity
           are UNIQUE and non-overlapping.

           A row will not be created unless a unique and
           non-overlapping range is specified."
       INDEX       {  mplsLdpEntityLdpId,
                      mplsLdpEntityIndex,
                      mplsLdpEntityGenLRMin,
                      mplsLdpEntityGenLRMax
                   }
       ::= { mplsLdpEntityGenLRTable 1 }

   MplsLdpEntityGenLREntry ::= SEQUENCE {
       mplsLdpEntityGenLRMin           Unsigned32,
       mplsLdpEntityGenLRMax           Unsigned32,
       mplsLdpEntityGenIfIndexOrZero   InterfaceIndexOrZero,
       mplsLdpEntityGenLRStorageType   StorageType,
       mplsLdpEntityGenLRRowStatus     RowStatus
   }
   mplsLdpEntityGenLRMin OBJECT-TYPE
       SYNTAX     Unsigned32(0..1048575)
       MAX-ACCESS not-accessible
       STATUS     current
       DESCRIPTION
           "The minimum label configured for this range."
       ::= { mplsLdpEntityGenLREntry 1 }

   mplsLdpEntityGenLRMax OBJECT-TYPE
       SYNTAX     Unsigned32(0..1048575)
       MAX-ACCESS not-accessible
       STATUS     current
       DESCRIPTION
           "The maximum label configured for this range."
       ::= { mplsLdpEntityGenLREntry 2 }

   mplsLdpEntityGenIfIndexOrZero OBJECT-TYPE
       SYNTAX      InterfaceIndexOrZero
       MAX-ACCESS  read-create
       STATUS      current
       DESCRIPTION
          "This value represents either the InterfaceIndex of
          the 'ifLayer' where these Generic Label would be created,
          or 0 (zero).  The value of zero means that the
          InterfaceIndex is not known.  For example, if
          the InterfaceIndex is  created subsequent to
          the Generic Label's creation, then it would not be
          known.  However, if the InterfaceIndex
          is known, then it must be represented by this value.

          If an InterfaceIndex becomes known, then the
          network management entity (e.g. SNMP agent) responsible
          for this object MUST change the value from 0 (zero) to the
          value of the InterfaceIndex."
       ::= { mplsLdpEntityGenLREntry 3 }

   mplsLdpEntityGenLRStorageType  OBJECT-TYPE
       SYNTAX      StorageType
       MAX-ACCESS  read-create
       STATUS      current
       DESCRIPTION
                "The storage type for this entry."
       ::= { mplsLdpEntityGenLREntry 4 }

   mplsLdpEntityGenLRRowStatus OBJECT-TYPE
       SYNTAX RowStatus
       MAX-ACCESS read-create
       STATUS current
       DESCRIPTION
           "An object that allows entries in this
           table to be created and deleted using
           the RowStatus convention.

           There must exist at least one entry in this
           table for every LDP Entity that has a
           generic label configured.

           NOTE:  This RowStatus object should
           have the same value of the 'mplsLdpEntityRowStatus'
           related to this entry."
       ::= { mplsLdpEntityGenLREntry 5 }


   --****************************************************************
   -- Module Conformance Statement
   --****************************************************************


   mplsLdpGenericGroups
       OBJECT IDENTIFIER ::= { mplsLdpGenericConformance 1 }

   mplsLdpGenericCompliances
       OBJECT IDENTIFIER ::= { mplsLdpGenericConformance 2 }

   --
   -- Full Compliance
   --

   mplsLdpGenModuleFullCompliance MODULE-COMPLIANCE
       STATUS current
       DESCRIPTION
           "The Module is implemented with support for
           read-create and read-write.  In other words,
           both monitoring and configuration
           are available when using this MODULE-COMPLIANCE."
       MODULE -- this module
           MANDATORY-GROUPS    {
                                  mplsLdpGenericGroup
                               }

       OBJECT       mplsLdpEntityGenLRRowStatus
       SYNTAX       RowStatus { active(1) }
       WRITE-SYNTAX RowStatus { createAndGo(4), destroy(6) }
       DESCRIPTION
          "Support for createAndWait and notInService is not required."

       ::= { mplsLdpGenericCompliances 1 }

   --
   -- Read-Only Compliance
   --

   mplsLdpGenModuleROCompliance MODULE-COMPLIANCE
       STATUS current
       DESCRIPTION
           "The Module is implemented with support for
           read-only.  In other words, only monitoring
           is available by implementing this MODULE-COMPLIANCE."
       MODULE -- this module
           MANDATORY-GROUPS    {
                                  mplsLdpGenericGroup
                               }

       OBJECT       mplsLdpEntityGenIfIndexOrZero
       MIN-ACCESS   read-only
       DESCRIPTION
          "Write access is not required."

       OBJECT       mplsLdpEntityGenLRStorageType
       MIN-ACCESS   read-only
       DESCRIPTION
          "Write access is not required."


       OBJECT       mplsLdpEntityGenLRRowStatus
       SYNTAX       RowStatus { active(1) }
       MIN-ACCESS   read-only
       DESCRIPTION
          "Write access is not required, and active is the
          only status that needs to be supported."

       ::= { mplsLdpGenericCompliances 2 }

   --
   -- units of conformance
   --

   mplsLdpGenericGroup OBJECT-GROUP
       OBJECTS {
       mplsLdpEntityGenIfIndexOrZero,
       mplsLdpEntityGenLRStorageType,
       mplsLdpEntityGenLRRowStatus
       }
       STATUS    current
       DESCRIPTION
           "Objects that apply to all MPLS LDP implementations
           using Generic Lables."
       ::= { mplsLdpGenericGroups 1 }

   END

-- 
--    Copyright (C) The Internet Society (2002). All Rights Reserved.
-- 
-- 
--    This document and translations of it may be copied and furnished to
--    others, and derivative works that comment on or otherwise explain it
--    or assist in its implementation may be prepared, copied, published
--    and distributed, in whole or in part, without restriction of any
--    kind, provided that the above copyright notice and this paragraph are
--    included on all such copies and derivative works.  However, this
--    document itself may not be modified in any way, such as by removing
--    the copyright notice or references to the Internet Society or other
--    Internet organizations, except as needed for the  purpose of
--    developing Internet standards in which case the procedures for
--    copyrights defined in the Internet Standards process must be
--    followed, or as required to translate it into languages other than
--    English.
-- 
--    The limited permissions granted above are perpetual and will not be
--    revoked by the Internet Society or its successors or assigns.
-- 
--    This document and the information contained herein is provided on an
--    "AS IS" basis and THE INTERNET SOCIETY AND THE INTERNET ENGINEERING
--    TASK FORCE DISCLAIMS ALL WARRANTIES, EXPRESS OR IMPLIED, INCLUDING
--    BUT NOT LIMITED TO ANY WARRANTY THAT THE USE OF THE INFORMATION
--    HEREIN WILL NOT INFRINGE ANY RIGHTS OR ANY IMPLIED WARRANTIES OF
--    MERCHANTABILITY OR FITNESS FOR A PARTICULAR PURPOSE.
