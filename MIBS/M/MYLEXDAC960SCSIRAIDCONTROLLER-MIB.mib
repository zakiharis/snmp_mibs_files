-- MIB generated by miftomib version 1.0a

MYLEXDAC960SCSIRAIDCONTROLLER-MIB DEFINITIONS ::= BEGIN

-- Mylex DAC960 SCSI RAID Controller

IMPORTS
    OBJECT-TYPE
    FROM RFC-1212
    Counter, enterprises
    FROM RFC1155-SMI
    DisplayString
    FROM RFC1213-MIB;

DmiCounter			::= Counter
DmiInteger			::= INTEGER
DmiDisplaystring	::= DisplayString
DmiDateX			::= OCTET STRING (SIZE (28))
DmiComponentIndex	::= INTEGER

mylex                   OBJECT IDENTIFIER ::= {enterprises 1608}
mib                     OBJECT IDENTIFIER ::= {mylex 3}
v2                      OBJECT IDENTIFIER ::= {mib 2}
dmtfGroups              OBJECT IDENTIFIER ::= {v2 1}

SComponentid ::= SEQUENCE {
	a1Manufacturer                          	DmiDisplaystring,
	a1Product                               	DmiDisplaystring,
	a1Version                               	DmiDisplaystring,
	a1SerialNumber                          	DmiDisplaystring,
	a1Installation                          	DmiDateX,
	a1Verify                                	DmiInteger
}

tComponentid OBJECT-TYPE
	SYNTAX		SEQUENCE OF SComponentid
	ACCESS		not-accessible
	STATUS		mandatory
	DESCRIPTION	"This group defines attributes common to allcomponents. This
group is required."
	::= {dmtfGroups 1}

eComponentid OBJECT-TYPE
	SYNTAX		SComponentid
	ACCESS		not-accessible
	STATUS		mandatory
	DESCRIPTION	""
	--INDEX		{DmiComponentIndex}
	::= {tComponentid 1}

a1Manufacturer OBJECT-TYPE
	SYNTAX		DmiDisplaystring
	ACCESS		read-only
	STATUS		mandatory
	DESCRIPTION	"Controller Manufacturer."
	::= {eComponentid 1}

a1Product OBJECT-TYPE
	SYNTAX		DmiDisplaystring
	ACCESS		read-only
	STATUS		mandatory
	DESCRIPTION	"Product Name for this Controller."
	::= {eComponentid 2}

a1Version OBJECT-TYPE
	SYNTAX		DmiDisplaystring
	ACCESS		not-accessible
	STATUS		mandatory
	DESCRIPTION	""
	::= {eComponentid 3}

a1SerialNumber OBJECT-TYPE
	SYNTAX		DmiDisplaystring
	ACCESS		not-accessible
	STATUS		mandatory
	DESCRIPTION	""
	::= {eComponentid 4}

a1Installation OBJECT-TYPE
	SYNTAX		DmiDateX
	ACCESS		not-accessible
	STATUS		mandatory
	DESCRIPTION	"The time and date for the last time this componentwas installed."
	::= {eComponentid 5}

a1Verify OBJECT-TYPE
	SYNTAX		DmiInteger
	ACCESS		read-only
	STATUS		mandatory
	DESCRIPTION	"A code that provides a level of verification thatthe component
is still installed and working."
	::= {eComponentid 6}

SControllerInformation ::= SEQUENCE {
	a2ControllerNumber                      	DmiInteger,
	a2OperationalState                      	DmiInteger,
	a2FirmwareRevision                      	DmiDisplaystring,
	a2ConfiguredChannels                    	DmiInteger,
	a2ActualChannels                        	DmiInteger,
	a2MaximumLogicalDrives                  	DmiInteger,
	a2MaximumTargetsPerChannel              	DmiInteger,
	a2MaximumTaggedRequests                 	DmiInteger,
	a2MaximumDataTransferSizePerIoRequestInK	DmiInteger,
	a2MaximumConcurrentCommands             	DmiInteger,
	a2RebuildRate                           	DmiInteger,
	a2LogicalSectorSizeInBytes              	DmiInteger,
	a2PhysicalSectorSizeInBytes             	DmiInteger,
	a2CacheLineSizeInBytes                  	DmiInteger,
	a2DramSizeInMb                          	DmiInteger,
	a2EpromSizeInKb                         	DmiInteger,
	a2BusType                               	DmiDisplaystring,
	a2SystemBusNumber                       	DmiInteger,
	a2SlotNumber                            	DmiInteger,
	a2InterruptVectorNumber                 	DmiInteger,
	a2InterruptMode                         	DmiDisplaystring
}

tControllerInformation OBJECT-TYPE
	SYNTAX		SEQUENCE OF SControllerInformation
	ACCESS		not-accessible
	STATUS		mandatory
	DESCRIPTION	"This group provides Controller Information."
	::= {dmtfGroups 2}

eControllerInformation OBJECT-TYPE
	SYNTAX		SControllerInformation
	ACCESS		not-accessible
	STATUS		mandatory
	DESCRIPTION	""
	--INDEX		{DmiComponentIndex, a2ControllerNumber}
	::= {tControllerInformation 1}

a2ControllerNumber OBJECT-TYPE
	SYNTAX		DmiInteger
	ACCESS		read-only
	STATUS		mandatory
	DESCRIPTION	"Controller Number assigned to this controller by the device
driver."
	::= {eControllerInformation 1}

a2OperationalState OBJECT-TYPE
	SYNTAX		DmiInteger
	ACCESS		read-only
	STATUS		mandatory
	DESCRIPTION	"Operational state of this controller as seen by the device
driver."
	::= {eControllerInformation 2}

a2FirmwareRevision OBJECT-TYPE
	SYNTAX		DmiDisplaystring
	ACCESS		read-only
	STATUS		mandatory
	DESCRIPTION	"Controller Firmware Revision."
	::= {eControllerInformation 3}

a2ConfiguredChannels OBJECT-TYPE
	SYNTAX		DmiInteger
	ACCESS		read-only
	STATUS		mandatory
	DESCRIPTION	"Number of Channels (SCSI Bus) that are part of controller
configuration."
	::= {eControllerInformation 4}

a2ActualChannels OBJECT-TYPE
	SYNTAX		DmiInteger
	ACCESS		read-only
	STATUS		mandatory
	DESCRIPTION	"Number of Channels (SCSI Bus) that are physically present
on-board the controller."
	::= {eControllerInformation 5}

a2MaximumLogicalDrives OBJECT-TYPE
	SYNTAX		DmiInteger
	ACCESS		read-only
	STATUS		mandatory
	DESCRIPTION	"Maximum number of logical drives that can be configured on
this controller."
	::= {eControllerInformation 6}

a2MaximumTargetsPerChannel OBJECT-TYPE
	SYNTAX		DmiInteger
	ACCESS		read-only
	STATUS		mandatory
	DESCRIPTION	"Maximum Number of SCSI Target IDs supported per SCSI Bus."
	::= {eControllerInformation 7}

a2MaximumTaggedRequests OBJECT-TYPE
	SYNTAX		DmiInteger
	ACCESS		read-only
	STATUS		mandatory
	DESCRIPTION	"Maximum Number of Tagged requests that may be sent to a Hard
disk device by Controller Firmware."
	::= {eControllerInformation 8}

a2MaximumDataTransferSizePerIoRequestInK OBJECT-TYPE
	SYNTAX		DmiInteger
	ACCESS		read-only
	STATUS		mandatory
	DESCRIPTION	"Maximum amount of data that can be transferred per a single
IO request - in KB."
	::= {eControllerInformation 9}

a2MaximumConcurrentCommands OBJECT-TYPE
	SYNTAX		DmiInteger
	ACCESS		read-only
	STATUS		mandatory
	DESCRIPTION	"Maximum number of requests that can be sent to the controller
simultaneouly."
	::= {eControllerInformation 10}

a2RebuildRate OBJECT-TYPE
	SYNTAX		DmiInteger
	ACCESS		read-only
	STATUS		mandatory
	DESCRIPTION	"Value of Rebuild Rate."
	::= {eControllerInformation 11}

a2LogicalSectorSizeInBytes OBJECT-TYPE
	SYNTAX		DmiInteger
	ACCESS		read-only
	STATUS		mandatory
	DESCRIPTION	"Logical Sector Size in Bytes (Default: 512 bytes)."
	::= {eControllerInformation 12}

a2PhysicalSectorSizeInBytes OBJECT-TYPE
	SYNTAX		DmiInteger
	ACCESS		read-only
	STATUS		mandatory
	DESCRIPTION	"Physical Sector Size in Bytes (Default: 512 bytes)."
	::= {eControllerInformation 13}

a2CacheLineSizeInBytes OBJECT-TYPE
	SYNTAX		DmiInteger
	ACCESS		read-only
	STATUS		mandatory
	DESCRIPTION	"Cache Line Size in Bytes."
	::= {eControllerInformation 14}

a2DramSizeInMb OBJECT-TYPE
	SYNTAX		DmiInteger
	ACCESS		read-only
	STATUS		mandatory
	DESCRIPTION	"Size of Controller EPROM Module - in MB."
	::= {eControllerInformation 15}

a2EpromSizeInKb OBJECT-TYPE
	SYNTAX		DmiInteger
	ACCESS		read-only
	STATUS		mandatory
	DESCRIPTION	"Size of Controller EPROM Module - in KB."
	::= {eControllerInformation 16}

a2BusType OBJECT-TYPE
	SYNTAX		DmiDisplaystring
	ACCESS		read-only
	STATUS		mandatory
	DESCRIPTION	"Controller - System Bus Interface Type."
	::= {eControllerInformation 17}

a2SystemBusNumber OBJECT-TYPE
	SYNTAX		DmiInteger
	ACCESS		read-only
	STATUS		mandatory
	DESCRIPTION	"System Bus Number, for the bus the controller is interfacing
with. This value is supplied by the Operating system and may not be defined
for all operating systems."
	::= {eControllerInformation 18}

a2SlotNumber OBJECT-TYPE
	SYNTAX		DmiInteger
	ACCESS		read-only
	STATUS		mandatory
	DESCRIPTION	"Slot Number where the controller is physically present. Defined
for EISA and MCA controller only. For PCI controller it will always be set
to 0."
	::= {eControllerInformation 19}

a2InterruptVectorNumber OBJECT-TYPE
	SYNTAX		DmiInteger
	ACCESS		read-only
	STATUS		mandatory
	DESCRIPTION	"Interrupt Vector Number being used by the controller.This
value is a mapped IRQ supplied by OperatingSystem and may not be same as
the actual Interrupt Vector."
	::= {eControllerInformation 20}

a2InterruptMode OBJECT-TYPE
	SYNTAX		DmiDisplaystring
	ACCESS		read-only
	STATUS		mandatory
	DESCRIPTION	"Interrupt Mode - Edge/Level."
	::= {eControllerInformation 21}

SLogicalDriveInformation ::= SEQUENCE {
	a3ControllerNumber                      	DmiInteger,
	a3LogicalDriveNumber                    	DmiInteger,
	a3OperationalState                      	DmiInteger,
	a3RaidLevel                             	DmiInteger,
	a3WritePolicy                           	DmiDisplaystring,
	a3SizeInMb                              	DmiInteger,
	a3StripeSizeInBytes                     	DmiInteger,
	a3PhysicalDriveMap                      	DmiDisplaystring
}

tLogicalDriveInformation OBJECT-TYPE
	SYNTAX		SEQUENCE OF SLogicalDriveInformation
	ACCESS		not-accessible
	STATUS		mandatory
	DESCRIPTION	"Provides information about Logical Drive Configuration."
	::= {dmtfGroups 3}

eLogicalDriveInformation OBJECT-TYPE
	SYNTAX		SLogicalDriveInformation
	ACCESS		not-accessible
	STATUS		mandatory
	DESCRIPTION	""
	--INDEX		{DmiComponentIndex, a3ControllerNumber, a3LogicalDriveNumber}
	::= {tLogicalDriveInformation 1}

a3ControllerNumber OBJECT-TYPE
	SYNTAX		DmiInteger
	ACCESS		read-only
	STATUS		mandatory
	DESCRIPTION	"Controller Number - used as a key."
	::= {eLogicalDriveInformation 1}

a3LogicalDriveNumber OBJECT-TYPE
	SYNTAX		DmiInteger
	ACCESS		read-only
	STATUS		mandatory
	DESCRIPTION	"Logical Drive Number - used as a Key."
	::= {eLogicalDriveInformation 2}

a3OperationalState OBJECT-TYPE
	SYNTAX		DmiInteger
	ACCESS		read-only
	STATUS		mandatory
	DESCRIPTION	"Logical Drive Operational State."
	::= {eLogicalDriveInformation 3}

a3RaidLevel OBJECT-TYPE
	SYNTAX		DmiInteger
	ACCESS		read-only
	STATUS		mandatory
	DESCRIPTION	"RAID Level associated with Logical Drive."
	::= {eLogicalDriveInformation 4}

a3WritePolicy OBJECT-TYPE
	SYNTAX		DmiDisplaystring
	ACCESS		read-only
	STATUS		mandatory
	DESCRIPTION	"Write Cache Policy associated with Logical Drive."
	::= {eLogicalDriveInformation 5}

a3SizeInMb OBJECT-TYPE
	SYNTAX		DmiInteger
	ACCESS		read-only
	STATUS		mandatory
	DESCRIPTION	"Logical Drive Size - in MB."
	::= {eLogicalDriveInformation 6}

a3StripeSizeInBytes OBJECT-TYPE
	SYNTAX		DmiInteger
	ACCESS		read-only
	STATUS		mandatory
	DESCRIPTION	"Stripe size associated with Logical Drive. Valid for RAID
Levels 0, 5 and 6 only. Value is specifed in bytes."
	::= {eLogicalDriveInformation 7}

a3PhysicalDriveMap OBJECT-TYPE
	SYNTAX		DmiDisplaystring
	ACCESS		read-only
	STATUS		mandatory
	DESCRIPTION	"List of all physical drives that make up this Logical Drive.
The information is provided in Channel-Target combination form."
	::= {eLogicalDriveInformation 8}

SPhyicalDeviceInformation ::= SEQUENCE {
	a4ControllerNumber                      	DmiInteger,
	a4ScsiBusId                             	DmiInteger,
	a4ScsiTargetId                          	DmiInteger,
	a4OperationalState                      	DmiInteger,
	a4VendorId                              	DmiDisplaystring,
	a4ProductId                             	DmiDisplaystring,
	a4ProductRevisionLevel                  	DmiDisplaystring,
	a4SizeInMb                              	DmiInteger,
	a4DeviceType                            	DmiDisplaystring,
	a4SoftErrorsCount                       	DmiCounter,
	a4HardErrorsCount                       	DmiCounter,
	a4ParityErrorsCount                     	DmiCounter,
	a4MiscErrorsCount                       	DmiCounter
}

tPhyicalDeviceInformation OBJECT-TYPE
	SYNTAX		SEQUENCE OF SPhyicalDeviceInformation
	ACCESS		not-accessible
	STATUS		mandatory
	DESCRIPTION	"SCSI Physical Device Information."
	::= {dmtfGroups 4}

ePhyicalDeviceInformation OBJECT-TYPE
	SYNTAX		SPhyicalDeviceInformation
	ACCESS		not-accessible
	STATUS		mandatory
	DESCRIPTION	""
	--INDEX		{DmiComponentIndex, a4ControllerNumber, a4ScsiBusId, a4ScsiTargetId}
	::= {tPhyicalDeviceInformation 1}

a4ControllerNumber OBJECT-TYPE
	SYNTAX		DmiInteger
	ACCESS		read-only
	STATUS		mandatory
	DESCRIPTION	"Controller Number - used as a key"
	::= {ePhyicalDeviceInformation 1}

a4ScsiBusId OBJECT-TYPE
	SYNTAX		DmiInteger
	ACCESS		read-only
	STATUS		mandatory
	DESCRIPTION	"SCSI Channel Number - used as a key"
	::= {ePhyicalDeviceInformation 2}

a4ScsiTargetId OBJECT-TYPE
	SYNTAX		DmiInteger
	ACCESS		read-only
	STATUS		mandatory
	DESCRIPTION	"SCSI Physical Device Target Id - used as a key"
	::= {ePhyicalDeviceInformation 3}

a4OperationalState OBJECT-TYPE
	SYNTAX		DmiInteger
	ACCESS		read-only
	STATUS		mandatory
	DESCRIPTION	"SCSI Physical Device State."
	::= {ePhyicalDeviceInformation 4}

a4VendorId OBJECT-TYPE
	SYNTAX		DmiDisplaystring
	ACCESS		read-only
	STATUS		mandatory
	DESCRIPTION	"Physical Device Vendor Id - from SCSI Inquiry Info."
	::= {ePhyicalDeviceInformation 5}

a4ProductId OBJECT-TYPE
	SYNTAX		DmiDisplaystring
	ACCESS		read-only
	STATUS		mandatory
	DESCRIPTION	"Physical Device Product Id - from SCSI Inquiry Info."
	::= {ePhyicalDeviceInformation 6}

a4ProductRevisionLevel OBJECT-TYPE
	SYNTAX		DmiDisplaystring
	ACCESS		read-only
	STATUS		mandatory
	DESCRIPTION	"Physical Device Product Revision Level - from SCSI Inquiry
Info."
	::= {ePhyicalDeviceInformation 7}

a4SizeInMb OBJECT-TYPE
	SYNTAX		DmiInteger
	ACCESS		read-only
	STATUS		mandatory
	DESCRIPTION	"Size in MB - from SCSI Read Capacity Data."
	::= {ePhyicalDeviceInformation 8}

a4DeviceType OBJECT-TYPE
	SYNTAX		DmiDisplaystring
	ACCESS		read-only
	STATUS		mandatory
	DESCRIPTION	"SCSI Device Type - from SCSI Inquiry Information."
	::= {ePhyicalDeviceInformation 9}

a4SoftErrorsCount OBJECT-TYPE
	SYNTAX		DmiCounter
	ACCESS		read-only
	STATUS		mandatory
	DESCRIPTION	"Number of Soft Errors."
	::= {ePhyicalDeviceInformation 10}

a4HardErrorsCount OBJECT-TYPE
	SYNTAX		DmiCounter
	ACCESS		read-only
	STATUS		mandatory
	DESCRIPTION	"Number of Hard Errors."
	::= {ePhyicalDeviceInformation 11}

a4ParityErrorsCount OBJECT-TYPE
	SYNTAX		DmiCounter
	ACCESS		read-only
	STATUS		mandatory
	DESCRIPTION	"Number of Parity Errors."
	::= {ePhyicalDeviceInformation 12}

a4MiscErrorsCount OBJECT-TYPE
	SYNTAX		DmiCounter
	ACCESS		read-only
	STATUS		mandatory
	DESCRIPTION	"Number of Misc Errors."
	::= {ePhyicalDeviceInformation 13}

SMylexDac960ComponentInstrumentationInfo ::= SEQUENCE {
	a5CiRevision                            	DmiDisplaystring,
	a5CiBuildDate                           	DmiDisplaystring,
	a5MdacDeviceDriverRevision              	DmiDisplaystring,
	a5MdacDeviceDriverBuildDate             	DmiDisplaystring
}

tMylexDac960ComponentInstrumentationInfo OBJECT-TYPE
	SYNTAX		SEQUENCE OF SMylexDac960ComponentInstrumentationInfo
	ACCESS		not-accessible
	STATUS		mandatory
	DESCRIPTION	"MDAC CI Software Version Information."
	::= {dmtfGroups 5}

eMylexDac960ComponentInstrumentationInfo OBJECT-TYPE
	SYNTAX		SMylexDac960ComponentInstrumentationInfo
	ACCESS		not-accessible
	STATUS		mandatory
	DESCRIPTION	""
	--INDEX		{DmiComponentIndex}
	::= {tMylexDac960ComponentInstrumentationInfo 1}

a5CiRevision OBJECT-TYPE
	SYNTAX		DmiDisplaystring
	ACCESS		read-only
	STATUS		mandatory
	DESCRIPTION	"CI Software Revision Information."
	::= {eMylexDac960ComponentInstrumentationInfo 1}

a5CiBuildDate OBJECT-TYPE
	SYNTAX		DmiDisplaystring
	ACCESS		read-only
	STATUS		mandatory
	DESCRIPTION	"CI Software Build Date Information - date/month/year format."
	::= {eMylexDac960ComponentInstrumentationInfo 2}

a5MdacDeviceDriverRevision OBJECT-TYPE
	SYNTAX		DmiDisplaystring
	ACCESS		read-only
	STATUS		mandatory
	DESCRIPTION	"Mylex DAC960 Controller Device driver Revision Info."
	::= {eMylexDac960ComponentInstrumentationInfo 3}

a5MdacDeviceDriverBuildDate OBJECT-TYPE
	SYNTAX		DmiDisplaystring
	ACCESS		read-only
	STATUS		mandatory
	DESCRIPTION	"Mylex DAC960 Device Driver Build Date Information  - date/month/
ear format."
	::= {eMylexDac960ComponentInstrumentationInfo 4}

SLogicalDriveStatistics ::= SEQUENCE {
	a6ControllerNumber                      	DmiInteger,
	a6LogicalDriveNumber                    	DmiInteger,
	a6ReadRequestsCount                     	DmiCounter,
	a6AmountOfDataReadInMb                  	DmiCounter,
	a6WriteRequestsCount                    	DmiCounter,
	a6AmountOfDataWrittenInMb               	DmiCounter,
	a6ReadCacheHit                          	DmiCounter
}

tLogicalDriveStatistics OBJECT-TYPE
	SYNTAX		SEQUENCE OF SLogicalDriveStatistics
	ACCESS		not-accessible
	STATUS		mandatory
	DESCRIPTION	"Logical Drive Performance Statistics"
	::= {dmtfGroups 6}

eLogicalDriveStatistics OBJECT-TYPE
	SYNTAX		SLogicalDriveStatistics
	ACCESS		not-accessible
	STATUS		mandatory
	DESCRIPTION	""
	--INDEX		{DmiComponentIndex, a6ControllerNumber, a6LogicalDriveNumber}
	::= {tLogicalDriveStatistics 1}

a6ControllerNumber OBJECT-TYPE
	SYNTAX		DmiInteger
	ACCESS		read-only
	STATUS		mandatory
	DESCRIPTION	"Controller Number - used as a key."
	::= {eLogicalDriveStatistics 1}

a6LogicalDriveNumber OBJECT-TYPE
	SYNTAX		DmiInteger
	ACCESS		read-only
	STATUS		mandatory
	DESCRIPTION	"Logical Drive Number - used as a key."
	::= {eLogicalDriveStatistics 2}

a6ReadRequestsCount OBJECT-TYPE
	SYNTAX		DmiCounter
	ACCESS		read-only
	STATUS		mandatory
	DESCRIPTION	"Number of Read Requests."
	::= {eLogicalDriveStatistics 3}

a6AmountOfDataReadInMb OBJECT-TYPE
	SYNTAX		DmiCounter
	ACCESS		read-only
	STATUS		mandatory
	DESCRIPTION	"Amount of Data Read - in MB."
	::= {eLogicalDriveStatistics 4}

a6WriteRequestsCount OBJECT-TYPE
	SYNTAX		DmiCounter
	ACCESS		read-only
	STATUS		mandatory
	DESCRIPTION	"Number of Write Requests."
	::= {eLogicalDriveStatistics 5}

a6AmountOfDataWrittenInMb OBJECT-TYPE
	SYNTAX		DmiCounter
	ACCESS		read-only
	STATUS		mandatory
	DESCRIPTION	"Amount of data written - in MB."
	::= {eLogicalDriveStatistics 6}

a6ReadCacheHit OBJECT-TYPE
	SYNTAX		DmiCounter
	ACCESS		read-only
	STATUS		mandatory
	DESCRIPTION	"Read Cache Hit Rate."
	::= {eLogicalDriveStatistics 7}

SPhysicalDriveStatistics ::= SEQUENCE {
	a7ControllerNumber                      	DmiInteger,
	a7ScsiBusId                             	DmiInteger,
	a7ScsiTargetId                          	DmiInteger,
	a7ReadRequestsCount                     	DmiCounter,
	a7AmountOfDataReadInKb                  	DmiCounter,
	a7WriteRequestsCount                    	DmiCounter,
	a7AmountOfDataWrittenInKb               	DmiCounter
}

tPhysicalDriveStatistics OBJECT-TYPE
	SYNTAX		SEQUENCE OF SPhysicalDriveStatistics
	ACCESS		not-accessible
	STATUS		mandatory
	DESCRIPTION	"Physical Drive Performance Statistics"
	::= {dmtfGroups 7}

ePhysicalDriveStatistics OBJECT-TYPE
	SYNTAX		SPhysicalDriveStatistics
	ACCESS		not-accessible
	STATUS		mandatory
	DESCRIPTION	""
	--INDEX		{DmiComponentIndex, a7ControllerNumber, a7ScsiBusId, a7ScsiTargetId}
	::= {tPhysicalDriveStatistics 1}

a7ControllerNumber OBJECT-TYPE
	SYNTAX		DmiInteger
	ACCESS		read-only
	STATUS		mandatory
	DESCRIPTION	"Controller Number - used as a key."
	::= {ePhysicalDriveStatistics 1}

a7ScsiBusId OBJECT-TYPE
	SYNTAX		DmiInteger
	ACCESS		read-only
	STATUS		mandatory
	DESCRIPTION	"SCSI Channel Number - used as a key."
	::= {ePhysicalDriveStatistics 2}

a7ScsiTargetId OBJECT-TYPE
	SYNTAX		DmiInteger
	ACCESS		read-only
	STATUS		mandatory
	DESCRIPTION	"SCSI Target Device Id - used as a key."
	::= {ePhysicalDriveStatistics 3}

a7ReadRequestsCount OBJECT-TYPE
	SYNTAX		DmiCounter
	ACCESS		read-only
	STATUS		mandatory
	DESCRIPTION	"Number of Read Requests."
	::= {ePhysicalDriveStatistics 4}

a7AmountOfDataReadInKb OBJECT-TYPE
	SYNTAX		DmiCounter
	ACCESS		read-only
	STATUS		mandatory
	DESCRIPTION	"Amount of Data Read - in KB."
	::= {ePhysicalDriveStatistics 5}

a7WriteRequestsCount OBJECT-TYPE
	SYNTAX		DmiCounter
	ACCESS		read-only
	STATUS		mandatory
	DESCRIPTION	"Number of Write Requests."
	::= {ePhysicalDriveStatistics 6}

a7AmountOfDataWrittenInKb OBJECT-TYPE
	SYNTAX		DmiCounter
	ACCESS		read-only
	STATUS		mandatory
	DESCRIPTION	"Amount of data written - in KB."
	::= {ePhysicalDriveStatistics 7}

SErrorControl ::= SEQUENCE {
	a98Selfid                               	DmiInteger,
	a98NumberOfFatalErrors                  	DmiCounter,
	a98NumberOfMajorErrors                  	DmiCounter,
	a98NumberOfWarnings                     	DmiCounter,
	a98ErrorStatus                          	DmiInteger,
	a98ErrorStatusType                      	DmiInteger,
	a98AlarmGeneration                      	DmiInteger
}

tErrorControl OBJECT-TYPE
	SYNTAX		SEQUENCE OF SErrorControl
	ACCESS		not-accessible
	STATUS		mandatory
	DESCRIPTION	"Indication control and status for the parent group"
	::= {dmtfGroups 98}

eErrorControl OBJECT-TYPE
	SYNTAX		SErrorControl
	ACCESS		not-accessible
	STATUS		mandatory
	DESCRIPTION	""
	--INDEX		{DmiComponentIndex, a98Selfid}
	::= {tErrorControl 1}

a98Selfid OBJECT-TYPE
	SYNTAX		DmiInteger
	ACCESS		read-only
	STATUS		mandatory
	DESCRIPTION	"Instance Identifier. A unique number that identifies this
row."
	::= {eErrorControl 1}

a98NumberOfFatalErrors OBJECT-TYPE
	SYNTAX		DmiCounter
	ACCESS		read-only
	STATUS		mandatory
	DESCRIPTION	"Count of all fatal errors since system startup."
	::= {eErrorControl 2}

a98NumberOfMajorErrors OBJECT-TYPE
	SYNTAX		DmiCounter
	ACCESS		read-only
	STATUS		mandatory
	DESCRIPTION	"Count of all major errors since system startup."
	::= {eErrorControl 3}

a98NumberOfWarnings OBJECT-TYPE
	SYNTAX		DmiCounter
	ACCESS		read-only
	STATUS		mandatory
	DESCRIPTION	"Count of all warning errors since system startup."
	::= {eErrorControl 4}

a98ErrorStatus OBJECT-TYPE
	SYNTAX		INTEGER {
		vOk                                     	(0),
		vWarning                                	(1),
		vMajor                                  	(2),
		vFatal                                  	(3),
		vInformational                          	(4)
	}
	ACCESS		read-only
	STATUS		mandatory
	DESCRIPTION	"current error status"
	::= {eErrorControl 5}

a98ErrorStatusType OBJECT-TYPE
	SYNTAX		INTEGER {
		vPost                                   	(0),
		vRuntime                                	(1),
		vDiagnosticTest                         	(2)
	}
	ACCESS		read-only
	STATUS		mandatory
	DESCRIPTION	"Indicates the type of detection that set the current error
status."
	::= {eErrorControl 6}

a98AlarmGeneration OBJECT-TYPE
	SYNTAX		INTEGER {
		vOff                                    	(0),
		vOn                                     	(1)
	}
	ACCESS		read-only
	STATUS		mandatory
	DESCRIPTION	"Controls indication generation for errors."
	::= {eErrorControl 7}

SMiftomib ::= SEQUENCE {
	a99MibName                              	DmiDisplaystring,
	a99MibOid                               	DmiDisplaystring,
	a99DisableTrap                          	DmiInteger
}

tMiftomib OBJECT-TYPE
	SYNTAX		SEQUENCE OF SMiftomib
	ACCESS		not-accessible
	STATUS		mandatory
	DESCRIPTION	"This group defines attributes required for DMI
to SNMP translati
n"
	::= {dmtfGroups 99}

eMiftomib OBJECT-TYPE
	SYNTAX		SMiftomib
	ACCESS		not-accessible
	STATUS		mandatory
	DESCRIPTION	""
	--INDEX		{DmiComponentIndex}
	::= {tMiftomib 1}

a99MibName OBJECT-TYPE
	SYNTAX		DmiDisplaystring
	ACCESS		read-only
	STATUS		mandatory
	DESCRIPTION	"The MIB name that defines this MIF"
	::= {eMiftomib 1}

a99MibOid OBJECT-TYPE
	SYNTAX		DmiDisplaystring
	ACCESS		read-only
	STATUS		mandatory
	DESCRIPTION	"The MIB OID that corresponds to this MIF"
	::= {eMiftomib 2}

a99DisableTrap OBJECT-TYPE
	SYNTAX		DmiInteger
	ACCESS		read-write
	STATUS		mandatory
	DESCRIPTION	"This attribute can be changed to disable sending of traps
from this component"
	::= {eMiftomib 3}

-- Here is the TRAP definition for the MIB
-- Append this to the MIB produced by MIFTOMIB
-- DO NOT CHANGE ANYTHING in this definition, SNMP-DMI translator only
--         handles this specific format of the TRAP
-- changing this format WILL cause trnaslator to fail

tTrapGroup OBJECT-TYPE
    SYNTAX        SEQUENCE OF STrapGroup
    ACCESS        not-accessible
    STATUS        mandatory
    DESCRIPTION    "This group defines attributes needed for Trap
            definition. This group does not exist in MIF file"
    ::= {dmtfGroups 9999}

STrapGroup ::= SEQUENCE {
    a9999ErrorTime              DisplayString,
    a9999ErrorStatus            DmiInteger,
    a9999ErrorGroupId           DmiInteger,
    a9999ErrorInstanceId        DmiInteger,
    a9999ComponentId            DmiInteger,
    a9999GroupId                DmiInteger,
    a9999InstanceId             DmiInteger,
    a9999VendorCode1            DmiInteger,
    a9999VendorCode2            DmiInteger,
    a9999VendorText             OCTET STRING,
    a9999ParentGroupId          DmiInteger,
    a9999ParentInstanceId       DmiInteger
}

eTrapGroup OBJECT-TYPE
    SYNTAX        STrapGroup
    ACCESS        not-accessible
    STATUS        mandatory
    DESCRIPTION    ""
    --INDEX        {DmiComponentIndex}
    ::= {tTrapGroup 1}

a9999ErrorTime OBJECT-TYPE
    SYNTAX        DisplayString
    ACCESS        read-only
    STATUS        mandatory
    DESCRIPTION    "The Date & Time when the error occured"
    ::= {eTrapGroup 1}

a9999ErrorStatus OBJECT-TYPE
    SYNTAX        DmiInteger
    ACCESS        read-only
    STATUS        mandatory
    DESCRIPTION    "Error Status Code"
    ::= {eTrapGroup 2}

a9999ErrorGroupId OBJECT-TYPE
    SYNTAX        DmiInteger
    ACCESS        read-only
    STATUS        mandatory
    DESCRIPTION    "Group ID of the errorControl Group"
    ::= {eTrapGroup 3}

a9999ErrorInstanceId OBJECT-TYPE
    SYNTAX        DmiInteger
    ACCESS        read-only
    STATUS        mandatory
    DESCRIPTION    "Instance ID of the errorControl Group"
    ::= {eTrapGroup 4}

a9999ComponentId OBJECT-TYPE
    SYNTAX        DmiInteger
    ACCESS        read-only
    STATUS        mandatory
    DESCRIPTION    "Component ID of the component that caused this error"
    ::= {eTrapGroup 5}

a9999GroupId OBJECT-TYPE
    SYNTAX        DmiInteger
    ACCESS        read-only
    STATUS        mandatory
    DESCRIPTION    "Group ID of the Group that caused this error"
    ::= {eTrapGroup 6}

a9999InstanceId OBJECT-TYPE
    SYNTAX        DmiInteger
    ACCESS        read-only
    STATUS        mandatory
    DESCRIPTION    "Instance ID of the Group that caused this error"
    ::= {eTrapGroup 7}

a9999VendorCode1 OBJECT-TYPE
    SYNTAX        DmiInteger
    ACCESS        read-only
    STATUS        mandatory
    DESCRIPTION    "Vendor specific code 1"
    ::= {eTrapGroup 8}

a9999VendorCode2 OBJECT-TYPE
    SYNTAX        DmiInteger
    ACCESS        read-only
    STATUS        mandatory
    DESCRIPTION    "Vendor specific code 2"
    ::= {eTrapGroup 9}

a9999VendorText OBJECT-TYPE
    SYNTAX        OCTET STRING
    ACCESS        read-only
    STATUS        mandatory
    DESCRIPTION    "Vendor specific octet string info"
    ::= {eTrapGroup 10}

a9999ParentGroupId OBJECT-TYPE
    SYNTAX        DmiInteger
    ACCESS        read-only
    STATUS        mandatory
    DESCRIPTION    "Group ID of parent of Group that caused this error"
    ::= {eTrapGroup 11}

a9999ParentInstanceId OBJECT-TYPE
    SYNTAX        DmiInteger
    ACCESS        read-only
    STATUS        mandatory
    DESCRIPTION    "Instance ID of parent of Group that caused this error"
    ::= {eTrapGroup 12}

mdacEventError TRAP-TYPE
    ENTERPRISE eTrapGroup
    VARIABLES  { a9999ErrorTime,
                 a9999ErrorStatus,
                 a9999ErrorGroupId,
                 a9999ErrorInstanceId,
                 a9999ComponentId,
                 a9999GroupId,
                 a9999InstanceId,
                 a9999VendorCode1,
                 a9999VendorCode2,
                 a9999VendorText,
                 a9999ParentGroupId,
                 a9999ParentInstanceId}

    DESCRIPTION "DMI Service Layer generated event for Mylex Raid"

    --NMS trap annotation

    --#TYPE       "DMI Mylex Raid Error Event"
    --#SUMMARY    "Event Data: (%s,%d,%d,%d) (%d,%d,%d,%d,%d) (%d,%d)"
    --#ARGUMENTS  {0, 1, 2, 3, 4, 5, 6, 7, 8, 10, 11}
    --#SEVERITY   CRITICAL
    --#TIMEINDEX  12
    --#STATE      DEGRADED
    ::= 1
END
