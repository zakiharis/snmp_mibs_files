-- extracted from draft-adwankar-netconf-symple-00.txt
-- at Thu Oct 23 06:15:15 2003

       MOBILE-MIB DEFINITIONS ::= BEGIN

          IMPORTS
                  mgmt, NetworkAddress, IpAddress, Counter, Gauge,
                          TimeTicks, internet
                      FROM RFC1155-SMI
                  OBJECT-TYPE
                          FROM RFC-1212;

          mgmt         OBJECT IDENTIFIER ::= { iso org(3) dod(6) internet(1) 
                                               mgmt(2) }
          directory    OBJECT IDENTIFIER ::= { internet 1 }
          experimental OBJECT IDENTIFIER ::= { internet 3 }
          private      OBJECT IDENTIFIER ::= { internet 4 }
          enterprises  OBJECT IDENTIFIER ::= { private 1 }
          company      OBJECT IDENTIFIER ::= { enterprises 1 }

          -- textual conventions

           DisplayString ::=
               OCTET STRING
          -- This data type is used to model textual information taken
          -- from the NVT ASCII character set.  By convention, objects
          -- with this syntax are declared as having
          --
                (SIZE (0..255))

           PhysAddress ::=
               OCTET STRING
          -- This data type is used to model media addresses.  For many
          -- types of media, this will be in a binary representation.
          -- For example, an ethernet address would be represented as
          -- a string of 6 octets.


          -- groups in MOBILE-MIB

          devInfo          OBJECT IDENTIFIER ::= { company 1 }
          devDetail        OBJECT IDENTIFIER ::= { company 2 }
          
          ext              OBJECT IDENTIFIER ::= { devDetail 1 }
          
          settings         OBJECT IDENTIFIER ::= { ext 1 }
          
          wap              OBJECT IDENTIFIER ::= { ext 2 }          
          
          log              OBJECT IDENTIFIER ::= { ext 3 }                    

          applications     OBJECT IDENTIFIER ::= { ext 4 }          
          
          app1             OBJECT IDENTIFIER ::= { applications 1 }                    

          -- the devInfo group

	  -- Directory which holds device info

          man         OBJECT-TYPE
              SYNTAX  DisplayString (SIZE (0..255))
              ACCESS  read-only
              STATUS  mandatory
              DESCRIPTION
                      "Manufacture name."
              ::= { devInfo 1 }

          mod         OBJECT-TYPE
              SYNTAX  DisplayString (SIZE (0..255))
              ACCESS  read-only
              STATUS  mandatory
              DESCRIPTION
                      "Model name."
              ::= { devInfo 2 }

          devID       OBJECT-TYPE
              SYNTAX  DisplayString (SIZE (0..255))
              ACCESS  read-only
              STATUS  mandatory
              DESCRIPTION
                      "Device serial number."
              ::= { devInfo 3 }

          lang        OBJECT-TYPE
              SYNTAX  DisplayString (SIZE (0..255))
              ACCESS  read-write
              STATUS  mandatory
              DESCRIPTION
                      "Device language."
              ::= { devInfo 4 }

          dmV         OBJECT-TYPE
              SYNTAX  DisplayString (SIZE (0..255))
              ACCESS  read-only
              STATUS  mandatory

            DESCRIPTION
                      "Device version."
              ::= { devInfo 5 }
              
          -- the DevDetail group
          
          oem         OBJECT-TYPE
              SYNTAX  DisplayString (SIZE (0..255))
              ACCESS  read-only
              STATUS  mandatory
              DESCRIPTION
                      "Specify OEM of the device (ex, Motorola)."
              ::= { devDetail 1 }

          fwV         OBJECT-TYPE
              SYNTAX  DisplayString (SIZE (0..255))
              ACCESS  read-only
              STATUS  mandatory
              DESCRIPTION
                      "Firmware version."
              ::= { devDetail 2 }

          swV         OBJECT-TYPE
              SYNTAX  DisplayString (SIZE (0..255))
              ACCESS  read-only
              STATUS  mandatory
              DESCRIPTION
                      "Software version."
              ::= { devDetail 3 }

          hwV         OBJECT-TYPE
              SYNTAX  DisplayString (SIZE (0..255))
              ACCESS  read-only
              STATUS  mandatory
              DESCRIPTION
                      "Hardware version."
              ::= { devDetail 4 }

          devTyp      OBJECT-TYPE
              SYNTAX  DisplayString (SIZE (0..255))
              ACCESS  read-only
              STATUS  mandatory
              DESCRIPTION
                      "Device type."
              ::= { devDetail 5 }

          bearer      OBJECT-TYPE
              SYNTAX  DisplayString (SIZE (0..255))
              ACCESS  read-only
              STATUS  mandatory
              DESCRIPTION
                      "Bearer."
              ::= { devDetail 6 }

          energyLevel OBJECT-TYPE
              SYNTAX  INTEGER
              ACCESS  read-only
              STATUS  mandatory
              DESCRIPTION
                      "Energy Level. e.g Battery level"
              ::= { devDetail 7 }
              
          -- the Settings group

          -- Parent Settings directory

          clock       OBJECT-TYPE
              SYNTAX  DisplayString (SIZE (0..255))
              ACCESS  read-write
              STATUS  mandatory
              DESCRIPTION
                      "Set date and time."
              ::= { settings 1 }

          activeRing  OBJECT-TYPE
              SYNTAX  INTEGER
              ACCESS  read-write
              STATUS  mandatory
              DESCRIPTION
                      "Replace active ring tone type setting."
              ::= { settings 2 }

          activeAlert OBJECT-TYPE
              SYNTAX  INTEGER
              ACCESS  read-write
              STATUS  mandatory
              DESCRIPTION
                      "Replace active alert type setting (Silent, Vibrate, 
                                                          Loud, etc)."
              ::= { settings 3 }

          alertLevel  OBJECT-TYPE
              SYNTAX  INTEGER
              ACCESS  read-write
              STATUS  mandatory
              DESCRIPTION
                      "Replace alert level setting."
              ::= { settings 4 }

          dtmf  OBJECT-TYPE
              SYNTAX  INTEGER
              ACCESS  read-write
              STATUS  mandatory
              DESCRIPTION
                      "Replace DTMF settings (Short, Long, Off)."
              ::= { settings 5 }

          securityCode  OBJECT-TYPE
              SYNTAX  DisplayString (SIZE (0..255))
              ACCESS  read-write
              STATUS  mandatory
              DESCRIPTION
                      "Replace the security code."
              ::= { settings 6 }

          lockState  OBJECT-TYPE
              SYNTAX  INTEGER
              ACCESS  read-write
              STATUS  mandatory
              DESCRIPTION
                      "Security lock state (Locked, Unlocked)."
              ::= { settings 7 }

               
          -- the WAP group

          -- WAP folder settings

          defaultwebsession OBJECT-TYPE         
              SYNTAX        DisplayString (SIZE (0..255))
              ACCESS        read-write
              STATUS        optional
              DESCRIPTION
                      "Set default web session on phone."
              ::= { wap 1 }

          -- the Log group

          -- Directory which holds Log Mgmt Node

          callProcessing OBJECT-TYPE         
              SYNTAX        DisplayString (SIZE (0..255))
              ACCESS        read-write
              STATUS        optional
              DESCRIPTION
                      "Call Processing Log."
              ::= { log 1 }

          location OBJECT-TYPE         
              SYNTAX        DisplayString (SIZE (0..255))
              ACCESS        read-write
              STATUS        optional
              DESCRIPTION
                      "Location Log."
              ::= { log 2 }

          -- the Applications group

          -- Directory which holds Applications Info

          executionCount OBJECT-TYPE         
              SYNTAX        INTEGER
              ACCESS        read-write
              STATUS        optional
              DESCRIPTION
                      "App1 Execution Count."
              ::= { app1 1 }

          END
