-- extracted from draft-ietf-sigtran-m3ua-mib-07.txt
-- at Thu Aug 12 06:22:35 2004

  M3UA-MIB DEFINITIONS ::= BEGIN

  IMPORTS
      MODULE-IDENTITY, OBJECT-TYPE, Unsigned32, Counter32, Counter64, mib-2
           FROM SNMPv2-SMI               -- RFC 2578

      TruthValue
            FROM SNMPv2-TC               -- RFC2579

      MODULE-COMPLIANCE, OBJECT-GROUP
           FROM SNMPv2-CONF              -- RFC 2580
      ;


  m3uaMIB MODULE-IDENTITY
       LAST-UPDATED "200306050000Z"       -- 5th June 2003
       ORGANIZATION "IETF SIGTRAN Working Group"
       CONTACT-INFO
            "
             WG EMail: sigtran@ietf.org

             Web Page:
                   http://www.ietf.org/html.charters/sigtran-charter.html

             Chair:     Lyndon Ong
                        Ciena Corporation
                        0480 Ridgeview Drive
                        Cupertino, CA  95014
                        USA
                        Tel:
                        Email: lyong@ciena.com

             Editors:   Antonio Roque-Alvarez
                        R&D Department
                        Ericsson Espana S. A.
                        Via de los Poblados, 13
                        28033 Madrid
                        Spain
                        Tel:   +34 91 339 3523
                        Email: Antonio.Roque@ericsson.com

                        Antonio Canete-Martinez
                        R&D Department
                        Ericsson Espana S. A.
                        Via de los Poblados, 13
                        28033 Madrid
                        Spain
                        Tel:   +34 91 339 2460
                        Email: Antonio.Canete@ericsson.com

                        Jose-Javier Pastor-Balbas
                        R&D Department
                        Ericsson Espana S. A.
                        Via de los Poblados, 13
                        28033 Madrid
                        Spain
                        Tel:   +34 91 339 1397
                        Email: J.Javier.Pastor@ericsson.com
            "
       DESCRIPTION
            "The MIB module for managing M3UA implementations.

            Copyright (C) The Internet Society (2003). This version of this
            MIB module is part of RFC YYYY; see the RFC itself for full
            legal notices. "

       REVISION "200306050000Z"       -- 5th June 2003

       DESCRIPTION " Initial version, published as RFC YYYY"
         -- RFC Editor: to assign YYYY

       ::= {  mib-2 1 }

         -- IANA: to assign xxxx
         -- RFC Editor: to change xxxx into the value assigned by IANA

  -- Top-level structure of the MIB


  m3uaManagement              OBJECT IDENTIFIER ::= { m3uaMIB 1 }
  m3uaConformance             OBJECT IDENTIFIER ::= { m3uaMIB 2 }

    m3uaAttributes            OBJECT IDENTIFIER ::= { m3uaManagement 1 }
      m3uaConfig              OBJECT IDENTIFIER ::= { m3uaAttributes 1 }
      m3uaStatistics          OBJECT IDENTIFIER ::= { m3uaAttributes 2 }


    m3uaTables                OBJECT IDENTIFIER ::= { m3uaManagement 2 }

      m3uaAsp                 OBJECT IDENTIFIER ::= { m3uaTables 1 }
        m3uaAspCfg            OBJECT IDENTIFIER ::= { m3uaAsp 1 }
   --     m3uaAspDestTable    OBJECT IDENTIFIER ::= { m3uaAspCfg 1 }
   --     m3uaAspSgpTable     OBJECT IDENTIFIER ::= { m3uaAspCfg 2 }
   --     m3uaAspAssocTable   OBJECT IDENTIFIER ::= { m3uaAspCfg 3 }
   --     m3uaAspRcTable      OBJECT IDENTIFIER ::= { m3uaAspCfg 4 }
        m3uaAspStat           OBJECT IDENTIFIER ::= { m3uaAsp 2 }
   --     m3uaAspStatTable    OBJECT IDENTIFIER ::= { m3uaAspStat 1 }

      m3uaSgpIpsp             OBJECT IDENTIFIER ::= { m3uaTables 2 }
        m3uaSgpIpspCfg        OBJECT IDENTIFIER ::= { m3uaSgpIpsp 1 }
   --     m3uaSgpIpspRtgTable OBJECT IDENTIFIER ::= { m3uaSgpIpspCfg 1 }
   --     m3uaSgpIpspAsTable  OBJECT IDENTIFIER ::= { m3uaSgpIpspCfg 2 }
   --     m3uaSgpIpspAspTable OBJECT IDENTIFIER ::= { m3uaSgpIpspCfg 3 }
   --     m3uaSgpIpspAssocTable OBJECT IDENTIFIER ::= {m3uaSgpIpspCfg 4}
        m3uaSgpIpspStat       OBJECT IDENTIFIER ::= { m3uaSgpIpsp 2 }
   --     m3uaSgIpspStatTable OBJECT IDENTIFIER ::= { m3uaSgpIpspStat 1 }

      m3uaGen                OBJECT IDENTIFIER ::= { m3uaTables 3 }
        m3uaGenCfg           OBJECT IDENTIFIER ::= { m3uaGen 1 }
   --     m3uaGenNaTable     OBJECT IDENTIFIER ::= { m3uaGenCfg 1 }

        m3uaGenStat          OBJECT IDENTIFIER ::= { m3uaGen 2 }
   --     m3uaGenStatTable   OBJECT IDENTIFIER ::= { m3uaGenStat 1 }






  -----------------------------------------------------------------------
  -- M3UA MANAGEMENT
  -----------------------------------------------------------------------
  -----------------------------------------------------------------------
  -- ATTRIBUTES - CONFIGURATION
  -----------------------------------------------------------------------

  m3uaVersion OBJECT-TYPE
      SYNTAX      Unsigned32
      MAX-ACCESS  read-only
      STATUS      current
      DESCRIPTION
              "Identifies the current version of the M3UA."

      ::= { m3uaConfig 1 }

  m3uaProcType OBJECT-TYPE
      SYNTAX      INTEGER {
                      sgp(1),     -- Signaling Gateway Process
                      asp(2),     -- Application Server Process
                      ipsp(3)     -- IP Server Process
                  }
      MAX-ACCESS  read-only
      STATUS      current
      DESCRIPTION
              "This variable indicates the type of the process where the
               M3UA layer is located."

      ::= { m3uaConfig 2 }

  m3uaLocalPort OBJECT-TYPE
      SYNTAX      Unsigned32
      MAX-ACCESS  read-only
      STATUS      current
      DESCRIPTION
              "Identifies the port of the M3UA service. Well-known Port for
              M3UA is 2905."
      DEFVAL {2905}  -- well-known port assigned by IANA to M3UA

      ::= { m3uaConfig 3 }

  m3uaTrInitValue OBJECT-TYPE
      SYNTAX      Unsigned32
      UNITS       "milliseconds"
      MAX-ACCESS  read-only
      STATUS      current
      DESCRIPTION
              "Initial value of the Failover timer Tr. Tr set with value 0
              disables buffering."
      DEFVAL {3000}  -- 3000 milliseconds its the recommended value

      ::= { m3uaConfig 4 }

  m3uaTPAudInitValue OBJECT-TYPE
      SYNTAX      Unsigned32
      UNITS       "milliseconds"
      MAX-ACCESS  read-only
      STATUS      current
      DESCRIPTION
              "Initial value of the Periodic Audit timer TPAud."
      DEFVAL {5000}  -- 5000 milliseconds its the recommended value

      ::= { m3uaConfig 5 }


  m3uaHeartBeat OBJECT-TYPE
      SYNTAX      TruthValue
      MAX-ACCESS  read-only
      STATUS      current
      DESCRIPTION
             "Activates or deactivates the heartbeat procedure at M3UA
             level.

             When the object is set to 'true' (1), the heartbeat procedure
             is enabled.

             When the object is set to 'false' (2), Heartbeat is disabled.
             No BEAT messages are sent but the BEAT messages received are
             responded."

      ::= { m3uaConfig 6 }

  m3uaTBeatInitValue OBJECT-TYPE
      SYNTAX      Unsigned32
      UNITS       "milliseconds"
      MAX-ACCESS  read-only
      STATUS      current
      DESCRIPTION
              "Initial value of the HeartBeat timer TBeat."
      DEFVAL {1000}  -- 1000 milliseconds is the recommended value

      ::= { m3uaConfig 7 }

  m3uaTAckInitValue OBJECT-TYPE
      SYNTAX      Unsigned32
      UNITS       "milliseconds"
      MAX-ACCESS  read-only
      STATUS      current
      DESCRIPTION
              "Initial value of the Retransmission timer TAck."

      DEFVAL {2000}  -- 2000 milliseconds is the recommended value

      ::= { m3uaConfig 8 }


  m3uaFailOverBuffSize OBJECT-TYPE
      SYNTAX      Unsigned32
      UNITS       "bytes"
      MAX-ACCESS  read-only
      STATUS      current
      DESCRIPTION
              "Size of the failover retransmission buffer. Recommended
              value is 64 Kbytes. Only valid if failover buffer
              option has been set to ON."
      DEFVAL {65535}  -- Recommended value is 64 Kbytes

      ::= { m3uaConfig 12 }

  -----------------------------------------------------------------------
  -- ATTRIBUTES-STATISTICS
  -----------------------------------------------------------------------

  m3uaRoutingFailures OBJECT-TYPE
      SYNTAX      Counter64
      MAX-ACCESS  read-only
      STATUS      current
      DESCRIPTION
              "The number of times a routing operation against Routing
              Table fails. No final SCTP Association ID is obtained from
              the routing operation. That is the reason why this is a
              general statistic instead a per association statistic."

      ::= { m3uaStatistics 1 }




  -----------------------------------------------------------------------
  -- M3UA TABLES
  -----------------------------------------------------------------------
  -----------------------------------------------------------------------
  -- ASP TABLES
  -----------------------------------------------------------------------
  -----------------------------------------------------------------------
  -- CONFIG
  -----------------------------------------------------------------------
  -----------------------------------------------------------------------
  -- DESTINATION TABLE
  -----------------------------------------------------------------------

  -- The Destination Table contains information about each destination
  -- that can be reached from the ASP where it is located.


  m3uaAspDestTable OBJECT-TYPE
      SYNTAX      SEQUENCE OF M3uaAspDestEntry
      MAX-ACCESS  not-accessible
      STATUS      current
      DESCRIPTION
              "A table containing per SS7 destination information. The
              state of destinations through each SG can be fetched per AS."

      ::= { m3uaAspCfg 1 }

  m3uaAspDestEntry OBJECT-TYPE
      SYNTAX      M3uaAspDestEntry
      MAX-ACCESS  not-accessible
      STATUS      current
      DESCRIPTION
              "Destination parameters and relation with SGs and ASes."
      INDEX   { m3uaAspDestNa, m3uaAspDestDpc, m3uaAspDestSgId,
                m3uaAspDestAsId }

      ::= { m3uaAspDestTable 1 }

  M3uaAspDestEntry ::= SEQUENCE {
       m3uaAspDestNa                 Unsigned32,
       m3uaAspDestDpc                Unsigned32,
       m3uaAspDestSgId               Unsigned32,
       m3uaAspDestAsId               Unsigned32,
       m3uaAspDestState              INTEGER
      }


  m3uaAspDestNa OBJECT-TYPE
      SYNTAX      Unsigned32
      MAX-ACCESS  not-accessible
      STATUS      current
      DESCRIPTION
              "Network Appearance. When this parameter is not used, Network
              Indicator parameter, as included in the MTP3 message, will be
              filled in."

      ::= { m3uaAspDestEntry 1 }

  m3uaAspDestDpc OBJECT-TYPE
      SYNTAX      Unsigned32
      MAX-ACCESS  not-accessible
      STATUS      current
      DESCRIPTION
              "Destination Point Code located in the SS7 network. It is the
              final destination for the message generated in the ASP which
              should reach the SS7 node traversing a Signaling Gateway."

      ::= { m3uaAspDestEntry 2 }

  m3uaAspDestSgId OBJECT-TYPE
      SYNTAX      Unsigned32
      MAX-ACCESS  not-accessible
      STATUS      current
      DESCRIPTION
              "Signaling Gateway (SG) Identifier. It represents an SG that
              is in the way to the final DPC located in the SS7 network."

      ::= { m3uaAspDestEntry 3 }

  m3uaAspDestAsId OBJECT-TYPE
      SYNTAX      Unsigned32
      MAX-ACCESS  not-accessible
      STATUS      current
      DESCRIPTION
              "Application Server (AS) Identifier. It represents an AS that
              is being served by the ASP. A specific destination address
              could be reachable or not from the ASP, depending on each AS
              this ASP is serving to."

      ::= { m3uaAspDestEntry 4 }

  m3uaAspDestState OBJECT-TYPE
      SYNTAX      INTEGER {
                      unknown (1),
                      available(2),
                      unavailable(3),
                      congested(4),
                      restricted(5)
                  }
      MAX-ACCESS  read-only
      STATUS      current
      DESCRIPTION
              "Destination reachability status. It is the status of the
               Signaling Point that is the final destination of a message
               within the SS7 network when the message travels through the
               Signaling Gateway (SG) identified by the m3uaAspDestSgId
               object."
      ::= { m3uaAspDestEntry 5 }


  -----------------------------------------------------------------------
  -- M3UA TABLES
  -----------------------------------------------------------------------
  -----------------------------------------------------------------------
  -- ASP TABLES
  -----------------------------------------------------------------------
  -----------------------------------------------------------------------
  -- CONFIG
  -----------------------------------------------------------------------
  -----------------------------------------------------------------------
  -- SIGNALING GATEWAY PROCESS TABLE
  -----------------------------------------------------------------------

  -- The SGP Table contains information about the SGPs per SG that can be
  -- reached from this ASP. It shows the state of each AS at each remote
  -- SGP.


  m3uaAspSgpTable OBJECT-TYPE
      SYNTAX      SEQUENCE OF M3uaAspSgpEntry
      MAX-ACCESS  not-accessible
      STATUS      current
      DESCRIPTION
              "A table containing SGP status information for each SG that
              is communicating with an AS served by this ASP."

      ::= { m3uaAspCfg 2 }

  m3uaAspSgpEntry OBJECT-TYPE
      SYNTAX      M3uaAspSgpEntry
      MAX-ACCESS  not-accessible
      STATUS      current
      DESCRIPTION
              " SGP related parameters. There are SGPs available depending
              on the AS the ASP is serving and the SG it wants to send the
              messages. It may be one or more SGP for each AS-SG pair."
      INDEX   { m3uaAspSgpAsId, m3uaAspSgpSgId, m3uaAspSgpId }

      ::= { m3uaAspSgpTable 1 }

  M3uaAspSgpEntry ::= SEQUENCE {
       m3uaAspSgpAsId                Unsigned32,
       m3uaAspSgpSgId                Unsigned32,
       m3uaAspSgpId                  Unsigned32,
       m3uaAspSgpState               INTEGER
      }


  m3uaAspSgpAsId OBJECT-TYPE
      SYNTAX      Unsigned32
      MAX-ACCESS  not-accessible
      STATUS      current
      DESCRIPTION
              "Application Server (AS) Identifier. It represents an AS that
              is being served by the ASP."

      ::= { m3uaAspSgpEntry 1 }

  m3uaAspSgpSgId OBJECT-TYPE
      SYNTAX      Unsigned32
      MAX-ACCESS  not-accessible
      STATUS      current
      DESCRIPTION
              "Signaling Gateway (SG) Identifier. It represents an SG
              composed of the SGPs identified by m3uaAspSgpId."

      ::= { m3uaAspSgpEntry 2 }

  m3uaAspSgpId OBJECT-TYPE
      SYNTAX      Unsigned32
      MAX-ACCESS  not-accessible
      STATUS      current
      DESCRIPTION
              "Signaling Gateway Process (SGP) Identifier. It represents an
              SGP that is serving the Signaling Gateway (SG) identified by
              the m3uaAspSgpSgId object."

      ::= { m3uaAspSgpEntry 3 }


  m3uaAspSgpState OBJECT-TYPE
      SYNTAX      INTEGER {
                      unknown (1),
                      active(2),
                      inactive(3),
                      down(4)
                  }
      MAX-ACCESS  read-only
      STATUS      current
      DESCRIPTION
              "AS state through each SGP in the SG."
      ::= { m3uaAspSgpEntry 4 }





  -----------------------------------------------------------------------
  -- M3UA TABLES
  -----------------------------------------------------------------------
  -----------------------------------------------------------------------
  -- ASP TABLES
  -----------------------------------------------------------------------
  -----------------------------------------------------------------------
  -- CONFIG
  -----------------------------------------------------------------------
  -----------------------------------------------------------------------
  -- ASSOCIATION TABLE
  -----------------------------------------------------------------------

  -- The Association Table contains information about the association
  -- towards each SGP that can be reached from this ASP when serving to any
  -- of its ASes. Limits of the streams that are data for the lower layer
  -- (SCTP) are also included.


  m3uaAspAssocTable OBJECT-TYPE
      SYNTAX      SEQUENCE OF M3uaAspAssocEntry
      MAX-ACCESS  not-accessible
      STATUS      current
      DESCRIPTION
              "A table containing SCTP association information information
              for each SGP that is communicating with this ASP."

      ::= { m3uaAspCfg 3 }

  m3uaAspAssocEntry OBJECT-TYPE
      SYNTAX      M3uaAspAssocEntry
      MAX-ACCESS  not-accessible
      STATUS      current
      DESCRIPTION
              " SCTP related parameters. There will be one association to
              each of the SGPs that this ASP has to talk to."
      INDEX   { m3uaAspAssocSgpId }

      ::= { m3uaAspAssocTable 1 }

  M3uaAspAssocEntry ::= SEQUENCE {
       m3uaAspAssocSgpId             Unsigned32,
       m3uaAspAssocId                Unsigned32,
       m3uaAspAssocMinOutStreams     Unsigned32,
       m3uaAspAssocMaxInStreams      Unsigned32
      }


  m3uaAspAssocSgpId OBJECT-TYPE
      SYNTAX      Unsigned32
      MAX-ACCESS  not-accessible
      STATUS      current
      DESCRIPTION
              "Signaling Gateway Process (SGP) Identifier. It represents an
              SGP."

      ::= { m3uaAspAssocEntry 1 }



  m3uaAspAssocId OBJECT-TYPE
      SYNTAX      Unsigned32
      MAX-ACCESS  read-only
      STATUS      current
      DESCRIPTION
              "Association Identification. It is the value that identifies
              the association that is established between this ASP and the
              SGP represented by m3uaAspAssocSgpId. This value is extracted
              from the SCTP association Id value returned by SCTP when the
              association is established to that endpoint. It is the link
              to get the transport values from the SCTP MIB."

      ::= { m3uaAspAssocEntry 2 }



  m3uaAspAssocMinOutStreams OBJECT-TYPE
      SYNTAX      Unsigned32
      MAX-ACCESS  read-only
      STATUS      current
      DESCRIPTION
              "If the SCTP association is initiated from this ASP,
              this will be the minimum number of outgoing streams that is
              requested to the remote peer at association start up."

      ::= { m3uaAspAssocEntry 3 }

  m3uaAspAssocMaxInStreams OBJECT-TYPE
      SYNTAX      Unsigned32
      MAX-ACCESS  read-only
      STATUS      current
      DESCRIPTION
              "It is the maximum number of input streams that this
              application can support. It is used during the Association
              establishment phase."

      ::= { m3uaAspAssocEntry 4 }



  -----------------------------------------------------------------------
  -- M3UA TABLES
  -----------------------------------------------------------------------
  -----------------------------------------------------------------------
  -- ASP TABLES
  -----------------------------------------------------------------------
  -----------------------------------------------------------------------
  -- CONFIG
  -----------------------------------------------------------------------
  -----------------------------------------------------------------------
  -- ROUTING CONTEXT TABLE
  -----------------------------------------------------------------------

  -- The Routing Context (RC) Table contains information about the
  -- association towards each SGP that can be reached from this ASP when
  -- serving to any of its ASes.


  m3uaAspRcTable OBJECT-TYPE
      SYNTAX      SEQUENCE OF M3uaAspAssocEntry
      MAX-ACCESS  not-accessible
      STATUS      current
      DESCRIPTION
              "A table containing the Routing Context (RC) values for each
              SGP-AS relationship. As indicated in the M3UA RFC, the RC
              values are SGP scoped."

      ::= { m3uaAspCfg 4 }

  m3uaAspRcEntry OBJECT-TYPE
      SYNTAX      M3uaAspRcEntry
      MAX-ACCESS  not-accessible
      STATUS      current
      DESCRIPTION
              " RC value for each AS as assigned by the SGP."
      INDEX   { m3uaAspRcSgpId, m3uaAspRcAsId }

      ::= { m3uaAspRcTable 1 }

  M3uaAspRcEntry ::= SEQUENCE {
       m3uaAspRcSgpId                Unsigned32,
       m3uaAspRcAsId                 Unsigned32,
       m3uaAspRcValue                Unsigned32
      }

  m3uaAspRcSgpId OBJECT-TYPE
      SYNTAX      Unsigned32
      MAX-ACCESS  not-accessible
      STATUS      current
      DESCRIPTION
              "Signaling Gateway Process (SGP) Identifier. It represents an
              SGP that communicates with this ASP."

      ::= { m3uaAspRcEntry 1 }

  m3uaAspRcAsId OBJECT-TYPE
      SYNTAX      Unsigned32
      MAX-ACCESS  not-accessible
      STATUS      current
      DESCRIPTION
              "Application Server (AS) Identifier. It represents an AS that
              is being served by the ASP."

      ::= { m3uaAspRcEntry 2 }

  m3uaAspRcValue OBJECT-TYPE
      SYNTAX      Unsigned32
      MAX-ACCESS  read-only
      STATUS      current
      DESCRIPTION
              "This is the value for the Routing Context that is share
              between the SGP identified by communicatinm3uaAspRcSgpId
              object and this ASP when serving to AS identified by the
              m3uaAspRcAsId object."

      ::= { m3uaAspRcEntry 3 }

  -----------------------------------------------------------------------
  -- M3UA TABLES
  -----------------------------------------------------------------------
  -----------------------------------------------------------------------
  -- ASP TABLES
  -----------------------------------------------------------------------
  -----------------------------------------------------------------------
  -- STATISTICS
  -----------------------------------------------------------------------
  -----------------------------------------------------------------------
  -- ASP STATISTICS TABLE
  -----------------------------------------------------------------------

  -- It defines statistics specific to an Application Server Process.
  -- Statistics applicable to SGP, ASP and IPSP are covered in the generic
  -- statistics table.

  -- The table contains statistics data related to the M3UA messages
  -- exchanged through each association at the ASP.


  m3uaAspStatTable OBJECT-TYPE
      SYNTAX      SEQUENCE OF M3uaAspStatEntry
      MAX-ACCESS  not-accessible
      STATUS      current
      DESCRIPTION
              "A table containing per association statistics."

      ::= { m3uaAspStat 1 }

  m3uaAspStatEntry OBJECT-TYPE
      SYNTAX      M3uaAspStatEntry
      MAX-ACCESS  not-accessible
      STATUS      current
      DESCRIPTION
              "It counts all the messages received and sent through a
              specific association."
      INDEX   { m3uaAspStatAssocId }

      ::= { m3uaAspStatTable 1 }

  M3uaAspStatEntry ::= SEQUENCE {
          m3uaAspStatAssocId            Unsigned32,
          m3uaAspStatAspupOut           Counter32,
          m3uaAspStatAspacOut           Counter32,
          m3uaAspStatAspdnOut           Counter32,
          m3uaAspStatAspiaOut           Counter32,
          m3uaAspStatAspupAckIn         Counter32,
          m3uaAspStatAspacAckIn         Counter32,
          m3uaAspStatAspdnAckIn         Counter32,
          m3uaAspStatAspiaAckIn         Counter32,
          m3uaAspStatNotifyIn           Counter32,
          m3uaAspStatDaudOut            Counter32,
          m3uaAspStatDunaIn             Counter32,
          m3uaAspStatDavaIn             Counter32,
          m3uaAspStatDupuIn             Counter32
      }

  -- Association Statistics

  -- ASPM Statistics per Association

  m3uaAspStatAssocId OBJECT-TYPE
      SYNTAX      Unsigned32
      MAX-ACCESS  not-accessible
      STATUS      current
      DESCRIPTION
              "Association Identification. It is the value that identifies
              the association that is established between this ASP and the
              SGP represented by m3uaAspAssocSgpId. This value is extracted
              from the SCTP association Id value returned by SCTP when the
              association is established to that endpoint. It is the link
              to get the transport values from the SCTP MIB."

      ::= { m3uaAspStatEntry 1 }


  m3uaAspStatAspupOut OBJECT-TYPE
      SYNTAX      Counter32
      MAX-ACCESS  read-only
      STATUS      current
      DESCRIPTION
              "Number of ASPUP messages sent through the association."

      ::= { m3uaAspStatEntry 2 }

  m3uaAspStatAspacOut OBJECT-TYPE
      SYNTAX      Counter32
      MAX-ACCESS  read-only
      STATUS      current
      DESCRIPTION
              "Number of ASPAC messages sent through the association."

      ::= { m3uaAspStatEntry 3 }

  m3uaAspStatAspdnOut OBJECT-TYPE
      SYNTAX      Counter32
      MAX-ACCESS  read-only
      STATUS      current
      DESCRIPTION
              "Number of ASPDN messages sent through the association."

      ::= { m3uaAspStatEntry 4 }

  m3uaAspStatAspiaOut OBJECT-TYPE
      SYNTAX      Counter32
      MAX-ACCESS  read-only
      STATUS      current
      DESCRIPTION
              "Number of ASPIA messages sent through the association."

      ::= { m3uaAspStatEntry 5 }

  m3uaAspStatAspupAckIn OBJECT-TYPE
      SYNTAX      Counter32
      MAX-ACCESS  read-only
      STATUS      current
      DESCRIPTION
              "Number of ASPUP ACK messages received through the
              association."

      ::= { m3uaAspStatEntry 6 }

  m3uaAspStatAspacAckIn OBJECT-TYPE
      SYNTAX      Counter32
      MAX-ACCESS  read-only
      STATUS      current
      DESCRIPTION
              "Number of ASPAC ACK messages received through the
              association."

      ::= { m3uaAspStatEntry 7 }

  m3uaAspStatAspdnAckIn OBJECT-TYPE
      SYNTAX      Counter32
      MAX-ACCESS  read-only
      STATUS      current
      DESCRIPTION
              "Number of ASPDN ACK messages received through the
              association."

      ::= { m3uaAspStatEntry 8 }

  m3uaAspStatAspiaAckIn OBJECT-TYPE
      SYNTAX      Counter32
      MAX-ACCESS  read-only
      STATUS      current
      DESCRIPTION
              "Number of ASPIA ACK messages received through the
              association."

      ::= { m3uaAspStatEntry 9 }

  -- End of ASPM Statistics per Association


  -- MGMT Statistics per Association

  m3uaAspStatNotifyIn OBJECT-TYPE
      SYNTAX      Counter32
      MAX-ACCESS  read-only
      STATUS      current
      DESCRIPTION
              "Number of NOTIFY messages received through the
              association."

      ::= { m3uaAspStatEntry 10 }

  -- End of MGMT Statistics per Association


  -- SSNM Statistics per Association

  m3uaAspStatDaudOut OBJECT-TYPE
      SYNTAX      Counter32
      MAX-ACCESS  read-only
      STATUS      current
      DESCRIPTION
              "Number of DAUD messages sent through the association."

      ::= { m3uaAspStatEntry 11 }

  m3uaAspStatDunaIn OBJECT-TYPE
      SYNTAX      Counter32
      MAX-ACCESS  read-only
      STATUS      current
      DESCRIPTION
              "Number of DUNA messages received through the association."

      ::= { m3uaAspStatEntry 12 }

  m3uaAspStatDavaIn OBJECT-TYPE
      SYNTAX      Counter32
      MAX-ACCESS  read-only
      STATUS      current
      DESCRIPTION
              "Number of DAVA messages received through the association."

      ::= { m3uaAspStatEntry 13 }

  m3uaAspStatDupuIn OBJECT-TYPE
      SYNTAX      Counter32
      MAX-ACCESS  read-only
      STATUS      current
      DESCRIPTION
              "Number of DUPU messages received through the association."

      ::= { m3uaAspStatEntry 14 }

  -- End of SSNM Statistics per Association




  -----------------------------------------------------------------------
  -- M3UA TABLES
  -----------------------------------------------------------------------
  -----------------------------------------------------------------------
  -- TABLES AT SGP/IPSP
  -----------------------------------------------------------------------
  -----------------------------------------------------------------------
  -- CONFIG
  -----------------------------------------------------------------------
  -----------------------------------------------------------------------
  -- ROUTING TABLE
  -----------------------------------------------------------------------

  -- The Routing table contains a list of routing keys, which translate to
  -- an Application Server ID and a corresponding Routing Context.

  -- As a Routing Key may be composed of any combination of basic SS7
  -- routing elements, if an element is not included in the routing key,
  -- a default value is assigned. This default value can continue being
  -- considered as an indexing value itself.


  m3uaSgpIpspRtgTable OBJECT-TYPE
      SYNTAX      SEQUENCE OF M3uaSgpIpspRtgEntry
      MAX-ACCESS  not-accessible
      STATUS      current
      DESCRIPTION
              "A table containing Routing-specific information."

      ::= { m3uaSgpIpspCfg 1 }

  m3uaSgpIpspRtgEntry OBJECT-TYPE
      SYNTAX      M3uaSgpIpspRtgEntry
      MAX-ACCESS  not-accessible
      STATUS      current
      DESCRIPTION
              "General common variables for a Routing Key."
      INDEX   { m3uaSgpIpspRtgNa,
                m3uaSgpIpspRtgDpc,
                m3uaSgpIpspRtgSi,
                m3uaSgpIpspRtgOpc }

      ::= { m3uaSgpIpspRtgTable 1 }

  M3uaSgpIpspRtgEntry ::= SEQUENCE {
       m3uaSgpIpspRtgNa             Unsigned32,
       m3uaSgpIpspRtgDpc            Unsigned32,
       m3uaSgpIpspRtgSi             Unsigned32,
       m3uaSgpIpspRtgOpc            Unsigned32,
       m3uaSgpIpspRtgAsId           Unsigned32,
       m3uaSgpIpspRtgRc             Unsigned32
     }

  m3uaSgpIpspRtgNa OBJECT-TYPE
      SYNTAX      Unsigned32
      MAX-ACCESS  not-accessible
      STATUS      current
      DESCRIPTION
              "Network Appearance for that routing key. A default value
              will be assigned if not present in the Routing Key."

      ::= { m3uaSgpIpspRtgEntry 1 }

  m3uaSgpIpspRtgDpc OBJECT-TYPE
      SYNTAX      Unsigned32
      MAX-ACCESS  not-accessible
      STATUS      current
      DESCRIPTION
              "Destination Point Code for that routing key. A default
              value will be assigned if not present in the Routing Key.
              Range: 0 - 16777215."

      ::= { m3uaSgpIpspRtgEntry 2 }

  m3uaSgpIpspRtgSi OBJECT-TYPE
      SYNTAX      Unsigned32
      MAX-ACCESS  not-accessible
      STATUS      current
      DESCRIPTION
              "Service Indicator for that routing key. A default value
              will be assigned if not present in the Routing Key.
              Range: 2 - 10."
      ::= { m3uaSgpIpspRtgEntry 3 }

  m3uaSgpIpspRtgOpc OBJECT-TYPE
      SYNTAX      Unsigned32
      MAX-ACCESS  not-accessible
      STATUS      current
      DESCRIPTION
              "Originating Point Code for that routing key. A default
              value will be assigned if not present in the Routing Key.
              Range: 0 to 16777215."

      ::= { m3uaSgpIpspRtgEntry 4 }


  m3uaSgpIpspRtgAsId OBJECT-TYPE
      SYNTAX      Unsigned32
      MAX-ACCESS  read-only
      STATUS      current
      DESCRIPTION
              "Application Server Identification Value."

      ::= { m3uaSgpIpspRtgEntry 5 }

  m3uaSgpIpspRtgRc OBJECT-TYPE
      SYNTAX      Unsigned32
      MAX-ACCESS  read-only
      STATUS      current
      DESCRIPTION
              "Routing Context for that routing key."

      ::= { m3uaSgpIpspRtgEntry 6 }



  -----------------------------------------------------------------------
  -- M3UA TABLES
  -----------------------------------------------------------------------
  -----------------------------------------------------------------------
  -- TABLES AT SGP/IPSP
  -----------------------------------------------------------------------
  -----------------------------------------------------------------------
  -- CONFIG
  -----------------------------------------------------------------------
  -----------------------------------------------------------------------
  -- APPLICATION SERVER (AS) TABLE
  -----------------------------------------------------------------------

  -- The Application Server table contains information on the state and
  -- traffic mode of each Application for which one or more routing keys
  -- can exist in the Signalling Gateway or IPSP routing table.



  m3uaSgpIpspAsTable OBJECT-TYPE
      SYNTAX      SEQUENCE OF M3uaSgpIpspAsEntry
      MAX-ACCESS  not-accessible
      STATUS      current
      DESCRIPTION
              "A table containing Application Server-specific information."

      ::= { m3uaSgpIpspCfg 2 }

  m3uaSgpIpspAsEntry OBJECT-TYPE
      SYNTAX      M3uaSgpIpspAsEntry
      MAX-ACCESS  not-accessible
      STATUS      current
      DESCRIPTION
              "General common variables for the Application Server"
      INDEX   { m3uaSgpIpspAsId }

      ::= { m3uaSgpIpspAsTable 1 }

  M3uaSgpIpspAsEntry ::= SEQUENCE {
       m3uaSgpIpspAsId                     Unsigned32,
       m3uaSgpIpspAsState                  INTEGER,
       m3uaSgpIpspAsTmt                    INTEGER
      }

  m3uaSgpIpspAsId OBJECT-TYPE
      SYNTAX      Unsigned32
      MAX-ACCESS  not-accessible
      STATUS      current
      DESCRIPTION
              "Application Server Identification Value."

      ::= { m3uaSgpIpspAsEntry 1 }


  m3uaSgpIpspAsState OBJECT-TYPE
      SYNTAX      INTEGER {
                      active(1),
                      inactive(2),
                      down(3),
                      pending(4)
                  }
      MAX-ACCESS  read-only
      STATUS      current
      DESCRIPTION
              "Current Application Server State. Based on the state
              of the Application Server Processes which serve it."

      ::= { m3uaSgpIpspAsEntry 2 }

  m3uaSgpIpspAsTmt OBJECT-TYPE
      SYNTAX      INTEGER {
                      override(1),
                      loadshare(2),
                      broadcast(3)
                  }
      MAX-ACCESS  read-only
      STATUS      current
      DESCRIPTION
              "Current Application Server Traffic Mode Type."
      ::= { m3uaSgpIpspAsEntry 3 }



  -----------------------------------------------------------------------
  -- M3UA TABLES
  -----------------------------------------------------------------------
  -----------------------------------------------------------------------
  -- TABLES AT SGP/IPSP
  -----------------------------------------------------------------------
  -----------------------------------------------------------------------
  -- CONFIG
  -----------------------------------------------------------------------
  -----------------------------------------------------------------------
  -- APPLICATION SERVER PROCESS TABLE
  -----------------------------------------------------------------------

  -- This table shows the State of the Application Server Process or IPSP
  -- for each Application Server, and the role of the ASP in the AS traffic
  -- distribution, according to each AS traffic mode.


  m3uaSgpIpspAspTable OBJECT-TYPE
      SYNTAX      SEQUENCE OF M3uaSgpIpspAspEntry
      MAX-ACCESS  not-accessible
      STATUS      current
      DESCRIPTION
              "A table containing Application Server Process-specific
              information."

      ::= { m3uaSgpIpspCfg 3 }

  m3uaSgpIpspAspEntry OBJECT-TYPE
      SYNTAX      M3uaSgpIpspAspEntry
      MAX-ACCESS  not-accessible
      STATUS      current
      DESCRIPTION
              "General common variables for the Application Server
              Process."
      INDEX   { m3uaSgpIpspAspAsId,
                m3uaSgpIpspAspId }

      ::= { m3uaSgpIpspAspTable 1 }

  M3uaSgpIpspAspEntry ::= SEQUENCE {
       m3uaSgpIpspAspAsId                        Unsigned32,
       m3uaSgpIpspAspId                          Unsigned32,
       m3uaSgpIpspAspState                       INTEGER,
       m3uaSgpIpspAspRole                        INTEGER
      }

  m3uaSgpIpspAspAsId OBJECT-TYPE
      SYNTAX      Unsigned32
      MAX-ACCESS  not-accessible
      STATUS      current
      DESCRIPTION
              "Application Server Identification Value."

      ::= { m3uaSgpIpspAspEntry 1 }


  m3uaSgpIpspAspId OBJECT-TYPE
      SYNTAX      Unsigned32
      MAX-ACCESS  not-accessible
      STATUS      current
      DESCRIPTION
              " Application Server Process Identification Value."

      ::= { m3uaSgpIpspAspEntry 2 }

  m3uaSgpIpspAspState OBJECT-TYPE
      SYNTAX      INTEGER {
                      aspDown(1),
                      aspUp(2),
                      aspActive(3)
                  }
      MAX-ACCESS  read-only
      STATUS      current
      DESCRIPTION
              "The state of this Application Server Process for a
              given AS."

      ::= { m3uaSgpIpspAspEntry 3 }

  m3uaSgpIpspAspRole OBJECT-TYPE
      SYNTAX      INTEGER {
                      primary(1),
                      backup(2),
                      loadsharing(3),
                      broadcast (4)
                  }
      MAX-ACCESS  read-only
      STATUS      current
      DESCRIPTION
              "The role of this Application Server Process within the
              traffic mode for each AS."

      ::= { m3uaSgpIpspAspEntry 4 }


  -----------------------------------------------------------------------
  -- M3UA TABLES
  -----------------------------------------------------------------------
  -----------------------------------------------------------------------
  -- TABLES AT SGP/IPSP
  -----------------------------------------------------------------------
  -----------------------------------------------------------------------
  -- CONFIG
  -----------------------------------------------------------------------
  -----------------------------------------------------------------------
  -- APPLICATION SERVER PROCESS (ASP) ASSOCIATION TABLE
  -----------------------------------------------------------------------

  -- Defines data related to the SCTP Association for an Application Server
  -- Process or IPSP.
  -- Further Association data can be obtained from the SCTP MIB.


  m3uaSgpIpspAssocTable OBJECT-TYPE
      SYNTAX      SEQUENCE OF M3uaSgpIpspAssocEntry
      MAX-ACCESS  not-accessible
      STATUS      current
      DESCRIPTION
              "A table containing ASP/IPSP Association-specific
              information."

      ::= { m3uaSgpIpspCfg 4 }

  m3uaSgpIpspAssocEntry OBJECT-TYPE
      SYNTAX      M3uaSgpIpspAssocEntry
      MAX-ACCESS  not-accessible
      STATUS      current
      DESCRIPTION
              "General common variables for the Association for an
              ASP."
      INDEX   { m3uaSgpIpspAssocAspId }

      ::= { m3uaSgpIpspAssocTable 1 }

  M3uaSgpIpspAssocEntry ::= SEQUENCE {
       m3uaSgpIpspAssocAspId                  Unsigned32,
       m3uaSgpIpspAssocId                     Unsigned32,
       m3uaSgpIpspAssocMinOutStreams          Unsigned32,
       m3uaSgpIpspAssocMaxInStreams           Unsigned32
      }

  m3uaSgpIpspAssocAspId OBJECT-TYPE
      SYNTAX      Unsigned32
      MAX-ACCESS  not-accessible
      STATUS      current
      DESCRIPTION
              " Application Server Process Identification Value."

      ::= { m3uaSgpIpspAssocEntry 1 }

  m3uaSgpIpspAssocId  OBJECT-TYPE
      SYNTAX      Unsigned32
      MAX-ACCESS  read-only
      STATUS      current
      DESCRIPTION
              "Association Identification. Value identifying the
              association for that ASP. This value is extracted from
              the SCTP association Id value returned by SCTP when the
              association is established to that endpoint."

      ::= { m3uaSgpIpspAssocEntry 2 }


  m3uaSgpIpspAssocMinOutStreams OBJECT-TYPE
      SYNTAX      Unsigned32
      MAX-ACCESS  read-only
      STATUS      current
      DESCRIPTION
              "If the SCTP association is initiated from this ASP,
              this will be the minimum number of outgoing streams that is
              requested to the remote peer at association start up."
      ::= { m3uaSgpIpspAssocEntry 3 }

  m3uaSgpIpspAssocMaxInStreams OBJECT-TYPE
      SYNTAX      Unsigned32
      MAX-ACCESS  read-only
      STATUS      current
      DESCRIPTION
              "It is the maximum number of input streams that this
              application can support. It is used during the Association
              establishment phase."
      ::= { m3uaSgpIpspAssocEntry 4 }









  -----------------------------------------------------------------------
  -- M3UA TABLES
  -----------------------------------------------------------------------
  -----------------------------------------------------------------------
  -- TABLES AT SGP/IPSP
  -----------------------------------------------------------------------
  -----------------------------------------------------------------------
  -- STATISTICS
  -----------------------------------------------------------------------
  -----------------------------------------------------------------------
  -- SGP / IPSP STATISTICS TABLE
  -----------------------------------------------------------------------

  -- It defines statistics specific to a Signaling Gateway Process or IP
  -- Signaling Process.

  -- Statistics applicable to SGP, ASP and IPSP are covered in the generic
  -- statistics table.

  -- For the IPSP, the ASP Statistics table also applies.

  -- The table contains statistics data related to the M3UA messages
  -- exchanged through each association at the SGP or IPSP.

  m3uaSgpIpspStatTable OBJECT-TYPE
      SYNTAX      SEQUENCE OF M3uaSgpIpspStatEntry
      MAX-ACCESS  not-accessible
      STATUS      current
      DESCRIPTION
              "A table containing per association statistics."

      ::= { m3uaSgpIpspStat 1 }

  m3uaSgpIpspStatEntry OBJECT-TYPE
      SYNTAX      M3uaSgpIpspStatEntry
      MAX-ACCESS  not-accessible
      STATUS      current
      DESCRIPTION
              "It counts all the messages received and sent through a
              specific association."
      INDEX   { m3uaSgpIpspStatAssocId }

      ::= { m3uaSgpIpspStatTable 1 }

  M3uaSgpIpspStatEntry ::= SEQUENCE {
          m3uaSgpIpspStatAssocId            Unsigned32,
          m3uaSgpIpspStatAspupAckOut        Counter32,
          m3uaSgpIpspStatAspacAckOut        Counter32,
          m3uaSgpIpspStatAspdnAckOut        Counter32,
          m3uaSgpIpspStatAspiaAckOut        Counter32,
          m3uaSgpIpspStatAspupIn            Counter32,
          m3uaSgpIpspStatAspacIn            Counter32,
          m3uaSgpIpspStatAspdnIn            Counter32,
          m3uaSgpIpspStatAspiaIn            Counter32,
          m3uaSgpIpspStatNotifyOut          Counter32,
          m3uaSgpIpspStatDunaOut            Counter32,
          m3uaSgpIpspStatDavaOut            Counter32,
          m3uaSgpIpspStatDupuOut            Counter32,
          m3uaSgpIpspStatDaudIn             Counter32
      }

  -- Association Statistics

  -- ASPM Statistics per Association

  m3uaSgpIpspStatAssocId OBJECT-TYPE
      SYNTAX      Unsigned32
      MAX-ACCESS  not-accessible
      STATUS      current
      DESCRIPTION
              "Association Identification. It is the value that identifies
              the association that is established between this SGP or IPSP
              and the remote ASP or IPSP. This value is extracted from the
              SCTP association Id value returned by SCTP when the
              association is established to that endpoint. It is the link
              to get the transport values from the SCTP MIB."

      ::= { m3uaSgpIpspStatEntry 1 }

  m3uaSgpIpspStatAspupAckOut OBJECT-TYPE
      SYNTAX      Counter32
      MAX-ACCESS  read-only
      STATUS      current
      DESCRIPTION
              "Number of ASPUP ACK messages sent through the association."

      ::= { m3uaSgpIpspStatEntry 2 }

  m3uaSgpIpspStatAspacAckOut OBJECT-TYPE
      SYNTAX      Counter32
      MAX-ACCESS  read-only
      STATUS      current
      DESCRIPTION
              "Number of ASPAC ACK messages sent through the association."

      ::= { m3uaSgpIpspStatEntry 3 }

  m3uaSgpIpspStatAspdnAckOut OBJECT-TYPE
      SYNTAX      Counter32
      MAX-ACCESS  read-only
      STATUS      current
      DESCRIPTION
              "Number of ASPDN ACK messages sent through the association."

      ::= { m3uaSgpIpspStatEntry 4 }

  m3uaSgpIpspStatAspiaAckOut OBJECT-TYPE
      SYNTAX      Counter32
      MAX-ACCESS  read-only
      STATUS      current
      DESCRIPTION
              "Number of ASPIA ACK messages sent through the association."

      ::= { m3uaSgpIpspStatEntry 5 }

  m3uaSgpIpspStatAspupIn OBJECT-TYPE
      SYNTAX      Counter32
      MAX-ACCESS  read-only
      STATUS      current
      DESCRIPTION
              "Number of ASPUP messages received through the association."
      ::= { m3uaSgpIpspStatEntry 6 }

  m3uaSgpIpspStatAspacIn OBJECT-TYPE
      SYNTAX      Counter32
      MAX-ACCESS  read-only
      STATUS      current
      DESCRIPTION
              "Number of ASPAC messages received through the association."

      ::= { m3uaSgpIpspStatEntry 7 }

  m3uaSgpIpspStatAspdnIn OBJECT-TYPE
      SYNTAX      Counter32
      MAX-ACCESS  read-only
      STATUS      current
      DESCRIPTION
              "Number of ASPDN messages received through the association."

      ::= { m3uaSgpIpspStatEntry 8 }

  m3uaSgpIpspStatAspiaIn OBJECT-TYPE
      SYNTAX      Counter32
      MAX-ACCESS  read-only
      STATUS      current
      DESCRIPTION
              "Number of ASPIA messages received through the association."

      ::= { m3uaSgpIpspStatEntry 9 }

  -- End of ASPM Statistics per Association


  -- MGMT Statistics per Association

  m3uaSgpIpspStatNotifyOut OBJECT-TYPE
      SYNTAX      Counter32
      MAX-ACCESS  read-only
      STATUS      current
      DESCRIPTION
              "Number of NOTIFY messages sent through the association."
      ::= { m3uaSgpIpspStatEntry 10 }


  -- End of MGMT Statistics per Association


  -- SSNM Statistics per Association
  m3uaSgpIpspStatDunaOut OBJECT-TYPE
      SYNTAX      Counter32
      MAX-ACCESS  read-only
      STATUS      current
      DESCRIPTION
              "Number of DUNA messages sent through the association."
      ::= { m3uaSgpIpspStatEntry 11 }

  m3uaSgpIpspStatDavaOut OBJECT-TYPE
      SYNTAX      Counter32
      MAX-ACCESS  read-only
      STATUS      current
      DESCRIPTION
              "Number of DAVA messages sent through the association."

      ::= { m3uaSgpIpspStatEntry 12 }

  m3uaSgpIpspStatDupuOut OBJECT-TYPE
      SYNTAX      Counter32
      MAX-ACCESS  read-only
      STATUS      current
      DESCRIPTION
              "Number of DUPU messages sent through the association."
      ::= { m3uaSgpIpspStatEntry 13 }

  m3uaSgpIpspStatDaudIn OBJECT-TYPE
      SYNTAX      Counter32
      MAX-ACCESS  read-only
      STATUS      current
      DESCRIPTION
              "Number of DAUD messages received through the association."
      ::= { m3uaSgpIpspStatEntry 14 }

  -- End of SSNM Statistics per Association



  -----------------------------------------------------------------------
  -- M3UA TABLES
  -----------------------------------------------------------------------
  -----------------------------------------------------------------------
  -- GENERIC
  -----------------------------------------------------------------------
  -----------------------------------------------------------------------
  -- CONFIG
  -----------------------------------------------------------------------
  -----------------------------------------------------------------------
  -- NETWORK APPEARANCE TABLE
  -----------------------------------------------------------------------



  m3uaGenNaTable OBJECT-TYPE
      SYNTAX      SEQUENCE OF M3uaGenNaEntry
      MAX-ACCESS  not-accessible
      STATUS      current
      DESCRIPTION
             "A table containing Network Appearance-specific information"
      ::= { m3uaGenCfg 1 }

  m3uaGenNaEntry  OBJECT-TYPE
      SYNTAX      M3uaGenNaEntry
      MAX-ACCESS  not-accessible
      STATUS      current
      DESCRIPTION
              "General common variables for a Network Appearance."
      INDEX   { m3uaGenNaValue }
      ::= { m3uaGenNaTable  1 }

  M3uaGenNaEntry  ::= SEQUENCE {
       m3uaGenNaValue                        Unsigned32,
       m3uaGenNaNi                           Unsigned32,
       m3uaGenNaMtp3ProtType                 INTEGER,
       m3uaGenNaMtp3ProtVariant              Unsigned32,
       m3uaGenNaMtp3ProtVersion              Unsigned32
      }

  m3uaGenNaValue OBJECT-TYPE
      SYNTAX      Unsigned32
      MAX-ACCESS  not-accessible
      STATUS      current
      DESCRIPTION
              "Network Appearance Value."

      ::= { m3uaGenNaEntry  2 }


  m3uaGenNaNi OBJECT-TYPE
      SYNTAX      Unsigned32
      MAX-ACCESS  read-only
      STATUS      current
      DESCRIPTION
              "Identifies the Network Indicator of the SG Node in the
               SS7 Network."

      ::= { m3uaGenNaEntry  3 }

  m3uaGenNaMtp3ProtType OBJECT-TYPE
      SYNTAX      INTEGER {
                      itu(1),
                      ansi(2),
                      china(3),
                      ttc(4),
                      other(5)
                  }
      MAX-ACCESS  read-only
      STATUS      current
      DESCRIPTION
              "The MTP3 protocol type for this NA."

      ::= { m3uaGenNaEntry  4 }

  m3uaGenNaMtp3ProtVariant OBJECT-TYPE
      SYNTAX      Unsigned32
      MAX-ACCESS  read-only
      STATUS      current
      DESCRIPTION
              "The MTP3 protocol variant for this NA."

      ::= { m3uaGenNaEntry  5 }


  m3uaGenNaMtp3ProtVersion OBJECT-TYPE
      SYNTAX      Unsigned32
      MAX-ACCESS  read-only
      STATUS      current
      DESCRIPTION
              "The MTP3 protocol version for this NA."

      ::= { m3uaGenNaEntry  6 }





  -----------------------------------------------------------------------
  -- M3UA TABLES
  -----------------------------------------------------------------------
  -----------------------------------------------------------------------
  -- GENERIC
  -----------------------------------------------------------------------
  -----------------------------------------------------------------------
  -- STATISTICS
  -----------------------------------------------------------------------
  -----------------------------------------------------------------------
  -- GENERIC STATISTICS TABLE
  -----------------------------------------------------------------------

  -- Defines statistics common to Application Server Processes,
  -- Signaling Gateway Processes and IP Signaling Processes.

  -- The table contains statistics data related to the M3UA messages
  -- exchanged through each association at the Signaling Process.


  m3uaGenStatTable OBJECT-TYPE
      SYNTAX      SEQUENCE OF M3uaGenStatEntry
      MAX-ACCESS  not-accessible
      STATUS      current
      DESCRIPTION
              "A table containing per association statistics."
      ::= { m3uaGenStat 1 }

  m3uaGenStatEntry OBJECT-TYPE
      SYNTAX      M3uaGenStatEntry
      MAX-ACCESS  not-accessible
      STATUS      current
      DESCRIPTION
              "It counts all the messages received and sent through a
              specific association."
      INDEX   { m3uaGenStatAssocId }
      ::= { m3uaGenStatTable 1 }

  M3uaGenStatEntry ::= SEQUENCE {
          m3uaGenStatAssocId            Unsigned32,
          m3uaGenStatDataOut            Counter32,
          m3uaGenStatDataIn             Counter32,
          m3uaGenStatErrorOut           Counter32,
          m3uaGenStatErrorIn            Counter32,
          m3uaGenStatSconOut            Counter32,
          m3uaGenStatSconIn             Counter32
      }

  -- Association Statistics

  -- DATA Statistics per Association

  m3uaGenStatAssocId OBJECT-TYPE
      SYNTAX      Unsigned32
      MAX-ACCESS  not-accessible
      STATUS      current
      DESCRIPTION
              "Association Identification. It is the value that identifies
              the association that is established between an ASP and an SGP
              or between 2 IPSPs. This value is extracted from the SCTP
              association Id value returned by SCTP when the association is
              established to that endpoint. It is the link to get the
              transport values from the SCTP MIB."
      ::= { m3uaGenStatEntry 1 }

  m3uaGenStatDataOut OBJECT-TYPE
      SYNTAX      Counter32
      MAX-ACCESS  read-only
      STATUS      current
      DESCRIPTION
              "Number of DATA messages sent through the association."
      ::= { m3uaGenStatEntry 2 }

  m3uaGenStatDataIn OBJECT-TYPE
      SYNTAX      Counter32
      MAX-ACCESS  read-only
      STATUS      current
      DESCRIPTION
              "Number of DATA messages received through the association."
      ::= { m3uaGenStatEntry 3 }

  -- End of DATA Statistics per Association

  -- MGMT Statistics per Association

  m3uaGenStatErrorOut OBJECT-TYPE
      SYNTAX      Counter32
      MAX-ACCESS  read-only
      STATUS      current
      DESCRIPTION
              "Number of ERROR messages sent through the association."
      ::= { m3uaGenStatEntry 4 }

  m3uaGenStatErrorIn OBJECT-TYPE
      SYNTAX      Counter32
      MAX-ACCESS  read-only
      STATUS      current
      DESCRIPTION
             "Number of ERROR messages received through the association."
      ::= { m3uaGenStatEntry 5 }

  -- End of MGMT Statistics per Association
  -- SSNM Statistics per Association

  m3uaGenStatSconOut OBJECT-TYPE
      SYNTAX      Counter32
      MAX-ACCESS  read-only
      STATUS      current
      DESCRIPTION
              "Number of SCON messages sent through the association."
      ::= { m3uaGenStatEntry 6 }

  m3uaGenStatSconIn OBJECT-TYPE
      SYNTAX      Counter32
      MAX-ACCESS  read-only
      STATUS      current
      DESCRIPTION
              "Number of SCON messages received through the association."
      ::= { m3uaGenStatEntry 7 }

  -- End of SSNM Statistics per Association



  -- 4.1 Conformance Information

  m3uaCompliances OBJECT IDENTIFIER ::= { m3uaConformance 1 }
  m3uaGroups      OBJECT IDENTIFIER ::= { m3uaConformance 2 }



  -- 4.1.1 Units of conformance

      m3uaAttributesGroup OBJECT-GROUP
      OBJECTS   { m3uaVersion,
                  m3uaProcType,
                  m3uaLocalPort,
                  m3uaTrValue,
                  m3uaTBeatValue,
                  m3uaTAckValue,
                  m3uaTPaudValue,
                  m3uaHeartBeat,
                  m3uaFailOverBuffSize,
                  m3uaRoutingFailures
                }
      STATUS    current
      DESCRIPTION
              "The m3ua group of objects providing for management of M3UA
              entities. Common parameters for the protocol."
      ::= { m3uaGroups 1 }





      m3uaAspCfgGroup OBJECT-GROUP

      OBJECTS   { m3uaAspDestState,
                  m3uaAspSgpState,
                  m3uaAspAssocId,
                  m3uaAspAssocMinOutStreams,
                  m3uaAspAssocMaxInStreams,
                  m3uaAspRcValue
                }
      STATUS    current
      DESCRIPTION
              "The m3ua group of objects to describe configuration values
              at the Application Server Process (ASP)."

      ::= { m3uaGroups 2 }

      m3uaAspStatsGroup OBJECT-GROUP
      OBJECTS   { m3uaAspStatAspupOut,
                  m3uaAspStatAspacOut,
                  m3uaAspStatAspdnOut,
                  m3uaAspStatAspiaOut,
                  m3uaAspStatAspupAckIn,
                  m3uaAspStatAspacAckIn,
                  m3uaAspStatAspdnAckIn,
                  m3uaAspStatAspiaAckIn,
                  m3uaAspStatNotifyIn,
                  m3uaAspStatDaudOut,
                  m3uaAspStatDunaIn,
                  m3uaAspStatDavaIn,
                  m3uaAspStatDupuIn
                }
      STATUS    current
      DESCRIPTION
              "The m3ua group of objects to count how the number of
              messages received/send by an ASP. Most of these messages
              applies to the M3UA client process and would also apply to an
              IPSP acting as a client."

      ::= { m3uaGroups 3 }

      m3uaSgpIpspCfgGroup OBJECT-GROUP
      OBJECTS   { m3uaSgpIpspRtgAsId,
                  m3uaSgpIpspRtgRc,
                  m3uaSgpIpspAsState,
                  m3uaSgpIpspAsTrafficMode,
                  m3uaSgpIpspAspState,
                  m3uaSgpIpspAspRole,
                  m3uaSgpIpspAssocId,
                  m3uaSgpIpspAssocMinOutStreams,
                  m3uaSgpIpspAssocMaxInStreams
                }

      STATUS    current
      DESCRIPTION
              "The m3ua group of objects to describe configuration values
              at either the Signaling Gateway Process (SGP) or the IP
              Server Process (IPSP)."

      ::= { m3uaGroups 4 }

      m3uaSgpIpspStatsGroup OBJECT-GROUP
      OBJECTS   { m3uaSgpIpspStatAspupAckOut,
                  m3uaSgpIpspStatAspacAckOut,
                  m3uaSgpIpspStatAspdnAckOut,
                  m3uaSgpIpspStatAspiaAckOut,
                  m3uaSgpIpspStatAspupIn,
                  m3uaSgpIpspStatAspacIn,
                  m3uaSgpIpspStatAspdnIn,
                  m3uaSgpIpspStatAspiaIn,
                  m3uaSgpIpspStatNotifyOut,
                  m3uaSgpIpspStatDunaOut,
                  m3uaSgpIpspStatDavaOut,
                  m3uaSgpIpspStatDupuOut,
                  m3uaSgpIpspStatDaudIn
                }

      STATUS    current
      DESCRIPTION
              "The m3ua group of objects to count how the number of
              messages received/send by a Signaling Process or IPSP."

      ::= { m3uaGroups 5 }

      m3uaGenCfgGroup OBJECT-GROUP
      OBJECTS   { m3uaGenNaNi,
                  m3uaGenNaMtp3ProtType,
                  m3uaGenNaMtp3ProtVariant,
                  m3uaGenNaMtp3ProtVersion
                }
      STATUS    current
      DESCRIPTION
              "The m3ua group of objects to describe the Network Appearance
              (NA) value."

      ::= { m3uaGroups 6 }


      m3uaGenStatsGroup OBJECT-GROUP
      OBJECTS   { m3uaGenStatDataOut,
                  m3uaGenStatDataIn,
                  m3uaGenStatErrorOut,
                  m3uaGenStatErrorIn,
                  m3uaGenStatSconOut,
                  m3uaGenStatSconIn
                }
      STATUS    current
      DESCRIPTION
              "The m3ua group of objects to count how the number of
              messages received/send by a Signaling Process. This objects
              are implemented in all kind of signaling processes: ASPs,
              SGPs and IPSPs."

      ::= { m3uaGroups 7 }



  -- 4.1.2 Compliance Statements

  m3uaAspCompliance MODULE-COMPLIANCE
      STATUS  current
      DESCRIPTION
          "The compliance statement for Application Server Processes (ASP)
           that implement this MIB in order to be managed using SNMP
           protocol."

      MODULE  -- this module
      MANDATORY-GROUPS { m3uaAttributesGroup,
                         m3uaAspCfgGroup,
                         m3uaGenCfgGroup,
                         m3uaAspStatsGroup,
                         m3uaGenStatsGroup
                       }

      ::= { m3uaCompliances 1 }

  m3uaSgpCompliance MODULE-COMPLIANCE
      STATUS  current
      DESCRIPTION
          "The compliance statement for Signaling Gateway Processes (SGP)
           that implement this MIB in order to be managed using SNMP
           protocol."


      MODULE  -- this module
      MANDATORY-GROUPS { m3uaAttributesGroup,
                         m3uaSgpIpspCfgGroup,
                         m3uaGenCfgGroup,
                         m3uaSgpIpspStatsGroup,
                         m3uaGenStatsGroup
                       }

      ::= { m3uaCompliances 2 }

  m3uaIpspCompliance MODULE-COMPLIANCE
      STATUS  current
      DESCRIPTION
          "The compliance statement IP Server Processes (IPSP) that
           implement this MIB in order to be managed using SNMP protocol."


      MODULE  -- this module
      MANDATORY-GROUPS { m3uaAttributesGroup,
                         m3uaSgpIpspCfgGroup,
                         m3uaGenCfgGroup,
                         m3uaAspStatsGroup,
                         m3uaSgpIpspStatsGroup,
                         m3uaGenStatsGroup
                       }

      ::= { m3uaCompliances 3 }


  END

-- 
--   Copyright (C) The Internet Society (2004).  All Rights Reserved.
-- 
--   This document and translations of it may be copied and furnished to
--   others, and derivative works that comment on or otherwise explain it or
--   assist in its implementation may be prepared, copied, published and
--   distributed, in whole or in part, without restriction of any kind,
--   provided that the above copyright notice and this paragraph are included
--   on all such copies and derivative works. However, this document itself
--   may not be modified in any way, such as by removing the copyright notice
--   or references to the Internet Society or other Internet organizations,
--   except as needed for the purpose of developing Internet standards in
--   which case the procedures for copyrights defined in the Internet
--   Standards process must be followed, or as required to translate it into
--   languages other than English.
-- 
--   The limited permissions granted above are perpetual and will not be
--   revoked by the Internet Society or its successors or assigns.
-- 
--   This document and the information contained herein is provided on an "AS
--   IS" basis and THE INTERNET SOCIETY AND THE INTERNET ENGINEERING TASK
--   FORCE DISCLAIMS ALL WARRANTIES, EXPRESS OR IMPLIED, INCLUDING BUT NOT
--   LIMITED TO ANY WARRANTY THAT THE USE OF THE INFORMATION HEREIN WILL NOT
--   INFRINGE ANY RIGHTS OR ANY IMPLIED WARRANTIES OF MERCHANTABILITY OR
--   FITNESS FOR A PARTICULAR PURPOSE.
